--
-- comVoip.mib
-- MIB generated by MG-SOFT Visual MIB Builder Version 3.0 Build 285
-- Wednesday, January 31, 2018 at 04:45:15
--

	ZHONE-COM-VOIP-MIB DEFINITIONS ::= BEGIN
 
		IMPORTS
			InetAddress, InetAddressType			
				FROM INET-ADDRESS-MIB			
			applIndex			
				FROM NETWORK-SERVICES-MIB			
			SnmpAdminString			
				FROM SNMP-FRAMEWORK-MIB			
			OBJECT-GROUP			
				FROM SNMPv2-CONF			
			IpAddress, Integer32, Unsigned32, OBJECT-TYPE, MODULE-IDENTITY, 
			OBJECT-IDENTITY			
				FROM SNMPv2-SMI			
			TruthValue			
				FROM SNMPv2-TC			
			ZhoneCodecType			
				FROM ZHONE-GEN-SUBSCRIBER			
			zhoneVoice			
				FROM Zhone			
			ZhoneRowStatus			
				FROM Zhone-TC;
	
	
-- To Create Protection Layer header and C code (run in /vob/mibs/src):
-- /vob/zhonetools/bin/pahrser.pl iftype.mib Zhone.mib Zhone-TC.mib
--   rfc2571.mib genSubscriberMib.mib rfc2233.mib rfc2514.mib
--   INET-ADDRESS-MIB.mib comVoip.mib
-- 
-- To Create Mib Handler file (run in /vob/mibs/src):
-- /vob/EPILOGUE/binaries/emissary/solaris/mibcomp iftype.mib
--   Zhone.mib Zhone-TC.mib rfc2571.mib rfc2514.mib rfc1907.mib
--   rfc2233.mib INET-ADDRESS-MIB.mib genSubscriberMib.mib 
--   rfc2788.mib comVoip.mib -stub -o voipSystemHdlrs.c
-- 
-- 
-- 
-- 
-- 
-- 
-- 
		-- 1.3.6.1.4.1.5504.4.3.4
		zhoneVoip MODULE-IDENTITY 
			LAST-UPDATED "201801310443Z"		-- January 31, 2018 at 04:43 GMT
			ORGANIZATION 
				"Zhone Technologies."
			CONTACT-INFO 
				"   Postal: 
				           Zhone Technologies, Inc.
				           @ Zhone Way
				           7001 Oakport Street
				           Oakland, CA  94621
				           USA
				Toll-Free: +1 877-ZHONE20 (+1 877-946-6320)
				      Tel: +1-510-777-7000
				      Fax: +1-510-777-7001
				   E-mail: support@zhone.com"
			DESCRIPTION 
				"Voice over IP configuration for Zhone products"
			REVISION "201801310443Z"		-- January 31, 2018 at 04:43 GMT
			DESCRIPTION 
				"This parameter is used to configured the dial plan 
specific features.

Bit        Feature
---        --------
 1         Supports enhanced 911
 2         Supports local tel URI for the dialed digits
 3         Supports three party call conference
 4         Supports disconnection of active call and switch to other party
 5         Supports holding active call and switch to other party
 6         Supports call transfer between other two parties"
			REVISION "201801310442Z"		-- January 31, 2018 at 04:42 GMT
			DESCRIPTION 
				" "
			REVISION "201704070033Z"		-- April 07, 2017 at 00:33 GMT
			DESCRIPTION 
				"1. Added new feature bit teluri to the field voip-features in voip-server-entry profile.
				2. Added new field area-code in voip-server-entry
				3. Added new bit localteluri to the field dialplan-class in sip-dialplan profile"
			REVISION "201607200619Z"		-- July 20, 2016 at 06:19 GMT
			DESCRIPTION 
				"Added new feature bit rtcp-xr to voip-features field
				of voip-server-entry"
			REVISION "201606020632Z"		-- June 02, 2016 at 06:32 GMT
			DESCRIPTION 
				"Added round-trip-timeout-ms, max-retransmit-interval-ms, esa-retry-count and 
				esa-recovery-count to voipServerEntry"
			REVISION "201510160545Z"		-- October 16, 2015 at 05:45 GMT
			DESCRIPTION 
				"Modified the valid range of values for register-timer-expiry field of voip-server-entry"
			REVISION "201510130249Z"		-- October 13, 2015 at 02:49 GMT
			DESCRIPTION 
				"Added new field register-timer-expiry to voip-server-entry"
			REVISION "201410240407Z"		-- October 24, 2014 at 04:07 GMT
			DESCRIPTION 
				"V01.07.28 Added new field zhoneVoipSipDialPlanDescription to sip-dialplan table"
			REVISION "201409240423Z"		-- September 24, 2014 at 04:23 GMT
			DESCRIPTION 
				"V01.07.27 Added rfc3262 feature to zhoneVoipSerFeatures"
			REVISION "201408102311Z"		-- August 10, 2014 at 23:11 GMT
			DESCRIPTION 
				"V01.07.26 Added dialplan-class field to sip-dialplan profile"
			REVISION "201407030240Z"		-- July 03, 2014 at 02:40 GMT
			DESCRIPTION 
				"V01.07.25 Added two new fields zhoneVoipServerTransportProtocol,
				zhoneVoipSigLocalPortNumber to voip-server-entry."
			REVISION "201406162140Z"		-- June 16, 2014 at 21:40 GMT
			DESCRIPTION 
				"V01.07.24 Add field zhoneVoipServerMessageRetryCount to 
				zhoneVoipServer table"
			REVISION "201405221409Z"		-- May 22, 2014 at 14:09 GMT
			DESCRIPTION 
				"V01.07.23 Added voipFeatures field to voip-server-entry"
			REVISION "201401022213Z"		-- January 02, 2014 at 22:13 GMT
			DESCRIPTION 
				"V01.07.22 Added Ericsson APZ60 to the list of Server IDs"
			REVISION "201209172342Z"		-- September 17, 2012 at 23:42 GMT
			DESCRIPTION 
				"V01.07.21 Added new field registerReadyTimeout to voip server entry"
			REVISION "201209172339Z"		-- September 17, 2012 at 23:39 GMT
			DESCRIPTION 
				"V01.07.20 Added new field dtmfPayloadId to voip server entry"
			REVISION "201112220224Z"		-- December 22, 2011 at 02:24 GMT
			DESCRIPTION 
				"V01.07.19 New softswitch alu-5060 is added in zhoneVoipServerId"
			REVISION "201110201214Z"		-- October 20, 2011 at 12:14 GMT
			DESCRIPTION 
				"V01.07.18 Added new sipDialPlanType intercom"
			REVISION "201107251144Z"		-- July 25, 2011 at 11:44 GMT
			DESCRIPTION 
				"V01.07.17 -- added rtpDSCP and signalingDSCP"
			REVISION "200910070141Z"		-- October 07, 2009 at 01:41 GMT
			DESCRIPTION 
				"V01.07.16 -- Added new softswitch genband-g6 to voip-server-entry profile"
			REVISION "200903210208Z"		-- March 21, 2009 at 02:08 GMT
			DESCRIPTION 
				"V01.07.15 -- Added new softswitch values to voip-server-entry profile"
			REVISION "200810310112Z"		-- October 31, 2008 at 01:12 GMT
			DESCRIPTION 
				"Added RTP Term Id Syntax in voip-server-entry profile."
			REVISION "200808272302Z"		-- August 27, 2008 at 23:02 GMT
			DESCRIPTION 
				"Added new sip-dialplan type isdnsig"
			REVISION "200806111740Z"		-- June 11, 2008 at 17:40 GMT
			DESCRIPTION 
				"V01.07.12 -- Added new soft switches and behaviorStringOne to voip-server-entry profile"
			REVISION "200707160245Z"		-- July 16, 2007 at 02:45 GMT
			DESCRIPTION 
				"V01.07.11 -- Added new soft switch values and protocl entry to voip-server-entry profile"
			REVISION "200604131553Z"		-- April 13, 2006 at 15:53 GMT
			DESCRIPTION 
				"V01.07.10 -- add megaco protocol"
			REVISION "200510111146Z"		-- October 11, 2005 at 11:46 GMT
			DESCRIPTION 
				"V01.07.09 -- copy content of sipCommonCfgExpiresMethodTable to voipserver"
			REVISION "200507121025Z"		-- July 12, 2005 at 10:25 GMT
			DESCRIPTION 
				"V01.07.08 -- copy content of voipsystem to voipserver"
			REVISION "200507071606Z"		-- July 07, 2005 at 16:06 GMT
			DESCRIPTION 
				"V01.07.07 -- Add overrideInterfDigitTimeout to zhoneVoipSipDialPlanEntry"
			REVISION "200507071512Z"		-- July 07, 2005 at 15:12 GMT
			DESCRIPTION 
				"V01.07.06 -- change number-of-digits from 1..32 to 0..32"
			REVISION "200506011109Z"		-- June 01, 2005 at 11:09 GMT
			DESCRIPTION 
				"V01.07.05 - Added ESA as one of the dialplan type"
			REVISION "200505191546Z"		-- May 19, 2005 at 15:46 GMT
			DESCRIPTION 
				"V01.07.04 - Changed voipServerEntry in sip-dialplan range to be 0 - 255 for peer to peer case."
			REVISION "200505142124Z"		-- May 14, 2005 at 21:24 GMT
			DESCRIPTION 
				"V01.07.04 - Added index to voip-server-entry"
			REVISION "200502281049Z"		-- February 28, 2005 at 10:49 GMT
			DESCRIPTION 
				"V01.07.03 - Added a new field Dial Plan Type"
			REVISION "200411011434Z"		-- November 01, 2004 at 14:34 GMT
			DESCRIPTION 
				"V01.07.03 - add zhoneVoipServerId"
			REVISION "200403031740Z"		-- March 03, 2004 at 17:40 GMT
			DESCRIPTION 
				"V01.07.02 - add zhoneVoipServerUdpPortNumber."
			REVISION "200402241236Z"		-- February 24, 2004 at 12:36 GMT
			DESCRIPTION 
				"V01.07.01 - Update voipServer markup."
			REVISION "200401061537Z"		-- January 06, 2004 at 15:37 GMT
			DESCRIPTION 
				"V01.07.00 - Added zhoneVoipServerTable."
			REVISION "200311061008Z"		-- November 06, 2003 at 10:08 GMT
			DESCRIPTION 
				"V01.06.00 - Added system-domain-name field to voip-system profile"
			REVISION "200310161453Z"		-- October 16, 2003 at 14:53 GMT
			DESCRIPTION 
				"V01.05.00 - Added ipTos entry."
			REVISION "200308271130Z"		-- August 27, 2003 at 11:30 GMT
			DESCRIPTION 
				"V01.04.00 - Added malicious caller entry"
			REVISION "200308081719Z"		-- August 08, 2003 at 17:19 GMT
			DESCRIPTION 
				"V01.03.00 - Added destName, prefix strip, prefix add to sip dial plan"
			REVISION "200305281200Z"		-- May 28, 2003 at 12:00 GMT
			DESCRIPTION 
				"V01.02.00 - added zhoneVoipHuntGroup"
			REVISION "200303311803Z"		-- March 31, 2003 at 18:03 GMT
			DESCRIPTION 
				"V01.01.00 - added sip dial plan"
			REVISION "200302181432Z"		-- February 18, 2003 at 14:32 GMT
			DESCRIPTION 
				"V01.00.00 - Initial revision"
			::= { zhoneVoice 4 }

		
	
	
--
-- Node definitions
--
	
		-- 1.3.6.1.4.1.5504.4.3.4.1
		zhoneVoipSystem OBJECT-IDENTITY
			STATUS deprecated
			DESCRIPTION 
				"Only SIP-PLAR is using this profile.  The regular SIP and MGCP
				setting is moving to Voip-Server-Entry profile."
			::= { zhoneVoip 1 }

		
		-- 1.3.6.1.4.1.5504.4.3.4.1.1
		zhoneVoipSystemProtocol OBJECT-TYPE
			SYNTAX INTEGER
				{
				sip(1),
				mgcp(2)
				}
			MAX-ACCESS read-only
			STATUS deprecated
			DESCRIPTION
				"The signalling protocol used for VOIP. Choicees are SIP (Session 
				Initiation Protocol) and MGCP (Media Gateway Control Protocol.  
				Currently, the device only supports SIP."
			DEFVAL { sip }
			::= { zhoneVoipSystem 1 }

		
		-- 1.3.6.1.4.1.5504.4.3.4.1.2
		zhoneVoipSystemSendCallProceedingTone OBJECT-TYPE
			SYNTAX TruthValue
			MAX-ACCESS read-write
			STATUS deprecated
			DESCRIPTION
				"Indicates whether, on call originations destined to the PSTN, the 
				device should play a call proceeding tone while waiting for 
				ring-back tone from the switch."
			DEFVAL { false }
			::= { zhoneVoipSystem 2 }

		
		-- 1.3.6.1.4.1.5504.4.3.4.1.3
		zhoneVoipSystemRtcpEnabled OBJECT-TYPE
			SYNTAX TruthValue
			MAX-ACCESS read-write
			STATUS deprecated
			DESCRIPTION
				"Indicates whether the Real-Time Control Protocol is enabled for
				the device. "
			DEFVAL { false }
			::= { zhoneVoipSystem 3 }

		
		-- 1.3.6.1.4.1.5504.4.3.4.1.4
		zhoneVoipSystemRtcpPacketInterval OBJECT-TYPE
			SYNTAX Integer32 (2500..10000)
			MAX-ACCESS read-write
			STATUS deprecated
			DESCRIPTION
				"RTCP packet interval, in milleseconds.  Range is 2500 to 10000 ms.
				This object's value is only pertinent if RTCP has been enabled."
			DEFVAL { 5000 }
			::= { zhoneVoipSystem 4 }

		
		-- 1.3.6.1.4.1.5504.4.3.4.1.5
		zhoneVoipSystemInterdigitTimeout OBJECT-TYPE
			SYNTAX Integer32
			MAX-ACCESS read-write
			STATUS deprecated
			DESCRIPTION
				"This parameter indicates the duration, in seconds, that the device 
				will wait after each digit is entered before assuming the user has 
				finished entering digits. "
			DEFVAL { 10 }
			::= { zhoneVoipSystem 5 }

		
		-- 1.3.6.1.4.1.5504.4.3.4.1.6
		zhoneVoipSystemIpTos OBJECT-TYPE
			SYNTAX Integer32
			MAX-ACCESS read-write
			STATUS deprecated
			DESCRIPTION
				"This parameter indicates the tos value that is set in the ip header for
				voice of ip traffic."
			DEFVAL { 0 }
			::= { zhoneVoipSystem 6 }

		
		-- 1.3.6.1.4.1.5504.4.3.4.1.7
		zhoneVoipSystemDomainName OBJECT-TYPE
			SYNTAX SnmpAdminString
			MAX-ACCESS read-only
			STATUS deprecated
			DESCRIPTION
				"This parameter is ignored."
			::= { zhoneVoipSystem 7 }

		
		-- 1.3.6.1.4.1.5504.4.3.4.2
		zhoneVoipObjects OBJECT-GROUP
			OBJECTS { nextVoipSipDialPlanId, zhoneVoipSipDialString, zhoneVoipSipDialIpAddr, zhoneVoipSipDialPlanRowStatus, nextZhoneVoipHuntGroupId, 
				zhoneVoipHuntGroupDestUri, zhoneVoipHuntGroupRowStatus, zhoneVoipSipDialPrefixAdd, zhoneVoipSipDialPrefixStrip, zhoneVoipSipDialNumOfDigits, 
				zhoneVoipSipDialDestName, zhoneVoipHuntGroupPortMembers, zhoneVoipHuntGroupDefaultCodec, nextVoipMaliciousCallerId, zhoneVoipMaliciousCallerUri, 
				zhoneVoipServerId, zhoneVoipServerUdpPortNumber, zhoneVoipServerAddr, zhoneVoipServerAddrType, zhoneVoipServerRowStatus, 
				zhoneVoipSipDialPlanType, zhoneVoipServerSessionTimer, zhoneVoipServerSessionExpiration, zhoneVoipServerSessionMinSE, zhoneVoipServerSessionCallerReqTimer, 
				zhoneVoipServerSessionCalleeReqTimer, zhoneVoipServerSessionCallerSpecifyRefresher, zhoneVoipServerSessionCalleeSpecifyRefresher, zhoneVoipServerExpiresInvite, zhoneVoipServerExpiresRegister, 
				zhoneVoipServerHeaderMethod, zhoneVoipServerEsaRecoveryCount, zhoneVoipServerEsaRetryCount, zhoneVoipServerMaxRetransmitIntervalMs, zhoneVoipServerRoundTripTimeoutMs, 
				zhoneVoipServerRegisterTimerExpiry, zhoneVoipServerAreaCode, zhoneVoipMaliciousCallerRowStatus, zhoneVoipMaliciousCallerEnable, zhoneVoipServerBehaviorStringOne
				 }
			STATUS current
			DESCRIPTION 
				"Zhone VOIP objects."
			::= { zhoneVoip 2 }

		
		-- 1.3.6.1.4.1.5504.4.3.4.3
		zhoneVoipSipDialPlan OBJECT IDENTIFIER::= { zhoneVoip 3 }

		
		-- 1.3.6.1.4.1.5504.4.3.4.3.1
		nextVoipSipDialPlanId OBJECT-TYPE
			SYNTAX Integer32
			MAX-ACCESS read-only
			STATUS current
			DESCRIPTION
				"Returns the next unused dial plan entry id.   "
			::= { zhoneVoipSipDialPlan 1 }

		
		-- 1.3.6.1.4.1.5504.4.3.4.3.2
		zhoneVoipSipDialPlanTable OBJECT-TYPE
			SYNTAX SEQUENCE OF ZhoneVoipSipDialPlanEntry
			MAX-ACCESS not-accessible
			STATUS current
			DESCRIPTION
				"This table defines a dialing plan for POTS to SIP originations.
				A dialing plan consists of a series of acceptable dial strings
				and the corresponding IP addresses to which SIP control messages
				(e.g., Invite) are sent to initiate the call.   Each dial string
				is represented as digits, wildcards, and regular-expression-like
				patterns as the following rules show:
				
				 1. A leading '*' or '#' are allowed.
				 2. Digits 0-9 are allowed.
				 3. A wildcard 'x' represents any digit 0-9
				 4. A digit range can be specified using brackets [ ], as follows:
				     [135] means a single digit with acceptable values 1,3, or 5.
				     [1-4] means a single digit with acceptable values 1,2,3, or 4.
				 
				
				Examples of valid dial strings:
				  911             - literal digit string 911
				  #87             - literal digit string #87   
				  *6x             - *6 followed by any single digit
				  35xxx           - 35 followed by any 3 digits
				  77xxx           - 77 followed by any 3 digits
				  3[35]xxx        - 33 or 35 followed by any 3 digits
				  31[1-3]xxxx     - 311, 312, 313, followed by any 4 digits
				
				Notes:
				(1) The length of the dial string is limited 1o 128 characters
				
				(2) Though the dialplan supports the '#' and '*' keys, the device
				may not support any features that use them (e.g., *69).
				
				(3) In the case where a collected digit set matches more than one
				dial string,  the device will pick the dial string with the most
				leading literal digits that match.  For example, given two dial strings:
				   35xxx
				   3[35]xxx
				
				and a collected digit set of 35123,  the first dial plan string is
				selected because it contains two leading literal digits that match,
				as opposed to the second, which has only one leading literal digit.
				
				(4) Variable length dial strings, e.g. 353 followed by any
				    number of digits,  are not supported.
				
				(5) In the future, a dial string may be configurable such that it
				only applies to a subset of the supported ports (e.g., ports with
				international calling capabilities might be restricted).   This is
				currently not supported; a dial string applies to all subscriberers.
				Support will be added for per-port control, most likely by adding
				port masks to the dial plan entry."
			::= { zhoneVoipSipDialPlan 2 }

		
		-- 1.3.6.1.4.1.5504.4.3.4.3.2.1
		zhoneVoipSipDialPlanEntry OBJECT-TYPE
			SYNTAX ZhoneVoipSipDialPlanEntry
			MAX-ACCESS not-accessible
			STATUS current
			DESCRIPTION
				"An entry in the SIP dial plan table."
			INDEX { zhoneVoipSipDialPlanId }
			::= { zhoneVoipSipDialPlanTable 1 }

		
		ZhoneVoipSipDialPlanEntry ::=
			SEQUENCE { 
				zhoneVoipSipDialPlanId
					INTEGER,
				zhoneVoipSipDialString
					SnmpAdminString,
				zhoneVoipSipDialIpAddr
					IpAddress,
				zhoneVoipSipDialPlanRowStatus
					ZhoneRowStatus,
				zhoneVoipSipDialDestName
					SnmpAdminString,
				zhoneVoipSipDialNumOfDigits
					INTEGER,
				zhoneVoipSipDialPrefixStrip
					INTEGER,
				zhoneVoipSipDialPrefixAdd
					SnmpAdminString,
				zhoneVoipSipDialPlanType
					INTEGER,
				zhoneVoipServerEntryIndex
					INTEGER,
				zhoneVoipOverrideInterdigitTimeout
					Integer32,
				zhoneVoipSipDialPlanClass
					BITS,
				zhoneVoipSipDialPlanDescription
					SnmpAdminString
			 }

		-- 1.3.6.1.4.1.5504.4.3.4.3.2.1.1
		zhoneVoipSipDialPlanId OBJECT-TYPE
			SYNTAX INTEGER (1..2147483647)
			MAX-ACCESS not-accessible
			STATUS current
			DESCRIPTION
				"The unique identifier of the dial plan entry."
			::= { zhoneVoipSipDialPlanEntry 1 }

		
		-- 1.3.6.1.4.1.5504.4.3.4.3.2.1.2
		zhoneVoipSipDialString OBJECT-TYPE
			SYNTAX SnmpAdminString (SIZE (1..128))
			MAX-ACCESS read-create
			STATUS current
			DESCRIPTION
				"A dial string against which collected digits are matched."
			::= { zhoneVoipSipDialPlanEntry 2 }

		
		-- 1.3.6.1.4.1.5504.4.3.4.3.2.1.3
		zhoneVoipSipDialIpAddr OBJECT-TYPE
			SYNTAX IpAddress
			MAX-ACCESS read-create
			STATUS current
			DESCRIPTION
				"Upon detecting a match between the collected digits and the 
				dial string for this table entry,  this IP address is used 
				for SIP negotiations to initiate the call."
			::= { zhoneVoipSipDialPlanEntry 3 }

		
		-- 1.3.6.1.4.1.5504.4.3.4.3.2.1.4
		zhoneVoipSipDialPlanRowStatus OBJECT-TYPE
			SYNTAX ZhoneRowStatus
			MAX-ACCESS read-create
			STATUS current
			DESCRIPTION
				"The row status is used to create or delete an entry in 
				this table."
			::= { zhoneVoipSipDialPlanEntry 4 }

		
		-- 1.3.6.1.4.1.5504.4.3.4.3.2.1.5
		zhoneVoipSipDialDestName OBJECT-TYPE
			SYNTAX SnmpAdminString
			MAX-ACCESS read-create
			STATUS current
			DESCRIPTION
				"Name of the destination for the dial string"
			::= { zhoneVoipSipDialPlanEntry 5 }

		
		-- 1.3.6.1.4.1.5504.4.3.4.3.2.1.6
		zhoneVoipSipDialNumOfDigits OBJECT-TYPE
			SYNTAX INTEGER (0..32)
			MAX-ACCESS read-create
			STATUS current
			DESCRIPTION
				"Number of digits to wait for before initiating the call"
			::= { zhoneVoipSipDialPlanEntry 6 }

		
		-- 1.3.6.1.4.1.5504.4.3.4.3.2.1.7
		zhoneVoipSipDialPrefixStrip OBJECT-TYPE
			SYNTAX INTEGER (0..32)
			MAX-ACCESS read-create
			STATUS current
			DESCRIPTION
				"Number of prefix digits to strip from dialled digits"
			::= { zhoneVoipSipDialPlanEntry 7 }

		
		-- 1.3.6.1.4.1.5504.4.3.4.3.2.1.8
		zhoneVoipSipDialPrefixAdd OBJECT-TYPE
			SYNTAX SnmpAdminString
			MAX-ACCESS read-create
			STATUS current
			DESCRIPTION
				"String to be added to the beginning of the dialled digits before call initiation"
			::= { zhoneVoipSipDialPlanEntry 8 }

		
		-- 1.3.6.1.4.1.5504.4.3.4.3.2.1.9
		zhoneVoipSipDialPlanType OBJECT-TYPE
			SYNTAX INTEGER
				{
				normal(1),
				callpark(2),
				esa(3),
				isdnsig(4),
				intercom(5)
				}
			MAX-ACCESS read-create
			STATUS current
			DESCRIPTION
				"DialPlanType indicates the type of the dial plan.  UA has
				to differenciate between normal dialing and dialing when
				call features like call park is initiated.  The different
				kinds of dial plan types are:
				           Normal
				           Call Park
				           ESA (Emergency stand alone)
				           isdnsig (ISDN-PRI)
				           Intercom"
			DEFVAL { normal }
			::= { zhoneVoipSipDialPlanEntry 9 }

		
		-- 1.3.6.1.4.1.5504.4.3.4.3.2.1.10
		zhoneVoipServerEntryIndex OBJECT-TYPE
			SYNTAX INTEGER (0..255)
			MAX-ACCESS read-create
			STATUS current
			DESCRIPTION
				"An index to associated voip-server-entry for this sip-dialplan."
			::= { zhoneVoipSipDialPlanEntry 10 }

		
		-- 1.3.6.1.4.1.5504.4.3.4.3.2.1.11
		zhoneVoipOverrideInterdigitTimeout OBJECT-TYPE
			SYNTAX Integer32
			MAX-ACCESS read-create
			STATUS current
			DESCRIPTION
				"This parameter overrides the interdigit timeout in voip-system profile.  
				It indicates the duration, in seconds, that the device
				will wait after each digit is entered before assuming the user has
				finished entering digits. "
			::= { zhoneVoipSipDialPlanEntry 11 }

		
		-- 1.3.6.1.4.1.5504.4.3.4.3.2.1.12
		zhoneVoipSipDialPlanClass OBJECT-TYPE
			SYNTAX BITS
				{
				emergency(0),
				localteluri(1),
				threepartyconf(2),
				discact(3),
				holdact(4),
				transfer(5)
				}
			MAX-ACCESS read-create
			STATUS deprecated
			DESCRIPTION
				"This parameter is used to configured the dial plan 
				specific features.
				
				Bit        Feature
				---        --------
				 1         Supports enhanced 911
				 2         Supports local tel URI for the dialed digits
				 3         Supports three party call conference
				 4         Supports disconnection of active call and switch to other party
				 5         Supports holding active call and switch to other party
				 6         Supports call transfer between other two parties"
			::= { zhoneVoipSipDialPlanEntry 12 }

		
		-- 1.3.6.1.4.1.5504.4.3.4.3.2.1.13
		zhoneVoipSipDialPlanDescription OBJECT-TYPE
			SYNTAX SnmpAdminString
			MAX-ACCESS read-write
			STATUS current
			DESCRIPTION
				"This field gives details about the sip-dialplan"
			::= { zhoneVoipSipDialPlanEntry 13 }

		
		-- 1.3.6.1.4.1.5504.4.3.4.4
		zhoneVoipHuntGroup OBJECT IDENTIFIER::= { zhoneVoip 4 }

		
		-- 1.3.6.1.4.1.5504.4.3.4.4.2
		nextZhoneVoipHuntGroupId OBJECT-TYPE
			SYNTAX Integer32
			MAX-ACCESS read-only
			STATUS current
			DESCRIPTION
				"Returns the next unused hunt group entry id. "
			::= { zhoneVoipHuntGroup 2 }

		
		-- 1.3.6.1.4.1.5504.4.3.4.4.3
		zhoneVoipHuntGroupTable OBJECT-TYPE
			SYNTAX SEQUENCE OF ZhoneVoipHuntGroupEntry
			MAX-ACCESS not-accessible
			STATUS current
			DESCRIPTION
				"A hunt groups is defined to map a SIP uniform resource identifier (URI) or 
				dirctory number (DN) to multiple DS0s, to allow a greater number of 
				incoming calls to that URI/DN.
				
				A hunt group consists of the following information:
				 - the target DN/URI 
				 - the default codec to be used for the call, and
				 - the DS0 ports in the hunt-group.
				
				Notes:
				
				A URI defined in a subscriber-voice-sip profile cannot also be 
				defined as part of a hunt group.  This is enforced by the device.
				
				A DS0 must be provisioned in the subVoiceSipTable before that DS0 
				can be used in a hunt group.  This is enforced by the device.
				
				A DS0 may be part of more than one hunt group.
				"
			::= { zhoneVoipHuntGroup 3 }

		
		-- 1.3.6.1.4.1.5504.4.3.4.4.3.1
		zhoneVoipHuntGroupEntry OBJECT-TYPE
			SYNTAX ZhoneVoipHuntGroupEntry
			MAX-ACCESS not-accessible
			STATUS current
			DESCRIPTION
				"An entry in the hunt group table."
			INDEX { zhoneVoipHuntGroupId }
			::= { zhoneVoipHuntGroupTable 1 }

		
		ZhoneVoipHuntGroupEntry ::=
			SEQUENCE { 
				zhoneVoipHuntGroupId
					INTEGER,
				zhoneVoipHuntGroupDestUri
					SnmpAdminString,
				zhoneVoipHuntGroupDefaultCodec
					ZhoneCodecType,
				zhoneVoipHuntGroupPortMembers
					BITS,
				zhoneVoipHuntGroupRowStatus
					ZhoneRowStatus
			 }

		-- 1.3.6.1.4.1.5504.4.3.4.4.3.1.1
		zhoneVoipHuntGroupId OBJECT-TYPE
			SYNTAX INTEGER (1..2147483647)
			MAX-ACCESS not-accessible
			STATUS current
			DESCRIPTION
				"The unique identifier of the hunt group entry."
			::= { zhoneVoipHuntGroupEntry 1 }

		
		-- 1.3.6.1.4.1.5504.4.3.4.4.3.1.2
		zhoneVoipHuntGroupDestUri OBJECT-TYPE
			SYNTAX SnmpAdminString (SIZE (1..128))
			MAX-ACCESS read-create
			STATUS current
			DESCRIPTION
				"The DN (directory number) or SIP URI (uniform resource identifier) being called.   
				This is the called party from the incoming SIP Invite message."
			::= { zhoneVoipHuntGroupEntry 2 }

		
		-- 1.3.6.1.4.1.5504.4.3.4.4.3.1.3
		zhoneVoipHuntGroupDefaultCodec OBJECT-TYPE
			SYNTAX ZhoneCodecType
			MAX-ACCESS read-create
			STATUS current
			DESCRIPTION
				"The default codec to use for a call to a member of this hunt group."
			DEFVAL { g711mu }
			::= { zhoneVoipHuntGroupEntry 3 }

		
		-- 1.3.6.1.4.1.5504.4.3.4.4.3.1.4
		zhoneVoipHuntGroupPortMembers OBJECT-TYPE
			SYNTAX BITS
				{
				port1(0),
				port2(1),
				port3(2),
				port4(3),
				port5(4),
				port6(5),
				port7(6),
				port8(7),
				port9(8),
				port10(9),
				port11(10),
				port12(11),
				port13(12),
				port14(13),
				port15(14),
				port16(15),
				port17(16),
				port18(17),
				port19(18),
				port20(19),
				port21(20),
				port22(21),
				port23(22),
				port24(23)
				}
			MAX-ACCESS read-create
			STATUS current
			DESCRIPTION
				"Indicates which ports are contained in the hunt group."
			::= { zhoneVoipHuntGroupEntry 4 }

		
		-- 1.3.6.1.4.1.5504.4.3.4.4.3.1.5
		zhoneVoipHuntGroupRowStatus OBJECT-TYPE
			SYNTAX ZhoneRowStatus
			MAX-ACCESS read-create
			STATUS current
			DESCRIPTION
				"The row status is used to create or delete an entry in 
				this table."
			::= { zhoneVoipHuntGroupEntry 5 }

		
		-- 1.3.6.1.4.1.5504.4.3.4.5
		zhoneVoipMaliciousCaller OBJECT IDENTIFIER::= { zhoneVoip 5 }

		
		-- 1.3.6.1.4.1.5504.4.3.4.5.1
		nextVoipMaliciousCallerId OBJECT-TYPE
			SYNTAX Integer32
			MAX-ACCESS read-only
			STATUS current
			DESCRIPTION
				"eturns the next unused malicious caller entry index"
			::= { zhoneVoipMaliciousCaller 1 }

		
		-- 1.3.6.1.4.1.5504.4.3.4.5.2
		zhoneVoipMaliciousCallerTable OBJECT-TYPE
			SYNTAX SEQUENCE OF ZhoneVoipMaliciousCallerEntry
			MAX-ACCESS not-accessible
			STATUS current
			DESCRIPTION
				"This table defines a malicious caller whose call will be rejected if enabled. 
				SIP terminal administrator needs to provision URI of this table exactly as it 
				appears in the incoming session notification's(SIP INVITE) calling user's 
				address-of-record(AOR) formatted as a SIP URI.
				The SIP URI can contain either a telephone number(RFC 2806) or an alphanumeric
				identification(RFC 2806)
				Entries in the table are case sensitive, shall not contain visual separations and 
				have the exact length as it appears in the SIP INVITE message
				
				"
			::= { zhoneVoipMaliciousCaller 2 }

		
		-- 1.3.6.1.4.1.5504.4.3.4.5.2.1
		zhoneVoipMaliciousCallerEntry OBJECT-TYPE
			SYNTAX ZhoneVoipMaliciousCallerEntry
			MAX-ACCESS not-accessible
			STATUS current
			DESCRIPTION
				"An entry in the malicious caller table"
			INDEX { zhoneVoipMaliciousCallerId }
			::= { zhoneVoipMaliciousCallerTable 1 }

		
		ZhoneVoipMaliciousCallerEntry ::=
			SEQUENCE { 
				zhoneVoipMaliciousCallerId
					INTEGER,
				zhoneVoipMaliciousCallerUri
					SnmpAdminString,
				zhoneVoipMaliciousCallerEnable
					TruthValue,
				zhoneVoipMaliciousCallerRowStatus
					ZhoneRowStatus
			 }

		-- 1.3.6.1.4.1.5504.4.3.4.5.2.1.1
		zhoneVoipMaliciousCallerId OBJECT-TYPE
			SYNTAX INTEGER (1..2147483647)
			MAX-ACCESS not-accessible
			STATUS current
			DESCRIPTION
				"The unique identifier of the malicious call reject entry."
			::= { zhoneVoipMaliciousCallerEntry 1 }

		
		-- 1.3.6.1.4.1.5504.4.3.4.5.2.1.2
		zhoneVoipMaliciousCallerUri OBJECT-TYPE
			SYNTAX SnmpAdminString
			MAX-ACCESS read-create
			STATUS current
			DESCRIPTION
				"Incoming call from this URI will be rejected. The network operator is responsible
				for provisioning exactly as per appearance in the incoming session notification
				(SIP INVITE) the calling user's address-of-record (AOR) formatted as a SIP URI"
			::= { zhoneVoipMaliciousCallerEntry 2 }

		
		-- 1.3.6.1.4.1.5504.4.3.4.5.2.1.3
		zhoneVoipMaliciousCallerEnable OBJECT-TYPE
			SYNTAX TruthValue
			MAX-ACCESS read-create
			STATUS current
			DESCRIPTION
				"Indicates whether the incoming call reject is enabled"
			DEFVAL { true }
			::= { zhoneVoipMaliciousCallerEntry 3 }

		
		-- 1.3.6.1.4.1.5504.4.3.4.5.2.1.4
		zhoneVoipMaliciousCallerRowStatus OBJECT-TYPE
			SYNTAX ZhoneRowStatus
			MAX-ACCESS read-create
			STATUS current
			DESCRIPTION
				"The row status is used to create or delete an entry in 
				this table."
			::= { zhoneVoipMaliciousCallerEntry 4 }

		
		-- 1.3.6.1.4.1.5504.4.3.4.6
		zhoneVoipServerCfg OBJECT IDENTIFIER::= { zhoneVoip 6 }

		
		-- 1.3.6.1.4.1.5504.4.3.4.6.1
		zhoneVoipServerTable OBJECT-TYPE
			SYNTAX SEQUENCE OF ZhoneVoipServerEntry
			MAX-ACCESS not-accessible
			STATUS current
			DESCRIPTION
				"Table of VOIP Server addresses applicable to each VOIP
				user agent within the system."
			::= { zhoneVoipServerCfg 1 }

		
		-- 1.3.6.1.4.1.5504.4.3.4.6.1.1
		zhoneVoipServerEntry OBJECT-TYPE
			SYNTAX ZhoneVoipServerEntry
			MAX-ACCESS not-accessible
			STATUS current
			DESCRIPTION
				"An entry within the table.  Indexed by applIndex, which
				is the slot number, and a user specified unique number."
			INDEX { applIndex, zhoneVoipServerAddressIndex }
			::= { zhoneVoipServerTable 1 }

		
		ZhoneVoipServerEntry ::=
			SEQUENCE { 
				zhoneVoipServerAddressIndex
					Unsigned32,
				zhoneVoipServerRowStatus
					ZhoneRowStatus,
				zhoneVoipServerAddrType
					InetAddressType,
				zhoneVoipServerAddr
					InetAddress,
				zhoneVoipServerUdpPortNumber
					Integer32,
				zhoneVoipServerId
					INTEGER,
				zhoneVoipServerProtocol
					INTEGER,
				zhoneVoipServerSendCallProceedingTone
					TruthValue,
				zhoneVoipServerRtcpEnabled
					TruthValue,
				zhoneVoipServerRtcpPacketInterval
					Integer32,
				zhoneVoipServerInterDigitTimeout
					Integer32,
				zhoneVoipServerIpTos
					Integer32,
				zhoneVoipServerDomainName
					SnmpAdminString,
				zhoneVoipServerExpiresInvite
					Unsigned32,
				zhoneVoipServerExpiresRegister
					Unsigned32,
				zhoneVoipServerHeaderMethod
					BITS,
				zhoneVoipServerSessionTimer
					INTEGER,
				zhoneVoipServerSessionExpiration
					Unsigned32,
				zhoneVoipServerSessionMinSE
					Unsigned32,
				zhoneVoipServerSessionCallerReqTimer
					INTEGER,
				zhoneVoipServerSessionCalleeReqTimer
					INTEGER,
				zhoneVoipServerSessionCallerSpecifyRefresher
					INTEGER,
				zhoneVoipServerSessionCalleeSpecifyRefresher
					INTEGER,
				zhoneVoipServerDtmfMode
					INTEGER,
				zhoneVoipServerBehaviorStringOne
					OCTET STRING,
				zhoneVoipServerRtpTermIdSyntax
					OCTET STRING,
				zhoneVoipServerRtpDSCP
					OCTET STRING,
				zhoneVoipServerSignalingDSCP
					OCTET STRING,
				zhoneVoipServerDtmfPayloadId
					Integer32,
				zhoneVoipServerRegisterReadyTimeout
					Unsigned32,
				zhoneVoipServerMessageRetryCount
					Integer32,
				zhoneVoipServerFeatures
					BITS,
				zhoneVoipServerTransportProtocol
					INTEGER,
				zhoneVoipSigLocalPortNumber
					Integer32,
				zhoneVoipServerRegisterTimerExpiry
					Unsigned32,
				zhoneVoipServerRoundTripTimeoutMs
					Unsigned32,
				zhoneVoipServerMaxRetransmitIntervalMs
					Unsigned32,
				zhoneVoipServerEsaRetryCount
					Unsigned32,
				zhoneVoipServerEsaRecoveryCount
					Unsigned32,
				zhoneVoipServerAreaCode
					SnmpAdminString
			 }

		-- 1.3.6.1.4.1.5504.4.3.4.6.1.1.1
		zhoneVoipServerAddressIndex OBJECT-TYPE
			SYNTAX Unsigned32
			MAX-ACCESS not-accessible
			STATUS current
			DESCRIPTION
				"A unique identifier of a server address when
				multiple addresses are configured by the MGCP entity.
				If one address isn't reachable, then another can
				be tried."
			::= { zhoneVoipServerEntry 1 }

		
		-- 1.3.6.1.4.1.5504.4.3.4.6.1.1.2
		zhoneVoipServerRowStatus OBJECT-TYPE
			SYNTAX ZhoneRowStatus
			MAX-ACCESS read-create
			STATUS current
			DESCRIPTION
				"Row Status is used to create, modify or delete an entry."
			::= { zhoneVoipServerEntry 2 }

		
		-- 1.3.6.1.4.1.5504.4.3.4.6.1.1.3
		zhoneVoipServerAddrType OBJECT-TYPE
			SYNTAX InetAddressType
			MAX-ACCESS read-create
			STATUS current
			DESCRIPTION
				"This object specifies the type of address contained
				in the associated instance of sipVoipServerAddr."
			DEFVAL { ipv4 }
			::= { zhoneVoipServerEntry 3 }

		
		-- 1.3.6.1.4.1.5504.4.3.4.6.1.1.4
		zhoneVoipServerAddr OBJECT-TYPE
			SYNTAX InetAddress
			MAX-ACCESS read-create
			STATUS current
			DESCRIPTION
				"This object specifies the address of a VOIP server
				this user agent will use to proxy/redirect calls."
			::= { zhoneVoipServerEntry 4 }

		
		-- 1.3.6.1.4.1.5504.4.3.4.6.1.1.5
		zhoneVoipServerUdpPortNumber OBJECT-TYPE
			SYNTAX Integer32 (1..65535)
			MAX-ACCESS read-create
			STATUS current
			DESCRIPTION
				"Specifies the UDP Port number for the MGCP Gateway.
				2427 is the IANA Registered MGCP Gateway port."
			DEFVAL { 2427 }
			::= { zhoneVoipServerEntry 5 }

		
		-- 1.3.6.1.4.1.5504.4.3.4.6.1.1.6
		zhoneVoipServerId OBJECT-TYPE
			SYNTAX INTEGER
				{
				longboard(1),
				asterisk(2),
				sipexpressrouter(3),
				metaswitch(4),
				sylantro(5),
				broadsoft(6),
				ubiquity(7),
				generalbandwidth(8),
				tekelec-T6000(9),
				generic(10),
				sonus(11),
				siemens(12),
				tekelec-T9000(13),
				lucent-telica(14),
				nortel-cs2000(15),
				nuera(16),
				lucent-imerge(17),
				coppercom(18),
				newcross(19),
				cisco-bts(20),
				cirpack-utp(21),
				italtel-issw(22),
				cisco-pgw(23),
				microtrol-msk10(24),
				nortel-dms10(25),
				verso-clarent-c5cm(26),
				cedarpoint-safari(27),
				huawei-softx3000(28),
				nortel-cs1500(29),
				taqua-t7000(30),
				utstarcom-mswitch(31),
				broadsoft-broadworks(32),
				broadsoft-m6(33),
				genband-g9(34),
				netcentrex(35),
				genband-g6(36),
				alu-5060(37),
				ericsson-apz60(38)
				}
			MAX-ACCESS read-create
			STATUS current
			DESCRIPTION
				"Identifies the voip server type."
			DEFVAL { generic }
			::= { zhoneVoipServerEntry 6 }

		
		-- 1.3.6.1.4.1.5504.4.3.4.6.1.1.7
		zhoneVoipServerProtocol OBJECT-TYPE
			SYNTAX INTEGER
				{
				sip(1),
				mgcp(2),
				megaco(3),
				ncs(4)
				}
			MAX-ACCESS read-create
			STATUS current
			DESCRIPTION
				"The signalling protocol used for VOIP. 
				Choicees are SIP (Session Initiation Protocol) and MGCP 
				(Media Gateway Control Protocol).  
				"
			DEFVAL { sip }
			::= { zhoneVoipServerEntry 7 }

		
		-- 1.3.6.1.4.1.5504.4.3.4.6.1.1.8
		zhoneVoipServerSendCallProceedingTone OBJECT-TYPE
			SYNTAX TruthValue
			MAX-ACCESS read-create
			STATUS current
			DESCRIPTION
				"ndicates whether, on call originations destined to the PSTN, the 
				device should play a call proceeding tone while waiting for 
				ring-back tone from the switch."
			DEFVAL { false }
			::= { zhoneVoipServerEntry 8 }

		
		-- 1.3.6.1.4.1.5504.4.3.4.6.1.1.9
		zhoneVoipServerRtcpEnabled OBJECT-TYPE
			SYNTAX TruthValue
			MAX-ACCESS read-create
			STATUS current
			DESCRIPTION
				"Indicates whether the Real-Time Control Protocol is enabled for
				the device. "
			DEFVAL { false }
			::= { zhoneVoipServerEntry 9 }

		
		-- 1.3.6.1.4.1.5504.4.3.4.6.1.1.10
		zhoneVoipServerRtcpPacketInterval OBJECT-TYPE
			SYNTAX Integer32
			MAX-ACCESS read-create
			STATUS current
			DESCRIPTION
				"RTCP packet interval, in milleseconds.  Range is 2500 to 10000 ms.
				This object's value is only pertinent if RTCP has been enabled."
			DEFVAL { 5000 }
			::= { zhoneVoipServerEntry 10 }

		
		-- 1.3.6.1.4.1.5504.4.3.4.6.1.1.11
		zhoneVoipServerInterDigitTimeout OBJECT-TYPE
			SYNTAX Integer32
			MAX-ACCESS read-create
			STATUS current
			DESCRIPTION
				"This parameter indicates the duration, in seconds, that the device 
				will wait after each digit is entered before assuming the user has 
				finished entering digits. "
			DEFVAL { 10 }
			::= { zhoneVoipServerEntry 11 }

		
		-- 1.3.6.1.4.1.5504.4.3.4.6.1.1.12
		zhoneVoipServerIpTos OBJECT-TYPE
			SYNTAX Integer32
			MAX-ACCESS read-create
			STATUS current
			DESCRIPTION
				"This parameter indicates the tos value that is set in the ip header for
				voice of ip traffic."
			DEFVAL { 0 }
			::= { zhoneVoipServerEntry 12 }

		
		-- 1.3.6.1.4.1.5504.4.3.4.6.1.1.13
		zhoneVoipServerDomainName OBJECT-TYPE
			SYNTAX SnmpAdminString
			MAX-ACCESS read-create
			STATUS current
			DESCRIPTION
				"This parameter indicates the Universal Resource Identifier (URI)
				of the system."
			::= { zhoneVoipServerEntry 13 }

		
		-- 1.3.6.1.4.1.5504.4.3.4.6.1.1.14
		zhoneVoipServerExpiresInvite OBJECT-TYPE
			SYNTAX Unsigned32
			UNITS "seconds"
			MAX-ACCESS read-create
			STATUS current
			DESCRIPTION
				"For user agent clients, this value is inserted into the  
				Expires header.  
				For proxy servers, if a received request contained an  
				Expires header, then the value in the header takes  
				precedence."
			::= { zhoneVoipServerEntry 14 }

		
		-- 1.3.6.1.4.1.5504.4.3.4.6.1.1.15
		zhoneVoipServerExpiresRegister OBJECT-TYPE
			SYNTAX Unsigned32
			UNITS "seconds"
			MAX-ACCESS read-create
			STATUS current
			DESCRIPTION
				"For user agent clients, this value is inserted into the  
				Expires header.  
				For registrar servers, if a received request contained an  
				Expires header, then the value in the header takes  
				precedence."
			::= { zhoneVoipServerEntry 15 }

		
		-- 1.3.6.1.4.1.5504.4.3.4.6.1.1.16
		zhoneVoipServerHeaderMethod OBJECT-TYPE
			SYNTAX BITS
				{
				invite(0),
				register(1)
				}
			MAX-ACCESS read-create
			STATUS current
			DESCRIPTION
				"This convention is a bit map. Each bit represents a  
				SIP method where the Expires header should be included.  
				If a bit has value 1, then the requests corresponding  
				to that SIP method must include an Expires header line.  
				If a bit has value 0, then the Expires header line will  
				not be added. 
				
				Combinations of bits can be set when the Expires header   
				line is required in multiple SIP methods.  
				
				bit 0   : INVITE method.  
				bit 1   : REGISTER Method."
			::= { zhoneVoipServerEntry 16 }

		
		-- 1.3.6.1.4.1.5504.4.3.4.6.1.1.17
		zhoneVoipServerSessionTimer OBJECT-TYPE
			SYNTAX INTEGER
				{
				on(1),
				off(2)
				}
			MAX-ACCESS read-create
			STATUS current
			DESCRIPTION
				"Support session timers
				
				on : Session timers are supported, 
				     and SIP messages will have a 'Supported: timer' header
				off: Session timers are NOT supported,
				     and SIP messages will NOT have a 'Supported: timer' header"
			DEFVAL { off }
			::= { zhoneVoipServerEntry 17 }

		
		-- 1.3.6.1.4.1.5504.4.3.4.6.1.1.18
		zhoneVoipServerSessionExpiration OBJECT-TYPE
			SYNTAX Unsigned32 (90..2147483647)
			UNITS "seconds"
			MAX-ACCESS read-create
			STATUS current
			DESCRIPTION
				"The time at which an element (proxy, UAC, UAS)
				will consider the SIP session timed out, if no 
				successful session refresh transaction occurs 
				beforehand."
			DEFVAL { 180 }
			::= { zhoneVoipServerEntry 18 }

		
		-- 1.3.6.1.4.1.5504.4.3.4.6.1.1.19
		zhoneVoipServerSessionMinSE OBJECT-TYPE
			SYNTAX Unsigned32 (90..2147483647)
			UNITS "seconds"
			MAX-ACCESS read-create
			STATUS current
			DESCRIPTION
				"Because of the processing load of mid-dialog 
				requests, all elements (proxy, UAC, UAS) can 
				have configured minimum value for the session 
				interval that they are willing to accept."
			DEFVAL { 180 }
			::= { zhoneVoipServerEntry 19 }

		
		-- 1.3.6.1.4.1.5504.4.3.4.6.1.1.20
		zhoneVoipServerSessionCallerReqTimer OBJECT-TYPE
			SYNTAX INTEGER
				{
				yes(1),
				no(2)
				}
			MAX-ACCESS read-create
			STATUS current
			DESCRIPTION
				"This field specifies the caller's action
				
				yes: Caller (UAC) will request for timer when 
				     making outbound calls
				no : Caller (UAC) will NOT request for timer
				     when making outbound calls"
			DEFVAL { no }
			::= { zhoneVoipServerEntry 20 }

		
		-- 1.3.6.1.4.1.5504.4.3.4.6.1.1.21
		zhoneVoipServerSessionCalleeReqTimer OBJECT-TYPE
			SYNTAX INTEGER
				{
				yes(1),
				no(2)
				}
			MAX-ACCESS read-create
			STATUS current
			DESCRIPTION
				"When caller supports timer but did not request one
				this field specifies the callee's action
				
				yes: Callee (UAS) will request for timer
				no : Callee (UAS) will NOT request for timer"
			DEFVAL { no }
			::= { zhoneVoipServerEntry 21 }

		
		-- 1.3.6.1.4.1.5504.4.3.4.6.1.1.22
		zhoneVoipServerSessionCallerSpecifyRefresher OBJECT-TYPE
			SYNTAX INTEGER
				{
				uac(1),
				uas(2),
				omit(3)
				}
			MAX-ACCESS read-create
			STATUS current
			DESCRIPTION
				"Caller specifies the refresher:
				
				UAC : Caller specifies itself (UAC) as the refresher
				UAS : Caller specifies the callee (UAS) as the refresher
				Omit: Caller does NOT explicitly specify the refresher"
			DEFVAL { omit }
			::= { zhoneVoipServerEntry 22 }

		
		-- 1.3.6.1.4.1.5504.4.3.4.6.1.1.23
		zhoneVoipServerSessionCalleeSpecifyRefresher OBJECT-TYPE
			SYNTAX INTEGER
				{
				uac(1),
				uas(2)
				}
			MAX-ACCESS read-create
			STATUS current
			DESCRIPTION
				"When UAC did not specify refresher tag, callee 
				specifies the refresher:
				
				UAC : Callee specifies the caller (UAC) as the refresher
				UAS : Callee specifies itself (UAS) as the refresher"
			DEFVAL { uac }
			::= { zhoneVoipServerEntry 23 }

		
		-- 1.3.6.1.4.1.5504.4.3.4.6.1.1.24
		zhoneVoipServerDtmfMode OBJECT-TYPE
			SYNTAX INTEGER
				{
				inband(1),
				rfc2833(2),
				rfc2833only(3)
				}
			MAX-ACCESS read-create
			STATUS current
			DESCRIPTION
				"Indicates whether dtmf digits are to be passed as codec 
				voice packets or special separate packets (rfc2833).
				"
			DEFVAL { rfc2833 }
			::= { zhoneVoipServerEntry 24 }

		
		-- 1.3.6.1.4.1.5504.4.3.4.6.1.1.25
		zhoneVoipServerBehaviorStringOne OBJECT-TYPE
			SYNTAX OCTET STRING (SIZE (0..512))
			UNITS "characters"
			MAX-ACCESS read-only
			STATUS current
			DESCRIPTION
				"This field is used to control any switch specific behavior of the VOIP Gateway."
			DEFVAL { "" }
			::= { zhoneVoipServerEntry 25 }

		
		-- 1.3.6.1.4.1.5504.4.3.4.6.1.1.26
		zhoneVoipServerRtpTermIdSyntax OBJECT-TYPE
			SYNTAX OCTET STRING (SIZE (0..96))
			UNITS "characters"
			MAX-ACCESS read-write
			STATUS current
			DESCRIPTION
				"This field describes the Ephemeral term ID syntax for the switch.
				The RTP syntax varies from switch to switch.But the string should 
				contain atleast one %eid format, eg <string>%eid<string> .
				This field is supported only for the Megaco protocol for all other
				protocols this field will be initialized to NULL.
				If the protocol is megaco and the field is NULL,
				Ephemeral term id will be updated to default syntax of the server Id given. 
				If the server Id is not provisioned with the default id then field 
				will be updated to NULL.
				"
			DEFVAL { "" }
			::= { zhoneVoipServerEntry 26 }

		
		-- 1.3.6.1.4.1.5504.4.3.4.6.1.1.27
		zhoneVoipServerRtpDSCP OBJECT-TYPE
			SYNTAX OCTET STRING (SIZE (1..8))
			MAX-ACCESS read-create
			STATUS current
			DESCRIPTION
				"This parameter indicates DSCP value for voip's rtp traffic.
				
				NOTE:zhoneVoipServerIpTos field must be zero before entering a new 
				value into this field.
				
				Valid code values:
				
				<0-63>   Differentiated services codepoint value 
				   af11     Mark packets with AF11 dscp (001010) 
				   af12     Mark packets with AF12 dscp (001100) 
				   af13     Mark packets with AF13 dscp (001110) 
				   af21     Mark packets with AF21 dscp (010010) 
				   af22     Mark packets with AF22 dscp (010100) 
				   af23     Mark packets with AF23 dscp (010110) 
				   af31     Mark packets with AF31 dscp (011010) 
				   af32     Mark packets with AF32 dscp (011100) 
				   af33     Mark packets with AF33 dscp (011110) 
				   af41     Mark packets with AF41 dscp (100010) 
				   af42     Mark packets with AF42 dscp (100100) 
				   af43     Mark packets with AF43 dscp (100110) 
				   cs1      Mark packets with CS1(precedence 1) dscp (001000) 
				   cs2      Mark packets with CS2(precedence 2) dscp (010000) 
				   cs3      Mark packets with CS3(precedence 3) dscp (011000) 
				   cs4      Mark packets with CS4(precedence 4) dscp (100000) 
				   cs5      Mark packets with CS5(precedence 5) dscp (101000) 
				   cs6      Mark packets with CS6(precedence 6) dscp (110000) 
				   cs7      Mark packets with CS7(precedence 7) dscp (111000) 
				   default  Mark packets with default dscp (000000) 
				   ef       Mark packets with EF dscp (101110) 
				"
			::= { zhoneVoipServerEntry 27 }

		
		-- 1.3.6.1.4.1.5504.4.3.4.6.1.1.28
		zhoneVoipServerSignalingDSCP OBJECT-TYPE
			SYNTAX OCTET STRING (SIZE (1..8))
			MAX-ACCESS read-create
			STATUS current
			DESCRIPTION
				"This parameter indicates DSCP value for voip's signaling traffic.
				
				Valid code values:
				
				<0-63>   Differentiated services codepoint value 
				   af11     Mark packets with AF11 dscp (001010) 
				   af12     Mark packets with AF12 dscp (001100) 
				   af13     Mark packets with AF13 dscp (001110) 
				   af21     Mark packets with AF21 dscp (010010) 
				   af22     Mark packets with AF22 dscp (010100) 
				   af23     Mark packets with AF23 dscp (010110) 
				   af31     Mark packets with AF31 dscp (011010) 
				   af32     Mark packets with AF32 dscp (011100) 
				   af33     Mark packets with AF33 dscp (011110) 
				   af41     Mark packets with AF41 dscp (100010) 
				   af42     Mark packets with AF42 dscp (100100) 
				   af43     Mark packets with AF43 dscp (100110) 
				   cs1      Mark packets with CS1(precedence 1) dscp (001000) 
				   cs2      Mark packets with CS2(precedence 2) dscp (010000) 
				   cs3      Mark packets with CS3(precedence 3) dscp (011000) 
				   cs4      Mark packets with CS4(precedence 4) dscp (100000) 
				   cs5      Mark packets with CS5(precedence 5) dscp (101000) 
				   cs6      Mark packets with CS6(precedence 6) dscp (110000) 
				   cs7      Mark packets with CS7(precedence 7) dscp (111000) 
				   default  Mark packets with default dscp (000000) 
				   ef       Mark packets with EF dscp (101110) 
				"
			::= { zhoneVoipServerEntry 28 }

		
		-- 1.3.6.1.4.1.5504.4.3.4.6.1.1.29
		zhoneVoipServerDtmfPayloadId OBJECT-TYPE
			SYNTAX Integer32 (96..127)
			MAX-ACCESS read-write
			STATUS current
			DESCRIPTION
				"Description."
			DEFVAL { 101 }
			::= { zhoneVoipServerEntry 29 }

		
		-- 1.3.6.1.4.1.5504.4.3.4.6.1.1.30
		zhoneVoipServerRegisterReadyTimeout OBJECT-TYPE
			SYNTAX Unsigned32
			UNITS "seconds"
			MAX-ACCESS read-create
			STATUS current
			DESCRIPTION
				"For Megaco Service change Messages this value will
				be used in service-change-delay."
			DEFVAL { 10 }
			::= { zhoneVoipServerEntry 30 }

		
		-- 1.3.6.1.4.1.5504.4.3.4.6.1.1.31
		zhoneVoipServerMessageRetryCount OBJECT-TYPE
			SYNTAX Integer32 (1..10)
			MAX-ACCESS read-create
			STATUS current
			DESCRIPTION
				"This field specifies the number of retries of SIP 
				message to every DNS resolved server IP addresses.
				The default behaviour means that the SIP message
				will be retransmitted to the first DNS resolved IP 
				address once and the remaining retransmissions will 
				be to the second DNS resolved IP address. 
				The default value of zero or DNS resolved to a single 
				IP address means that the default behaviour will take
				effect"
			DEFVAL { 1 }
			::= { zhoneVoipServerEntry 31 }

		
		-- 1.3.6.1.4.1.5504.4.3.4.6.1.1.32
		zhoneVoipServerFeatures OBJECT-TYPE
			SYNTAX BITS
				{
				sip-outbound(0),
				gruu(1),
				rfc3262(2),
				rtcp-xr(3),
				teluri(4)
				}
			MAX-ACCESS read-create
			STATUS current
			DESCRIPTION
				"Set of features can be enabled for voip server
				  Bit      Feature
				  ---      --------
				  1        sip outbound : Supports rfc-5626,Managing Client-Initiated Connections
				                          in the SIP         
				  2        gruu         : Supports rfc-5627,Obtaining and Using Globally Routable User Agent URIs (GRUUs)
				                          in the SIP 
				  3        rfc-3262     : Supports Reliability of Provisional Responses
				                          in the SIP
				  4        rtcp-xr      : Supports rtcp and rtcp-xr features. Rfc-3611
				  5        teluri       : Supports tel URI."
			::= { zhoneVoipServerEntry 32 }

		
		-- 1.3.6.1.4.1.5504.4.3.4.6.1.1.33
		zhoneVoipServerTransportProtocol OBJECT-TYPE
			SYNTAX INTEGER
				{
				udp(1),
				tcp(2)
				}
			MAX-ACCESS read-create
			STATUS current
			DESCRIPTION
				"This field specifies type of transport protocol configured.
				Possible values are udp and tcp."
			DEFVAL { udp }
			::= { zhoneVoipServerEntry 33 }

		
		-- 1.3.6.1.4.1.5504.4.3.4.6.1.1.34
		zhoneVoipSigLocalPortNumber OBJECT-TYPE
			SYNTAX Integer32 (1..65535)
			MAX-ACCESS read-create
			STATUS current
			DESCRIPTION
				"This field specifies signalling local port number,
				used when tcp is configured as tranport protocol."
			DEFVAL { 5060 }
			::= { zhoneVoipServerEntry 34 }

		
		-- 1.3.6.1.4.1.5504.4.3.4.6.1.1.35
		zhoneVoipServerRegisterTimerExpiry OBJECT-TYPE
			SYNTAX Unsigned32 (0..100)
			MAX-ACCESS read-create
			STATUS current
			DESCRIPTION
				"This field describes how much percentage of register expiry 
				received from server will be used as registration expiry time.
												
				The default value 0 indicates registration expiry time is equal to 
				register expiry received from server - 32 Sec."
			DEFVAL { 0 }
			::= { zhoneVoipServerEntry 35 }

		
		-- 1.3.6.1.4.1.5504.4.3.4.6.1.1.36
		zhoneVoipServerRoundTripTimeoutMs OBJECT-TYPE
			SYNTAX Unsigned32
			UNITS "milliseconds"
			MAX-ACCESS read-create
			STATUS current
			DESCRIPTION
				"Message timeout time. The estimate of the roundtrip time (RTT) 
				between the client and server transactions i.e the time it takes 
				between sending out the request to the point of getting a response.
				In rfc-3261(SIP), this field refers to timer T1."
			DEFVAL { 500 }
			::= { zhoneVoipServerEntry 36 }

		
		-- 1.3.6.1.4.1.5504.4.3.4.6.1.1.37
		zhoneVoipServerMaxRetransmitIntervalMs OBJECT-TYPE
			SYNTAX Unsigned32
			UNITS "milliseconds"
			MAX-ACCESS read-create
			STATUS current
			DESCRIPTION
				"The maximum retransmit interval. In rfc-3261(SIP), 
				this field refers to timer T2 i.e maximum retransmission 
				interval for non-INVITE requests and INVITE responses."
			DEFVAL { 4000 }
			::= { zhoneVoipServerEntry 37 }

		
		-- 1.3.6.1.4.1.5504.4.3.4.6.1.1.38
		zhoneVoipServerEsaRetryCount OBJECT-TYPE
			SYNTAX Unsigned32 (1..50)
			MAX-ACCESS read-create
			STATUS current
			DESCRIPTION
				"This field indicates maximum number of times sip monitor message 
				needs to be re-transmitted before enter into ESA mode."
			DEFVAL { 10 }
			::= { zhoneVoipServerEntry 38 }

		
		-- 1.3.6.1.4.1.5504.4.3.4.6.1.1.39
		zhoneVoipServerEsaRecoveryCount OBJECT-TYPE
			SYNTAX Unsigned32 (1..50)
			MAX-ACCESS read-create
			STATUS current
			DESCRIPTION
				"This field indicates minimum number of times should receive response 
				for sip monitor message from switch before exiting from ESA mode."
			DEFVAL { 5 }
			::= { zhoneVoipServerEntry 39 }

		
		-- 1.3.6.1.4.1.5504.4.3.4.6.1.1.40
		zhoneVoipServerAreaCode OBJECT-TYPE
			SYNTAX SnmpAdminString
			MAX-ACCESS read-create
			STATUS current
			DESCRIPTION
				"Indicates the local area code"
			::= { zhoneVoipServerEntry 40 }

		
	
	END

--
-- comVoip.mib
--
