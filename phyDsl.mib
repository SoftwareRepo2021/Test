--
-- phyDsl.mib
-- MIB generated by MG-SOFT Visual MIB Builder Version 3.0 Build 285
-- Tuesday, January 26, 2016 at 10:56:42
--

	ZhoneDsl-MIB DEFINITIONS ::= BEGIN
 
		IMPORTS
			adslLineEntry, adslAtucChanCurrTxRate, adslAtucChanPrevTxRate, adslAturChanCurrTxRate, adslAturChanPrevTxRate, 
			adslLineConfProfileEntry			
				FROM ADSL-LINE-MIB			
			ifIndex			
				FROM IF-MIB			
			OBJECT-GROUP			
				FROM SNMPv2-CONF			
			TimeTicks, Integer32, Unsigned32, Counter32, OBJECT-TYPE, 
			MODULE-IDENTITY, OBJECT-IDENTITY, NOTIFICATION-TYPE			
				FROM SNMPv2-SMI			
			TruthValue, RowStatus, DateAndTime, TEXTUAL-CONVENTION			
				FROM SNMPv2-TC			
			zhoneDsl, zhoneModules			
				FROM Zhone			
			ZhoneAdminString, ZhoneRowStatus, ZhoneEnabledFlag			
				FROM Zhone-TC;
	
	
-- 
-- To create generated protection layer for the Malc:
--     $ /vob/zhonetools/bin/pahrser.pl rfc2571.mib rfc2662.mib phyDsl.mib
-- To create generated mib handler for the Malc:
--     $ cd /vob/mibs/src
--     $ /vob/EPILOGUE/binaries/emissary/solaris/mibcomp \
--       rfc1907.mib \
--       iftype.mib \
--       Zhone.mib \
--       Zhone-TC.mib \
--       rfc2233.mib \
--       rfc2571.mib \
--       rfc2493.mib \
--       rfc2662tc.mib \
--       rfc2662.mib \
--       -stub -o dslMibHdlr.c phyDsl.mib
-- 
-- Overview of Zhone DSL mib
-- 
-- The Zhone DSL mib provides configuration, status and performance parameters
-- used/provided by Zhone implementation of HDSL2 SDSL and SHDSL interfaces. 
-- The following tables are described in this mib
-- 
-- zhoneDslLineTable
-- This table provides the lineType and configProfileName associated with the 
-- line. There will be one entry in this table for each interface line available
-- in the system. This table is indexed by interface's ifIndex. 
-- In the case of dynamic profiles implementation,When the system comes up for the 
-- first time, the zhoneDslLineType is defaulted to hdsl2 and the
-- zhoneDslConfigProfName is set to "zhonedefault". User can change this value 
-- by creating new type specific configuration profiles and pointing it to the new
-- type specific config profile name. For example, if the user want to change zhonedefalut
-- to say "BOBHDSL2PROFILE", then he/she should first create a zhoneHdsl2ConfigProfileEntry
-- with the name "BOBHDSL2PROFILE" and change the value of zhoneDslConfigProfName to
-- "BOBHDSL2PROFILE". In this example we are assuming the zhoneDslLineType as hdsl2.
-- Similarly zhoneDslAlarmProfName identifies an entry in the zhoneDslAlarmProfileTable.
-- 
-- In the case of static profiles implementation, there will be 1:1 relationship between profiles
-- and the number of interfaces supported in the system. In this case the zhoneDslConfigProfName and
-- zhoneDslAlarmProfName are defaulted to ifIndex (ascii value). The user is not allowed to 
-- modify zhoneDslConfigProfName and zhoneDslAlarmProfName. Also in this case user is not allowed to create/delete any
-- profiles in the system. All the profiles will be created in the system when the system comes up for 
-- the first time and user is allowed only to modify these profiles.
-- 
-- This table also provides common status objects provided by both HDSL2 and SDSL interfaces. 
-- Depending on  zhoneDslLineType user can use type specific status table.
-- 
-- zhoneHdsl2ConfigProfileTable
-- This table provides HDSL2 specific configuration parameters. This table is indexed by
-- zhoneHdsl2ConfigProfileName. User can create many instances of this table entry. Set operation
-- with a specific instance triggers row creation if the specified instance is not found
-- in the system.
--  
-- zhoneSdslConfigProfileTable
-- This table provides SDSL specific configuration parameters  This table is indexed by
-- zhoneSdslConfigProfileName.User can create many instances of this table entry. Set operation
-- with a specific instance triggers row creation if the specified instance is not found
-- in the system.
-- 
-- zhoneHdsl2StatusTable 
-- This table provides HDSL2 specific status information. This table is indexed by ifIndex
-- zhoneSdslStatusTable
-- This table provides SDSL specific status information. This table is indexed by ifIndex
-- 
-- zhoneDslPerfDataTotalTable 
-- This table provides generic total performance parameters. This table is not specific to
-- any type of DSL interface. This table AUGMENTS zhoneDslLineTable
-- 
-- zhoneDslPerfDataCurTable
-- This table provides current 15min interval performance parameters. This table is not 
-- specific to any type of DSL interface. This table AUGMENTS zhoneDslLineTable
-- 
-- zhoneDslAlarmProfileTable
-- This table defines the threshold values for alarm conditions. This table is also indexed by
-- zhoneDslAlarmProfileName. User can create many instances of this table entry. Set operation
-- with a specific instance triggers row creation if the specified instance is not found
-- in the system.
-- 
-- The SHDSL is supported on ZEdge and BAN products. On ZEdge it will be supported in release 1.1
-- zhoneShdslConfigProfileTable.
-- This table provides SHDSL specific configuration parameters  This table is indexed by
-- zhoneShdslConfigProfileName.User can create many instances of this table entry. Set operation
-- with a specific instance triggers row creation if the specified instance is not found
-- in the system.
-- 
-- zhoneShdslStatusTable
-- This table provides SHDSL specific status information. This table is indexed by ifIndex
-- 
-- zhoneAdslLineExtTable
-- This table provides ADSL specific configuration parameters  This table is indexed by ifIndex.
-- 
-- zhoneAdslLineProfileName.User can create many instances of this table entry. Set operation
-- with a specific instance triggers row creation if the specified instance is not found
-- in the system.
-- 
-- zhoneVdslControlTable
-- This table provides VDSL specific configuration parameters.
-- 
-- zhoneVdslStatusTable
-- This table provides VDSL specific status information.  This table is indexed by ifIndex.
-- 
-- zhoneVdslPerfMonTable
-- This table provides VDSL specific performance monitoring statistics.  This table is indexed by ifIndex.
-- 
-- zhoneAdslSelt
-- zhoneAdslDelt
-- The objects in these hierarchys provide a way to perform Single-Ended
-- and Dual-Ended Line Testing of ADSL lines.
-- 
-- zhoneDslDpboProfileTable allows configuration of the following
-- ITU-T G.997.1, paragraph 7.3.1.2.13 Downstream Power Back-Off 
-- profile parameters:
--   DPBOESEL  - E-Side Electrical Length
--   DPBOESCMA - E-Side Cable Model Parm A 
--   DPBOESCMB - E-Side Cable Model Parm B
--   DPBOESCMC - E-Side Cable Model Parm C
--   DPBOMUS   - Minimum Usable Signal
--   DPBOFMIN  - Minimum frequency
--   DPBOFMAX  - Maximum frequency
-- 
-- zhoneDslDpboEpsdTable allows configuration of the ITU-T G.997.1, 
-- paragraph 7.3.1.2.13 Downstream Power Back-Off DPBO Assumed exchange 
-- PSD mask (DPBOEPSD) breakpoints for the associated DPBO profile. 
-- There is a maximum of 16 breakpoints. This set of breakpoints define
-- the PSD mask that is assumed to be permitted at the exchange. Each 
-- breakpoint supports the following parameters:
--   DPBOEPSD Freq  - Assumed exchange PSD mask (DPBOEPSD) Frequency
--   DPBOEPSD Level - Assumed exchange PSD mask (DPBOEPSD) Level
-- 
-- zhoneDslDpboPsdMaskTable allows configuration of the ITU-T G.997.1, 
-- paragraph 7.3.1.2.13 Downstream Power Back-Off DPBO maximum PSD 
-- mask downstream (DPBOPSDMASKds) breakpoints for the associated DPBO 
-- profile. There is a maximum of 16 breakpoints. Each breakpoint 
-- supports the following parameters:
--   DPBOPSDMASKds Freq  - max PSD mask ds (DPBOPSDMASKds) Frequency
--   DPBOPSDMASKds Level - max PSD mask ds (DPBOPSDMASKds) Level
-- 
-- zhoneDslDpboLfoTable allows configuration of the ITU-T G.997.1, 
-- paragraph 7.3.1.2.13 Downstream Power Back-Off DPBO low frequency 
-- override (DPBOLFO) breakpoints for the associated DPBO profile. 
-- There is a maximum of 16 breakpoints. This set of breakpoints define
-- the PSD mask that overrides DPBO at low frequencies. Each breakpoint 
-- supports the following parameters:
--   DPBOLFO Freq  - DPBO low frequency override (DPBOLFO) Frequency
--   DPBOLFO Level - DPBO low frequency override (DPBOLFO) Level
-- 
-- In the case dynamic profile implementation user is allowed to create/delete any of the 
-- type specific configuration tables entries.
-- 
-- Following objects from ifTable defined in rfc2233.mib is supported
-- ifIndex :
-- This is a unique number generated in the system. ifIndex is used as 
-- index to some of the tables described above.
-- 
-- ifType: the interface types supported in this mib are hdsl2,sdsl and shdsl
-- ifAdminStatus: The desired state of the interface. (up, down or testing)
-- 
-- 
-- 
-- 
-- 
-- 
-- 
-- 
--  
--  
-- 
-- 
-- 
-- 
-- 
-- 
-- 
-- 
-- 
-- 
-- 
-- 
-- 
-- 
-- 
-- 
		-- 1.3.6.1.4.1.5504.6.3
		zhoneDslMib MODULE-IDENTITY 
			LAST-UPDATED "201601251715Z"		-- January 25, 2016 at 17:15 GMT
			ORGANIZATION 
				"Zhone Technologies, Inc."
			CONTACT-INFO 
				"Postal: 
				       Zhone Technologies, Inc.
				       @ Zhone Way
				       7001 Oakport Street
				       Oakland, CA 94621
				       USA
				
				Toll-Free: +1 877-ZHONE20 (+1 877-946-6320)
				      Tel: +1 510-777-7000
				      Fax: +1 510-777-7001
				    Email: support@zhone.com"
			DESCRIPTION 
				"This is a mib for the Zhone Technologies, Inc.
				proprietary dsl support based on the Zhone Technologies, Inc.
				specific implementation of  HDSL2, SDSL and VDSL. Also includes
				extension counters for ADSL. "
			REVISION "201601251715Z"		-- January 25, 2016 at 17:15 GMT
			DESCRIPTION 
				"Adding SELT Line Capacity"
			REVISION "201410011233Z"		-- October 01, 2014 at 12:33 GMT
			DESCRIPTION 
				"Expanded zhoneAdslSeltLnfEntry to allow for transfer of VDSL tone results."
			REVISION "201302272000Z"		-- February 27, 2013 at 20:00 GMT
			DESCRIPTION 
				"Adding support for G.INP / ITU-T G.998.4"
			REVISION "201301251744Z"		-- January 25, 2013 at 17:44 GMT
			DESCRIPTION 
				"Updating DELT device string"
			REVISION "201301091200Z"		-- January 09, 2013 at 12:00 GMT
			DESCRIPTION 
				"Add integer enum to zhoneAdslSeltDevice and update description."
			REVISION "201201201653Z"		-- January 20, 2012 at 16:53 GMT
			DESCRIPTION 
				"Add zhoneDslUpstreamTrafficAlarm
				and zhoneDslUpstreamTrafficAlarmChange."
			REVISION "201106281638Z"		-- June 28, 2011 at 16:38 GMT
			DESCRIPTION 
				"Updated zhoneDslDpboProfileIndex"
			REVISION "201103271909Z"		-- March 27, 2011 at 19:09 GMT
			DESCRIPTION 
				"Adding fields and tables for DPBO"
			REVISION "201102011638Z"		-- February 01, 2011 at 16:38 GMT
			DESCRIPTION 
				"Add zhoneAdslAnnexJModeEnabled"
			REVISION "201009282338Z"		-- September 28, 2010 at 23:38 GMT
			DESCRIPTION 
				"V01.05.41
				-add zhoneAdslAtucPhyRActive
				-add zhoneAdslAturPhyRActive"
			REVISION "201003090025Z"		-- March 09, 2010 at 00:25 GMT
			DESCRIPTION 
				"Added transmitted codewords, corrected code words and uncorrectable codewords to ATUC and ATUR tables
				"
			REVISION "200908201812Z"		-- August 20, 2009 at 18:12 GMT
			DESCRIPTION 
				"Adding Cabinet Mode support"
			REVISION "200907140805Z"		-- July 14, 2009 at 08:05 GMT
			DESCRIPTION 
				"Add Broadcom value subset to minINP"
			REVISION "200901072257Z"		-- January 07, 2009 at 22:57 GMT
			DESCRIPTION 
				"V01.05.37 - Added txPowerAttenuation in Adsl Co profile."
			REVISION "200811180615Z"		-- November 18, 2008 at 06:15 GMT
			DESCRIPTION 
				"Added new leaf to clear stats."
			REVISION "200806021355Z"		-- June 02, 2008 at 13:55 GMT
			DESCRIPTION 
				"V01.05.36
				- adjust range and default value of
				atucPhyRmaxINP and aturPhyRmaxINP"
			REVISION "200802271414Z"		-- February 27, 2008 at 14:14 GMT
			DESCRIPTION 
				"V01.05.35
				- add zhoneAdslAtucPhyRSupport
				- add zhoneAdslAturPhyRSupport
				- add zhoneAdslAtucPhyRMaxINP
				- add zhoneAdslAturPhyRMaxINP
				- add zhoneAdslAtucPhyRminRSoverhead
				- add zhoneAdslAturPhyRminRSoverhead
				- add zhoneAdslAtucPhyRRtxRatio
				- add zhoneAdslAturPhyRRtxRatio"
			REVISION "200802190918Z"		-- February 19, 2008 at 09:18 GMT
			DESCRIPTION 
				"V01.05.34
				- add zhoneAdslAnnexMPsdMask
				- add zhoneAdslAtucMinINP
				- add zhoneAdslAturMinINP"
			REVISION "200710191214Z"		-- October 19, 2007 at 12:14 GMT
			DESCRIPTION 
				"V01.05.33
				- add more values to zhoneDslLineStatus
				- cleanup text and remove unprintable character
				  in notes for ZhoneSdslConfigConnectMode
				"
			REVISION "200709141656Z"		-- September 14, 2007 at 16:56 GMT
			DESCRIPTION 
				"V01.05.32
				- add more error codes to zhoneAdslSeltStatus
				- add more error codes to zhoneAdsl2LineCmndConfLdsfFailReason"
			REVISION "200709131724Z"		-- September 13, 2007 at 17:24 GMT
			DESCRIPTION 
				"V01.05.31 - Add shdsl-2btl to zhoneDslLineType."
			REVISION "200609191244Z"		-- September 19, 2006 at 12:44 GMT
			DESCRIPTION 
				"V01.05.30
				Add config parameters for Selt."
			REVISION "200608221709Z"		-- August 22, 2006 at 17:09 GMT
			DESCRIPTION 
				"V01.05.29
				- Remove ZHONE keywords from
				  - VdslConfigProfile
				  - VdslStatusProfile
				  - VdslPerfDataCurr
				- Remove ZHONE keywords from objects in the following tables:
				  - zhoneVdslControlTable
				  - zhoneVdslStatusTable
				  - zhoneVdslPerfTable"
			REVISION "200606141011Z"		-- June 14, 2006 at 10:11 GMT
			DESCRIPTION 
				"V01.05.28
				- Fix ZHONE_KEYWORDs for SELT/DELT.
				- Add a Selt status value."
			REVISION "200606091253Z"		-- June 09, 2006 at 12:53 GMT
			DESCRIPTION 
				"V01.05.27 - move VDSL to another mib
				- obsolete zhoneVdslControlTable
				- obsolete zhoneVdslStatusTable
				- obsolete zhoneVdslPerfMonTable"
			REVISION "200604121600Z"		-- April 12, 2006 at 16:00 GMT
			DESCRIPTION 
				"V01.05.26 -- Add SELT and DELT"
			REVISION "200601231228Z"		-- January 23, 2006 at 12:28 GMT
			DESCRIPTION 
				"V01.05.25
				1.  add new transmission modes to zhoneAdslAtucActualTxMode
				2.  change reachOnlyMode to reachDSLMode in zhoneAdslTransmissionMode"
			REVISION "200512211757Z"		-- December 21, 2005 at 17:57 GMT
			DESCRIPTION 
				"1. Add reachOnlyMode to zoneAdslTransmissionMode
				2. Add zhoneAdslAnnexMModeEnabled to ZhoneAdslLineExtEntry"
			REVISION "200510291717Z"		-- October 29, 2005 at 17:17 GMT
			DESCRIPTION 
				"01.05.24 - add Min Tx/Rx Rates."
			REVISION "200505251857Z"		-- May 25, 2005 at 18:57 GMT
			DESCRIPTION 
				"V01.05.23 - Added zhoneAdslAtucActualTxMode in zhoneAdslAtucPerfEntry."
			REVISION "200412031030Z"		-- December 03, 2004 at 10:30 GMT
			DESCRIPTION 
				"V01.05.22 -- add counter for low signal quality"
			REVISION "200407291856Z"		-- July 29, 2004 at 18:56 GMT
			DESCRIPTION 
				"V01.05.21 -- show line alarm when admin-up"
			REVISION "200407081401Z"		-- July 08, 2004 at 14:01 GMT
			DESCRIPTION 
				"V01.05.20 -- add uptime,upcount,and postresult in dslSTatus"
			REVISION "200406101222Z"		-- June 10, 2004 at 12:22 GMT
			DESCRIPTION 
				"V01.05.19 - add shdsl BERT config and stats"
			REVISION "200405121815Z"		-- May 12, 2004 at 18:15 GMT
			DESCRIPTION 
				"V01.05.18 - Add adsl2/2Plus provisioning
				and stats."
			REVISION "200404161418Z"		-- April 16, 2004 at 14:18 GMT
			DESCRIPTION 
				"V01.05.17 - Added adslplus and adslplus2
				provisioning."
			REVISION "200403111151Z"		-- March 11, 2004 at 11:51 GMT
			DESCRIPTION 
				"V01.05.16 - Added LOSS counters in the zhoneAdslAtuc/Atur tables."
			REVISION "200402041242Z"		-- February 04, 2004 at 12:42 GMT
			DESCRIPTION 
				"V01.05.15 - Added zhoneAdslAtucPerfTable and zhoneAdslAturPerfEntry extended ADSL statistics
				"
			REVISION "200311101539Z"		-- November 10, 2003 at 15:39 GMT
			DESCRIPTION 
				"V01.05.14 - Removed zhoneVdslControlLineStatusTrapEnable."
			REVISION "200311031330Z"		-- November 03, 2003 at 13:30 GMT
			DESCRIPTION 
				"V01.05.13 - Added zhoneDslLineAlarmStatusChange trap."
			REVISION "200307241455Z"		-- July 24, 2003 at 14:55 GMT
			DESCRIPTION 
				"V01.05.12 - Add new shdsl line-rates
				for new 4-Wire G.SHDSL card."
			REVISION "200307141715Z"		-- July 14, 2003 at 17:15 GMT
			DESCRIPTION 
				"V01.05.11 - Changed incorrect value for UsRsFrameRate in the VdslControlTable."
			REVISION "200303211057Z"		-- March 21, 2003 at 10:57 GMT
			DESCRIPTION 
				"V01.05.10 - Add line status change trap for VDSL."
			REVISION "200303191400Z"		-- March 19, 2003 at 14:00 GMT
			DESCRIPTION 
				"V01.05.09 - Add VDSL mib definitions"
			REVISION "200212031230Z"		-- December 03, 2002 at 12:30 GMT
			DESCRIPTION 
				"V01.05.08 - Add Pots Low Bypass
				Filter Relay mib definitions."
			REVISION "200209061337Z"		-- September 06, 2002 at 13:37 GMT
			DESCRIPTION 
				"V01.05.07
				-- add currOutputPwr for dsl"
			REVISION "200207081235Z"		-- July 08, 2002 at 12:35 GMT
			DESCRIPTION 
				"V01.05.06 - 
				add tone range for ISDN to UpstreamToneIndices"
			REVISION "200206061313Z"		-- June 06, 2002 at 13:13 GMT
			DESCRIPTION 
				"V01.05.05 - 
				add more line rate
				for shdsl"
			REVISION "200204011047Z"		-- April 01, 2002 at 10:47 GMT
			DESCRIPTION 
				"V01.05.04 - Added zhoneDslLineStatusChangeTrapEnable
				entry in zhoneDslLineEntry table."
			REVISION "200203201223Z"		-- March 20, 2002 at 12:23 GMT
			DESCRIPTION 
				"V01.05.03 - Add new ADSL tone range leafs
				to the zhoneAdslLineExtTable:
				 1) zhoneAdslMaxDownstreamToneIndex
				 2) zhoneAdslMinDownstreamToneIndex
				 3) zhoneAdslMaxUpstreamToneIndex
				 4) zhoneAdslMinUpstreamToneIndex"
			REVISION "200202111000Z"		-- February 11, 2002 at 10:00 GMT
			DESCRIPTION 
				"V01.05.02 - Added Additional variables to the
				zhoneDslPerfDataCur and zhoneDslPerfDataTotal tables."
			REVISION "200111200240Z"		-- November 20, 2001 at 02:40 GMT
			DESCRIPTION 
				"V01.05.01 - Added two new parameters for zhoneDslLineType and zhoneDslLineCapabilities."
			REVISION "200110101047Z"		-- October 10, 2001 at 10:47 GMT
			DESCRIPTION 
				"V01.05.00 - Added two new variables for zhoneDslLineTable"
			REVISION "200103062113Z"		-- March 06, 2001 at 21:13 GMT
			DESCRIPTION 
				"V01.04.00 - Added new field zhoneAdslChannelMode"
			REVISION "200012271127Z"		-- December 27, 2000 at 11:27 GMT
			DESCRIPTION 
				"V01.03.00 - SHDSL config and status table added"
			REVISION "200012011150Z"		-- December 01, 2000 at 11:50 GMT
			DESCRIPTION 
				"V01.02.02 - Changed power scale value to dec."
			REVISION "200011171605Z"		-- November 17, 2000 at 16:05 GMT
			DESCRIPTION 
				"V01.02.01 - new linerates enums added to zhoneSdslConfigLineRate"
			REVISION "200011171019Z"		-- November 17, 2000 at 10:19 GMT
			DESCRIPTION 
				"V01.01.01 - Description for decoderCoefficient B changed to reflect B rather than A"
			REVISION "200009211130Z"		-- September 21, 2000 at 11:30 GMT
			DESCRIPTION 
				"V01.01.00 Added zhoneSdslConfigPowerScale
				          Changed DEFVAL of zhoneSdslConfigConnectMode    from basic-2b1q-mode to
					  flowpoint-mode
				          Added enum values for new zhoneSdslConfigLineRate"
			REVISION "200009121314Z"		-- September 12, 2000 at 13:14 GMT
			DESCRIPTION 
				"V01.00.00 - Initial Revision
				"
			::= { zhoneModules 3 }

		
	
--
-- Textual conventions
--
	
		ZhoneAdsl2Direction ::= TEXTUAL-CONVENTION
			STATUS current
			DESCRIPTION 
				"Identifies the direction of a band as being
				either upstream or downstream.  Specified as an INTEGER
				the two values are:
				 upstream(1)
				 downstream(2)"
			SYNTAX INTEGER
				{
				upstream(1),
				downstream(2)
				}

	
--
-- Node definitions
--
	
		-- 1.3.6.1.4.1.5504.5.4.1
		zhoneDslLineTable OBJECT-TYPE
			SYNTAX SEQUENCE OF ZhoneDslLineEntry
			MAX-ACCESS not-accessible
			STATUS current
			DESCRIPTION
				"This table contains common attributes describing a DSL entry in
				the ifEntry table for DSLs without a MIB standard. There is one entry in the system for
				every DSL interface line supported on that system and these entries are never deleted."
			::= { zhoneDsl 1 }

		
		-- 1.3.6.1.4.1.5504.5.4.1.1
		zhoneDslLineEntry OBJECT-TYPE
			SYNTAX ZhoneDslLineEntry
			MAX-ACCESS not-accessible
			STATUS current
			DESCRIPTION
				"An entry in the zhoneDslLine Table."
			INDEX { ifIndex }
			::= { zhoneDslLineTable 1 }

		
		ZhoneDslLineEntry ::=
			SEQUENCE { 
				zhoneDslLineType
					INTEGER,
				zhoneDslLineCapabilities
					BITS,
				zhoneDslConfigUnitMode
					INTEGER,
				zhoneDslTipRingStatus
					INTEGER,
				zhoneDslLineStatus
					INTEGER,
				zhoneDslUpLineRate
					Integer32,
				zhoneDslDownLineRate
					Integer32,
				zhoneDslConfigProfName
					ZhoneAdminString,
				zhoneDslAlarmProfName
					ZhoneAdminString,
				zhoneDslMaxAttainableUpLineRate
					Integer32,
				zhoneDslMaxAttainableDownLineRate
					Integer32,
				zhoneDslLineSnrMgn
					Integer32,
				zhoneDslLineAtn
					Integer32,
				zhoneDslLineAlarmStatus
					BITS,
				zhoneDslLineStatusChangeTrapEnable
					INTEGER,
				zhoneDslLineCurrOutputPwr
					Integer32,
				zhoneDslLinePostValid
					TruthValue,
				zhoneDslLineUpTime
					TimeTicks,
				zhoneDslLineDownCount
					Integer32,
				zhoneDslAdminUpLineAlarm
					INTEGER,
				zhoneDslLineNumOfLowSQ
					Integer32,
				zhoneDslLineClearStats
					INTEGER,
				zhoneDslDpboProfile
					Unsigned32,
				zhoneDslDpboFallbackProfile
					Unsigned32,
				zhoneDslUpstreamTrafficAlarm
					ZhoneEnabledFlag
			 }

-- 
		-- 1.3.6.1.4.1.5504.5.4.1.1.1
		zhoneDslLineType OBJECT-TYPE
			SYNTAX INTEGER
				{
				hdsl2(1),
				shdsl(2),
				sdsl(3),
				adsl(4),
				shdsllatest(5),
				sdsllatest(6),
				vdsl(7),
				shdsl-2btl(8)
				}
			MAX-ACCESS read-write
			STATUS current
			DESCRIPTION
				"The DSL type. Many modem vendors allow software selection between
				HDSL2 and SDSL. Using zhoneDslLineCapabilities field the user
				can see what dsl option is available on this interface. The default is sdsl.
				
				hdsl2: Globespan version B112
				shdsl: Globespan version R110 - not compatible with shdsl latest firmware
				sdsl:  Globespan version A78 - not compatible with sdsl latest firmware
				shdsllatest: Globespan shdsl latest firmware - compatible 
				sdsllatest:  Globespan sdsl latest firmware - compatible
				"
			DEFVAL { 3 }
			::= { zhoneDslLineEntry 1 }

		
--  
-- 
		-- 1.3.6.1.4.1.5504.5.4.1.1.2
		zhoneDslLineCapabilities OBJECT-TYPE
			SYNTAX BITS
				{
				hdsl2(0),
				shdsl(1),
				sdsl(2),
				adsl(3),
				shdsllatest(4),
				sdsllatest(5)
				}
			MAX-ACCESS read-only
			STATUS current
			DESCRIPTION
				"The DSL types supported on this interface. This is a bit-map of possible
				types. This variable can be used to determine possible values for zhoneDslLineType."
			::= { zhoneDslLineEntry 2 }

		
-- 
		-- 1.3.6.1.4.1.5504.5.4.1.1.3
		zhoneDslConfigUnitMode OBJECT-TYPE
			SYNTAX INTEGER
				{
				co(1),
				cpe(2)
				}
			MAX-ACCESS read-write
			STATUS current
			DESCRIPTION
				"Unit is configured as the CO (central office) or CPE (customer premise) side.
				The default value is co"
			::= { zhoneDslLineEntry 3 }

		
-- 
		-- 1.3.6.1.4.1.5504.5.4.1.1.4
		zhoneDslTipRingStatus OBJECT-TYPE
			SYNTAX INTEGER
				{
				normal(1),
				reverse(2)
				}
			MAX-ACCESS read-only
			STATUS current
			DESCRIPTION
				"Indicates whether the tip and ring points from the local unit match the
				tip and ring points of the remote."
			::= { zhoneDslLineEntry 4 }

		
-- 
		-- 1.3.6.1.4.1.5504.5.4.1.1.5
		zhoneDslLineStatus OBJECT-TYPE
			SYNTAX INTEGER
				{
				down(1),
				downloading(2),
				activated(3),
				training(4),
				up(5),
				test(6),
				handshake(7),
				discovery(8),
				analysis(9),
				selt(10),
				delt(11),
				invalid(12)
				}
			MAX-ACCESS read-only
			STATUS current
			DESCRIPTION
				"The DSL modem status. This field indicates the status of 
				HDSL2/SDSL Transceiver
				down(1) - Transceiver is in IDLE MODE
				downloading(2) - downloading the BOOT code
				activated(3) - Transceiver is activated
				training (4) - Synchronization phase
				up (5) - Transceiver is in DATA MODE
				test (6) - Transceiver is in TEST mode
				handshake (7) - Transceiver is in HANDSHAKE phase
				discovery (8) - Transceiver is in DISCOVERY phase
				analysis (9) - Transceiver is in ANALYSIS phase
				selt (10) - SELT is in progress for this transceiver
				delt (11) - DELT is in progress for this transceiver
				invalid (12) - An unknown or invalid operation state
				               was reported by the transceiver"
			::= { zhoneDslLineEntry 5 }

		
-- 
		-- 1.3.6.1.4.1.5504.5.4.1.1.6
		zhoneDslUpLineRate OBJECT-TYPE
			SYNTAX Integer32
			UNITS "bps"
			MAX-ACCESS read-only
			STATUS current
			DESCRIPTION
				"The DSL upstream (cpe->co) line rate on this interface."
			::= { zhoneDslLineEntry 6 }

		
-- 
		-- 1.3.6.1.4.1.5504.5.4.1.1.7
		zhoneDslDownLineRate OBJECT-TYPE
			SYNTAX Integer32
			UNITS "bps"
			MAX-ACCESS read-only
			STATUS current
			DESCRIPTION
				"The DSL downstream (co->cpe) line rate on this interface."
			::= { zhoneDslLineEntry 7 }

		
		-- 1.3.6.1.4.1.5504.5.4.1.1.8
		zhoneDslConfigProfName OBJECT-TYPE
			SYNTAX ZhoneAdminString (SIZE (1..10))
			MAX-ACCESS read-write
			STATUS current
			DESCRIPTION
				"The value of this object identifies the row in the
				respective dsl configuration profile table. (Ex:
				if zhoneDslLineType is HDSL2, then the profile identifies
				an HDSL2 configuration profile.) It is assumed that all 
				profile names are unique to the system.
				
				The default value is ifIndex (Ascii String value) for 
				static profiles and zhonedefault for dynamic profiles
				
				we are supporting only static profiles.
				"
			::= { zhoneDslLineEntry 8 }

		
		-- 1.3.6.1.4.1.5504.5.4.1.1.9
		zhoneDslAlarmProfName OBJECT-TYPE
			SYNTAX ZhoneAdminString (SIZE (1..10))
			MAX-ACCESS read-write
			STATUS current
			DESCRIPTION
				"The value of this object identifies the row in the
				DslAlarmProfileTable.  It is assumed that all 
				profile names are unique to the system.
				
				The default value is ifIndex (Ascii String value) for 
				static profiles and zhonedefault for dynamic profiles
				
				we are supporting only static profiles."
			::= { zhoneDslLineEntry 9 }

		
-- 
-- 
-- 
-- This variable is currently supported on only  ADSL for now.
		-- 1.3.6.1.4.1.5504.5.4.1.1.10
		zhoneDslMaxAttainableUpLineRate OBJECT-TYPE
			SYNTAX Integer32
			MAX-ACCESS read-only
			STATUS current
			DESCRIPTION
				"This is the MAX line rate that can be supported on the line 
				in the upstream direction."
			::= { zhoneDslLineEntry 10 }

		
-- 
-- 
-- This variable is currently supported on only  ADSL for now.
		-- 1.3.6.1.4.1.5504.5.4.1.1.11
		zhoneDslMaxAttainableDownLineRate OBJECT-TYPE
			SYNTAX Integer32
			MAX-ACCESS read-only
			STATUS current
			DESCRIPTION
				"This is the MAX line rate that can be supported on the line 
				in the downstream direction."
			::= { zhoneDslLineEntry 11 }

		
-- 
		-- 1.3.6.1.4.1.5504.5.4.1.1.12
		zhoneDslLineSnrMgn OBJECT-TYPE
			SYNTAX Integer32
			UNITS "tenths dB"
			MAX-ACCESS read-only
			STATUS current
			DESCRIPTION
				"Noise Margin as seen by this line with respect to its
				received signal in tenth dB."
			::= { zhoneDslLineEntry 12 }

		
-- 
		-- 1.3.6.1.4.1.5504.5.4.1.1.13
		zhoneDslLineAtn OBJECT-TYPE
			SYNTAX Integer32
			UNITS "tenths dB"
			MAX-ACCESS read-only
			STATUS current
			DESCRIPTION
				"Measured difference in the total power transmitted by
				the peer ATU and the total power received by this ATU."
			::= { zhoneDslLineEntry 13 }

		
-- 
		-- 1.3.6.1.4.1.5504.5.4.1.1.14
		zhoneDslLineAlarmStatus OBJECT-TYPE
			SYNTAX BITS
				{
				noDefect(0),
				powerBackoff(1),
				deviceFault(2),
				dcContinuityFault(3),
				snrMarginAlarm(4),
				loopAttenuationAlarm(5),
				loswFailureAlarm(6),
				configInitFailure(7),
				protocolInitFailure(8),
				noNeighborPresent(9),
				loopBackActive(10)
				}
			MAX-ACCESS read-only
			STATUS current
			DESCRIPTION
				"Indicates current state of the DSL line and this is
				only applicable to HDSL2 and SHDSL inteface types.
				adslAtucCurrStatus defined in  RFC 2662 should be used
				to query line state for ADSL line types.
				
				This is a bit-map of possible conditions.  The various bit
				positions are:
				
				0      noDefect             There no defects on the line
				
				1      powerBackoff         Indicates enhanced Power Backoff.
				                            - Not supported
				
				2      deviceFault          Vendor-dependent diagnostic or 
				                            self test fault has been detected.
				                            - Not supported
				
				3      dcContinuityFault    Indicates vendor-depend conditions that
				                            interfere with span powering such as 
				                            short and open circuits.
				                            - Not supported
				
				4      snrMarginAlarm       Declared when the Noise Margin
				                            falls below the Minimum Noise
				                            Margin, or the bit-error-rate
				                            exceeds 10^-7.
				
				
				5      loopAttenuationAlarm Indicates that the loop attenuation
				                            exceeds the alarm threshold.
				                            - Not supported
				
				6      loswFailureAlarm     Indicates a forward LOSW alarm.
				
				7      configInitFailure    Endpoint failure during initialization
				                            due to paired endpoint not able to
				                            support requested configuration.
				
				8      protocolInitFailure  Endpoint failure during initialization
				                            due to incompatible protocol used by
				                            the paired endpoint.
				
				9      noNeighborPresent    Endpoint failure during initialization
				                            due to activation sequence detected
				                            from paired endpoint.
				
				10     loopbackActive       A loopback is currently active at this
				                            Segment Endpoint.
				
				
				This is intended to supplement ifOperStatus."
			REFERENCE
				"RFC 3276; HDSL2 Section 7.5.3.7; SHDSL Section 9.5.5.7."
			::= { zhoneDslLineEntry 14 }

		
-- 
		-- 1.3.6.1.4.1.5504.5.4.1.1.15
		zhoneDslLineStatusChangeTrapEnable OBJECT-TYPE
			SYNTAX INTEGER
				{
				enabled(1),
				disabled(2),
				auto(3)
				}
			MAX-ACCESS read-write
			STATUS current
			DESCRIPTION
				"Indicates whether DSL line status change traps
				should be generated for this interface.
				
				For ADSL, when auto is set, a trap is generated on a
				line status change which is not due to a dying gasp."
			DEFVAL { enabled }
			::= { zhoneDslLineEntry 15 }

		
-- 
		-- 1.3.6.1.4.1.5504.5.4.1.1.16
		zhoneDslLineCurrOutputPwr OBJECT-TYPE
			SYNTAX Integer32
			UNITS "tenths dBm"
			MAX-ACCESS read-only
			STATUS current
			DESCRIPTION
				"Measured difference in the total power transmitted by
				the peer ATU and the total power received by this ATU."
			DEFVAL { '0'b }
			::= { zhoneDslLineEntry 16 }

		
-- 
		-- 1.3.6.1.4.1.5504.5.4.1.1.17
		zhoneDslLinePostValid OBJECT-TYPE
			SYNTAX TruthValue
			MAX-ACCESS read-only
			STATUS current
			DESCRIPTION
				"Indicate whether the POST is valid or not.  If the POST failed,
				this will indicate FALSE."
			::= { zhoneDslLineEntry 17 }

		
-- 
		-- 1.3.6.1.4.1.5504.5.4.1.1.18
		zhoneDslLineUpTime OBJECT-TYPE
			SYNTAX TimeTicks
			MAX-ACCESS read-only
			STATUS current
			DESCRIPTION
				"Shows how long this link has been UP in DD:HH:MM format."
			::= { zhoneDslLineEntry 18 }

		
-- 
		-- 1.3.6.1.4.1.5504.5.4.1.1.19
		zhoneDslLineDownCount OBJECT-TYPE
			SYNTAX Integer32
			MAX-ACCESS read-only
			STATUS current
			DESCRIPTION
				"Indicates how many times the link has been changed from UP
				to DOWN."
			::= { zhoneDslLineEntry 19 }

		
-- 
		-- 1.3.6.1.4.1.5504.5.4.1.1.20
		zhoneDslAdminUpLineAlarm OBJECT-TYPE
			SYNTAX INTEGER
				{
				enabled(1),
				disabled(2)
				}
			MAX-ACCESS read-write
			STATUS current
			DESCRIPTION
				"Indicates whether DSL line status should be generated when admin-up"
			DEFVAL { disabled }
			::= { zhoneDslLineEntry 20 }

		
-- 
		-- 1.3.6.1.4.1.5504.5.4.1.1.21
		zhoneDslLineNumOfLowSQ OBJECT-TYPE
			SYNTAX Integer32
			MAX-ACCESS read-only
			STATUS current
			DESCRIPTION
				"Indicates how many times the low signal quality event has occurred.
				
				Note:
				
				For GobleSpan shdsl device, this count incremented when zhoneDsllineSnrMgn
				drops below 24.5db."
			::= { zhoneDslLineEntry 21 }

		
		-- 1.3.6.1.4.1.5504.5.4.1.1.22
		zhoneDslLineClearStats OBJECT-TYPE
			SYNTAX INTEGER
				{
				normalStats(1),
				clearStats(2)
				}
			MAX-ACCESS read-write
			STATUS current
			DESCRIPTION
				"This leaf is used to clear dsl stats counters.  
				When the value is set to clearStats (2) the stats 
				are cleared for this port. Once the stats have 
				been cleared a read of this entry will return the 
				value for normalStats (1). Only valid user settable 
				value is clearStats (2)."
			::= { zhoneDslLineEntry 22 }

		
-- 1.3.6.1.4.1.5504.5.4.1.1.23
		-- 1.3.6.1.4.1.5504.5.4.1.1.23
		zhoneDslDpboProfile OBJECT-TYPE
			SYNTAX Unsigned32
			UNITS "zhoneDslDpboProfileIndex"
			MAX-ACCESS read-write
			STATUS current
			DESCRIPTION
				"This leaf is used to specify a DSL DPBO profile. A zero index 
				disables DPBO. A valid zhoneDslDpboProfileIndex value of an extent
				DPBO profile activates DPBO for the interface. An invalid 
				zhoneDslDpboProfileIndex value is rejected."
			DEFVAL { 0 }
			::= { zhoneDslLineEntry 23 }

		
-- 1.3.6.1.4.1.5504.5.4.1.1.24
		-- 1.3.6.1.4.1.5504.5.4.1.1.24
		zhoneDslDpboFallbackProfile OBJECT-TYPE
			SYNTAX Unsigned32
			UNITS "zhoneDslDpboProfileIndex"
			MAX-ACCESS read-write
			STATUS current
			DESCRIPTION
				"This leaf is used to specify a DSL DPBO fallback profile. The fallback
				profile is only used for VDSL fallback when falling back to ADSL mode.
				A zero index disables DPBO during the fallback mode. A valid 
				zhoneDslDpboProfileIndex of an extent DPBO profile activates DPBO 
				for the interface during VDSL fallback mode. Invalid indexes are rejected."
			DEFVAL { 0 }
			::= { zhoneDslLineEntry 24 }

		
		-- 1.3.6.1.4.1.5504.5.4.1.1.25
		zhoneDslUpstreamTrafficAlarm OBJECT-TYPE
			SYNTAX ZhoneEnabledFlag
			MAX-ACCESS read-write
			STATUS current
			DESCRIPTION
				"Indicates whether DSL upstream traffic should be monitored for
				        bridging/interface config errors and internal hardware errors."
			DEFVAL { disabled }
			::= { zhoneDslLineEntry 25 }

		
		-- 1.3.6.1.4.1.5504.5.4.2
		zhoneHdsl2ConfigProfileTable OBJECT-TYPE
			SYNTAX SEQUENCE OF ZhoneHdsl2ConfigProfileEntry
			MAX-ACCESS not-accessible
			STATUS current
			DESCRIPTION
				"This table contains information for HDSL2 configuration."
			::= { zhoneDsl 2 }

		
		-- 1.3.6.1.4.1.5504.5.4.2.1
		zhoneHdsl2ConfigProfileEntry OBJECT-TYPE
			SYNTAX ZhoneHdsl2ConfigProfileEntry
			MAX-ACCESS not-accessible
			STATUS current
			DESCRIPTION
				"An entry in the zhoneHdsl2ConfigProfile Table."
			INDEX { IMPLIED zhoneHdsl2ConfigProfileName }
			::= { zhoneHdsl2ConfigProfileTable 1 }

		
		ZhoneHdsl2ConfigProfileEntry ::=
			SEQUENCE { 
				zhoneHdsl2ConfigProfileName
					ZhoneAdminString,
				zhoneHdsl2ConfigTransmitPowerBackoffMode
					INTEGER,
				zhoneHdsl2ConfigDecoderCoeffA
					Integer32,
				zhoneHdsl2ConfigDecoderCoeffB
					Integer32,
				zhoneHdsl2ConfigFrameSyncWord
					Integer32,
				zhoneHdsl2ConfigStuffBits
					Integer32,
				zhoneHdsl2ConfigRowStatus
					ZhoneRowStatus
			 }

		-- 1.3.6.1.4.1.5504.5.4.2.1.1
		zhoneHdsl2ConfigProfileName OBJECT-TYPE
			SYNTAX ZhoneAdminString (SIZE (1..10))
			MAX-ACCESS not-accessible
			STATUS current
			DESCRIPTION
				"Configuration profile name. Used by the zhoneHdsl2ConfigProfile entry
				to map zhoneDslLine Entry to the appropriate profile.
				
				              When `dynamic' profiles are implemented, the profile
				              name is user specified.  Also, the system will always
				              provide a default profile whose name is zhonedefault.
				
				              When `static' profiles are implemented, there is a
				              one-to-one relationship between each line and its
				              profile.  In which case, the profile name will
				              need to algorithmically represent the Line's InterfaceIndex.
				              Therefore, the profile's name is a decimal zed string
				              of the InterfaceIndex that is fixed-length (i.e., 10) with
				              leading zero(s).  For example, the profile name for
				              ifIndex which equals '15' will be '0000000015'.
				
				 we are supporting only static profiles."
			::= { zhoneHdsl2ConfigProfileEntry 1 }

		
-- 
		-- 1.3.6.1.4.1.5504.5.4.2.1.2
		zhoneHdsl2ConfigTransmitPowerBackoffMode OBJECT-TYPE
			SYNTAX INTEGER
				{
				backoffDisable(1),
				backoffEnable(2),
				noChangeBackoff(3)
				}
			MAX-ACCESS read-create
			STATUS current
			DESCRIPTION
				"Determines if the transmit power backoff defined in HDSL2 standard 
				is used. The default value is backoffDisable"
			DEFVAL { backoffDisable }
			::= { zhoneHdsl2ConfigProfileEntry 2 }

		
-- 
		-- 1.3.6.1.4.1.5504.5.4.2.1.3
		zhoneHdsl2ConfigDecoderCoeffA OBJECT-TYPE
			SYNTAX Integer32 (0..2097151)
			MAX-ACCESS read-create
			STATUS current
			DESCRIPTION
				"21 bit value corresponding to the decoder coefficient A. The Default value
				is 0x16e"
			DEFVAL { '16E'h }
			::= { zhoneHdsl2ConfigProfileEntry 3 }

		
-- 
		-- 1.3.6.1.4.1.5504.5.4.2.1.4
		zhoneHdsl2ConfigDecoderCoeffB OBJECT-TYPE
			SYNTAX Integer32 (0..2097151)
			MAX-ACCESS read-create
			STATUS current
			DESCRIPTION
				"21 bit value corresponding to the decoder coefficient B.
				The default value is 0x331"
			DEFVAL { '331'h }
			::= { zhoneHdsl2ConfigProfileEntry 4 }

		
-- 
		-- 1.3.6.1.4.1.5504.5.4.2.1.5
		zhoneHdsl2ConfigFrameSyncWord OBJECT-TYPE
			SYNTAX Integer32 (0..1023)
			MAX-ACCESS read-create
			STATUS current
			DESCRIPTION
				"10 bit frame sync word. The default value is 0x2d"
			DEFVAL { '2d'h }
			::= { zhoneHdsl2ConfigProfileEntry 5 }

		
-- 
		-- 1.3.6.1.4.1.5504.5.4.2.1.6
		zhoneHdsl2ConfigStuffBits OBJECT-TYPE
			SYNTAX Integer32 (0..15)
			MAX-ACCESS read-create
			STATUS current
			DESCRIPTION
				"4 bit stuff pattern. The default is 0x0f."
			DEFVAL { '0f'h }
			::= { zhoneHdsl2ConfigProfileEntry 6 }

		
		-- 1.3.6.1.4.1.5504.5.4.2.1.7
		zhoneHdsl2ConfigRowStatus OBJECT-TYPE
			SYNTAX ZhoneRowStatus
			MAX-ACCESS read-create
			STATUS current
			DESCRIPTION
				"zhoneHdsl2ConfigRowStatus is used to create/delete an entry in zhoneHdsl2ConfigProfileTable"
			::= { zhoneHdsl2ConfigProfileEntry 7 }

		
		-- 1.3.6.1.4.1.5504.5.4.3
		zhoneSdslConfigProfileTable OBJECT-TYPE
			SYNTAX SEQUENCE OF ZhoneSdslConfigProfileEntry
			MAX-ACCESS not-accessible
			STATUS current
			DESCRIPTION
				"This table contains information for SDSL configuration."
			::= { zhoneDsl 3 }

		
		-- 1.3.6.1.4.1.5504.5.4.3.1
		zhoneSdslConfigProfileEntry OBJECT-TYPE
			SYNTAX ZhoneSdslConfigProfileEntry
			MAX-ACCESS not-accessible
			STATUS current
			DESCRIPTION
				"An entry in the zhoneSdslConfigProfile Table."
			INDEX { IMPLIED zhoneSdslConfigProfileName }
			::= { zhoneSdslConfigProfileTable 1 }

		
		ZhoneSdslConfigProfileEntry ::=
			SEQUENCE { 
				zhoneSdslConfigProfileName
					ZhoneAdminString,
				zhoneSdslConfigLineRate
					INTEGER,
				zhoneSdslConfigFixBitRate
					INTEGER,
				zhoneSdslConfigConnectMode
					INTEGER,
				zhoneSdslConfigNTR
					INTEGER,
				zhoneSdslConfigFramerType
					INTEGER,
				zhoneSdslConfigPowerScale
					Integer32,
				zhoneSdslConfigRowStatus
					ZhoneRowStatus
			 }

		-- 1.3.6.1.4.1.5504.5.4.3.1.1
		zhoneSdslConfigProfileName OBJECT-TYPE
			SYNTAX ZhoneAdminString (SIZE (1..10))
			MAX-ACCESS not-accessible
			STATUS current
			DESCRIPTION
				"Configuration profile name. Used by the zhoneSdslConfigProfile entry
				to map zhoneDslLine Entry to the appropriate profile.
				
				              When `dynamic' profiles are implemented, the profile
				              name is user specified.  Also, the system will always
				              provide a default profile whose name is zhonedefault
				
				              When `static' profiles are implemented, there is a
				              one-to-one relationship between each line and its
				              profile.  In which case, the profile name will
				              need to algorithmically represent the Line's InterfaceIndex.
				              Therefore, the profile's name is a decimal zed string
				              of the InterfaceIndex that is fixed-length (i.e., 10) with
				              leading zero(s).  For example, the profile name for
				              ifIndex which equals '15' will be '0000000015'.
				
				
				we are supporting only static profiles."
			::= { zhoneSdslConfigProfileEntry 1 }

		
-- 
		-- 1.3.6.1.4.1.5504.5.4.3.1.2
		zhoneSdslConfigLineRate OBJECT-TYPE
			SYNTAX INTEGER
				{
				line-rate-144kbps(1),
				line-rate-160kbps(2),
				line-rate-192kbps(3),
				line-rate-208kbps(4),
				line-rate-224kbps(5),
				line-rate-256kbps(6),
				line-rate-272kbps(7),
				line-rate-320kbps(8),
				line-rate-368kbps(9),
				line-rate-384kbps(10),
				line-rate-400kbps(11),
				line-rate-416kbps(12),
				line-rate-528kbps(13),
				line-rate-768kbps(14),
				line-rate-784kbps(16),
				line-rate-1040kbps(17),
				line-rate-1152kbps(18),
				line-rate-1168kbps(19),
				line-rate-1536kbps(20),
				line-rate-1552kbps(22),
				line-rate-1568kbps(23),
				line-rate-2320kbps(24),
				line-rate-176kbps(25),
				line-rate-240kbps(26),
				line-rate-288kbps(27),
				line-rate-304kbps(28),
				line-rate-336kbps(29),
				line-rate-352kbps(30),
				line-rate-432kbps(31),
				line-rate-464kbps(32),
				line-rate-496kbps(33),
				line-rate-560kbps(34),
				line-rate-592kbps(35),
				line-rate-624kbps(36),
				line-rate-656kbps(37),
				line-rate-688kbps(38),
				line-rate-720kbps(39),
				line-rate-752kbps(40),
				line-rate-816kbps(41),
				line-rate-848kbps(42),
				line-rate-880kbps(43),
				line-rate-912kbps(44),
				line-rate-944kbps(45),
				line-rate-976kbps(46),
				line-rate-1008kbps(47),
				line-rate-1072kbps(48),
				line-rate-1104kbps(49),
				line-rate-1136kbps(50),
				line-rate-1200kbps(51),
				line-rate-1232kbps(52),
				line-rate-1264kbps(53),
				line-rate-1296kbps(54),
				line-rate-1328kbps(55),
				line-rate-1360kbps(56),
				line-rate-1392kbps(57),
				line-rate-1424kbps(58),
				line-rate-1456kbps(59),
				line-rate-1488kbps(60),
				line-rate-1520kbps(61),
				line-rate-1584kbps(62),
				line-rate-1616kbps(63),
				line-rate-1648kbps(64),
				line-rate-1680kbps(65),
				line-rate-1712kbps(66),
				line-rate-1744kbps(67),
				line-rate-1776kbps(68),
				line-rate-1808kbps(69),
				line-rate-1840kbps(70),
				line-rate-1872kbps(71),
				line-rate-1904kbps(72),
				line-rate-1936kbps(73),
				line-rate-1968kbps(74),
				line-rate-2000kbps(75),
				line-rate-2032kbps(76),
				line-rate-2064kbps(77),
				line-rate-2096kbps(78),
				line-rate-2128kbps(79),
				line-rate-2160kbps(80),
				line-rate-2192kbps(81),
				line-rate-2224kbps(82),
				line-rate-2256kbps(83),
				line-rate-2288kbps(84)
				}
			MAX-ACCESS read-create
			STATUS current
			DESCRIPTION
				"The line rate selection. 
				The default value is line-rate-2320kbps
				line-rate-772kbps(15) and line-rate-1544kbps(21) are not supported by Globespan hardware
				and hence are deleted from the mib"
			DEFVAL { line-rate-2320kbps }
			::= { zhoneSdslConfigProfileEntry 2 }

		
-- 
		-- 1.3.6.1.4.1.5504.5.4.3.1.3
		zhoneSdslConfigFixBitRate OBJECT-TYPE
			SYNTAX INTEGER
				{
				fix-bit-enable(1),
				fix-bit-disable(2)
				}
			MAX-ACCESS read-create
			STATUS current
			DESCRIPTION
				"Normally, if the CO and CPE select different line rates 
				at startup, the lower of the two rate will be selected. By using the fix bit 
				rate the CO can override the default procedure and require startup at the rate 
				specified in zhoneSdslConfigLineRate. Note: this option is available only if 
				zhoneDslConfigUnitMode is co. This value is ignored if 
				zhoneDslConfigUnitMode is cpe
				
				The default value is fix-bit-disable"
			DEFVAL { fix-bit-disable }
			::= { zhoneSdslConfigProfileEntry 3 }

		
-- 
		-- 1.3.6.1.4.1.5504.5.4.3.1.4
		zhoneSdslConfigConnectMode OBJECT-TYPE
			SYNTAX INTEGER
				{
				basic-2b1q-mode(1),
				globespan-neg-mode(2),
				copper-mtn-mode(3),
				flowpoint-mode(4)
				}
			MAX-ACCESS read-create
			STATUS current
			DESCRIPTION
				"Connection mode compatibility.
				
				basic-2b1q-mode: basic operating mode
				
				globebspan-neg-mode: Globespan mode where CO and CPE 
				                 can have different rates syncing on the
				                 lower rate.
				
				Copper-mtn-mode: operating mode compatible with
				                 Copper Mountain
				
				Flowpoint-mode:  operating mode compatible with
				                 FlowPoint Corp.
				
				The default value is flowpoint-mode"
			DEFVAL { flowpoint-mode }
			::= { zhoneSdslConfigProfileEntry 4 }

		
-- 
		-- 1.3.6.1.4.1.5504.5.4.3.1.5
		zhoneSdslConfigNTR OBJECT-TYPE
			SYNTAX INTEGER
				{
				ntr-disable(1),
				ntr-enable(2)
				}
			MAX-ACCESS read-create
			STATUS current
			DESCRIPTION
				"Determines whether network timing 
				recovery is enabled or disabled. The default value is disabled"
			DEFVAL { ntr-disable }
			::= { zhoneSdslConfigProfileEntry 5 }

		
-- 
		-- 1.3.6.1.4.1.5504.5.4.3.1.6
		zhoneSdslConfigFramerType OBJECT-TYPE
			SYNTAX INTEGER
				{
				atm-clear-channel(1),
				atm-dlcc(2),
				atm-g991-1(3)
				}
			MAX-ACCESS read-create
			STATUS current
			DESCRIPTION
				"This sets the type of framer used.
				atm-clear-channel: direct cell mapping,
				atm-dlcc: uses DLCC framing specification,
				atm-g991-1: uses framing specified in G.991.1"
			DEFVAL { atm-clear-channel }
			::= { zhoneSdslConfigProfileEntry 6 }

		
-- 
		-- 1.3.6.1.4.1.5504.5.4.3.1.7
		zhoneSdslConfigPowerScale OBJECT-TYPE
			SYNTAX Integer32 (1..32767)
			MAX-ACCESS read-create
			STATUS current
			DESCRIPTION
				"zhoneSdslConfigPowerScale is used to adjust transmit 
				power in small increments to compensate for minor 
				differences on power between units. It is recommended that value should
				remain in the range of 20992 (-3 db) to 32767 (+0.8 db). 
				This value is calculated using the following formula
				PowerScale = (10 ^ (Db / 20)) * 29952.
				Where Db is in the range of -3 to 0.8. A value of 29952
				corresponds to 0 db. The value should not be limited to 
				the range 20992 to 32767.In some circumstances a value 
				outside of this range maybe needed."
			DEFVAL { 29952 }
			::= { zhoneSdslConfigProfileEntry 7 }

		
		-- 1.3.6.1.4.1.5504.5.4.3.1.8
		zhoneSdslConfigRowStatus OBJECT-TYPE
			SYNTAX ZhoneRowStatus
			MAX-ACCESS read-create
			STATUS current
			DESCRIPTION
				"zhoneSdslConfigRowStatus is used to create/delete an entry in zhoneSdslConfigProfileTable"
			::= { zhoneSdslConfigProfileEntry 8 }

		
		-- 1.3.6.1.4.1.5504.5.4.4
		zhoneHdsl2StatusTable OBJECT-TYPE
			SYNTAX SEQUENCE OF ZhoneHdsl2StatusEntry
			MAX-ACCESS not-accessible
			STATUS current
			DESCRIPTION
				"This table contains HDSL2 specific line status information.
				
				An entry into this table is automatically created whenever a
				zhoneDslLineEntry is created and the type is HDSL2."
			::= { zhoneDsl 4 }
-- As it is possible to change the line type of a Dsl port, and we do 
-- not de-register the oid for a changed port, we will return a null 
-- record for a request for an instance that is no longer valid.
		
		-- 1.3.6.1.4.1.5504.5.4.4.1
		zhoneHdsl2StatusEntry OBJECT-TYPE
			SYNTAX ZhoneHdsl2StatusEntry
			MAX-ACCESS not-accessible
			STATUS current
			DESCRIPTION
				"An entry in the zhoneHdsl2Status Table."
			INDEX { ifIndex }
			::= { zhoneHdsl2StatusTable 1 }

		
		ZhoneHdsl2StatusEntry ::=
			SEQUENCE { 
				zhoneHdsl2DriftAlarm
					INTEGER,
				zhoneHdsl2FramerIBStatus
					OCTET STRING,
				zhoneHdsl2LocalPSDMaskStatus
					Integer32,
				zhoneHdsl2LoopAttenuation
					Integer32,
				zhoneHdsl2LossWordStatus
					INTEGER,
				zhoneHdsl2RmtPSDMaskStatus
					Integer32,
				zhoneHdsl2RmtCountryCode
					Integer32,
				zhoneHdsl2RmtVersion
					Integer32,
				zhoneHdsl2RmtProviderCode
					Integer32,
				zhoneHdsl2RmtVendorData
					OCTET STRING,
				zhoneHdsl2RmtTxEncoderA
					Integer32,
				zhoneHdsl2RmtTxEncoderB
					Integer32,
				zhoneHdsl2FrameSyncWord
					Integer32,
				zhoneHdsl2StuffBits
					Integer32
			 }

-- 
		-- 1.3.6.1.4.1.5504.5.4.4.1.1
		zhoneHdsl2DriftAlarm OBJECT-TYPE
			SYNTAX INTEGER
				{
				rxClkAlarm(1),
				txClkAlarm(2),
				txRxClkAlarm(3),
				noDriftAlarm(4),
				notApplicable(5)
				}
			MAX-ACCESS read-only
			STATUS current
			DESCRIPTION
				" Indicates that the framer automatically attempted to adjust for clock 
				drift. This is not applicable for ATM."
			::= { zhoneHdsl2StatusEntry 1 }

		
-- 
		-- 1.3.6.1.4.1.5504.5.4.4.1.2
		zhoneHdsl2FramerIBStatus OBJECT-TYPE
			SYNTAX OCTET STRING (SIZE (1))
			MAX-ACCESS read-only
			STATUS current
			DESCRIPTION
				"Returns the segd,sega,uib and losd bits. The format of the octet is:
				x x x x segd sega uib losd."
			::= { zhoneHdsl2StatusEntry 2 }

		
-- 
		-- 1.3.6.1.4.1.5504.5.4.4.1.3
		zhoneHdsl2LocalPSDMaskStatus OBJECT-TYPE
			SYNTAX Integer32
			MAX-ACCESS read-only
			STATUS current
			DESCRIPTION
				"Returns a number corresponding to the transmit power backoff requested
				by the local unit."
			::= { zhoneHdsl2StatusEntry 3 }

		
-- 
		-- 1.3.6.1.4.1.5504.5.4.4.1.4
		zhoneHdsl2LoopAttenuation OBJECT-TYPE
			SYNTAX Integer32
			UNITS "tenth DB"
			MAX-ACCESS read-only
			STATUS current
			DESCRIPTION
				"Estimation of the loop attenuation in tenths of a DB.
				by the local unit."
			::= { zhoneHdsl2StatusEntry 4 }

		
-- 
		-- 1.3.6.1.4.1.5504.5.4.4.1.5
		zhoneHdsl2LossWordStatus OBJECT-TYPE
			SYNTAX INTEGER
				{
				noLosswDefect(1),
				losswDefect(2)
				}
			MAX-ACCESS read-only
			STATUS current
			DESCRIPTION
				"This indicates loss of sync."
			::= { zhoneHdsl2StatusEntry 5 }

		
-- 
		-- 1.3.6.1.4.1.5504.5.4.4.1.6
		zhoneHdsl2RmtPSDMaskStatus OBJECT-TYPE
			SYNTAX Integer32
			MAX-ACCESS read-only
			STATUS current
			DESCRIPTION
				"Returns a number corresponding to the transmit power backoff requested
				by the remote unit."
			::= { zhoneHdsl2StatusEntry 6 }

		
-- 
		-- 1.3.6.1.4.1.5504.5.4.4.1.7
		zhoneHdsl2RmtCountryCode OBJECT-TYPE
			SYNTAX Integer32
			MAX-ACCESS read-only
			STATUS current
			DESCRIPTION
				"ANSI HDSL2 Country code of the remote unit."
			::= { zhoneHdsl2StatusEntry 7 }

		
-- 
		-- 1.3.6.1.4.1.5504.5.4.4.1.8
		zhoneHdsl2RmtVersion OBJECT-TYPE
			SYNTAX Integer32
			MAX-ACCESS read-only
			STATUS current
			DESCRIPTION
				"HDSL2 version of the remote unit."
			::= { zhoneHdsl2StatusEntry 8 }

		
-- 
		-- 1.3.6.1.4.1.5504.5.4.4.1.9
		zhoneHdsl2RmtProviderCode OBJECT-TYPE
			SYNTAX Integer32
			MAX-ACCESS read-only
			STATUS current
			DESCRIPTION
				"Provider word of the remote unit."
			::= { zhoneHdsl2StatusEntry 9 }

		
-- 
		-- 1.3.6.1.4.1.5504.5.4.4.1.10
		zhoneHdsl2RmtVendorData OBJECT-TYPE
			SYNTAX OCTET STRING (SIZE (8))
			MAX-ACCESS read-only
			STATUS current
			DESCRIPTION
				"The remote unit's vendor-provided data."
			::= { zhoneHdsl2StatusEntry 10 }

		
-- 
		-- 1.3.6.1.4.1.5504.5.4.4.1.11
		zhoneHdsl2RmtTxEncoderA OBJECT-TYPE
			SYNTAX Integer32 (0..2097151)
			MAX-ACCESS read-only
			STATUS current
			DESCRIPTION
				"The remote unit's 21 bit encoder coefficient A"
			::= { zhoneHdsl2StatusEntry 11 }

		
-- 
		-- 1.3.6.1.4.1.5504.5.4.4.1.12
		zhoneHdsl2RmtTxEncoderB OBJECT-TYPE
			SYNTAX Integer32 (0..2097151)
			MAX-ACCESS read-only
			STATUS current
			DESCRIPTION
				"The remote unit's 21 bit encoder coefficient B"
			::= { zhoneHdsl2StatusEntry 12 }

		
-- 
		-- 1.3.6.1.4.1.5504.5.4.4.1.13
		zhoneHdsl2FrameSyncWord OBJECT-TYPE
			SYNTAX Integer32 (0..1023)
			MAX-ACCESS read-only
			STATUS current
			DESCRIPTION
				"A 10 bit number indicating the frame sync word used. LSB justified"
			::= { zhoneHdsl2StatusEntry 13 }

		
-- 
		-- 1.3.6.1.4.1.5504.5.4.4.1.14
		zhoneHdsl2StuffBits OBJECT-TYPE
			SYNTAX Integer32 (0..15)
			MAX-ACCESS read-only
			STATUS current
			DESCRIPTION
				"A 4 bit number for the stuff bits. LSB justified."
			::= { zhoneHdsl2StatusEntry 14 }

		
		-- 1.3.6.1.4.1.5504.5.4.5
		zhoneSdslStatusTable OBJECT-TYPE
			SYNTAX SEQUENCE OF ZhoneSdslStatusEntry
			MAX-ACCESS not-accessible
			STATUS current
			DESCRIPTION
				"This table contains SDSL specific line status 
				information.
								
								An entry into this table is automatically created 
				whenever a
								zhoneDslLineEntry is created and the type is SDSL."
			::= { zhoneDsl 5 }
-- As it is possible to change the line type of a Dsl port, and we do 
-- not de-register the oid for a changed port, we will return a null 
-- record for a request for an instance that is no longer valid.
		
		-- 1.3.6.1.4.1.5504.5.4.5.1
		zhoneSdslStatusEntry OBJECT-TYPE
			SYNTAX ZhoneSdslStatusEntry
			MAX-ACCESS not-accessible
			STATUS current
			DESCRIPTION
				"An entry in the zhoneSdslStatus Table."
			INDEX { ifIndex }
			::= { zhoneSdslStatusTable 1 }

		
		ZhoneSdslStatusEntry ::=
			SEQUENCE { 
				zhoneSdslFixBitStatus
					INTEGER,
				zhoneSdslDSPVersion
					INTEGER,
				zhoneSdslFirmwareVersion
					OCTET STRING
			 }

-- 
		-- 1.3.6.1.4.1.5504.5.4.5.1.1
		zhoneSdslFixBitStatus OBJECT-TYPE
			SYNTAX INTEGER
				{
				fix-bit-enable(1),
				fix-bit-disable(2)
				}
			MAX-ACCESS read-only
			STATUS current
			DESCRIPTION
				" Indicates that the fix bit feature is enabled. This value applies only to the co side and
				should be ignored for cpe side"
			::= { zhoneSdslStatusEntry 1 }

		
-- 
		-- 1.3.6.1.4.1.5504.5.4.5.1.2
		zhoneSdslDSPVersion OBJECT-TYPE
			SYNTAX INTEGER
			MAX-ACCESS read-only
			STATUS current
			DESCRIPTION
				"The version of the DSP/Framer VLSI in the transceiver."
			::= { zhoneSdslStatusEntry 2 }

		
-- 
		-- 1.3.6.1.4.1.5504.5.4.5.1.3
		zhoneSdslFirmwareVersion OBJECT-TYPE
			SYNTAX OCTET STRING (SIZE (4))
			MAX-ACCESS read-only
			STATUS current
			DESCRIPTION
				" The firmware release number (in ASCII)"
			::= { zhoneSdslStatusEntry 3 }

		
		-- 1.3.6.1.4.1.5504.5.4.6
		zhoneDslPerfDataTotalTable OBJECT-TYPE
			SYNTAX SEQUENCE OF ZhoneDslPerfDataTotalEntry
			MAX-ACCESS not-accessible
			STATUS current
			DESCRIPTION
				"This table provides one row for each modem interface. This table
				provides the total performance data for each modem interface line."
			::= { zhoneDsl 6 }

		
		-- 1.3.6.1.4.1.5504.5.4.6.1
		zhoneDslPerfDataTotalEntry OBJECT-TYPE
			SYNTAX ZhoneDslPerfDataTotalEntry
			MAX-ACCESS not-accessible
			STATUS current
			DESCRIPTION
				"An entry in zhoneDslPerfDataTotal Table."
			AUGMENTS { zhoneDslLineEntry }
			::= { zhoneDslPerfDataTotalTable 1 }

		
		ZhoneDslPerfDataTotalEntry ::=
			SEQUENCE { 
				zhoneDslPerfTotalLofs
					Counter32,
				zhoneDslPerfTotalLoss
					Counter32,
				zhoneDslPerfTotalLols
					Counter32,
				zhoneDslPerfTotalInits
					Counter32,
				zhoneDslPerfTotalES
					Counter32,
				zhoneDslPerfTotalSES
					Counter32,
				zhoneDslPerfTotalCRCAnomalies
					Counter32,
				zhoneDslPerfTotalLOSWS
					Counter32,
				zhoneDslPerfTotalUAS
					Counter32
			 }

-- 
		-- 1.3.6.1.4.1.5504.5.4.6.1.1
		zhoneDslPerfTotalLofs OBJECT-TYPE
			SYNTAX Counter32
			MAX-ACCESS read-only
			STATUS current
			DESCRIPTION
				"Count of the number of Loss of Framing failures since agent reset."
			::= { zhoneDslPerfDataTotalEntry 1 }

		
-- 
		-- 1.3.6.1.4.1.5504.5.4.6.1.2
		zhoneDslPerfTotalLoss OBJECT-TYPE
			SYNTAX Counter32
			MAX-ACCESS read-only
			STATUS current
			DESCRIPTION
				"Count of the number of Loss of Signal failures since agent reset."
			::= { zhoneDslPerfDataTotalEntry 2 }

		
-- 
		-- 1.3.6.1.4.1.5504.5.4.6.1.3
		zhoneDslPerfTotalLols OBJECT-TYPE
			SYNTAX Counter32
			MAX-ACCESS read-only
			STATUS current
			DESCRIPTION
				"Count of the number of Loss of Link failures since agent reset."
			::= { zhoneDslPerfDataTotalEntry 3 }

		
-- 
		-- 1.3.6.1.4.1.5504.5.4.6.1.4
		zhoneDslPerfTotalInits OBJECT-TYPE
			SYNTAX Counter32
			MAX-ACCESS read-only
			STATUS current
			DESCRIPTION
				"Count of the line initialization attempts since agent reset. Includes 
				both successful and failed attempts."
			::= { zhoneDslPerfDataTotalEntry 4 }

		
-- 
		-- 1.3.6.1.4.1.5504.5.4.6.1.5
		zhoneDslPerfTotalES OBJECT-TYPE
			SYNTAX Counter32
			UNITS "seconds"
			MAX-ACCESS read-only
			STATUS current
			DESCRIPTION
				"Count of the line errored seconds 
				since agent reset."
			::= { zhoneDslPerfDataTotalEntry 5 }

		
-- 
		-- 1.3.6.1.4.1.5504.5.4.6.1.6
		zhoneDslPerfTotalSES OBJECT-TYPE
			SYNTAX Counter32
			UNITS "seconds"
			MAX-ACCESS read-only
			STATUS current
			DESCRIPTION
				"Count of the line severely errored seconds 
				since agent reset."
			::= { zhoneDslPerfDataTotalEntry 6 }

		
-- 
		-- 1.3.6.1.4.1.5504.5.4.6.1.7
		zhoneDslPerfTotalCRCAnomalies OBJECT-TYPE
			SYNTAX Counter32
			UNITS "seconds"
			MAX-ACCESS read-only
			STATUS current
			DESCRIPTION
				"Count of the line CRC anomalies 
				since agent reset."
			::= { zhoneDslPerfDataTotalEntry 7 }

		
		-- 1.3.6.1.4.1.5504.5.4.6.1.8
		zhoneDslPerfTotalLOSWS OBJECT-TYPE
			SYNTAX Counter32
			UNITS "seconds"
			MAX-ACCESS read-only
			STATUS current
			DESCRIPTION
				"Count of the line loss-of-sync-word seconds 
				since agent reset."
			::= { zhoneDslPerfDataTotalEntry 8 }

		
-- 
		-- 1.3.6.1.4.1.5504.5.4.6.1.9
		zhoneDslPerfTotalUAS OBJECT-TYPE
			SYNTAX Counter32
			UNITS "seconds"
			MAX-ACCESS read-only
			STATUS current
			DESCRIPTION
				"Count of the line unavailable seconds 
				since agent reset."
			::= { zhoneDslPerfDataTotalEntry 9 }

		
		-- 1.3.6.1.4.1.5504.5.4.7
		zhoneDslPerfDataCurTable OBJECT-TYPE
			SYNTAX SEQUENCE OF ZhoneDslPerfDataCurEntry
			MAX-ACCESS not-accessible
			STATUS current
			DESCRIPTION
				"This table provides the current 15 min interval performance data
				for each modem interface lines."
			::= { zhoneDsl 7 }

		
		-- 1.3.6.1.4.1.5504.5.4.7.1
		zhoneDslPerfDataCurEntry OBJECT-TYPE
			SYNTAX ZhoneDslPerfDataCurEntry
			MAX-ACCESS not-accessible
			STATUS current
			DESCRIPTION
				"An entry in zhoneDslPerfDataCur Table."
			AUGMENTS { zhoneDslLineEntry }
			::= { zhoneDslPerfDataCurTable 1 }

		
		ZhoneDslPerfDataCurEntry ::=
			SEQUENCE { 
				zhoneDslPerfLofs
					Counter32,
				zhoneDslPerfLoss
					Counter32,
				zhoneDslPerfLols
					Counter32,
				zhoneDslPerfInits
					Counter32,
				zhoneDslPerfTimeElapsed
					INTEGER,
				zhoneDslPerfES
					INTEGER,
				zhoneDslPerfSES
					INTEGER,
				zhoneDslPerfCRCAnomalies
					INTEGER,
				zhoneDslPerfLOSWS
					INTEGER,
				zhoneDslPerfUAS
					INTEGER
			 }

-- 
		-- 1.3.6.1.4.1.5504.5.4.7.1.1
		zhoneDslPerfLofs OBJECT-TYPE
			SYNTAX Counter32
			MAX-ACCESS read-only
			STATUS current
			DESCRIPTION
				"Count of the number of Loss of Framing failures in the current 15 minute interval."
			::= { zhoneDslPerfDataCurEntry 1 }

		
-- 
		-- 1.3.6.1.4.1.5504.5.4.7.1.2
		zhoneDslPerfLoss OBJECT-TYPE
			SYNTAX Counter32
			MAX-ACCESS read-only
			STATUS current
			DESCRIPTION
				"Count of the number of Loss of Signal failures in the current 15 minute interval."
			::= { zhoneDslPerfDataCurEntry 2 }

		
-- 
		-- 1.3.6.1.4.1.5504.5.4.7.1.3
		zhoneDslPerfLols OBJECT-TYPE
			SYNTAX Counter32
			MAX-ACCESS read-only
			STATUS current
			DESCRIPTION
				"Count of the number of Loss of Link failures in the current 15 minute interval."
			::= { zhoneDslPerfDataCurEntry 3 }

		
-- 
		-- 1.3.6.1.4.1.5504.5.4.7.1.4
		zhoneDslPerfInits OBJECT-TYPE
			SYNTAX Counter32
			MAX-ACCESS read-only
			STATUS current
			DESCRIPTION
				"Count of the line initialization attempts in the current 15 minute interval. Includes 
				both successful and failed attempts."
			::= { zhoneDslPerfDataCurEntry 4 }

		
-- 
		-- 1.3.6.1.4.1.5504.5.4.7.1.5
		zhoneDslPerfTimeElapsed OBJECT-TYPE
			SYNTAX INTEGER (0..899)
			UNITS "seconds"
			MAX-ACCESS read-only
			STATUS current
			DESCRIPTION
				"The number of seconds elapsed since the start of the current measurement period."
			::= { zhoneDslPerfDataCurEntry 5 }

		
		-- 1.3.6.1.4.1.5504.5.4.7.1.6
		zhoneDslPerfES OBJECT-TYPE
			SYNTAX INTEGER (0..900)
			UNITS "seconds"
			MAX-ACCESS read-only
			STATUS current
			DESCRIPTION
				"The number of errored-seconds since the start
				of the current measurement period."
			::= { zhoneDslPerfDataCurEntry 6 }

		
		-- 1.3.6.1.4.1.5504.5.4.7.1.7
		zhoneDslPerfSES OBJECT-TYPE
			SYNTAX INTEGER (0..900)
			UNITS "seconds"
			MAX-ACCESS read-only
			STATUS current
			DESCRIPTION
				"The number of severely-errored-seconds since the start
				of the current measurement period."
			::= { zhoneDslPerfDataCurEntry 7 }

		
		-- 1.3.6.1.4.1.5504.5.4.7.1.8
		zhoneDslPerfCRCAnomalies OBJECT-TYPE
			SYNTAX INTEGER (0..900)
			UNITS "seconds"
			MAX-ACCESS read-only
			STATUS current
			DESCRIPTION
				"The number of CRC anomalies since the start
				of the current measurement period."
			::= { zhoneDslPerfDataCurEntry 8 }

		
		-- 1.3.6.1.4.1.5504.5.4.7.1.9
		zhoneDslPerfLOSWS OBJECT-TYPE
			SYNTAX INTEGER (0..900)
			UNITS "seconds"
			MAX-ACCESS read-only
			STATUS current
			DESCRIPTION
				"The number of loss-of-sync-word seconds since the start
				of the current measurement period."
			::= { zhoneDslPerfDataCurEntry 9 }

		
		-- 1.3.6.1.4.1.5504.5.4.7.1.10
		zhoneDslPerfUAS OBJECT-TYPE
			SYNTAX INTEGER (0..900)
			UNITS "seconds"
			MAX-ACCESS read-only
			STATUS current
			DESCRIPTION
				"The number of unavailable seconds since the start
				of the current measurement period."
			::= { zhoneDslPerfDataCurEntry 10 }

		
		-- 1.3.6.1.4.1.5504.5.4.8
		zhoneDslAlarmProfileTable OBJECT-TYPE
			SYNTAX SEQUENCE OF ZhoneDslAlarmProfileEntry
			MAX-ACCESS not-accessible
			STATUS current
			DESCRIPTION
				"This table contains information for Alarm conditions. This table is indexed by 
				zhoneDslAlarmProfineName ."
			::= { zhoneDsl 8 }

		
		-- 1.3.6.1.4.1.5504.5.4.8.1
		zhoneDslAlarmProfileEntry OBJECT-TYPE
			SYNTAX ZhoneDslAlarmProfileEntry
			MAX-ACCESS not-accessible
			STATUS current
			DESCRIPTION
				"An entry in the zhoneDslAlarmProfile Table."
			INDEX { IMPLIED zhoneDslAlarmProfileName }
			::= { zhoneDslAlarmProfileTable 1 }

		
		ZhoneDslAlarmProfileEntry ::=
			SEQUENCE { 
				zhoneDslAlarmProfileName
					ZhoneAdminString,
				zhoneDslThreshold15MinLoss
					INTEGER,
				zhoneDslThreshold15MinLols
					INTEGER,
				zhoneDslThreshold15MinLofs
					INTEGER,
				zhoneDslAlarmRowStatus
					ZhoneRowStatus
			 }

		-- 1.3.6.1.4.1.5504.5.4.8.1.1
		zhoneDslAlarmProfileName OBJECT-TYPE
			SYNTAX ZhoneAdminString (SIZE (1..10))
			MAX-ACCESS not-accessible
			STATUS current
			DESCRIPTION
				"Alarm profile name. Used by the zhoneDslAlarmProfile entry
				to map zhoneDslLine Entry to the appropriate profile.
				
				              When `dynamic' profiles are implemented, the profile
				              name is user specified.  Also, the system will always
				              provide a default profile whose name is zhonedefault
				
				              When `static' profiles are implemented, there is an
				              one-to-one relationship between each line and its
				              profile.  In which case, the profile name will
				              need to algorithmically represent the Line's InterfaceIndex.
				              Therefore, the profile's name is a decimal zed string
				              of the InterfaceIndex that is fixed-length (i.e., 10) with
				              leading zero(s).  For example, the profile name for
				              ifIndex which equals '15' will be '0000000015'.
				
				we are supporting only static profiles.."
			::= { zhoneDslAlarmProfileEntry 1 }

		
-- 
		-- 1.3.6.1.4.1.5504.5.4.8.1.2
		zhoneDslThreshold15MinLoss OBJECT-TYPE
			SYNTAX INTEGER (0..900)
			MAX-ACCESS read-create
			STATUS current
			DESCRIPTION
				"The number of Loss of signal seconds on a DSL interface within any
				given 15 minutes performance data collection period, which causes the
				SNMP agent to send a TRAP. 0 will disable the trap. The default value is 0"
			DEFVAL { 0 }
			::= { zhoneDslAlarmProfileEntry 2 }

		
-- 
		-- 1.3.6.1.4.1.5504.5.4.8.1.3
		zhoneDslThreshold15MinLols OBJECT-TYPE
			SYNTAX INTEGER (0..900)
			MAX-ACCESS read-create
			STATUS current
			DESCRIPTION
				"The number of Loss of link seconds on a DSL interface within any
				given 15 minutes performance data collection period, which causes the
				SNMP agent to send a TRAP. 0 will disable the trap.The default value is 0"
			DEFVAL { 0 }
			::= { zhoneDslAlarmProfileEntry 3 }

		
-- 
		-- 1.3.6.1.4.1.5504.5.4.8.1.4
		zhoneDslThreshold15MinLofs OBJECT-TYPE
			SYNTAX INTEGER (0..900)
			MAX-ACCESS read-create
			STATUS current
			DESCRIPTION
				"The number of Loss of framing seconds on a DSL interface within any
				given 15 minutes performance data collection period, which causes the
				SNMP agent to send a TRAP. 0 will disable the trap. The default value is 0"
			DEFVAL { 0 }
			::= { zhoneDslAlarmProfileEntry 4 }

		
		-- 1.3.6.1.4.1.5504.5.4.8.1.5
		zhoneDslAlarmRowStatus OBJECT-TYPE
			SYNTAX ZhoneRowStatus
			MAX-ACCESS read-create
			STATUS current
			DESCRIPTION
				"zhoneDslAlarmRowStatus is used to create/delete an entry in zhoneDlsAlarmProfileTable"
			::= { zhoneDslAlarmProfileEntry 5 }

		
		-- 1.3.6.1.4.1.5504.5.4.9
		zhoneShdslConfigProfileTable OBJECT-TYPE
			SYNTAX SEQUENCE OF ZhoneShdslConfigProfileEntry
			MAX-ACCESS not-accessible
			STATUS current
			DESCRIPTION
				"This table contains information for SHDSL configuration."
			::= { zhoneDsl 9 }

		
		-- 1.3.6.1.4.1.5504.5.4.9.1
		zhoneShdslConfigProfileEntry OBJECT-TYPE
			SYNTAX ZhoneShdslConfigProfileEntry
			MAX-ACCESS not-accessible
			STATUS current
			DESCRIPTION
				"An entry in zhoneShdslConfigProfileTable"
			INDEX { IMPLIED zhoneShdslConfigProfileName }
			::= { zhoneShdslConfigProfileTable 1 }

		
		ZhoneShdslConfigProfileEntry ::=
			SEQUENCE { 
				zhoneShdslConfigProfileName
					ZhoneAdminString,
				zhoneShdslConfigLineRate
					INTEGER,
				zhoneShdslConfigTransmitPowerBackoffMode
					INTEGER,
				zhoneShdslConfigFixBitRate
					INTEGER,
				zhoneShdslConfigNTR
					INTEGER,
				zhoneShdslConfigClockOffset
					Integer32,
				zhoneShdslConfigRepeaterId
					INTEGER,
				zhoneShdslConfigStandard
					INTEGER,
				zhoneShdslConfigStartupMargin
					Integer32,
				zhoneShdslConfigWireMode
					INTEGER,
				zhoneShdslConfigFrameSync
					Integer32,
				zhoneShdslConfigDecoderCoeffA
					Integer32,
				zhoneShdslConfigDecoderCoeffB
					Integer32,
				zhoneShdslConfigPowerScale
					Integer32,
				zhoneShdslConfigRowStatus
					ZhoneRowStatus,
				zhoneShdslConfigBertType
					INTEGER,
				zhoneShdslConfigBertDuration
					INTEGER,
				zhoneShdslConfigBertBootRun
					INTEGER,
				zhoneShdslBertCmd
					INTEGER
			 }

		-- 1.3.6.1.4.1.5504.5.4.9.1.1
		zhoneShdslConfigProfileName OBJECT-TYPE
			SYNTAX ZhoneAdminString (SIZE (1..10))
			MAX-ACCESS not-accessible
			STATUS current
			DESCRIPTION
				"Configuration profile name. Used by the zhoneShdslConfigProfile entry
				to map zhoneDslLine Entry to the appropriate profile.
				
				When `dynamic' profiles are implemented, the profile
				name is user specified.  Also, the system will always
				provide a default profile whose name is zhonedefault.
				
				When `static' profiles are implemented, there is a
				one-to-one relationship between each line and its
				profile.  In which case, the profile name will
				need to algorithmically represent the Line's InterfaceIndex.
				Therefore, the profile's name is a decimal zed string
				of the InterfaceIndex that is fixed-length (i.e., 10) with
				leading zero(s).  For example, the profile name for
				ifIndex which equals '15' will be '0000000015'.
				
				we are supporting only static profiles."
			::= { zhoneShdslConfigProfileEntry 1 }

		
-- 
-- - default for zedge is line-rate-2320kbps
-- 
		-- 1.3.6.1.4.1.5504.5.4.9.1.2
		zhoneShdslConfigLineRate OBJECT-TYPE
			SYNTAX INTEGER
				{
				line-rate-72kbps(1),
				line-rate-80kbps(2),
				line-rate-136kbps(3),
				line-rate-144kbps(4),
				line-rate-200kbps(5),
				line-rate-208kbps(6),
				line-rate-264kbps(7),
				line-rate-272kbps(8),
				line-rate-328kbps(9),
				line-rate-336kbps(10),
				line-rate-392kbps(11),
				line-rate-400kbps(12),
				line-rate-456kbps(13),
				line-rate-464kbps(14),
				line-rate-520kbps(15),
				line-rate-528kbps(16),
				line-rate-584kbps(17),
				line-rate-592kbps(18),
				line-rate-648kbps(19),
				line-rate-656kbps(20),
				line-rate-712kbps(21),
				line-rate-720kbps(22),
				line-rate-776kbps(23),
				line-rate-784kbps(24),
				line-rate-840kbps(25),
				line-rate-848kbps(26),
				line-rate-904kbps(27),
				line-rate-912kbps(28),
				line-rate-968kbps(29),
				line-rate-976kbps(30),
				line-rate-1032kbps(31),
				line-rate-1040kbps(32),
				line-rate-1096kbps(33),
				line-rate-1104kbps(34),
				line-rate-1160kbps(35),
				line-rate-1168kbps(36),
				line-rate-1224kbps(37),
				line-rate-1232kbps(38),
				line-rate-1288kbps(39),
				line-rate-1296kbps(40),
				line-rate-1352kbps(41),
				line-rate-1360kbps(42),
				line-rate-1416kbps(43),
				line-rate-1424kbps(44),
				line-rate-1480kbps(45),
				line-rate-1488kbps(46),
				line-rate-1544kbps(47),
				line-rate-1552kbps(48),
				line-rate-1608kbps(49),
				line-rate-1616kbps(50),
				line-rate-1672kbps(51),
				line-rate-1680kbps(52),
				line-rate-1736kbps(53),
				line-rate-1744kbps(54),
				line-rate-1800kbps(55),
				line-rate-1808kbps(56),
				line-rate-1864kbps(57),
				line-rate-1872kbps(58),
				line-rate-1928kbps(59),
				line-rate-1936kbps(60),
				line-rate-1992kbps(61),
				line-rate-2000kbps(62),
				line-rate-2056kbps(63),
				line-rate-2064kbps(64),
				line-rate-2120kbps(65),
				line-rate-2128kbps(66),
				line-rate-2184kbps(67),
				line-rate-2192kbps(68),
				line-rate-2248kbps(69),
				line-rate-2256kbps(70),
				line-rate-2312kbps(71),
				line-rate-2320kbps(72),
				line-rate-2368kbps(73),
				line-rate-192kbps(74),
				line-rate-384kbps(75),
				line-rate-416kbps(76),
				line-rate-4w-384kbps(77),
				line-rate-4w-512kbps(78),
				line-rate-4w-640kbps(79),
				line-rate-4w-768kbps(80),
				line-rate-4w-896kbps(81),
				line-rate-4w-1024kbps(82),
				line-rate-4w-1152kbps(83),
				line-rate-4w-1280kbps(84),
				line-rate-4w-1408kbps(85),
				line-rate-4w-1536kbps(86),
				line-rate-4w-1664kbps(87),
				line-rate-4w-1792kbps(88),
				line-rate-4w-1920kbps(89),
				line-rate-4w-2048kbps(90),
				line-rate-4w-2176kbps(91),
				line-rate-4w-2304kbps(92),
				line-rate-4w-2432kbps(93),
				line-rate-4w-2560kbps(94),
				line-rate-4w-2688kbps(95),
				line-rate-4w-2816kbps(96),
				line-rate-4w-2944kbps(97),
				line-rate-4w-3072kbps(98),
				line-rate-4w-3200kbps(99),
				line-rate-4w-3328kbps(100),
				line-rate-4w-3456kbps(101),
				line-rate-4w-3584kbps(102),
				line-rate-4w-3712kbps(103),
				line-rate-4w-3840kbps(104),
				line-rate-4w-3968kbps(105),
				line-rate-4w-4096kbps(106),
				line-rate-4w-4224kbps(107),
				line-rate-4w-4352kbps(108),
				line-rate-4w-4480kbps(109),
				line-rate-4w-4608kbps(110)
				}
			MAX-ACCESS read-create
			STATUS current
			DESCRIPTION
				"The line rate selection. 
				
				For 2 Wire G.SHDSL cards, the only valid values
				are the ones not containing the '4w' string.
				The 2 Wire default value is line-rate-2368kbps.
				
				For 4 Wire G.SHDSL card, the only valid
				values are the ones containing the '4w' string.
				The 4 Wire default value is line-rate-4w-4608bps.
				"
			DEFVAL { line-rate-2368kbps }
			::= { zhoneShdslConfigProfileEntry 2 }

		
-- 
-- default for zedge is backoffEnable
-- 
		-- 1.3.6.1.4.1.5504.5.4.9.1.3
		zhoneShdslConfigTransmitPowerBackoffMode OBJECT-TYPE
			SYNTAX INTEGER
				{
				backoffDisable(1),
				backoffEnable(2),
				noChangeBackoff(3)
				}
			MAX-ACCESS read-create
			STATUS current
			DESCRIPTION
				"Determines if the transmit power backoff defined in SHDSL standard 
				is used. The default value is backoffDisable"
			DEFVAL { backoffDisable }
			::= { zhoneShdslConfigProfileEntry 3 }

		
-- 
		-- 1.3.6.1.4.1.5504.5.4.9.1.4
		zhoneShdslConfigFixBitRate OBJECT-TYPE
			SYNTAX INTEGER
				{
				fix-bit-enable(1),
				fix-bit-disable(2)
				}
			MAX-ACCESS read-create
			STATUS current
			DESCRIPTION
				"Normally, if the co side and cpe side select different line rates 
				at startup, the lower of the two rate will be selected. By using the fix bit 
				rate the co side can override the default procedure and require startup at the rate 
				specified in zhoneShdslConfigLineRate. Note: this option is available only if 
				zhoneDslConfigUnitMode is co. This value is ignored if 
				zhoneDslConfigUnitMode is cpe
				
				The default value is fix-bit-disable"
			DEFVAL { fix-bit-disable }
			::= { zhoneShdslConfigProfileEntry 4 }

		
-- 
		-- 1.3.6.1.4.1.5504.5.4.9.1.5
		zhoneShdslConfigNTR OBJECT-TYPE
			SYNTAX INTEGER
				{
				ntr-local-osc(1),
				ntr-refck-8KHz(2),
				ntr-refck-8192KHz(3)
				}
			MAX-ACCESS read-create
			STATUS current
			DESCRIPTION
				"Determines whether network timing 
				recovery is enabled or disabled. The default value is disabled"
			DEFVAL { ntr-local-osc }
			::= { zhoneShdslConfigProfileEntry 5 }

		
-- 
		-- 1.3.6.1.4.1.5504.5.4.9.1.6
		zhoneShdslConfigClockOffset OBJECT-TYPE
			SYNTAX Integer32 (-100..100)
			UNITS "ppm"
			MAX-ACCESS read-create
			STATUS current
			DESCRIPTION
				"The value of this variable is used to help achieve a low frequency wander and jitter 
				between network and DSL system clock."
			DEFVAL { '0'b }
			::= { zhoneShdslConfigProfileEntry 6 }

		
-- 
		-- 1.3.6.1.4.1.5504.5.4.9.1.7
		zhoneShdslConfigRepeaterId OBJECT-TYPE
			SYNTAX INTEGER
				{
				repeaterEnable(1),
				repeaterDisable(2),
				noChangeRepeater(3)
				}
			MAX-ACCESS read-create
			STATUS current
			DESCRIPTION
				"This value identifies if the STU is being used as a repeater."
			DEFVAL { repeaterDisable }
			::= { zhoneShdslConfigProfileEntry 7 }

		
-- 
		-- 1.3.6.1.4.1.5504.5.4.9.1.8
		zhoneShdslConfigStandard OBJECT-TYPE
			SYNTAX INTEGER
				{
				annex-a(1),
				annex-b(2)
				}
			MAX-ACCESS read-create
			STATUS current
			DESCRIPTION
				"This variable determines the SHDSL standards"
			DEFVAL { annex-a }
			::= { zhoneShdslConfigProfileEntry 8 }

		
-- 
-- default for zedge is 6
-- 
		-- 1.3.6.1.4.1.5504.5.4.9.1.9
		zhoneShdslConfigStartupMargin OBJECT-TYPE
			SYNTAX Integer32 (0..15)
			UNITS "dB"
			MAX-ACCESS read-create
			STATUS current
			DESCRIPTION
				"The value of this variable is used to negotiate the bit rate during startup.
				The amount of margin is specified in dB and its value ranges from 0 to 15. 
				Current Implementation supports only 0dB."
			DEFVAL { '0'b }
			::= { zhoneShdslConfigProfileEntry 9 }

		
-- 
		-- 1.3.6.1.4.1.5504.5.4.9.1.10
		zhoneShdslConfigWireMode OBJECT-TYPE
			SYNTAX INTEGER
				{
				four-wire-disable(1),
				four-wire-enable-byte-interleave(2),
				four-wire-enable-bit-interleave(3),
				four-wire-enable-non-interleave(4)
				}
			MAX-ACCESS read-create
			STATUS current
			DESCRIPTION
				"This variable is used to disable or enable 4-wire-framing."
			DEFVAL { four-wire-disable }
			::= { zhoneShdslConfigProfileEntry 10 }

		
-- 
-- default for zedge is 45
-- 
		-- 1.3.6.1.4.1.5504.5.4.9.1.11
		zhoneShdslConfigFrameSync OBJECT-TYPE
			SYNTAX Integer32 (0..65535)
			MAX-ACCESS read-create
			STATUS current
			DESCRIPTION
				"This variable enable the user to select a 14 bit frame sync workd (FSW) of his/her
				choice. The possible values are 
				Frame sysnc default which is 0
				no change frame sync word whic is 0xffff, or a
				user slelected 14 bit value."
			DEFVAL { '0'h }
			::= { zhoneShdslConfigProfileEntry 11 }

		
-- 
		-- 1.3.6.1.4.1.5504.5.4.9.1.12
		zhoneShdslConfigDecoderCoeffA OBJECT-TYPE
			SYNTAX Integer32 (0..2097151)
			MAX-ACCESS read-create
			STATUS current
			DESCRIPTION
				"21 bit value corresponding to the decoder coefficient A. The Default value
				is 0x16e"
			DEFVAL { '16E'h }
			::= { zhoneShdslConfigProfileEntry 12 }

		
-- 
		-- 1.3.6.1.4.1.5504.5.4.9.1.13
		zhoneShdslConfigDecoderCoeffB OBJECT-TYPE
			SYNTAX Integer32 (0..2097151)
			MAX-ACCESS read-create
			STATUS current
			DESCRIPTION
				"21 bit value corresponding to the decoder coefficient B.
				The default value is 0x331"
			DEFVAL { '331'h }
			::= { zhoneShdslConfigProfileEntry 13 }

		
-- 
-- default for zedge is 29298
-- 
		-- 1.3.6.1.4.1.5504.5.4.9.1.14
		zhoneShdslConfigPowerScale OBJECT-TYPE
			SYNTAX Integer32
			MAX-ACCESS read-create
			STATUS current
			DESCRIPTION
				"zhoneShdslConfigPowerScale is used to adjust transmit 
				power in small increments to compensate for minor 
				differences on power between units. It is recommended that value should
				remain in the range of 20992 (-3 db) to 32767 (+0.8 db). 
				This value is calculated using the following formula
				PowerScale = (10 ^ (Db / 20)) * 29952.
				Where Db is in the range of -3 to 0.8. A value of 29952
				corresponds to 0 db. The value should not be limited to 
				the range 20992 to 32767.In some circumstances a value 
				outside of this range maybe needed."
			DEFVAL { 29952 }
			::= { zhoneShdslConfigProfileEntry 14 }

		
		-- 1.3.6.1.4.1.5504.5.4.9.1.15
		zhoneShdslConfigRowStatus OBJECT-TYPE
			SYNTAX ZhoneRowStatus
			MAX-ACCESS read-create
			STATUS current
			DESCRIPTION
				"zhoneShdslConfigRowStatus is used to create/delete an entry in 
				zhoneShdslConfigProfileTable"
			::= { zhoneShdslConfigProfileEntry 15 }

		
-- 
-- 
		-- 1.3.6.1.4.1.5504.5.4.9.1.16
		zhoneShdslConfigBertType OBJECT-TYPE
			SYNTAX INTEGER
				{
				localloopback(1),
				farendloopback(2)
				}
			MAX-ACCESS read-create
			STATUS current
			DESCRIPTION
				"Determine which Bit Error Rate Test to run.  Local loopback means
				the framer will be placed into local loopback, and then it 
				will perform BERT.  Farend loopback means the farend device will be
				placed into network/core loopback, and the near-end device will
				perform BERT Rx and Tx.
				
				Farend-loopback requires the farend device to support EOC message."
			DEFVAL { localloopback }
			::= { zhoneShdslConfigProfileEntry 16 }

		
-- 
		-- 1.3.6.1.4.1.5504.5.4.9.1.17
		zhoneShdslConfigBertDuration OBJECT-TYPE
			SYNTAX INTEGER
				{
				minute1(1),
				minute5(2),
				minute10(3),
				minute15(4),
				minute20(5)
				}
			MAX-ACCESS read-create
			STATUS current
			DESCRIPTION
				"Determines if the length of BERT in minutes."
			DEFVAL { minute1 }
			::= { zhoneShdslConfigProfileEntry 17 }

		
-- 
		-- 1.3.6.1.4.1.5504.5.4.9.1.18
		zhoneShdslConfigBertBootRun OBJECT-TYPE
			SYNTAX INTEGER
				{
				disabled(1),
				enabled(2)
				}
			MAX-ACCESS read-create
			STATUS current
			DESCRIPTION
				"Determines if the BERT will be performed after the device
				is rebooted.
				
				If this feature is enabled, it will use the same value in
				ConfigBerType and ConfigBertDuration to perform the boot-time
				BERT.  The result of boot-time BERT will be in shdslStatus entry
				with BootTime at the end.
				"
			DEFVAL { disabled }
			::= { zhoneShdslConfigProfileEntry 18 }

		
-- 
-- 
		-- 1.3.6.1.4.1.5504.5.4.9.1.19
		zhoneShdslBertCmd OBJECT-TYPE
			SYNTAX INTEGER
				{
				none(1),
				start(2),
				stop(3)
				}
			MAX-ACCESS read-create
			STATUS current
			DESCRIPTION
				"Defines the control of current Bit Error Rate Test.
				
				none  - no action.
				start - start the test.
				stop  - stop the current test.
				
				Note: this field does not apply for boot-time BERT."
			DEFVAL { none }
			::= { zhoneShdslConfigProfileEntry 19 }

		
		-- 1.3.6.1.4.1.5504.5.4.10
		zhoneShdslStatusTable OBJECT-TYPE
			SYNTAX SEQUENCE OF ZhoneShdslStatusEntry
			MAX-ACCESS not-accessible
			STATUS current
			DESCRIPTION
				"This table contains SHDSL specific line status information.
				An entry into this table is automatically created 
				whenever a zhoneDslLineEntry is created and the type is SHDSL."
			::= { zhoneDsl 10 }

		
		-- 1.3.6.1.4.1.5504.5.4.10.1
		zhoneShdslStatusEntry OBJECT-TYPE
			SYNTAX ZhoneShdslStatusEntry
			MAX-ACCESS not-accessible
			STATUS current
			DESCRIPTION
				"An entry in zhoneShdslStatusTable"
			INDEX { ifIndex }
			::= { zhoneShdslStatusTable 1 }

		
		ZhoneShdslStatusEntry ::=
			SEQUENCE { 
				zhoneShdslFixBitStatus
					INTEGER,
				zhoneShdslDSPVersion
					Integer32,
				zhoneShdslFirmwareVersion
					OCTET STRING,
				zhoneShdslSignalQuality
					Integer32,
				zhoneShdslTransmitPower
					Integer32,
				zhoneShdslStartProgress
					INTEGER,
				zhoneShdslBertAccuError
					INTEGER,
				zhoneShdslBertAccuErrorBootTime
					INTEGER,
				zhoneShdslBertErrorSecond
					INTEGER,
				zhoneShdslBertErrorSecondBootTime
					INTEGER,
				zhoneShdslBertNoErrorSecond
					INTEGER,
				zhoneShdslBertNoErrorSecondBootTime
					INTEGER,
				zhoneShdslBertActualType
					INTEGER,
				zhoneShdslBertActualTypeBootTime
					INTEGER,
				zhoneShdslBertRemoteEoc
					INTEGER,
				zhoneShdslBertRemoteBootTime
					INTEGER,
				zhoneShdslBertStatus
					INTEGER,
				zhoneShdslBertStatusBootTime
					INTEGER
			 }

-- 
		-- 1.3.6.1.4.1.5504.5.4.10.1.1
		zhoneShdslFixBitStatus OBJECT-TYPE
			SYNTAX INTEGER
				{
				fix-bit-enable(1),
				fix-bit-disable(2)
				}
			MAX-ACCESS read-only
			STATUS current
			DESCRIPTION
				"Indicates that the fix bit feature is enabled. This value applies only to the co side
				and shoud be ignored for cpe side"
			::= { zhoneShdslStatusEntry 1 }

		
-- 
		-- 1.3.6.1.4.1.5504.5.4.10.1.2
		zhoneShdslDSPVersion OBJECT-TYPE
			SYNTAX Integer32
			MAX-ACCESS read-only
			STATUS current
			DESCRIPTION
				"The version of the DSP/Framer VLSI in the transceiver."
			::= { zhoneShdslStatusEntry 2 }

		
-- 
		-- 1.3.6.1.4.1.5504.5.4.10.1.3
		zhoneShdslFirmwareVersion OBJECT-TYPE
			SYNTAX OCTET STRING (SIZE (0..4))
			MAX-ACCESS read-only
			STATUS current
			DESCRIPTION
				"The firmware release number (in ASCII)"
			::= { zhoneShdslStatusEntry 3 }

		
-- 
		-- 1.3.6.1.4.1.5504.5.4.10.1.4
		zhoneShdslSignalQuality OBJECT-TYPE
			SYNTAX Integer32
			MAX-ACCESS read-only
			STATUS current
			DESCRIPTION
				"This value is used to compute the signal-to-noise ratio. To determine the signal-to-noise
				ratio take the returned high and low bytes to form a 16 bit integer, I. Using 
				this information apply the following formula
				
				Received S/N(dB) = 58.4-10 log10(I)"
			::= { zhoneShdslStatusEntry 4 }

		
-- 
		-- 1.3.6.1.4.1.5504.5.4.10.1.5
		zhoneShdslTransmitPower OBJECT-TYPE
			SYNTAX Integer32
			UNITS "dBm"
			MAX-ACCESS read-only
			STATUS current
			DESCRIPTION
				"Nominal transmit power"
			::= { zhoneShdslStatusEntry 5 }

		
-- 
		-- 1.3.6.1.4.1.5504.5.4.10.1.6
		zhoneShdslStartProgress OBJECT-TYPE
			SYNTAX INTEGER
				{
				startup-handshake-in-progress(16),
				startup-training-in-progress(24),
				startup-framer-sync-in-progress(26)
				}
			MAX-ACCESS read-only
			STATUS current
			DESCRIPTION
				"Defines the current detailed startup state of the transceiver."
			::= { zhoneShdslStatusEntry 6 }

		
-- 
		-- 1.3.6.1.4.1.5504.5.4.10.1.7
		zhoneShdslBertAccuError OBJECT-TYPE
			SYNTAX INTEGER
			MAX-ACCESS read-only
			STATUS current
			DESCRIPTION
				"Defines the acculumated bit errors during the last performed BERT."
			DEFVAL { 0 }
			::= { zhoneShdslStatusEntry 7 }

		
-- 
		-- 1.3.6.1.4.1.5504.5.4.10.1.8
		zhoneShdslBertAccuErrorBootTime OBJECT-TYPE
			SYNTAX INTEGER
			MAX-ACCESS read-only
			STATUS current
			DESCRIPTION
				"Defines the acculumated bit errors during the boot-time BERT."
			DEFVAL { 0 }
			::= { zhoneShdslStatusEntry 8 }

		
-- 
		-- 1.3.6.1.4.1.5504.5.4.10.1.9
		zhoneShdslBertErrorSecond OBJECT-TYPE
			SYNTAX INTEGER
			MAX-ACCESS read-only
			STATUS current
			DESCRIPTION
				"Defines the number of seconds which contains bit error during 
				the last performed BERT."
			DEFVAL { 0 }
			::= { zhoneShdslStatusEntry 9 }

		
-- 
		-- 1.3.6.1.4.1.5504.5.4.10.1.10
		zhoneShdslBertErrorSecondBootTime OBJECT-TYPE
			SYNTAX INTEGER
			MAX-ACCESS read-only
			STATUS current
			DESCRIPTION
				"Defines the number of seconds which contains bit error during 
				the boot-time BERT."
			DEFVAL { 0 }
			::= { zhoneShdslStatusEntry 10 }

		
-- 
		-- 1.3.6.1.4.1.5504.5.4.10.1.11
		zhoneShdslBertNoErrorSecond OBJECT-TYPE
			SYNTAX INTEGER
			MAX-ACCESS read-only
			STATUS current
			DESCRIPTION
				"Defines the number of seconds which contains NO bit error during 
				the last performed BERT."
			DEFVAL { 0 }
			::= { zhoneShdslStatusEntry 11 }

		
-- 
		-- 1.3.6.1.4.1.5504.5.4.10.1.12
		zhoneShdslBertNoErrorSecondBootTime OBJECT-TYPE
			SYNTAX INTEGER
			MAX-ACCESS read-only
			STATUS current
			DESCRIPTION
				"Defines the number of seconds which contains NO bit error during 
				the boot-time BERT."
			DEFVAL { 0 }
			::= { zhoneShdslStatusEntry 12 }

		
-- 
		-- 1.3.6.1.4.1.5504.5.4.10.1.13
		zhoneShdslBertActualType OBJECT-TYPE
			SYNTAX INTEGER
				{
				none(1),
				localloopback(2),
				farendloopback(3)
				}
			MAX-ACCESS read-only
			STATUS current
			DESCRIPTION
				"Defines the actual BERT type ran as result of last performed
				BERT.
				
				The actual BERT type performed can be different from the request
				BERT type, due to line conditions, farend device support, etc.
				
				If the actual BERT type is different from the request BERT type,
				refer to bertStatus code for the cause. "
			DEFVAL { none }
			::= { zhoneShdslStatusEntry 13 }

		
-- 
		-- 1.3.6.1.4.1.5504.5.4.10.1.14
		zhoneShdslBertActualTypeBootTime OBJECT-TYPE
			SYNTAX INTEGER
				{
				none(1),
				localloopback(2),
				farendloopback(3)
				}
			MAX-ACCESS read-only
			STATUS current
			DESCRIPTION
				"Defines the actual BERT type ran as result of boot-time
				BERT.
				
				The actual BERT type performed can be different from the request
				BERT type, due to line conditions, farend device support, etc.
				
				If the actual BERT type is different from the request BERT type,
				refer to bertStatus code for the cause. "
			DEFVAL { none }
			::= { zhoneShdslStatusEntry 14 }

		
-- 
		-- 1.3.6.1.4.1.5504.5.4.10.1.15
		zhoneShdslBertRemoteEoc OBJECT-TYPE
			SYNTAX INTEGER
				{
				notsupported(1),
				supported(2)
				}
			MAX-ACCESS read-only
			STATUS current
			DESCRIPTION
				"Defines whether the farend device supports EOC messages during
				the last performed BERT. "
			DEFVAL { notsupported }
			::= { zhoneShdslStatusEntry 15 }

		
-- 
		-- 1.3.6.1.4.1.5504.5.4.10.1.16
		zhoneShdslBertRemoteBootTime OBJECT-TYPE
			SYNTAX INTEGER
				{
				notsupported(1),
				supported(2)
				}
			MAX-ACCESS read-only
			STATUS current
			DESCRIPTION
				"Defines whether the farend device supports EOC messages during
				the boot-time BERT. "
			DEFVAL { notsupported }
			::= { zhoneShdslStatusEntry 16 }

		
-- 
		-- 1.3.6.1.4.1.5504.5.4.10.1.17
		zhoneShdslBertStatus OBJECT-TYPE
			SYNTAX INTEGER
				{
				none(1),
				sucessful(2),
				inprogress(3),
				aborted(4),
				bertoutofsync(5),
				portnotready(6),
				portlinetype(7),
				other(8)
				}
			MAX-ACCESS read-only
			STATUS current
			DESCRIPTION
				"Defines the cause/result of last performed BERT.
				
				none - default value.
				successful - test was performed successfully.
				in_progress - test is in progress.
				aborted - test was aborted by user.
				bert_out_of_sync - test pattern can not be in sync.
				port_not_ready - port was not ready for test, etc admin-down, training.
				port_line_type - test can not be performed on the specified lineType.
				other - other causes."
			DEFVAL { none }
			::= { zhoneShdslStatusEntry 17 }

		
-- 
		-- 1.3.6.1.4.1.5504.5.4.10.1.18
		zhoneShdslBertStatusBootTime OBJECT-TYPE
			SYNTAX INTEGER
				{
				none(1),
				sucessful(2),
				inprogress(3),
				aborted(4),
				bertoutofsync(5),
				portnotready(6),
				portlinetype(7),
				other(8)
				}
			MAX-ACCESS read-only
			STATUS current
			DESCRIPTION
				"Defines the cause/result of boot-time BERT.
				
				none - default value.
				successful - test was performed successfully.
				in_progress - test is in progress.
				aborted - test was aborted by user.
				bert_out_of_sync - test pattern can not be in sync.
				port_not_ready - port was not ready for test, etc admin-down, training.
				port_line_type - test can not be performed on the specified lineType.
				other - other causes."
			DEFVAL { none }
			::= { zhoneShdslStatusEntry 18 }

		
		-- 1.3.6.1.4.1.5504.5.4.11
		zhoneAdslLineExtTable OBJECT-TYPE
			SYNTAX SEQUENCE OF ZhoneAdslLineExtEntry
			MAX-ACCESS not-accessible
			STATUS current
			DESCRIPTION
				"This table contains ADSL line configuration and 
				monitoring information not defined in the adslLineTable 
				from the ADSL-LINE-MIB. This includes the capabilities 
				and actual ADSL transmission system."
			::= { zhoneDsl 11 }

		
		-- 1.3.6.1.4.1.5504.5.4.11.1
		zhoneAdslLineExtEntry OBJECT-TYPE
			SYNTAX ZhoneAdslLineExtEntry
			MAX-ACCESS not-accessible
			STATUS current
			DESCRIPTION
				"An entry extends the adslLineEntry defined in the 
				ADSL-LINE-MIB. Each entry corresponds to an ADSL line."
			AUGMENTS { adslLineEntry }
			::= { zhoneAdslLineExtTable 1 }

		
		ZhoneAdslLineExtEntry ::=
			SEQUENCE { 
				zhoneAdslTrellisModeEnabled
					TruthValue,
				zhoneAdslNTRModeEnabled
					TruthValue,
				zhoneAdslTransmissionMode
					INTEGER,
				zhoneAdslChannelMode
					INTEGER,
				zhoneAdslMaxDownstreamToneIndex
					Integer32,
				zhoneAdslMinDownstreamToneIndex
					Integer32,
				zhoneAdslMaxUpstreamToneIndex
					Integer32,
				zhoneAdslMinUpstreamToneIndex
					Integer32,
				zhoneAdslPotsBypassRelayMaxDuration
					Integer32,
				zhoneAdslPotsBypassRelayStatus
					INTEGER,
				zhoneAdslLineDMTConfMode
					INTEGER,
				zhoneAdslAnnexMModeEnabled
					TruthValue,
				zhoneAdslAnnexMPsdMask
					INTEGER,
				zhoneAdslAnnexJModeEnabled
					TruthValue
			 }

		-- 1.3.6.1.4.1.5504.5.4.11.1.1
		zhoneAdslTrellisModeEnabled OBJECT-TYPE
			SYNTAX TruthValue
			MAX-ACCESS read-write
			STATUS current
			DESCRIPTION
				"This field indicates whether trellis mode is enabled on the adsl modem.
				If this field is set to 'true' trellis mode is enabled, if it set to false
				it is not."
			DEFVAL { true }
			::= { zhoneAdslLineExtEntry 1 }

		
		-- 1.3.6.1.4.1.5504.5.4.11.1.2
		zhoneAdslNTRModeEnabled OBJECT-TYPE
			SYNTAX TruthValue
			MAX-ACCESS read-write
			STATUS current
			DESCRIPTION
				"This field indicates whether Network Timing Recovery mode is enabled on the adsl modem.
				If this field is set to 'true' Network Timing Recovery mode is enabled, if it set to false
				it is not."
			DEFVAL { true }
			::= { zhoneAdslLineExtEntry 2 }

		
		-- 1.3.6.1.4.1.5504.5.4.11.1.3
		zhoneAdslTransmissionMode OBJECT-TYPE
			SYNTAX INTEGER
				{
				autoNegotiateMode(1),
				fullRateMode(2),
				gliteMode(3),
				t1Mode(4),
				gdmtMode(5),
				ghsMode(6),
				adsl2Mode(7),
				adsl2PlusMode(8),
				reachDslMode(9)
				}
			MAX-ACCESS read-write
			STATUS current
			DESCRIPTION
				"This field indicates the line transmission mode for each available adsl
				Line. Possible values are:
				       autoNegotiateMode(1),
				       fullRateMode(2),
				       gliteMode(3),
				       t1Mode(4),
				       gdmtMode(5),
				       ghsMode(6)
				       adsl2Mode (7),
				       adsl2PlusMode (8),
				       reachDslMode (9)
				
				For the meaning of these values please consult the hardware reference
				manual.
				"
			DEFVAL { autoNegotiateMode }
			::= { zhoneAdslLineExtEntry 3 }

		
		-- 1.3.6.1.4.1.5504.5.4.11.1.4
		zhoneAdslChannelMode OBJECT-TYPE
			SYNTAX INTEGER
				{
				fastOnly(1),
				interleavedOnly(2),
				fastAndInterleaved(3),
				fastOrInterleaved(4)
				}
			MAX-ACCESS read-write
			STATUS current
			DESCRIPTION
				"This field describes the channelization mode for the adsl modems. The 
				supported values are:
				
				fastOnly - No channelization, fast transmission mode
				interleavedOnly - No channelization, interleaved transmission mode
				fastAndInterleaved - Dual channelization, channel 1 Fast Mode, channel 2 Interleaved Mode
				fastOrInterleaved - Dynamic unchannelized transmission mode assignment
				
				In release one only the fastOnly and interleavedOnly modes are supported. Future releases
				may support fastAndInterleaved.
				
				There are no plans to support fastOrInterleaved at this time"
			DEFVAL { fastOnly }
			::= { zhoneAdslLineExtEntry 4 }

		
-- 
		-- 1.3.6.1.4.1.5504.5.4.11.1.5
		zhoneAdslMaxDownstreamToneIndex OBJECT-TYPE
			SYNTAX Integer32 (6..1023)
			MAX-ACCESS read-write
			STATUS current
			DESCRIPTION
				"Index of end tone (last active tone) in the 
				downstream direction.  For POTS this must be in 
				the range 32-255.  For ISDN this must be in the 
				range 60-255.  Default assumes POTS.
				
				1023 - Default for all Annexes and ADSL2/ADSL2Plus"
			DEFVAL { 255 }
			::= { zhoneAdslLineExtEntry 5 }

		
		-- 1.3.6.1.4.1.5504.5.4.11.1.6
		zhoneAdslMinDownstreamToneIndex OBJECT-TYPE
			SYNTAX Integer32 (6..1023)
			MAX-ACCESS read-write
			STATUS current
			DESCRIPTION
				"Index of start tone (first active tone) in the 
				downstream direction.  For POTS this must be in 
				the range 32-255.  For ISDN this must be in the 
				range 60-255.  Default assumes POTS.
				
				32 - Default for ADSL2/ADSL2Plus
				6  - Default for Annex A if G.Span and/or
				     G.Span Plus are also defined.
				64 - Default for Annex B
				6  - Default for Annex C/C.x
				6  - Default for G.Span
				6  - Default for G.Span Plus"
			DEFVAL { 32 }
			::= { zhoneAdslLineExtEntry 6 }

		
		-- 1.3.6.1.4.1.5504.5.4.11.1.7
		zhoneAdslMaxUpstreamToneIndex OBJECT-TYPE
			SYNTAX Integer32 (1..63)
			MAX-ACCESS read-write
			STATUS current
			DESCRIPTION
				"Index of end tone (last active tone) in the 
				upstream direction.  For POTS this must be in 
				the range 6-30.  For ISDN this must be in the 
				range 33-60. Default assumes POTS.
				
				63 - Default for all Annexes and ADSL2/ADSL2Plus"
			DEFVAL { 30 }
			::= { zhoneAdslLineExtEntry 7 }

		
		-- 1.3.6.1.4.1.5504.5.4.11.1.8
		zhoneAdslMinUpstreamToneIndex OBJECT-TYPE
			SYNTAX Integer32 (1..63)
			MAX-ACCESS read-write
			STATUS current
			DESCRIPTION
				"Index of start tone (first active tone) in the 
				upstream direction.  For POTS this must be in 
				the range 6-30.  For ISDN this must be in the 
				range 33-60.  Default assumes POTS.
				
				6 - Default for Annex A
				1 - Default for Annex B
				6 - Default for Annex C/C.x
				6 - Default for G.Span/ADSL+
				6 - Default for G.Span Plus
				6 - Default for ADSL2/ADSL2Plus"
			DEFVAL { 6 }
			::= { zhoneAdslLineExtEntry 8 }

		
		-- 1.3.6.1.4.1.5504.5.4.11.1.9
		zhoneAdslPotsBypassRelayMaxDuration OBJECT-TYPE
			SYNTAX Integer32 (1..300)
			MAX-ACCESS read-write
			STATUS current
			DESCRIPTION
				"The maximum duration in seconds that an Adsl Pots Low
				Pass Filter Bypass Relay will remain active (meaning
				closed/energized). As a fail-safe mechanism, the relay
				will automatically return a line back to normal
				operational mode when this timer has expired.
				
				This object is only valid for Adsl Pots Splitter
				cards containing the Pots LPF Bypass Relays."
			DEFVAL { 60 }
			::= { zhoneAdslLineExtEntry 9 }

		
		-- 1.3.6.1.4.1.5504.5.4.11.1.10
		zhoneAdslPotsBypassRelayStatus OBJECT-TYPE
			SYNTAX INTEGER
				{
				normal(1),
				closed(2)
				}
			MAX-ACCESS read-write
			STATUS current
			DESCRIPTION
				"Indicates whether a particular Adsl Pots Bypass Relay
				is in a normal or closed loop condition.  By setting this
				parameter, the manager can switch the relays in order
				to bypass the Low Pass Filter for POTS closed loop
				testing (closed) or force a relay back to normal
				operation mode before the zhoneAdslPotsBypassRelayMaxDuration
				timer expires.
				
				This object is only valid for Adsl Pots Splitter
				cards containing the Pots LBF Relays."
			DEFVAL { normal }
			::= { zhoneAdslLineExtEntry 10 }

		
		-- 1.3.6.1.4.1.5504.5.4.11.1.11
		zhoneAdslLineDMTConfMode OBJECT-TYPE
			SYNTAX INTEGER
				{
				echoCancel(1),
				freqDivMux(2)
				}
			MAX-ACCESS read-write
			STATUS current
			DESCRIPTION
				"Discrete Multi-Tone parameter that selects whether there is overlap (echoCancel)
				or no overlap (freqDivMux) of bins."
			DEFVAL { freqDivMux }
			::= { zhoneAdslLineExtEntry 11 }

		
		-- 1.3.6.1.4.1.5504.5.4.11.1.12
		zhoneAdslAnnexMModeEnabled OBJECT-TYPE
			SYNTAX TruthValue
			MAX-ACCESS read-write
			STATUS current
			DESCRIPTION
				"This field indicates whether Annex-M mode is enabled on the adsl modem.
				If this field is set to 'true' Annex-M mode is enabled, if it set to false
				it is not."
			DEFVAL { false }
			::= { zhoneAdslLineExtEntry 12 }

		
		-- 1.3.6.1.4.1.5504.5.4.11.1.13
		zhoneAdslAnnexMPsdMask OBJECT-TYPE
			SYNTAX INTEGER
				{
				eu64(1),
				eu60(2),
				eu56(3),
				eu52(4),
				eu48(5),
				eu44(6),
				eu40(7),
				eu36(8),
				eu32(9),
				all(10)
				}
			MAX-ACCESS read-write
			STATUS current
			DESCRIPTION
				"This object specifies the maximum transmit PSD
				allowed in the downstream channel on an
				Annex-M line."
			::= { zhoneAdslLineExtEntry 13 }

		
		-- 1.3.6.1.4.1.5504.5.4.11.1.14
		zhoneAdslAnnexJModeEnabled OBJECT-TYPE
			SYNTAX TruthValue
			MAX-ACCESS read-write
			STATUS current
			DESCRIPTION
				"Description."
			DEFVAL { false }
			::= { zhoneAdslLineExtEntry 14 }

		
		-- 1.3.6.1.4.1.5504.5.4.12
		zhoneDslTraps OBJECT-IDENTITY
			STATUS current
			DESCRIPTION 
				"All Zhone Dsl traps are defined under this OID."
			::= { zhoneDsl 12 }

		
		-- 1.3.6.1.4.1.5504.5.4.12.0
		zhoneDslV2Traps OBJECT-IDENTITY
			STATUS current
			DESCRIPTION 
				"This object identity adds a zero(0) for the next to last
				sub-identifier which should be used for new SNMPv2 Traps."
			::= { zhoneDslTraps 0 }

		
		-- 1.3.6.1.4.1.5504.5.4.12.0.1
		zhoneAdslPotsBypassRelayChangeNotification NOTIFICATION-TYPE
			OBJECTS { ifIndex, zhoneAdslPotsBypassRelayStatus }
			STATUS current
			DESCRIPTION 
				"This notification is sent to the manager after
				a bypass relay status change and reports the new
				status.  This notification is sent on a per
				port basis.
				
				This object is only valid for Adsl Pots Splitter
				cards containing the Pots LBF Bypass Relays."
			::= { zhoneDslV2Traps 1 }

		
		-- 1.3.6.1.4.1.5504.5.4.12.0.2
		zhoneVdslLineStatusChangeNotification NOTIFICATION-TYPE
			OBJECTS { ifIndex, zhoneVdslStatusLineState }
			STATUS obsolete
			DESCRIPTION 
				"This notification is sent to the manager after
				a VDSL line status change and reports the new
				status.  This notification is sent on a per
				port basis."
			::= { zhoneDslV2Traps 2 }

		
		-- 1.3.6.1.4.1.5504.5.4.12.0.3
		zhoneDslLineAlarmStatusChange NOTIFICATION-TYPE
			OBJECTS { zhoneDslLineAlarmStatus }
			STATUS current
			DESCRIPTION 
				"A zhoneDslLineAlarmStatusChange trap is sent when the value
				of zhoneLineAlarmStatus changes for a DSL line.
				
				When the ifAdminStatus for the DSL port is down, this
				trap will not be generated."
			::= { zhoneDslV2Traps 3 }

		
		-- 1.3.6.1.4.1.5504.5.4.12.0.4
		zhoneDslBertStatusChange NOTIFICATION-TYPE
			OBJECTS { zhoneShdslBertStatus }
			STATUS current
			DESCRIPTION 
				"A zhoneDslBertStatusChange trap is sent after a Bit Error Rate
				Test has been performed.
				
				Note: the boot-time BERT will not generate this trap."
			::= { zhoneDslV2Traps 4 }

		
		-- 1.3.6.1.4.1.5504.5.4.12.0.5
		zhoneAdslAtucMinTxThreshAlarmFailure NOTIFICATION-TYPE
			OBJECTS { ifIndex, adslAtucChanCurrTxRate, adslAturChanPrevTxRate, zhoneAdslAtucMinTxThreshAlarm }
			STATUS current
			DESCRIPTION 
				"This trap is thrown when the ATUC line rate syncs below the
				threshold rate as defined by zhoneAdslAtucMinTxThreshAlarm
				mib object."
			::= { zhoneDslV2Traps 5 }

		
		-- 1.3.6.1.4.1.5504.5.4.12.0.6
		zhoneAdslAturMinTxThreshAlarmFailure NOTIFICATION-TYPE
			OBJECTS { ifIndex, adslAturChanCurrTxRate, adslAturChanPrevTxRate, zhoneAdslAturMinTxThreshAlarm }
			STATUS current
			DESCRIPTION 
				"This trap is thrown when the ATUR line rate syncs below the
				threshold rate as defined by zhoneAdslAturMinTxThreshAlarm
				mib object."
			::= { zhoneDslV2Traps 6 }

		
		-- 1.3.6.1.4.1.5504.5.4.12.0.7
		zhoneDslUpstreamTrafficAlarmChange NOTIFICATION-TYPE
			OBJECTS { ifIndex }
			STATUS current
			DESCRIPTION 
				"A zhoneDslUpstreamTrafficAlarmChange trap is enabled when upstream
				traffic is completely stalled for a DSL line."
			::= { zhoneDslV2Traps 7 }

		
		-- 1.3.6.1.4.1.5504.5.4.13
		zhoneAdslPotsBypassRelayGroup OBJECT-GROUP
			OBJECTS { zhoneAdslPotsBypassRelayMaxDuration, zhoneAdslPotsBypassRelayStatus }
			STATUS current
			DESCRIPTION 
				"The objects contained in this ojbect group are all
				objects used for provisioning and viewing the Adsl Pots
				Bypass Relays."
			::= { zhoneDsl 13 }

		
		-- 1.3.6.1.4.1.5504.5.4.14
		zhoneVdslControlTable OBJECT-TYPE
			SYNTAX SEQUENCE OF ZhoneVdslControlEntry
			MAX-ACCESS not-accessible
			STATUS obsolete
			DESCRIPTION
				"VDSL provisioning information table.  The rows in
				this table are not creatable/deletable.  There is
				only one entry in the table per VDSL port."
			::= { zhoneDsl 14 }

		
		-- 1.3.6.1.4.1.5504.5.4.14.1
		zhoneVdslControlEntry OBJECT-TYPE
			SYNTAX ZhoneVdslControlEntry
			MAX-ACCESS not-accessible
			STATUS obsolete
			DESCRIPTION
				"VDSL provisioning table entry definitions."
			INDEX { ifIndex }
			::= { zhoneVdslControlTable 1 }

		
		ZhoneVdslControlEntry ::=
			SEQUENCE { 
				zhoneVdslControlMode
					INTEGER,
				zhoneVdslControlPlan
					INTEGER,
				zhoneVdslControlUsPbo
					INTEGER,
				zhoneVdslControlDsSymRateSel
					INTEGER,
				zhoneVdslControlDsMinMargin
					Integer32,
				zhoneVdslControlDsBerLimit
					INTEGER,
				zhoneVdslControlDsMaxRate
					Integer32,
				zhoneVdslControlDsMaxConst
					INTEGER,
				zhoneVdslControlDsRsFrame
					INTEGER,
				zhoneVdslControlUsSymRateSel
					INTEGER,
				zhoneVdslControlUsMinMargin
					Integer32,
				zhoneVdslControlUsBerLimit
					INTEGER,
				zhoneVdslControlUsMaxRate
					Integer32,
				zhoneVdslControlUsMaxConst
					INTEGER,
				zhoneVdslControlUsRsFrame
					INTEGER
			 }

-- 
-- 
		-- 1.3.6.1.4.1.5504.5.4.14.1.1
		zhoneVdslControlMode OBJECT-TYPE
			SYNTAX INTEGER
				{
				vtu-o(1),
				vtu-r(2)
				}
			MAX-ACCESS read-write
			STATUS obsolete
			DESCRIPTION
				"Set to vtu-r(2) for customer premise equipment.  
				Set to vtu-o(1) for central office."
			DEFVAL { vtu-o }
			::= { zhoneVdslControlEntry 1 }

		
		-- 1.3.6.1.4.1.5504.5.4.14.1.2
		zhoneVdslControlPlan OBJECT-TYPE
			SYNTAX INTEGER
				{
				plan-998-l(1),
				plan-997-l(2),
				asym-vdsl-1(3),
				asym-vdsl-2(4),
				asym-vdsl-3(5)
				}
			MAX-ACCESS read-write
			STATUS obsolete
			DESCRIPTION
				"VDSL spectral plan. Values:
				    Plan_998_L
				        Low frequency band, US standard.
				        Optimal performance.
				    Plan_997_L
				        Low frequency band, European standard.
				        Reduced performance.
				    Asym_Vdsl_1
				        Not currently supported.
				    Asym_Vdsl_2
				        Not currently supported.
				    Asym_Vdsl_3
				        Not currently supported."
			DEFVAL { plan-998-l }
			::= { zhoneVdslControlEntry 2 }

		
		-- 1.3.6.1.4.1.5504.5.4.14.1.3
		zhoneVdslControlUsPbo OBJECT-TYPE
			SYNTAX INTEGER
				{
				upstream-power-backoff-enable(1),
				upstream-power-backoff-disable(2)
				}
			MAX-ACCESS read-write
			STATUS obsolete
			DESCRIPTION
				"Upstream power back-off enable for the VTU-R."
			DEFVAL { upstream-power-backoff-enable }
			::= { zhoneVdslControlEntry 3 }

		
		-- 1.3.6.1.4.1.5504.5.4.14.1.4
		zhoneVdslControlDsSymRateSel OBJECT-TYPE
			SYNTAX INTEGER
				{
				ds-sym-rate-sel-bit-0(1),
				ds-sym-rate-sel-bit-1(2),
				ds-sym-rate-sel-bit-2(4),
				ds-sym-rate-sel-bit-3(8),
				ds-sym-rate-sel-bit-4(16),
				ds-sym-rate-sel-bit-5(32),
				ds-sym-rate-sel-bit-6(64),
				ds-sym-rate-sel-bit-7(128)
				}
			MAX-ACCESS read-write
			STATUS obsolete
			DESCRIPTION
				"Select symbol rates to use by the rate 
				adaptive algorithm.  There are eight 
				optional downstream symbol rates, and 
				each one can be individually selected 
				or deselected by toggling a bit within 
				this parameter."
			DEFVAL { ds-sym-rate-sel-bit-7 }
			::= { zhoneVdslControlEntry 4 }

		
		-- 1.3.6.1.4.1.5504.5.4.14.1.5
		zhoneVdslControlDsMinMargin OBJECT-TYPE
			SYNTAX Integer32 (0..255)
			UNITS "0.125 dB"
			MAX-ACCESS read-write
			STATUS obsolete
			DESCRIPTION
				"Minimum downstream SNR margin (in dB times 8), 
				for SNR measured at QPSK, used to compute 
				maximum constellation size for each symbol rate.
				
				Values are entered in 1/8th of a dB.  The default
				value (24) yields a margin of 3.0dB."
			DEFVAL { 24 }
			::= { zhoneVdslControlEntry 5 }

		
		-- 1.3.6.1.4.1.5504.5.4.14.1.6
		zhoneVdslControlDsBerLimit OBJECT-TYPE
			SYNTAX INTEGER
				{
				one-e-minus-03(1),
				one-e-minus-04(2),
				one-e-minus-05(3),
				one-e-minus-06(4)
				}
			MAX-ACCESS read-write
			STATUS obsolete
			DESCRIPTION
				"Maximum allowable bit error rate prior
				to forward error correction.
				
				Values: 1E-03 to 1E-06."
			DEFVAL { one-e-minus-05 }
			::= { zhoneVdslControlEntry 6 }

		
		-- 1.3.6.1.4.1.5504.5.4.14.1.7
		zhoneVdslControlDsMaxRate OBJECT-TYPE
			SYNTAX Integer32
			UNITS "Mbps / 1000"
			MAX-ACCESS read-write
			STATUS obsolete
			DESCRIPTION
				"Equals target downstream line rate, in Mbps,
				that the software will attempt to achieve.
				If this cannot be done subject to other 
				constraints, the highest achievable rates 
				instead will be delivered.  The delivered
				downstream line rate may be less than, equal
				to, or greater than DsMaxRate."
			DEFVAL { 207900 }
			::= { zhoneVdslControlEntry 7 }

		
		-- 1.3.6.1.4.1.5504.5.4.14.1.8
		zhoneVdslControlDsMaxConst OBJECT-TYPE
			SYNTAX INTEGER
				{
				qam-4(1),
				qam-8(2),
				qam-16(3),
				qam-32(4),
				qam-64(5),
				qam-128(6),
				qam-256(7)
				}
			MAX-ACCESS read-write
			STATUS obsolete
			DESCRIPTION
				"Restrict downstream constellations to use those that 
				do not exceed this maximum.
				
				Values: QAM-4, QAM-8, QAM-16, QAM-32, QAM-64,
				        QAM-128, QAM-256."
			DEFVAL { qam-128 }
			::= { zhoneVdslControlEntry 8 }

		
		-- 1.3.6.1.4.1.5504.5.4.14.1.9
		zhoneVdslControlDsRsFrame OBJECT-TYPE
			SYNTAX INTEGER
				{
				rs-1-1-1(1),
				rs-255-239-1(2),
				rs-255-239-16(3),
				rs-142-126-29(4),
				rs-255-239-143(5),
				rs-193-177-191(6)
				}
			MAX-ACCESS read-write
			STATUS obsolete
			DESCRIPTION
				"Input: specifies the desired final value for 
				       downstream Reed-Solomon code word size 
				       and interleaving depth.
				
				Output: specifies the final downstream RS 
				        parameters that are actually used."
			DEFVAL { rs-255-239-143 }
			::= { zhoneVdslControlEntry 9 }

		
		-- 1.3.6.1.4.1.5504.5.4.14.1.10
		zhoneVdslControlUsSymRateSel OBJECT-TYPE
			SYNTAX INTEGER
				{
				us-sym-rate-sel-bit-0(1),
				us-sym-rate-sel-bit-1(2),
				us-sym-rate-sel-bit-2(4),
				us-sym-rate-sel-bit-3(8),
				us-sym-rate-sel-bit-4(16),
				us-sym-rate-sel-bit-5(32),
				us-sym-rate-sel-bit-6(64),
				us-sym-rate-sel-bit-7(128)
				}
			MAX-ACCESS read-write
			STATUS obsolete
			DESCRIPTION
				"Select symbol rates to use by the rate 
				adaptive algorithm.  There are eight 
				optional upstream symbol rates, and each
				one can be individually selected or 
				deselected by toggling a bit within this 
				parameter."
			DEFVAL { us-sym-rate-sel-bit-7 }
			::= { zhoneVdslControlEntry 10 }

		
		-- 1.3.6.1.4.1.5504.5.4.14.1.11
		zhoneVdslControlUsMinMargin OBJECT-TYPE
			SYNTAX Integer32 (0..255)
			UNITS "0.125 dB"
			MAX-ACCESS read-write
			STATUS obsolete
			DESCRIPTION
				"Equals the minimum upstream SNR margin, for 
				SNR measured at QPSK, used to compute maximum 
				constellation size.
				
				Values are entered in 1/8th of a dB.  The default
				value (24) yields a margin of 3.0dB."
			DEFVAL { 24 }
			::= { zhoneVdslControlEntry 11 }

		
		-- 1.3.6.1.4.1.5504.5.4.14.1.12
		zhoneVdslControlUsBerLimit OBJECT-TYPE
			SYNTAX INTEGER
				{
				one-e-minus-03(1),
				one-e-minus-04(2),
				one-e-minus-05(3),
				one-e-minus-06(4)
				}
			MAX-ACCESS read-write
			STATUS obsolete
			DESCRIPTION
				"Maximum allowable bit error rate prior
				to forward error correction.
				
				Values: 1E-03 to 1E-06."
			DEFVAL { one-e-minus-05 }
			::= { zhoneVdslControlEntry 12 }

		
		-- 1.3.6.1.4.1.5504.5.4.14.1.13
		zhoneVdslControlUsMaxRate OBJECT-TYPE
			SYNTAX Integer32
			UNITS "Mbps / 1000"
			MAX-ACCESS read-write
			STATUS obsolete
			DESCRIPTION
				"Equals target upstream line rate, in Mbps,
				that the software will attempt to achieve.
				If this cannot be done subject to other 
				constraints, the highest achievable rates 
				instead will be delivered.  The delivered
				downstream line rate may be less than, equal
				to, or greater than UsMaxRate."
			DEFVAL { 70875 }
			::= { zhoneVdslControlEntry 13 }

		
		-- 1.3.6.1.4.1.5504.5.4.14.1.14
		zhoneVdslControlUsMaxConst OBJECT-TYPE
			SYNTAX INTEGER
				{
				qam-4(1),
				qam-8(2),
				qam-16(3),
				qam-32(4),
				qam-64(5),
				qam-128(6),
				qam-256(7)
				}
			MAX-ACCESS read-write
			STATUS obsolete
			DESCRIPTION
				"Restrict upstream constellations to use those that 
				do not exceed this maximum.
				
				Values: QAM-4, QAM-8, QAM-16, QAM-32, QAM-64,
				        QAM-128, QAM-256"
			DEFVAL { qam-128 }
			::= { zhoneVdslControlEntry 14 }

		
		-- 1.3.6.1.4.1.5504.5.4.14.1.15
		zhoneVdslControlUsRsFrame OBJECT-TYPE
			SYNTAX INTEGER
				{
				rs-1-1-1(1),
				rs-255-239-1(2),
				rs-255-239-16(3),
				rs-142-126-29(4),
				rs-255-239-143(5),
				rs-193-177-191(6)
				}
			MAX-ACCESS read-write
			STATUS obsolete
			DESCRIPTION
				"Input: specifies the desired final value for 
				       upstream Reed-Solomon code word size 
				       and interleaving depth.
				
				Output: specifies the final upstream RS 
				        parameters that are actually used."
			DEFVAL { rs-255-239-143 }
			::= { zhoneVdslControlEntry 15 }

		
		-- 1.3.6.1.4.1.5504.5.4.15
		zhoneVdslStatusTable OBJECT-TYPE
			SYNTAX SEQUENCE OF ZhoneVdslStatusEntry
			MAX-ACCESS not-accessible
			STATUS obsolete
			DESCRIPTION
				"This table provides VDSL specific status 
				information.  Table is indexed by ifIndex.
				The rows in this table are not creatable/
				deletable.  There is only one entry in the 
				table per VDSL port."
			::= { zhoneDsl 15 }

		
		-- 1.3.6.1.4.1.5504.5.4.15.1
		zhoneVdslStatusEntry OBJECT-TYPE
			SYNTAX ZhoneVdslStatusEntry
			MAX-ACCESS not-accessible
			STATUS obsolete
			DESCRIPTION
				"VDSL status table entry definitions."
			INDEX { ifIndex }
			::= { zhoneVdslStatusTable 1 }

		
		ZhoneVdslStatusEntry ::=
			SEQUENCE { 
				zhoneVdslStatusLineState
					INTEGER,
				zhoneVdslStatusDsLineRate
					Integer32,
				zhoneVdslStatusDsSnr
					Integer32,
				zhoneVdslStatusDsConst
					Integer32,
				zhoneVdslStatusDsRsFinal
					Integer32,
				zhoneVdslStatusUsLineRate
					Integer32,
				zhoneVdslStatusUsSnr
					Integer32,
				zhoneVdslStatusUsConst
					Integer32,
				zhoneVdslStatusUsRsFinal
					Integer32
			 }

		-- 1.3.6.1.4.1.5504.5.4.15.1.1
		zhoneVdslStatusLineState OBJECT-TYPE
			SYNTAX INTEGER
				{
				idle(1),
				training(2),
				active(3),
				loopback(4)
				}
			MAX-ACCESS read-only
			STATUS obsolete
			DESCRIPTION
				"Line status for a VDSL channel."
			::= { zhoneVdslStatusEntry 1 }

		
		-- 1.3.6.1.4.1.5504.5.4.15.1.2
		zhoneVdslStatusDsLineRate OBJECT-TYPE
			SYNTAX Integer32 (0..65535)
			MAX-ACCESS read-only
			STATUS obsolete
			DESCRIPTION
				"Measured downstream line rate."
			::= { zhoneVdslStatusEntry 2 }

		
		-- 1.3.6.1.4.1.5504.5.4.15.1.3
		zhoneVdslStatusDsSnr OBJECT-TYPE
			SYNTAX Integer32
			MAX-ACCESS read-only
			STATUS obsolete
			DESCRIPTION
				"Measured downstream EQ output SNR (in dB times 8)."
			::= { zhoneVdslStatusEntry 3 }

		
		-- 1.3.6.1.4.1.5504.5.4.15.1.4
		zhoneVdslStatusDsConst OBJECT-TYPE
			SYNTAX Integer32
			MAX-ACCESS read-only
			STATUS obsolete
			DESCRIPTION
				"Downstream constellation size in use."
			::= { zhoneVdslStatusEntry 4 }

		
		-- 1.3.6.1.4.1.5504.5.4.15.1.5
		zhoneVdslStatusDsRsFinal OBJECT-TYPE
			SYNTAX Integer32
			MAX-ACCESS read-only
			STATUS obsolete
			DESCRIPTION
				"Downstream Reed-Solomon code word and depth."
			::= { zhoneVdslStatusEntry 5 }

		
		-- 1.3.6.1.4.1.5504.5.4.15.1.6
		zhoneVdslStatusUsLineRate OBJECT-TYPE
			SYNTAX Integer32
			MAX-ACCESS read-only
			STATUS obsolete
			DESCRIPTION
				"Measured upstream line rate."
			::= { zhoneVdslStatusEntry 6 }

		
		-- 1.3.6.1.4.1.5504.5.4.15.1.7
		zhoneVdslStatusUsSnr OBJECT-TYPE
			SYNTAX Integer32
			MAX-ACCESS read-only
			STATUS obsolete
			DESCRIPTION
				"Measured upstream EQ output SNR (in dB times 8)."
			::= { zhoneVdslStatusEntry 7 }

		
		-- 1.3.6.1.4.1.5504.5.4.15.1.8
		zhoneVdslStatusUsConst OBJECT-TYPE
			SYNTAX Integer32
			MAX-ACCESS read-only
			STATUS obsolete
			DESCRIPTION
				"Upstream constellation size in use."
			::= { zhoneVdslStatusEntry 8 }

		
		-- 1.3.6.1.4.1.5504.5.4.15.1.9
		zhoneVdslStatusUsRsFinal OBJECT-TYPE
			SYNTAX Integer32
			MAX-ACCESS read-only
			STATUS obsolete
			DESCRIPTION
				"Upstream Reed-Solomon code word and depth."
			::= { zhoneVdslStatusEntry 9 }

		
		-- 1.3.6.1.4.1.5504.5.4.16
		zhoneVdslPerfMonTable OBJECT-TYPE
			SYNTAX SEQUENCE OF ZhoneVdslPerfMonEntry
			MAX-ACCESS not-accessible
			STATUS obsolete
			DESCRIPTION
				"This table contains performance data for
				VDSL ports in the system.  The rows in 
				this table are not creatable/deletable.  
				There is only one entry in the table per 
				VDSL port."
			::= { zhoneDsl 16 }

		
		-- 1.3.6.1.4.1.5504.5.4.16.1
		zhoneVdslPerfMonEntry OBJECT-TYPE
			SYNTAX ZhoneVdslPerfMonEntry
			MAX-ACCESS not-accessible
			STATUS obsolete
			DESCRIPTION
				"VDSL Performance Monitoring table entry definitions."
			INDEX { ifIndex }
			::= { zhoneVdslPerfMonTable 1 }

		
		ZhoneVdslPerfMonEntry ::=
			SEQUENCE { 
				zhoneVdslPerfMonDsCorrOctets
					Counter32,
				zhoneVdslPerfMonDsUncorrOctets
					Counter32,
				zhoneVdslPerfMonUsCorrOctets
					Counter32,
				zhoneVdslPerfMonUsUncorrOctets
					Counter32
			 }

		-- 1.3.6.1.4.1.5504.5.4.16.1.1
		zhoneVdslPerfMonDsCorrOctets OBJECT-TYPE
			SYNTAX Counter32
			MAX-ACCESS read-only
			STATUS obsolete
			DESCRIPTION
				"Number of errored octets corrected by Reed-
				Solomon in the downstream channel."
			::= { zhoneVdslPerfMonEntry 1 }

		
		-- 1.3.6.1.4.1.5504.5.4.16.1.2
		zhoneVdslPerfMonDsUncorrOctets OBJECT-TYPE
			SYNTAX Counter32
			MAX-ACCESS read-only
			STATUS obsolete
			DESCRIPTION
				"Number of uncorrectable octets in the 
				downstream channel."
			::= { zhoneVdslPerfMonEntry 2 }

		
		-- 1.3.6.1.4.1.5504.5.4.16.1.3
		zhoneVdslPerfMonUsCorrOctets OBJECT-TYPE
			SYNTAX Counter32
			MAX-ACCESS read-only
			STATUS obsolete
			DESCRIPTION
				"Number of errored octets corrected by Reed-
				Solomon in the upstream channel."
			::= { zhoneVdslPerfMonEntry 3 }

		
		-- 1.3.6.1.4.1.5504.5.4.16.1.4
		zhoneVdslPerfMonUsUncorrOctets OBJECT-TYPE
			SYNTAX Counter32
			MAX-ACCESS read-only
			STATUS obsolete
			DESCRIPTION
				"Number of uncorrectable octets in the 
				upstream channel."
			::= { zhoneVdslPerfMonEntry 4 }

		
		-- 1.3.6.1.4.1.5504.5.4.17
		zhoneAdslAtucPerfTable OBJECT-TYPE
			SYNTAX SEQUENCE OF ZhoneAdslAtucPerfEntry
			MAX-ACCESS not-accessible
			STATUS current
			DESCRIPTION
				"This table is an extension to rfc2662. It provides additional
				Atuc statistical counters for ADSL."
			::= { zhoneDsl 17 }

		
		-- 1.3.6.1.4.1.5504.5.4.17.1
		zhoneAdslAtucPerfEntry OBJECT-TYPE
			SYNTAX ZhoneAdslAtucPerfEntry
			MAX-ACCESS not-accessible
			STATUS current
			DESCRIPTION
				"Adsl extension Atuc counters definition."
			INDEX { ifIndex }
			::= { zhoneAdslAtucPerfTable 1 }

		
		ZhoneAdslAtucPerfEntry ::=
			SEQUENCE { 
				zhoneAdslAtucPerfErrorInterleaved
					Counter32,
				zhoneAdslAtucPerfErrorFast
					Counter32,
				zhoneAdslAtucPerfFecCorrectedInterleaved
					Counter32,
				zhoneAdslAtucPerfFecCorrectedFast
					Counter32,
				zhoneAdslAtucPerfBackgroundErrorBlks
					Counter32,
				zhoneAdslAtucPerfNonSESBlks
					Counter32,
				zhoneAdslAtucPerfFastRetrains
					Counter32,
				zhoneAdslAtucPerfFastRetrainFailures
					Counter32,
				zhoneAdslAtucPerfSuccessfulConnects
					Counter32,
				zhoneAdslAtucPerfDisconnects
					Counter32,
				zhoneAdslAtucPerfSESs
					Counter32,
				zhoneAdslAtucPerfUASs
					Counter32,
				zhoneAdslAtucPerfFECs
					Counter32,
				zhoneAdslAtucPerfSECs
					Counter32,
				zhoneAdslAtucPerfHiBERs
					Counter32,
				zhoneAdslAtucPerfLOSS
					Counter32,
				zhoneAdslAtucPerfStatFecsL
					Counter32,
				zhoneAdslAtucPerfCurr15MinFecsL
					Counter32,
				zhoneAdslAtucPerfCurr1DayFecsL
					Counter32,
				zhoneAdslAtucPerfPrev1DayFecsL
					Counter32,
				zhoneAdslAtucPerfStatLossL
					Counter32,
				zhoneAdslAtucChanPerfCD
					Counter32,
				zhoneAdslAtucChanPerfCU
					Counter32,
				zhoneAdslAtucChanPerfBE
					Counter32,
				zhoneAdslAtucActualTxMode
					INTEGER,
				zhoneAdslAtucPhyrRetransmittedCodewords
					Counter32,
				zhoneAdslAtucPhyrCorrectedRetransmittedCodewords
					Counter32,
				zhoneAdslAtucPhyrUncorrectableRetransmittedCodewords 
					Counter32,
				zhoneAdslAtucPhyrCurr15MinRetransmittedCodewords
					Counter32,
				zhoneAdslAtucPhyrCurr15MinCorrectedRetransmittedCodewords
					Counter32,
				zhoneAdslAtucPhyrCurr15MinUncorrectableRetransmittedCodewords
					Counter32,
				zhoneAdslAtucPhyrCurr1DayRetransmittedCodewords
					Counter32,
				zhoneAdslAtucPhyrCurr1DayCorrectedRetransmittedCodewords
					Counter32,
				zhoneAdslAtucPhyrCurr1DayUncorrectableRetransmittedCodewords
					Counter32,
				zhoneAdslAtucPhyrPrev1DayRetransmittedCodewords
					Counter32,
				zhoneAdslAtucPhyrPrev1DayCorrectedRetransmittedCodewords
					Counter32,
				zhoneAdslAtucPhyrPrev1DayUncorrectableRetransmittedCodewords
					Counter32,
				zhoneAdslAtucPhyRActive
					TruthValue,
				zhoneAdslAtucGinpLeftrSecs
					Counter32,
				zhoneAdslAtucGinpErrorFreeBits
					Counter32,
				zhoneAdslAtucGinpMinEftr
					Counter32,
				zhoneAdslAtucGinpCurr15MinLeftrSecs
					Counter32,
				zhoneAdslAtucGinpCurr15MinErrorFreeBits
					Counter32,
				zhoneAdslAtucGinpCurr15MinMinEftr
					Counter32,
				zhoneAdslAtucGinpCurr1DayLeftrSecs
					Counter32,
				zhoneAdslAtucGinpCurr1DayErrorFreeBits
					Counter32,
				zhoneAdslAtucGinpCurr1DayMinEftr
					Counter32,
				zhoneAdslAtucGinpPrev1DayLeftrSecs
					Counter32,
				zhoneAdslAtucGinpPrev1DayErrorFreeBits
					Counter32,
				zhoneAdslAtucGinpPrev1DayMinEftr
					Counter32,
				zhoneAdslAtucGinpActive
					TruthValue
			 }

		-- 1.3.6.1.4.1.5504.5.4.17.1.1
		zhoneAdslAtucPerfErrorInterleaved OBJECT-TYPE
			SYNTAX Counter32
			MAX-ACCESS read-only
			STATUS current
			DESCRIPTION
				"crc errors on interleaved buffer at near end."
			::= { zhoneAdslAtucPerfEntry 1 }

		
		-- 1.3.6.1.4.1.5504.5.4.17.1.2
		zhoneAdslAtucPerfErrorFast OBJECT-TYPE
			SYNTAX Counter32
			MAX-ACCESS read-only
			STATUS current
			DESCRIPTION
				"crc errors on fast buffer at near end."
			::= { zhoneAdslAtucPerfEntry 2 }

		
		-- 1.3.6.1.4.1.5504.5.4.17.1.3
		zhoneAdslAtucPerfFecCorrectedInterleaved OBJECT-TYPE
			SYNTAX Counter32
			MAX-ACCESS read-only
			STATUS current
			DESCRIPTION
				"FEC corrections on interleaved buffer at near end."
			::= { zhoneAdslAtucPerfEntry 3 }

		
		-- 1.3.6.1.4.1.5504.5.4.17.1.4
		zhoneAdslAtucPerfFecCorrectedFast OBJECT-TYPE
			SYNTAX Counter32
			MAX-ACCESS read-only
			STATUS current
			DESCRIPTION
				"FEC corrections on fast buffer at near end."
			::= { zhoneAdslAtucPerfEntry 4 }

		
		-- 1.3.6.1.4.1.5504.5.4.17.1.5
		zhoneAdslAtucPerfBackgroundErrorBlks OBJECT-TYPE
			SYNTAX Counter32
			MAX-ACCESS read-only
			STATUS current
			DESCRIPTION
				"background errored blocks at near end."
			::= { zhoneAdslAtucPerfEntry 5 }

		
		-- 1.3.6.1.4.1.5504.5.4.17.1.6
		zhoneAdslAtucPerfNonSESBlks OBJECT-TYPE
			SYNTAX Counter32
			MAX-ACCESS read-only
			STATUS current
			DESCRIPTION
				"non SES blocks received at the near end."
			::= { zhoneAdslAtucPerfEntry 6 }

		
		-- 1.3.6.1.4.1.5504.5.4.17.1.7
		zhoneAdslAtucPerfFastRetrains OBJECT-TYPE
			SYNTAX Counter32
			MAX-ACCESS read-only
			STATUS current
			DESCRIPTION
				"fast retrains."
			::= { zhoneAdslAtucPerfEntry 7 }

		
		-- 1.3.6.1.4.1.5504.5.4.17.1.8
		zhoneAdslAtucPerfFastRetrainFailures OBJECT-TYPE
			SYNTAX Counter32
			MAX-ACCESS read-only
			STATUS current
			DESCRIPTION
				"fast retrains failures."
			::= { zhoneAdslAtucPerfEntry 8 }

		
		-- 1.3.6.1.4.1.5504.5.4.17.1.9
		zhoneAdslAtucPerfSuccessfulConnects OBJECT-TYPE
			SYNTAX Counter32
			MAX-ACCESS read-only
			STATUS current
			DESCRIPTION
				"successful connects."
			::= { zhoneAdslAtucPerfEntry 9 }

		
		-- 1.3.6.1.4.1.5504.5.4.17.1.10
		zhoneAdslAtucPerfDisconnects OBJECT-TYPE
			SYNTAX Counter32
			MAX-ACCESS read-only
			STATUS current
			DESCRIPTION
				"number of disconnects."
			::= { zhoneAdslAtucPerfEntry 10 }

		
		-- 1.3.6.1.4.1.5504.5.4.17.1.11
		zhoneAdslAtucPerfSESs OBJECT-TYPE
			SYNTAX Counter32
			MAX-ACCESS read-only
			STATUS current
			DESCRIPTION
				"Severely errored seconds at the near end."
			::= { zhoneAdslAtucPerfEntry 11 }

		
		-- 1.3.6.1.4.1.5504.5.4.17.1.12
		zhoneAdslAtucPerfUASs OBJECT-TYPE
			SYNTAX Counter32
			MAX-ACCESS read-only
			STATUS current
			DESCRIPTION
				"Unavailable seconds at the near end."
			::= { zhoneAdslAtucPerfEntry 12 }

		
		-- 1.3.6.1.4.1.5504.5.4.17.1.13
		zhoneAdslAtucPerfFECs OBJECT-TYPE
			SYNTAX Counter32
			MAX-ACCESS read-only
			STATUS current
			DESCRIPTION
				"Seconds with one or more FECs at the near end."
			::= { zhoneAdslAtucPerfEntry 13 }

		
		-- 1.3.6.1.4.1.5504.5.4.17.1.14
		zhoneAdslAtucPerfSECs OBJECT-TYPE
			SYNTAX Counter32
			MAX-ACCESS read-only
			STATUS current
			DESCRIPTION
				"Elapsed seconds at the near end."
			::= { zhoneAdslAtucPerfEntry 14 }

		
		-- 1.3.6.1.4.1.5504.5.4.17.1.15
		zhoneAdslAtucPerfHiBERs OBJECT-TYPE
			SYNTAX Counter32
			MAX-ACCESS read-only
			STATUS current
			DESCRIPTION
				"Seconds declared as hi BER by the near end."
			::= { zhoneAdslAtucPerfEntry 15 }

		
		-- 1.3.6.1.4.1.5504.5.4.17.1.16
		zhoneAdslAtucPerfLOSS OBJECT-TYPE
			SYNTAX Counter32
			MAX-ACCESS read-only
			STATUS current
			DESCRIPTION
				"loss of signal seconds at the near end."
			::= { zhoneAdslAtucPerfEntry 16 }

		
		-- 1.3.6.1.4.1.5504.5.4.17.1.17
		zhoneAdslAtucPerfStatFecsL OBJECT-TYPE
			SYNTAX Counter32
			MAX-ACCESS read-only
			STATUS current
			DESCRIPTION
				"Count of 1-second intervals with one or more forward
				error correction (FEC) anomalies since agent reset.
				
				
				Supported for ADSL2/ADSL2plus Only.
				Not available for ADSL."
			::= { zhoneAdslAtucPerfEntry 17 }

		
		-- 1.3.6.1.4.1.5504.5.4.17.1.18
		zhoneAdslAtucPerfCurr15MinFecsL OBJECT-TYPE
			SYNTAX Counter32
			MAX-ACCESS read-only
			STATUS current
			DESCRIPTION
				"Count of 1-second intervals, in the current 15 minute
				interval, with one or more forward error correction
				(FEC) anomalies.
				
				
				Supported for ADSL2/ADSL2plus Only.
				Not available for ADSL."
			::= { zhoneAdslAtucPerfEntry 18 }

		
		-- 1.3.6.1.4.1.5504.5.4.17.1.19
		zhoneAdslAtucPerfCurr1DayFecsL OBJECT-TYPE
			SYNTAX Counter32
			MAX-ACCESS read-only
			STATUS current
			DESCRIPTION
				"Count of 1-second intervals, during the current day as
				measured by adslAtucPerfCurr1Day-TimeElapsed, with one or
				more forward error correction (FEC) anomalies.
				
				
				Supported for ADSL2/ADSL2plus Only.
				Not available for ADSL."
			::= { zhoneAdslAtucPerfEntry 19 }

		
		-- 1.3.6.1.4.1.5504.5.4.17.1.20
		zhoneAdslAtucPerfPrev1DayFecsL OBJECT-TYPE
			SYNTAX Counter32
			MAX-ACCESS read-only
			STATUS current
			DESCRIPTION
				"Count of 1-second intervals, within the most recent
				previous 1-day period, with one or more forward error
				correction (FEC) anomalies.
				
				
				Supported for ADSL2/ADSL2plus Only.
				Not available for ADSL."
			::= { zhoneAdslAtucPerfEntry 20 }

		
		-- 1.3.6.1.4.1.5504.5.4.17.1.21
		zhoneAdslAtucPerfStatLossL OBJECT-TYPE
			SYNTAX Counter32
			MAX-ACCESS read-only
			STATUS current
			DESCRIPTION
				"Count of 1-second intervals containing one or more loss
				of signal (LOS) defects.
				
				
				Supported for ADSL2/ADSL2plus Only.
				Not available for ADSL."
			::= { zhoneAdslAtucPerfEntry 21 }

		
		-- 1.3.6.1.4.1.5504.5.4.17.1.22
		zhoneAdslAtucChanPerfCD OBJECT-TYPE
			SYNTAX Counter32
			MAX-ACCESS read-only
			STATUS current
			DESCRIPTION
				"Near-end delineated total cell count.
				
				The near-end delineated total cell count performance
				parameter is a count of the total number of cells passed
				through the cell delineation and HEC function process
				operating on the ATM Data Path while in the SYNC state.
				
				Supported for ADSL2/ADSL2plus Only.
				Not available for ADSL."
			::= { zhoneAdslAtucPerfEntry 22 }

		
		-- 1.3.6.1.4.1.5504.5.4.17.1.23
		zhoneAdslAtucChanPerfCU OBJECT-TYPE
			SYNTAX Counter32
			MAX-ACCESS read-only
			STATUS current
			DESCRIPTION
				"This parameter returns a count of the total number of
				data-only cells received by the ATU-C
				
				The near-end user total cell count performance parameter
				is a count of the total number of cells in the ATM Data
				Path delivered at the V-C (for ATU-C) or T-R (for ATU-R)
				interface.
				
				Supported for ADSL2/ADSL2plus Only.
				Not available for ADSL.
				"
			::= { zhoneAdslAtucPerfEntry 23 }

		
		-- 1.3.6.1.4.1.5504.5.4.17.1.24
		zhoneAdslAtucChanPerfBE OBJECT-TYPE
			SYNTAX Counter32
			MAX-ACCESS read-only
			STATUS current
			DESCRIPTION
				"Near end idle cell bit error count.
				
				The near-end idle bit error count performance parameter is
				a count of the number of bit errors in the idle cell
				payload received in the ATM Data Path at the near-end.
				
				Supported for ADSL2/ADSL2plus Only.
				Not available for ADSL."
			::= { zhoneAdslAtucPerfEntry 24 }

		
		-- 1.3.6.1.4.1.5504.5.4.17.1.25
		zhoneAdslAtucActualTxMode OBJECT-TYPE
			SYNTAX INTEGER
				{
				unknownMode(1),
				t1413Mode(2),
				alctl14Mode(3),
				alctlMode(4),
				adiMode(5),
				gdmtMode(6),
				gliteMode(7),
				gadslPlusMode(8),
				gspanPlusMode(9),
				adsl2PlusMode(10),
				adsl2Mode(11),
				readsl2Mode(12),
				uawgMode(13),
				centLiteMode(14),
				centFullMode(15),
				tiAnnBMode(16),
				alctAnnBMode(17),
				reachDslMode(18),
				adsl2PlusAnnexMMode(19),
				adsl2AnnexMMode(20)
				}
			MAX-ACCESS read-only
			STATUS current
			DESCRIPTION
				"This field provides actual standard used for the connection
				 based on outcome of negotiation with ATU-R. Possible values:
				  unknownMode(1), unknown mode or no connection made.
				  T1413Mode(2), connection using T1.413 standard.
				  alctl14Mode(3), connection with Alcatel 14 CPE.
				  alctlMode(4), connection with Alcatel CPE.
				  adiMode(5), connection with Analog Device CPE.
				  gdmtMode(6), connection using G.dmt standard.
				  gliteMode(7), connection using G.lite standard.
				  gadslPlusMode(8), connection using ADSL+ standard.
				  gspanPlusMode(9), connection with GlobeSpan+ CPE.
				  adsl2PlusMode(10), connection using ADSL2+ standard.
				  adsl2Mode(11), connection using ADSL2 standard.
				  readsl2Mode(12), connection using Reach Extended ADSL2 standard.
				  uawgMode(13), connection with UAWG (Universal ADSL Working Group) type CPE.
				  centLiteMode(14), connection with Centillium G.Lite CPE.
				  centFullMode(15), connection with Centillium CPE.
				  tiAnnBMode(16),connection with TI AnnexB CPE.
				  alctAnnBMode(17), connection with Alcatel AnnexB CPE.
				  reachDSLMode(18), connection with Paradyne ReachDSL CPE.
				  adsl2PlusAnnexMMode(19), connection using ADSL2+ and Annex-M standards.
				  adsl2AnnexMMode(20), connection using ADSL2 and Annex-M standards."
			::= { zhoneAdslAtucPerfEntry 25 }

		
		-- 1.3.6.1.4.1.5504.5.4.17.1.26
		zhoneAdslAtucPhyrRetransmittedCodewords OBJECT-TYPE
			SYNTAX Counter32
			MAX-ACCESS read-only
			STATUS current
			DESCRIPTION
				"Retransmitted codewords."
			::= { zhoneAdslAtucPerfEntry 26 }

		
		-- 1.3.6.1.4.1.5504.5.4.17.1.27
		zhoneAdslAtucPhyrCorrectedRetransmittedCodewords OBJECT-TYPE
			SYNTAX Counter32
			MAX-ACCESS read-only
			STATUS current
			DESCRIPTION
				"Retransmitted corrected codewords."
			::= { zhoneAdslAtucPerfEntry 27 }

		
		-- 1.3.6.1.4.1.5504.5.4.17.1.28
		zhoneAdslAtucPhyrUncorrectableRetransmittedCodewords  OBJECT-TYPE
			SYNTAX Counter32
			MAX-ACCESS read-only
			STATUS current
			DESCRIPTION
				"Retransmitted uncorrectable codewords."
			::= { zhoneAdslAtucPerfEntry 28 }

		
		-- 1.3.6.1.4.1.5504.5.4.17.1.29
		zhoneAdslAtucPhyrCurr15MinRetransmittedCodewords OBJECT-TYPE
			SYNTAX Counter32
			MAX-ACCESS read-only
			STATUS current
			DESCRIPTION
				"Current 15 minutes Retransmitted codewords."
			::= { zhoneAdslAtucPerfEntry 29 }

		
		-- 1.3.6.1.4.1.5504.5.4.17.1.30
		zhoneAdslAtucPhyrCurr15MinCorrectedRetransmittedCodewords OBJECT-TYPE
			SYNTAX Counter32
			MAX-ACCESS read-only
			STATUS current
			DESCRIPTION
				"Current 15 minutes Retransmitted corrected codewords."
			::= { zhoneAdslAtucPerfEntry 30 }

		
		-- 1.3.6.1.4.1.5504.5.4.17.1.31
		zhoneAdslAtucPhyrCurr15MinUncorrectableRetransmittedCodewords OBJECT-TYPE
			SYNTAX Counter32
			MAX-ACCESS read-only
			STATUS current
			DESCRIPTION
				"Current 15 minutes Retransmitted uncorrectable codewords."
			::= { zhoneAdslAtucPerfEntry 31 }

		
		-- 1.3.6.1.4.1.5504.5.4.17.1.32
		zhoneAdslAtucPhyrCurr1DayRetransmittedCodewords OBJECT-TYPE
			SYNTAX Counter32
			MAX-ACCESS read-only
			STATUS current
			DESCRIPTION
				"Current Day Retransmitted codewords."
			::= { zhoneAdslAtucPerfEntry 32 }

		
		-- 1.3.6.1.4.1.5504.5.4.17.1.33
		zhoneAdslAtucPhyrCurr1DayCorrectedRetransmittedCodewords OBJECT-TYPE
			SYNTAX Counter32
			MAX-ACCESS read-only
			STATUS current
			DESCRIPTION
				"Current Day Retransmitted corrected codewords."
			::= { zhoneAdslAtucPerfEntry 33 }

		
		-- 1.3.6.1.4.1.5504.5.4.17.1.34
		zhoneAdslAtucPhyrCurr1DayUncorrectableRetransmittedCodewords OBJECT-TYPE
			SYNTAX Counter32
			MAX-ACCESS read-only
			STATUS current
			DESCRIPTION
				"Current Day Retransmitted uncorrectable codewords."
			::= { zhoneAdslAtucPerfEntry 34 }

		
		-- 1.3.6.1.4.1.5504.5.4.17.1.35
		zhoneAdslAtucPhyrPrev1DayRetransmittedCodewords OBJECT-TYPE
			SYNTAX Counter32
			MAX-ACCESS read-only
			STATUS current
			DESCRIPTION
				"Previous Day Retransmitted codewords."
			::= { zhoneAdslAtucPerfEntry 35 }

		
		-- 1.3.6.1.4.1.5504.5.4.17.1.36
		zhoneAdslAtucPhyrPrev1DayCorrectedRetransmittedCodewords OBJECT-TYPE
			SYNTAX Counter32
			MAX-ACCESS read-only
			STATUS current
			DESCRIPTION
				"Previous Day Retransmitted Corrected Codewords."
			::= { zhoneAdslAtucPerfEntry 36 }

		
		-- 1.3.6.1.4.1.5504.5.4.17.1.37
		zhoneAdslAtucPhyrPrev1DayUncorrectableRetransmittedCodewords OBJECT-TYPE
			SYNTAX Counter32
			MAX-ACCESS read-only
			STATUS current
			DESCRIPTION
				"Previous Day Retransmitted Uncorrectable Codewords."
			::= { zhoneAdslAtucPerfEntry 37 }

		
		-- 1.3.6.1.4.1.5504.5.4.17.1.38
		zhoneAdslAtucPhyRActive OBJECT-TYPE
			SYNTAX TruthValue
			MAX-ACCESS read-only
			STATUS current
			DESCRIPTION
				"ATUC Phy Retransmit Rx Queue Active."
			::= { zhoneAdslAtucPerfEntry 38 }

		
		-- 1.3.6.1.4.1.5504.5.4.17.1.39
		zhoneAdslAtucGinpLeftrSecs OBJECT-TYPE
			SYNTAX Counter32
			MAX-ACCESS read-only
			STATUS current
			DESCRIPTION
				"LEFTRS - This counter counts the number of seconds that experienced a Low
				Error Free Throughput Rate (LEFTR), i,e., seconds during which the Error
				Free Throughput dropped below the configured threshold."
			::= { zhoneAdslAtucPerfEntry 39 }

		
		-- 1.3.6.1.4.1.5504.5.4.17.1.40
		zhoneAdslAtucGinpErrorFreeBits OBJECT-TYPE
			SYNTAX Counter32
			MAX-ACCESS read-only
			STATUS current
			DESCRIPTION
				"errorFreeBits - This counter counts the number of bits that crossed the
				alpha1/beta1 interface (bits available to carry user payload). "
			::= { zhoneAdslAtucPerfEntry 40 }

		
		-- 1.3.6.1.4.1.5504.5.4.17.1.41
		zhoneAdslAtucGinpMinEftr OBJECT-TYPE
			SYNTAX Counter32
			MAX-ACCESS read-only
			STATUS current
			DESCRIPTION
				"minEFTR - This performance monitoring parameter records the lowest value
				of Error Free Throughput during the current interval."
			::= { zhoneAdslAtucPerfEntry 41 }

		
		-- 1.3.6.1.4.1.5504.5.4.17.1.42
		zhoneAdslAtucGinpCurr15MinLeftrSecs OBJECT-TYPE
			SYNTAX Counter32
			MAX-ACCESS read-only
			STATUS current
			DESCRIPTION
				"LEFTRS - This counter counts the number of seconds that experienced a Low
				Error Free Throughput Rate (LEFTR), i,e., seconds during which the Error
				Free Throughput dropped below the configured threshold. This count is
				for the current 15 minutes."
			::= { zhoneAdslAtucPerfEntry 42 }

		
		-- 1.3.6.1.4.1.5504.5.4.17.1.43
		zhoneAdslAtucGinpCurr15MinErrorFreeBits OBJECT-TYPE
			SYNTAX Counter32
			MAX-ACCESS read-only
			STATUS current
			DESCRIPTION
				"errorFreeBits - This counter counts the number of bits that crossed the
				alpha1/beta1 interface (bits available to carry user payload). This count 
				is for the current 15 minutes."
			::= { zhoneAdslAtucPerfEntry 43 }

		
		-- 1.3.6.1.4.1.5504.5.4.17.1.44
		zhoneAdslAtucGinpCurr15MinMinEftr OBJECT-TYPE
			SYNTAX Counter32
			MAX-ACCESS read-only
			STATUS current
			DESCRIPTION
				"minEFTR - This performance monitoring parameter records the lowest value
				of Error Free Throughput during the current interval.  This count is for
				the current 15 minutes."
			::= { zhoneAdslAtucPerfEntry 44 }

		
		-- 1.3.6.1.4.1.5504.5.4.17.1.45
		zhoneAdslAtucGinpCurr1DayLeftrSecs OBJECT-TYPE
			SYNTAX Counter32
			MAX-ACCESS read-only
			STATUS current
			DESCRIPTION
				"LEFTRS - This counter counts the number of seconds that experienced a Low
				Error Free Throughput Rate (LEFTR), i,e., seconds during which the Error
				Free Throughput dropped below the configured threshold. This count is
				for the current day."
			::= { zhoneAdslAtucPerfEntry 45 }

		
		-- 1.3.6.1.4.1.5504.5.4.17.1.46
		zhoneAdslAtucGinpCurr1DayErrorFreeBits OBJECT-TYPE
			SYNTAX Counter32
			MAX-ACCESS read-only
			STATUS current
			DESCRIPTION
				"errorFreeBits - This counter counts the number of bits that crossed the
				alpha1/beta1 interface (bits available to carry user payload). This count 
				is for the current day."
			::= { zhoneAdslAtucPerfEntry 46 }

		
		-- 1.3.6.1.4.1.5504.5.4.17.1.47
		zhoneAdslAtucGinpCurr1DayMinEftr OBJECT-TYPE
			SYNTAX Counter32
			MAX-ACCESS read-only
			STATUS current
			DESCRIPTION
				"minEFTR - This performance monitoring parameter records the lowest value
				of Error Free Throughput during the current interval.  This count is for
				the current day."
			::= { zhoneAdslAtucPerfEntry 47 }

		
		-- 1.3.6.1.4.1.5504.5.4.17.1.48
		zhoneAdslAtucGinpPrev1DayLeftrSecs OBJECT-TYPE
			SYNTAX Counter32
			MAX-ACCESS read-only
			STATUS current
			DESCRIPTION
				"LEFTRS - This counter counts the number of seconds that experienced a Low
				Error Free Throughput Rate (LEFTR), i,e., seconds during which the Error
				Free Throughput dropped below the configured threshold. This count is
				for the previous day."
			::= { zhoneAdslAtucPerfEntry 48 }

		
		-- 1.3.6.1.4.1.5504.5.4.17.1.49
		zhoneAdslAtucGinpPrev1DayErrorFreeBits OBJECT-TYPE
			SYNTAX Counter32
			MAX-ACCESS read-only
			STATUS current
			DESCRIPTION
				"errorFreeBits - This counter counts the number of bits that crossed the
				alpha1/beta1 interface (bits available to carry user payload). This count 
				is for the previous day."
			::= { zhoneAdslAtucPerfEntry 49 }

		
		-- 1.3.6.1.4.1.5504.5.4.17.1.50
		zhoneAdslAtucGinpPrev1DayMinEftr OBJECT-TYPE
			SYNTAX Counter32
			MAX-ACCESS read-only
			STATUS current
			DESCRIPTION
				"minEFTR - This performance monitoring parameter records the lowest value
				of Error Free Throughput during the current interval.  This count is for
				the previous day."
			::= { zhoneAdslAtucPerfEntry 50 }

		
		-- 1.3.6.1.4.1.5504.5.4.17.1.51
		zhoneAdslAtucGinpActive OBJECT-TYPE
			SYNTAX TruthValue
			MAX-ACCESS read-only
			STATUS current
			DESCRIPTION
				"ATUC G.INP / ITU-T G.998.4 Active."
			::= { zhoneAdslAtucPerfEntry 51 }

		
		-- 1.3.6.1.4.1.5504.5.4.18
		zhoneAdslAturPerfTable OBJECT-TYPE
			SYNTAX SEQUENCE OF ZhoneAdslAturPerfEntry
			MAX-ACCESS not-accessible
			STATUS current
			DESCRIPTION
				"This table is an extension to rfc2662. It provides additional
				Atur statistical counters for ADSL."
			::= { zhoneDsl 18 }

		
		-- 1.3.6.1.4.1.5504.5.4.18.1
		zhoneAdslAturPerfEntry OBJECT-TYPE
			SYNTAX ZhoneAdslAturPerfEntry
			MAX-ACCESS not-accessible
			STATUS current
			DESCRIPTION
				"Adsl extension Atur counters definition."
			INDEX { ifIndex }
			::= { zhoneAdslAturPerfTable 1 }

		
		ZhoneAdslAturPerfEntry ::=
			SEQUENCE { 
				zhoneAdslAturPerfErrorInterleaved
					Counter32,
				zhoneAdslAturPerfErrorFast
					Counter32,
				zhoneAdslAturPerfFecCorrectedInterleaved
					Counter32,
				zhoneAdslAturPerfFecCorrectedFast
					Counter32,
				zhoneAdslAturPerfBackgroundErrorBlks
					Counter32,
				zhoneAdslAturPerfNonSESBlks
					Counter32,
				zhoneAdslAturPerfSESs
					Counter32,
				zhoneAdslAturPerfUASs
					Counter32,
				zhoneAdslAturPerfFECs
					Counter32,
				zhoneAdslAturPerfSECs
					Counter32,
				zhoneAdslAturPerfHiBERs
					Counter32,
				zhoneAdslAturPerfLprs
					Counter32,
				zhoneAdslAturPerfLOSS
					Counter32,
				zhoneAdslAturPerfStatFecsL
					Counter32,
				zhoneAdslAturPerfCurr15MinFecsL
					Counter32,
				zhoneAdslAturPerfCurr1DayFecsL
					Counter32,
				zhoneAdslAturPerfPrev1DayFecsL
					Counter32,
				zhoneAdslAturPerfStatLossL
					Counter32,
				zhoneAdslAturChanPerfCD
					Counter32,
				zhoneAdslAturChanPerfCU
					Counter32,
				zhoneAdslAturChanPerfBE
					Counter32,
				zhoneAdslAturPhyrRetransmittedCodewords
					Counter32,
				zhoneAdslAturPhyrCorrectedRetransmittedCodewords
					Counter32,
				zhoneAdslAturPhyrUncorrectableRetransmittedCodewords
					Counter32,
				zhoneAdslAturPhyrCurr15MinRetransmittedCodewords
					Counter32,
				zhoneAdslAturPhyrCurr15MinCorrectedRetransmittedCodewords
					Counter32,
				zhoneAdslAturPhyrCurr15MinUncorrectableRetransmittedCodewords
					Counter32,
				zhoneAdslAturPhyrCurr1DayRetransmittedCodewords
					Counter32,
				zhoneAdslAturPhyrCurr1DayCorrectedRetransmittedCodewords
					Counter32,
				zhoneAdslAturPhyrCurr1DayUncorrectableRetransmittedCodewords
					Counter32,
				zhoneAdslAturPhyrPrev1DayRetransmittedCodewords
					Counter32,
				zhoneAdslAturPhyrPrev1DayCorrectedRetransmittedCodewords
					Counter32,
				zhoneAdslAturPhyrPrev1DayUncorrectableRetransmittedCodewords
					Counter32,
				zhoneAdslAturPhyRActive
					TruthValue,
				zhoneAdslAturGinpLeftrSecs
					Counter32,
				zhoneAdslAturGinpErrorFreeBits
					Counter32,
				zhoneAdslAturGinpMinEftr
					Counter32,
				zhoneAdslAturGinpCurr15MinLeftrSecs
					Counter32,
				zhoneAdslAturGinpCurr15MinErrorFreeBits
					Counter32,
				zhoneAdslAturGinpCurr15MinMinEftr
					Counter32,
				zhoneAdslAturGinpCurr1DayLeftrSecs
					Counter32,
				zhoneAdslAturGinpCurr1DayErrorFreeBits
					Counter32,
				zhoneAdslAturGinpCurr1DayMinEftr
					Counter32,
				zhoneAdslAturGinpPrev1DayLeftrSecs
					Counter32,
				zhoneAdslAturGinpPrev1DayErrorFreeBits
					Counter32,
				zhoneAdslAturGinpPrev1DayMinEftr
					Counter32,
				zhoneAdslAturGinpActive
					TruthValue
			 }

		-- 1.3.6.1.4.1.5504.5.4.18.1.1
		zhoneAdslAturPerfErrorInterleaved OBJECT-TYPE
			SYNTAX Counter32
			MAX-ACCESS read-only
			STATUS current
			DESCRIPTION
				"crc errors on interleaved buffer at far end."
			::= { zhoneAdslAturPerfEntry 1 }

		
		-- 1.3.6.1.4.1.5504.5.4.18.1.2
		zhoneAdslAturPerfErrorFast OBJECT-TYPE
			SYNTAX Counter32
			MAX-ACCESS read-only
			STATUS current
			DESCRIPTION
				"crc errors on fast buffer at far end."
			::= { zhoneAdslAturPerfEntry 2 }

		
		-- 1.3.6.1.4.1.5504.5.4.18.1.3
		zhoneAdslAturPerfFecCorrectedInterleaved OBJECT-TYPE
			SYNTAX Counter32
			MAX-ACCESS read-only
			STATUS current
			DESCRIPTION
				"FEC corrections on interleaved buffer at far end."
			::= { zhoneAdslAturPerfEntry 3 }

		
		-- 1.3.6.1.4.1.5504.5.4.18.1.4
		zhoneAdslAturPerfFecCorrectedFast OBJECT-TYPE
			SYNTAX Counter32
			MAX-ACCESS read-only
			STATUS current
			DESCRIPTION
				"FEC corrections on fast buffer at far end."
			::= { zhoneAdslAturPerfEntry 4 }

		
		-- 1.3.6.1.4.1.5504.5.4.18.1.5
		zhoneAdslAturPerfBackgroundErrorBlks OBJECT-TYPE
			SYNTAX Counter32
			MAX-ACCESS read-only
			STATUS current
			DESCRIPTION
				"background errored blocks at far end."
			::= { zhoneAdslAturPerfEntry 5 }

		
		-- 1.3.6.1.4.1.5504.5.4.18.1.6
		zhoneAdslAturPerfNonSESBlks OBJECT-TYPE
			SYNTAX Counter32
			MAX-ACCESS read-only
			STATUS current
			DESCRIPTION
				"non SES blocks received at the far end."
			::= { zhoneAdslAturPerfEntry 6 }

		
		-- 1.3.6.1.4.1.5504.5.4.18.1.7
		zhoneAdslAturPerfSESs OBJECT-TYPE
			SYNTAX Counter32
			MAX-ACCESS read-only
			STATUS current
			DESCRIPTION
				"Severely errored seconds at the far end."
			::= { zhoneAdslAturPerfEntry 7 }

		
		-- 1.3.6.1.4.1.5504.5.4.18.1.8
		zhoneAdslAturPerfUASs OBJECT-TYPE
			SYNTAX Counter32
			MAX-ACCESS read-only
			STATUS current
			DESCRIPTION
				"Unavailable seconds at the far end."
			::= { zhoneAdslAturPerfEntry 8 }

		
		-- 1.3.6.1.4.1.5504.5.4.18.1.9
		zhoneAdslAturPerfFECs OBJECT-TYPE
			SYNTAX Counter32
			MAX-ACCESS read-only
			STATUS current
			DESCRIPTION
				"Seconds with one or more FECs at the far end."
			::= { zhoneAdslAturPerfEntry 9 }

		
		-- 1.3.6.1.4.1.5504.5.4.18.1.10
		zhoneAdslAturPerfSECs OBJECT-TYPE
			SYNTAX Counter32
			MAX-ACCESS read-only
			STATUS current
			DESCRIPTION
				"Elapsed seconds at the far end."
			::= { zhoneAdslAturPerfEntry 10 }

		
		-- 1.3.6.1.4.1.5504.5.4.18.1.11
		zhoneAdslAturPerfHiBERs OBJECT-TYPE
			SYNTAX Counter32
			MAX-ACCESS read-only
			STATUS current
			DESCRIPTION
				"Seconds declared as hi BER by the far end."
			::= { zhoneAdslAturPerfEntry 11 }

		
		-- 1.3.6.1.4.1.5504.5.4.18.1.12
		zhoneAdslAturPerfLprs OBJECT-TYPE
			SYNTAX Counter32
			MAX-ACCESS read-only
			STATUS current
			DESCRIPTION
				"Loss of power seconds at the far end (dying gasp)"
			::= { zhoneAdslAturPerfEntry 12 }

		
		-- 1.3.6.1.4.1.5504.5.4.18.1.13
		zhoneAdslAturPerfLOSS OBJECT-TYPE
			SYNTAX Counter32
			MAX-ACCESS read-only
			STATUS current
			DESCRIPTION
				"loss of signal seconds at the far end."
			::= { zhoneAdslAturPerfEntry 13 }

		
		-- 1.3.6.1.4.1.5504.5.4.18.1.14
		zhoneAdslAturPerfStatFecsL OBJECT-TYPE
			SYNTAX Counter32
			MAX-ACCESS read-only
			STATUS current
			DESCRIPTION
				"Retrieved via OAM.  Count of 1-second intervals with one or
				more far end forward error correction (FFEC) anomalies
				since agent reset.
				
				Supported for ADSL2/ADSL2plus Only.
				Not available for ADSL."
			::= { zhoneAdslAturPerfEntry 14 }

		
		-- 1.3.6.1.4.1.5504.5.4.18.1.15
		zhoneAdslAturPerfCurr15MinFecsL OBJECT-TYPE
			SYNTAX Counter32
			MAX-ACCESS read-only
			STATUS current
			DESCRIPTION
				"Retrieved via OAM.  Count of 1-second intervals, in the
				current 15 minute interval, with one or more far end forward
				error correction (FFEC) anomalies.
				
				Supported for ADSL2/ADSL2plus Only.
				Not available for ADSL."
			::= { zhoneAdslAturPerfEntry 15 }

		
		-- 1.3.6.1.4.1.5504.5.4.18.1.16
		zhoneAdslAturPerfCurr1DayFecsL OBJECT-TYPE
			SYNTAX Counter32
			MAX-ACCESS read-only
			STATUS current
			DESCRIPTION
				"Retrieved via OAM.  Count of 1-second intervals, during the
				current day as measured by adslAturPerfCurr1Day-TimeElapsed,
				with one or more far end forward error
				correction (FFEC) anomalies.
				
				Supported for ADSL2/ADSL2plus Only.
				Not available for ADSL."
			::= { zhoneAdslAturPerfEntry 16 }

		
		-- 1.3.6.1.4.1.5504.5.4.18.1.17
		zhoneAdslAturPerfPrev1DayFecsL OBJECT-TYPE
			SYNTAX Counter32
			MAX-ACCESS read-only
			STATUS current
			DESCRIPTION
				"Retrieved via OAM. Count of 1-second intervals, within the
				most recent previous 1-day period, with one or more far end
				forward error correction (FFEC) anomalies.
				
				Supported for ADSL2/ADSL2plus Only.
				Not available for ADSL."
			::= { zhoneAdslAturPerfEntry 17 }

		
		-- 1.3.6.1.4.1.5504.5.4.18.1.18
		zhoneAdslAturPerfStatLossL OBJECT-TYPE
			SYNTAX Counter32
			MAX-ACCESS read-only
			STATUS current
			DESCRIPTION
				"Retrieved via OAM.  Count of 1-second intervals containing
				one or more far-end loss of signal (LOS) defects.
				
				Supported for ADSL2/ADSL2plus Only.
				Not available for ADSL."
			::= { zhoneAdslAturPerfEntry 18 }

		
		-- 1.3.6.1.4.1.5504.5.4.18.1.19
		zhoneAdslAturChanPerfCD OBJECT-TYPE
			SYNTAX Counter32
			MAX-ACCESS read-only
			STATUS current
			DESCRIPTION
				"Retrieved via OAM.  Far-end delineated total cell count.
				
				Supported for ADSL2/ADSL2plus Only.
				Not available for ADSL."
			::= { zhoneAdslAturPerfEntry 19 }

		
		-- 1.3.6.1.4.1.5504.5.4.18.1.20
		zhoneAdslAturChanPerfCU OBJECT-TYPE
			SYNTAX Counter32
			MAX-ACCESS read-only
			STATUS current
			DESCRIPTION
				"Retrieved via OAM.  Far-end user total cell count.
				
				Supported for ADSL2/ADSL2plus Only.
				Not available for ADSL."
			::= { zhoneAdslAturPerfEntry 20 }

		
		-- 1.3.6.1.4.1.5504.5.4.18.1.21
		zhoneAdslAturChanPerfBE OBJECT-TYPE
			SYNTAX Counter32
			MAX-ACCESS read-only
			STATUS current
			DESCRIPTION
				"Retrieved via OAM.  Far end idle cell bit error count.
				
				Supported for ADSL2/ADSL2plus Only.
				Not available for ADSL."
			::= { zhoneAdslAturPerfEntry 21 }

		
		-- 1.3.6.1.4.1.5504.5.4.18.1.22
		zhoneAdslAturPhyrRetransmittedCodewords OBJECT-TYPE
			SYNTAX Counter32
			MAX-ACCESS read-only
			STATUS current
			DESCRIPTION
				"Retransmitted codewords."
			::= { zhoneAdslAturPerfEntry 22 }

		
		-- 1.3.6.1.4.1.5504.5.4.18.1.23
		zhoneAdslAturPhyrCorrectedRetransmittedCodewords OBJECT-TYPE
			SYNTAX Counter32
			MAX-ACCESS read-only
			STATUS current
			DESCRIPTION
				"Retransmitted corrected codewords."
			::= { zhoneAdslAturPerfEntry 23 }

		
		-- 1.3.6.1.4.1.5504.5.4.18.1.24
		zhoneAdslAturPhyrUncorrectableRetransmittedCodewords OBJECT-TYPE
			SYNTAX Counter32
			MAX-ACCESS read-only
			STATUS current
			DESCRIPTION
				"Retransmitted uncorrected codewords."
			::= { zhoneAdslAturPerfEntry 24 }

		
		-- 1.3.6.1.4.1.5504.5.4.18.1.25
		zhoneAdslAturPhyrCurr15MinRetransmittedCodewords OBJECT-TYPE
			SYNTAX Counter32
			MAX-ACCESS read-only
			STATUS current
			DESCRIPTION
				"Current 15 Minutes Retransmitted codewords."
			::= { zhoneAdslAturPerfEntry 25 }

		
		-- 1.3.6.1.4.1.5504.5.4.18.1.26
		zhoneAdslAturPhyrCurr15MinCorrectedRetransmittedCodewords OBJECT-TYPE
			SYNTAX Counter32
			MAX-ACCESS read-only
			STATUS current
			DESCRIPTION
				"Current 15 Minutes Retransmitted Corrected codewords."
			::= { zhoneAdslAturPerfEntry 26 }

		
		-- 1.3.6.1.4.1.5504.5.4.18.1.27
		zhoneAdslAturPhyrCurr15MinUncorrectableRetransmittedCodewords OBJECT-TYPE
			SYNTAX Counter32
			MAX-ACCESS read-only
			STATUS current
			DESCRIPTION
				"Current 15 Minutes Retransmitted Uncorrectable codewords."
			::= { zhoneAdslAturPerfEntry 27 }

		
		-- 1.3.6.1.4.1.5504.5.4.18.1.28
		zhoneAdslAturPhyrCurr1DayRetransmittedCodewords OBJECT-TYPE
			SYNTAX Counter32
			MAX-ACCESS read-only
			STATUS current
			DESCRIPTION
				"Current Day Retransmitted Codewords."
			::= { zhoneAdslAturPerfEntry 28 }

		
		-- 1.3.6.1.4.1.5504.5.4.18.1.29
		zhoneAdslAturPhyrCurr1DayCorrectedRetransmittedCodewords OBJECT-TYPE
			SYNTAX Counter32
			MAX-ACCESS read-only
			STATUS current
			DESCRIPTION
				"Current Day Retransmitted Corrected Codewords."
			::= { zhoneAdslAturPerfEntry 29 }

		
		-- 1.3.6.1.4.1.5504.5.4.18.1.30
		zhoneAdslAturPhyrCurr1DayUncorrectableRetransmittedCodewords OBJECT-TYPE
			SYNTAX Counter32
			MAX-ACCESS read-only
			STATUS current
			DESCRIPTION
				"Current Day Retransmitted Uncorrectable Codewords."
			::= { zhoneAdslAturPerfEntry 30 }

		
		-- 1.3.6.1.4.1.5504.5.4.18.1.31
		zhoneAdslAturPhyrPrev1DayRetransmittedCodewords OBJECT-TYPE
			SYNTAX Counter32
			MAX-ACCESS read-only
			STATUS current
			DESCRIPTION
				"Previous Day Retransmitted Codewords."
			::= { zhoneAdslAturPerfEntry 31 }

		
		-- 1.3.6.1.4.1.5504.5.4.18.1.32
		zhoneAdslAturPhyrPrev1DayCorrectedRetransmittedCodewords OBJECT-TYPE
			SYNTAX Counter32
			MAX-ACCESS read-only
			STATUS current
			DESCRIPTION
				"Previous Day Retransmitted Corrected Codewords."
			::= { zhoneAdslAturPerfEntry 32 }

		
		-- 1.3.6.1.4.1.5504.5.4.18.1.33
		zhoneAdslAturPhyrPrev1DayUncorrectableRetransmittedCodewords OBJECT-TYPE
			SYNTAX Counter32
			MAX-ACCESS read-only
			STATUS current
			DESCRIPTION
				"Previous Day Retransmitted Uncorrectable Codewords."
			::= { zhoneAdslAturPerfEntry 33 }

		
		-- 1.3.6.1.4.1.5504.5.4.18.1.34
		zhoneAdslAturPhyRActive OBJECT-TYPE
			SYNTAX TruthValue
			MAX-ACCESS read-only
			STATUS current
			DESCRIPTION
				"ATUR Phy Retransmit Rx Queue Active."
			::= { zhoneAdslAturPerfEntry 34 }

		
		-- 1.3.6.1.4.1.5504.5.4.18.1.35
		zhoneAdslAturGinpLeftrSecs OBJECT-TYPE
			SYNTAX Counter32
			MAX-ACCESS read-only
			STATUS current
			DESCRIPTION
				"LEFTRS - This counter counts the number of seconds that experienced a Low
				Error Free Throughput Rate (LEFTR), i,e., seconds during which the Error
				Free Throughput dropped below the configured threshold."
			::= { zhoneAdslAturPerfEntry 35 }

		
		-- 1.3.6.1.4.1.5504.5.4.18.1.36
		zhoneAdslAturGinpErrorFreeBits OBJECT-TYPE
			SYNTAX Counter32
			MAX-ACCESS read-only
			STATUS current
			DESCRIPTION
				"errorFreeBits - This counter counts the number of bits that crossed the
				alpha1/beta1 interface (bits available to carry user payload)."
			::= { zhoneAdslAturPerfEntry 36 }

		
		-- 1.3.6.1.4.1.5504.5.4.18.1.37
		zhoneAdslAturGinpMinEftr OBJECT-TYPE
			SYNTAX Counter32
			MAX-ACCESS read-only
			STATUS current
			DESCRIPTION
				"minEFTR - This performance monitoring parameter records the lowest value
				of Error Free Throughput during the current interval."
			::= { zhoneAdslAturPerfEntry 37 }

		
		-- 1.3.6.1.4.1.5504.5.4.18.1.38
		zhoneAdslAturGinpCurr15MinLeftrSecs OBJECT-TYPE
			SYNTAX Counter32
			MAX-ACCESS read-only
			STATUS current
			DESCRIPTION
				"LEFTRS - This counter counts the number of seconds that experienced a Low
				Error Free Throughput Rate (LEFTR), i,e., seconds during which the Error
				Free Throughput dropped below the configured threshold. This count is
				for the current 15 minutes."
			::= { zhoneAdslAturPerfEntry 38 }

		
		-- 1.3.6.1.4.1.5504.5.4.18.1.39
		zhoneAdslAturGinpCurr15MinErrorFreeBits OBJECT-TYPE
			SYNTAX Counter32
			MAX-ACCESS read-only
			STATUS current
			DESCRIPTION
				"errorFreeBits - This counter counts the number of bits that crossed the
				alpha1/beta1 interface (bits available to carry user payload). This count 
				is for the current 15 minutes."
			::= { zhoneAdslAturPerfEntry 39 }

		
		-- 1.3.6.1.4.1.5504.5.4.18.1.40
		zhoneAdslAturGinpCurr15MinMinEftr OBJECT-TYPE
			SYNTAX Counter32
			MAX-ACCESS read-only
			STATUS current
			DESCRIPTION
				"minEFTR - This performance monitoring parameter records the lowest value
				of Error Free Throughput during the current interval.  This count is for
				the current 15 minutes."
			::= { zhoneAdslAturPerfEntry 40 }

		
		-- 1.3.6.1.4.1.5504.5.4.18.1.41
		zhoneAdslAturGinpCurr1DayLeftrSecs OBJECT-TYPE
			SYNTAX Counter32
			MAX-ACCESS read-only
			STATUS current
			DESCRIPTION
				"LEFTRS - This counter counts the number of seconds that experienced a Low
				Error Free Throughput Rate (LEFTR), i,e., seconds during which the Error
				Free Throughput dropped below the configured threshold. This count is
				for the current day."
			::= { zhoneAdslAturPerfEntry 41 }

		
		-- 1.3.6.1.4.1.5504.5.4.18.1.42
		zhoneAdslAturGinpCurr1DayErrorFreeBits OBJECT-TYPE
			SYNTAX Counter32
			MAX-ACCESS read-only
			STATUS current
			DESCRIPTION
				"errorFreeBits - This counter counts the number of bits that crossed the
				alpha1/beta1 interface (bits available to carry user payload). This count 
				is for the current day."
			::= { zhoneAdslAturPerfEntry 42 }

		
		-- 1.3.6.1.4.1.5504.5.4.18.1.43
		zhoneAdslAturGinpCurr1DayMinEftr OBJECT-TYPE
			SYNTAX Counter32
			MAX-ACCESS read-only
			STATUS current
			DESCRIPTION
				"minEFTR - This performance monitoring parameter records the lowest value
				of Error Free Throughput during the current interval.  This count is for
				the current day."
			::= { zhoneAdslAturPerfEntry 43 }

		
		-- 1.3.6.1.4.1.5504.5.4.18.1.44
		zhoneAdslAturGinpPrev1DayLeftrSecs OBJECT-TYPE
			SYNTAX Counter32
			MAX-ACCESS read-only
			STATUS current
			DESCRIPTION
				"LEFTRS - This counter counts the number of seconds that experienced a Low
				Error Free Throughput Rate (LEFTR), i,e., seconds during which the Error
				Free Throughput dropped below the configured threshold. This count is
				for the previous day."
			::= { zhoneAdslAturPerfEntry 44 }

		
		-- 1.3.6.1.4.1.5504.5.4.18.1.45
		zhoneAdslAturGinpPrev1DayErrorFreeBits OBJECT-TYPE
			SYNTAX Counter32
			MAX-ACCESS read-only
			STATUS current
			DESCRIPTION
				"errorFreeBits - This counter counts the number of bits that crossed the
				alpha1/beta1 interface (bits available to carry user payload). This count 
				is for the previous day."
			::= { zhoneAdslAturPerfEntry 45 }

		
		-- 1.3.6.1.4.1.5504.5.4.18.1.46
		zhoneAdslAturGinpPrev1DayMinEftr OBJECT-TYPE
			SYNTAX Counter32
			MAX-ACCESS read-only
			STATUS current
			DESCRIPTION
				"minEFTR - This performance monitoring parameter records the lowest value
				of Error Free Throughput during the current interval.  This count is for
				the previous day."
			::= { zhoneAdslAturPerfEntry 46 }

		
		-- 1.3.6.1.4.1.5504.5.4.18.1.47
		zhoneAdslAturGinpActive OBJECT-TYPE
			SYNTAX TruthValue
			MAX-ACCESS read-only
			STATUS current
			DESCRIPTION
				"ATUR G.INP / ITU-T G.998.4 Active."
			::= { zhoneAdslAturPerfEntry 47 }

		
		-- 1.3.6.1.4.1.5504.5.4.19
		zhoneAdslLineConfProfileExtTable OBJECT-TYPE
			SYNTAX SEQUENCE OF ZhoneAdslLineConfProfileExtEntry
			MAX-ACCESS not-accessible
			STATUS current
			DESCRIPTION
				"Description."
			::= { zhoneDsl 19 }

		
		-- 1.3.6.1.4.1.5504.5.4.19.1
		zhoneAdslLineConfProfileExtEntry OBJECT-TYPE
			SYNTAX ZhoneAdslLineConfProfileExtEntry
			MAX-ACCESS not-accessible
			STATUS current
			DESCRIPTION
				"Description."
			AUGMENTS { adslLineConfProfileEntry }
			::= { zhoneAdslLineConfProfileExtTable 1 }

		
		ZhoneAdslLineConfProfileExtEntry ::=
			SEQUENCE { 
				zhoneAdslAtucConfREADSL2
					INTEGER,
				zhoneAdslAtucMinTxThreshAlarm
					Unsigned32,
				zhoneAdslAturMinTxThreshAlarm
					Unsigned32,
				zhoneAdslAtucMinINP
					INTEGER,
				zhoneAdslAturMinINP
					INTEGER,
				zhoneAdslAtucPhyRSupport
					INTEGER,
				zhoneAdslAturPhyRSupport
					INTEGER,
				zhoneAdslAtucPhyRmaxINP
					INTEGER,
				zhoneAdslAturPhyRmaxINP
					INTEGER,
				zhoneAdslAtucPhyRminRSoverhead
					INTEGER,
				zhoneAdslAturPhyRminRSoverhead
					INTEGER,
				zhoneAdslAtucPhyRRtxRatio
					INTEGER,
				zhoneAdslAturPhyRRtxRatio
					INTEGER,
				zhoneAdslAtucTxPowerAttenuation
					INTEGER,
				zhoneAdslAtucCabMode
					INTEGER,
				zhoneAdslAtucGinpSupport
					INTEGER,
				zhoneAdslAturGinpSupport
					INTEGER,
				zhoneAdslAtucGinpEtrMax
					Unsigned32,
				zhoneAdslAturGinpEtrMax
					Unsigned32,
				zhoneAdslAtucGinpEtrMin
					Unsigned32,
				zhoneAdslAturGinpEtrMin
					Unsigned32,
				zhoneAdslAtucGinpNdrMax
					Unsigned32,
				zhoneAdslAturGinpNdrMax
					Unsigned32,
				zhoneAdslAtucGinpShineRatio
					Unsigned32,
				zhoneAdslAturGinpShineRatio
					Unsigned32,
				zhoneAdslAtucGinpLeftrThreshold
					Unsigned32,
				zhoneAdslAturGinpLeftrThreshold
					Unsigned32,
				zhoneAdslAtucGinpMaxDelay
					Unsigned32,
				zhoneAdslAturGinpMaxDelay
					Unsigned32,
				zhoneAdslAtucGinpMinDelay
					Unsigned32,
				zhoneAdslAturGinpMinDelay
					Unsigned32,
				zhoneAdslAtucGinpMin
					Unsigned32,
				zhoneAdslAturGinpMin
					Unsigned32,
				zhoneAdslAtucGinpMinRSoverhead
					Unsigned32,
				zhoneAdslAturGinpMinRSoverhead
					Unsigned32,
				zhoneAdslAtucGinpReinCfg
					Unsigned32,
				zhoneAdslAturGinpReinCfg
					Unsigned32,
				zhoneAdslAtucGinpReinFreq
					INTEGER,
				zhoneAdslAturGinpReinFreq
					INTEGER,
				zhoneAdslAtucGinpRtxMode
					INTEGER,
				zhoneAdslAturGinpRtxMode
					INTEGER
			 }

-- 
		-- 1.3.6.1.4.1.5504.5.4.19.1.1
		zhoneAdslAtucConfREADSL2 OBJECT-TYPE
			SYNTAX INTEGER
				{
				enable(1),
				disable(2)
				}
			MAX-ACCESS read-write
			STATUS current
			DESCRIPTION
				"Supported for ADSL2 ONLY
				
				This READSL2 configuration parameter defines whether
				downstream READSL2 operation should be forced by the ATU-C.
				
				WARNING:
				
				READSL2 has been designed to provide rate/reach benefits for
				long loops. Therefore, for loop lengths less 16 Kft, rates will
				actually decrease if READSL2 is enabled since the
				downstream end bin is limited to 128 for READSL2 operation.
				
				Supported for ADSL2/ADSL2plus Only.
				Not available for ADSL."
			DEFVAL { enable }
			::= { zhoneAdslLineConfProfileExtEntry 1 }

		
		-- 1.3.6.1.4.1.5504.5.4.19.1.2
		zhoneAdslAtucMinTxThreshAlarm OBJECT-TYPE
			SYNTAX Unsigned32
			MAX-ACCESS read-write
			STATUS current
			DESCRIPTION
				"Minimum CO Tx Sync rate threshold alarm.  If set to 0,
				this field is disregarded.  Otherwise, if Tx Sync 
				rate falls below this value, a trap and alarm will
				be issued."
			DEFVAL { 0 }
			::= { zhoneAdslLineConfProfileExtEntry 2 }

		
		-- 1.3.6.1.4.1.5504.5.4.19.1.3
		zhoneAdslAturMinTxThreshAlarm OBJECT-TYPE
			SYNTAX Unsigned32
			MAX-ACCESS read-write
			STATUS current
			DESCRIPTION
				"Minimum CPE Tx Sync rate threshold alarm.  If set to 0,
				this field is disregarded.  Otherwise, if Tx Sync 
				rate falls below this value, a trap and alarm will
				be issued."
			DEFVAL { 0 }
			::= { zhoneAdslLineConfProfileExtEntry 3 }

		
		-- 1.3.6.1.4.1.5504.5.4.19.1.4
		zhoneAdslAtucMinINP OBJECT-TYPE
			SYNTAX INTEGER (0..1 | 5..160)
			MAX-ACCESS read-write
			STATUS current
			DESCRIPTION
				"Minimum impulse noise protection.
				
				A value of 0 specifies no protection.
				
				A value of 1 specifies AUTO configuration which 
				automatically selects the INP value based on
				configured line rate and configured max-delay.
				
				The values 5 through 160 specify the number of 
				symbols in 1/10 increments.
				
				Conexant Annex-A ports only support 0, 1, 5, 10, 20, 
				40, 80, and 160 configuration values.
				
				Connexant Annex-B ports only support 0, 1, 5, 10, and
				20 configuration values.
				
				Broadcom ports only support the configuration values
				0, and 5 through 160. They do not support the AUTO
				configuration setting."
			DEFVAL { 1 }
			::= { zhoneAdslLineConfProfileExtEntry 4 }

		
		-- 1.3.6.1.4.1.5504.5.4.19.1.5
		zhoneAdslAturMinINP OBJECT-TYPE
			SYNTAX INTEGER (0..1 | 5..160)
			MAX-ACCESS read-write
			STATUS current
			DESCRIPTION
				"Minimum impulse noise protection.
				
				A value of 0 specifies no protection.
				
				A value of 1 specifies AUTO configuration which 
				automatically selects the INP value based on
				configured line rate and configured max-delay.
				
				The values 5 through 160 specify the number of 
				symbols in 1/10 increments.
				
				Conexant Annex-A ports only support 0, 1, 5, 10, and 
				20 configuration values.
				
				Connexant Annex-B ports do not support this object.
				
				Broadcom ports only support the configuration values
				0, and 5 through 160. They do not support the AUTO
				configuration setting."
			DEFVAL { 1 }
			::= { zhoneAdslLineConfProfileExtEntry 5 }

		
		-- 1.3.6.1.4.1.5504.5.4.19.1.6
		zhoneAdslAtucPhyRSupport OBJECT-TYPE
			SYNTAX INTEGER
				{
				enable(1),
				disable(2)
				}
			MAX-ACCESS read-write
			STATUS current
			DESCRIPTION
				"Enable or disable downstream PHYR.
				Only supported by Broadcom PHYR ports."
			DEFVAL { disable }
			::= { zhoneAdslLineConfProfileExtEntry 6 }

		
		-- 1.3.6.1.4.1.5504.5.4.19.1.7
		zhoneAdslAturPhyRSupport OBJECT-TYPE
			SYNTAX INTEGER
				{
				enable(1),
				disable(2)
				}
			MAX-ACCESS read-write
			STATUS current
			DESCRIPTION
				"Enable or disable upstream PHYR.
				Only supported by Broadcom PHYR ports."
			DEFVAL { disable }
			::= { zhoneAdslLineConfProfileExtEntry 7 }

		
		-- 1.3.6.1.4.1.5504.5.4.19.1.8
		zhoneAdslAtucPhyRmaxINP OBJECT-TYPE
			SYNTAX INTEGER (0 | 5..160)
			MAX-ACCESS read-write
			STATUS current
			DESCRIPTION
				"PHYR maximum impulse noise protection.
				
				A value of 0 specifies no protection.
				
				The values 5 through 160 specify the number of 
				symbols in 1/10 increments.
				
				Only supported by Broadcom PHYR ports."
			DEFVAL { 0 }
			::= { zhoneAdslLineConfProfileExtEntry 8 }

		
		-- 1.3.6.1.4.1.5504.5.4.19.1.9
		zhoneAdslAturPhyRmaxINP OBJECT-TYPE
			SYNTAX INTEGER (0 | 5..160)
			MAX-ACCESS read-write
			STATUS current
			DESCRIPTION
				"PHYR maximum impulse noise protection.
				
				A value of 0 specifies no protection.
				
				The values 5 through 160 specify the number of 
				symbols in 1/10 increments.
				
				Only supported by Broadcom PHYR ports."
			DEFVAL { 0 }
			::= { zhoneAdslLineConfProfileExtEntry 9 }

		
		-- 1.3.6.1.4.1.5504.5.4.19.1.10
		zhoneAdslAtucPhyRminRSoverhead OBJECT-TYPE
			SYNTAX INTEGER (0..255)
			MAX-ACCESS read-write
			STATUS current
			DESCRIPTION
				"PHYR minimum RS overhead.
				Only supported by Broadcom PHYR ports."
			DEFVAL { 0 }
			::= { zhoneAdslLineConfProfileExtEntry 10 }

		
		-- 1.3.6.1.4.1.5504.5.4.19.1.11
		zhoneAdslAturPhyRminRSoverhead OBJECT-TYPE
			SYNTAX INTEGER (0..255)
			MAX-ACCESS read-write
			STATUS current
			DESCRIPTION
				"PHYR minimum RS overhead.
				
				Only supported by Broadcom PHYR ports."
			DEFVAL { 0 }
			::= { zhoneAdslLineConfProfileExtEntry 11 }

		
		-- 1.3.6.1.4.1.5504.5.4.19.1.12
		zhoneAdslAtucPhyRRtxRatio OBJECT-TYPE
			SYNTAX INTEGER (0..255)
			MAX-ACCESS read-write
			STATUS current
			DESCRIPTION
				"PHYR minimum fraction of the line rate 
				allocated for retransmission.
				Only supported by Broadcom PHYR ports."
			DEFVAL { 0 }
			::= { zhoneAdslLineConfProfileExtEntry 12 }

		
		-- 1.3.6.1.4.1.5504.5.4.19.1.13
		zhoneAdslAturPhyRRtxRatio OBJECT-TYPE
			SYNTAX INTEGER (0..255)
			MAX-ACCESS read-write
			STATUS current
			DESCRIPTION
				"PHYR minimum fraction of the line rate 
				allocated for retransmission.
				Only supported by Broadcom PHYR ports."
			DEFVAL { 0 }
			::= { zhoneAdslLineConfProfileExtEntry 13 }

		
		-- 1.3.6.1.4.1.5504.5.4.19.1.14
		zhoneAdslAtucTxPowerAttenuation OBJECT-TYPE
			SYNTAX INTEGER (-255..255)
			MAX-ACCESS read-write
			STATUS current
			DESCRIPTION
				"Transmit power attenuation.Value ranges from -255 to 255 dB."
			DEFVAL { 0 }
			::= { zhoneAdslLineConfProfileExtEntry 14 }

		
		-- 1.3.6.1.4.1.5504.5.4.19.1.15
		zhoneAdslAtucCabMode OBJECT-TYPE
			SYNTAX INTEGER (0..15)
			MAX-ACCESS read-write
			STATUS current
			DESCRIPTION
				"ADSL2+ Cabinet Mode Setting
				Values:
				
				Conexant Chipset Based Blades: 
				0 = OFF
				1 - 15 = Sets Cabinet Mode to ON and downstream cut-off frequency is 
				set to 1.1 Mhz. 
				Note: there is no difference for values 1-15 as all values set 
				Cabinet Mode to on.
				
				Broadcom Chipset Based Blades: 
				0 = OFF
				1 - 15 = Sets Cabinet Mode to ON and selects TX Filter 1-15. The TX 
				Filters set the downstream cut-off frequency as per the following table:
				
				    Filter#  Cutoff Frequency 
				     1        603.75  Khz
				     2        646.875 Khz
				     3        690     Khz
				     4        733.125 Khz
				     5        776.25  Khz
				     6        819.375 Khz
				     7        862.5   Khz
				     8        905.625 Khz
				     9        948.75  Khz
				    10        991.875 Khz
				    11       1035     Khz
				    12       1078.125 Khz
				    13       1121.25  Khz
				    14       1164.375 Khz
				    15       1207.5   Khz
				
				"
			DEFVAL { 0 }
			::= { zhoneAdslLineConfProfileExtEntry 15 }

		
		-- 1.3.6.1.4.1.5504.5.4.19.1.16
		zhoneAdslAtucGinpSupport OBJECT-TYPE
			SYNTAX INTEGER
				{
				enable(1),
				disable(2)
				}
			MAX-ACCESS read-write
			STATUS current
			DESCRIPTION
				"gInpSupport - Enable or disable downstream G.INP / ITU-G.998.4.
				Only supported by Broadcom ports."
			DEFVAL { disable }
			::= { zhoneAdslLineConfProfileExtEntry 16 }

		
		-- 1.3.6.1.4.1.5504.5.4.19.1.17
		zhoneAdslAturGinpSupport OBJECT-TYPE
			SYNTAX INTEGER
				{
				enable(1),
				disable(2)
				}
			MAX-ACCESS read-write
			STATUS current
			DESCRIPTION
				"gInpSupport - Enable or disable upstream G.INP / ITU-G.998.4.
				Only supported by Broadcom ports."
			DEFVAL { disable }
			::= { zhoneAdslLineConfProfileExtEntry 17 }

		
		-- 1.3.6.1.4.1.5504.5.4.19.1.18
		zhoneAdslAtucGinpEtrMax OBJECT-TYPE
			SYNTAX Unsigned32 (64..200000)
			UNITS "kbps"
			MAX-ACCESS read-write
			STATUS current
			DESCRIPTION
				"gInpEtrMax - Maximum allowed value for downstream expected throughput 
				(ETR) in kbit/s. The valid values are all multiples of 8 from 0 to 
				the maximum of the valid values of the maximum net data rate 
				specified in the associated Recommendation. ITU-T G.998.4 7.1.1 
				Control parameters and 7.1.2 Valid configurations."
			DEFVAL { 32736 }
			::= { zhoneAdslLineConfProfileExtEntry 18 }

		
		-- 1.3.6.1.4.1.5504.5.4.19.1.19
		zhoneAdslAturGinpEtrMax OBJECT-TYPE
			SYNTAX Unsigned32 (64..200000)
			UNITS "kbps"
			MAX-ACCESS read-write
			STATUS current
			DESCRIPTION
				"gInpEtrMax - Maximum allowed value for upstream expected throughput 
				(ETR) in kbit/s. The valid values are all multiples of 8 from 0 to 
				the maximum of the valid values of the maximum net data rate 
				specified in the associated Recommendation. ITU-T G.998.4 7.1.1 
				Control parameters and 7.1.2 Valid configurations."
			DEFVAL { 1536 }
			::= { zhoneAdslLineConfProfileExtEntry 19 }

		
		-- 1.3.6.1.4.1.5504.5.4.19.1.20
		zhoneAdslAtucGinpEtrMin OBJECT-TYPE
			SYNTAX Unsigned32 (64..200000)
			UNITS "kbps"
			MAX-ACCESS read-write
			STATUS current
			DESCRIPTION
				"gInpEtrMin - Minimum allowed value for downstream expected throughput
				(ETR) in kbit/s. The valid values are all multiples of 8 from 0 to 
				the maximum of the valid values of the minimum net data rate specified
				in the associated Recommendation. ITU-T G.998.4 7.1.1 Control parameters
				and 7.1.2 Valid configurations."
			DEFVAL { 64 }
			::= { zhoneAdslLineConfProfileExtEntry 20 }

		
		-- 1.3.6.1.4.1.5504.5.4.19.1.21
		zhoneAdslAturGinpEtrMin OBJECT-TYPE
			SYNTAX Unsigned32 (64..200000)
			UNITS "kbps"
			MAX-ACCESS read-write
			STATUS current
			DESCRIPTION
				"gInpEtrMin - Minimum allowed value for upstream expected throughput
				(ETR) in kbit/s. The valid values are all multiples of 8 from 0 to 
				the maximum of the valid values of the minimum net data rate specified
				in the associated Recommendation. ITU-T G.998.4 7.1.1 Control parameters
				and 7.1.2 Valid configurations."
			DEFVAL { 64 }
			::= { zhoneAdslLineConfProfileExtEntry 21 }

		
		-- 1.3.6.1.4.1.5504.5.4.19.1.22
		zhoneAdslAtucGinpNdrMax OBJECT-TYPE
			SYNTAX Unsigned32 (64..200000)
			UNITS "kbps"
			MAX-ACCESS read-write
			STATUS current
			DESCRIPTION
				"gInpNdrMax - Maximum allowed value for downstream net data rate (NDR)
				in kbit/s. The valid values are all multiples of 8 from 0 to the 
				maximum of the valid values of the maximum net data rate specified 
				in the associated Recommendation. ITU-T G.998.4 7.1.1 Control parameters
				and 7.1.2 Valid configurations."
			DEFVAL { 32736 }
			::= { zhoneAdslLineConfProfileExtEntry 22 }

		
		-- 1.3.6.1.4.1.5504.5.4.19.1.23
		zhoneAdslAturGinpNdrMax OBJECT-TYPE
			SYNTAX Unsigned32 (64..200000)
			UNITS "kbps"
			MAX-ACCESS read-write
			STATUS current
			DESCRIPTION
				"gInpNdrMax - Maximum allowed value for upstream net data rate (NDR)
				in kbit/s. The valid values are all multiples of 8 from 0 to the 
				maximum of the valid values of the maximum net data rate specified 
				in the associated Recommendation. ITU-T G.998.4 7.1.1 Control parameters
				and 7.1.2 Valid configurations."
			DEFVAL { 1536 }
			::= { zhoneAdslLineConfProfileExtEntry 23 }

		
		-- 1.3.6.1.4.1.5504.5.4.19.1.24
		zhoneAdslAtucGinpShineRatio OBJECT-TYPE
			SYNTAX Unsigned32 (0..255)
			UNITS "ratio"
			MAX-ACCESS read-write
			STATUS current
			DESCRIPTION
				"gInpShineRatio - The downstream loss of rate in a 1 second interval 
				expressed as a fraction of NDR due to a single high impulse noise 
				event (SHINE) impulse noise environment expected by the operator 
				to occur at a probability acceptable for the services. The valid 
				values are all multiples of 0.001 from 0 to 0.1.  This field uses 
				1 to equal 0.001 and 100 to equal 0.1. ITU-T G.998.4 7.1.1 Control
				parameters and 7.1.2 Valid configurations."
			DEFVAL { 10 }
			::= { zhoneAdslLineConfProfileExtEntry 24 }

		
		-- 1.3.6.1.4.1.5504.5.4.19.1.25
		zhoneAdslAturGinpShineRatio OBJECT-TYPE
			SYNTAX Unsigned32 (0..255)
			UNITS "ratio"
			MAX-ACCESS read-write
			STATUS current
			DESCRIPTION
				"gInpShineRatio - The upstream loss of rate in a 1 second interval 
				expressed as a fraction of NDR due to a single high impulse noise 
				event (SHINE) impulse noise environment expected by the operator 
				to occur at a probability acceptable for the services. The valid 
				values are all multiples of 0.001 from 0 to 0.1.  This field uses 
				1 to equal 0.001 and 100 to equal 0.1. ITU-T G.998.4 7.1.1 Control
				parameters and 7.1.2 Valid configurations."
			DEFVAL { 10 }
			::= { zhoneAdslLineConfProfileExtEntry 25 }

		
		-- 1.3.6.1.4.1.5504.5.4.19.1.26
		zhoneAdslAtucGinpLeftrThreshold OBJECT-TYPE
			SYNTAX Unsigned32 (0..99)
			UNITS "ratio"
			MAX-ACCESS read-write
			STATUS current
			DESCRIPTION
				"gInpLeftrThreshold - The downstream rate Threshold below which the 
				Low Error Free Rate (LEFTR) defect is declared. The threshold used 
				to declare leftr defects is expressed in fraction of the net data 
				rate (NDR). The value 0 is a special value to indicate that the 
				receiver shall use a special value for declaring leftr defect. 
				The minimum valid threshold to declare leftr is ETR/2. The receiver 
				shall ignore threshold values that are less than the minimum and shall
				use ETR/2 for declaring leftr defect instead. The valid values are 
				all multiples of 0.01 from 0.01 to 0.99. This field uses 1 to equal
				0.01 and 99 to equal 0.99."
			DEFVAL { 0 }
			::= { zhoneAdslLineConfProfileExtEntry 26 }

		
		-- 1.3.6.1.4.1.5504.5.4.19.1.27
		zhoneAdslAturGinpLeftrThreshold OBJECT-TYPE
			SYNTAX Unsigned32 (0..99)
			UNITS "ratio"
			MAX-ACCESS read-write
			STATUS current
			DESCRIPTION
				"gInpLeftrThreshold - The upstream rate Threshold below which the 
				Low Error Free Rate (LEFTR) defect is declared. The threshold used 
				to declare leftr defects is expressed in fraction of the net data 
				rate (NDR). The value 0 is a special value to indicate that the 
				receiver shall use a special value for declaring leftr defect. 
				The minimum valid threshold to declare leftr is ETR/2. The receiver 
				shall ignore threshold values that are less than the minimum and shall
				use ETR/2 for declaring leftr defect instead. The valid values are 
				all multiples of 0.01 from 0.01 to 0.99. This field uses 1 to equal
				0.01 and 99 to equal 0.99."
			DEFVAL { 0 }
			::= { zhoneAdslLineConfProfileExtEntry 27 }

		
		-- 1.3.6.1.4.1.5504.5.4.19.1.28
		zhoneAdslAtucGinpMaxDelay OBJECT-TYPE
			SYNTAX Unsigned32 (0..63)
			UNITS "mSecs"
			MAX-ACCESS read-write
			STATUS current
			DESCRIPTION
				"gInpMaxDelay - The maximum downstream delay in ms. This is the upper 
				limit for the delay that is added to the transmission delay only caused 
				by retransmissions. Here the receiver anAdding support for G.INP / ITU-T G.998.4d/or the transmitter shall 
				identify and discard all DTUs whose payload cannot be transferred over 
				the reference point at the receiver without violating the delay_max 
				limit. The time stamp shall be the criterion for discarding the DTUs. 
				The processing delay between the U-interface and the retransmission 
				sub-layer of the receiver in the retransmission data path direction 
				shall be excluded from consideration for delay_max in the retransmission 
				data path direction. The valid values are all integers from 1 to 63. 
				ITU-T G.998.4 7.1.1 Control parameters, 7.1.2 Valid configurations, and 
				8.1.6 Time Stamp."
			DEFVAL { 20 }
			::= { zhoneAdslLineConfProfileExtEntry 28 }

		
		-- 1.3.6.1.4.1.5504.5.4.19.1.29
		zhoneAdslAturGinpMaxDelay OBJECT-TYPE
			SYNTAX Unsigned32 (0..63)
			UNITS "mSecs"
			MAX-ACCESS read-write
			STATUS current
			DESCRIPTION
				"gInpMaxDelay - The maximum upstream delay in ms. This is the upper 
				limit for the delay that is added to the transmission delay only caused 
				by retransmissions. Here the receiver anAdding support for G.INP / ITU-T G.998.4d/or the transmitter shall 
				identify and discard all DTUs whose payload cannot be transferred over 
				the reference point at the receiver without violating the delay_max 
				limit. The time stamp shall be the criterion for discarding the DTUs. 
				The processing delay between the U-interface and the retransmission 
				sub-layer of the receiver in the retransmission data path direction 
				shall be excluded from consideration for delay_max in the retransmission 
				data path direction. The valid values are all integers from 1 to 63. 
				ITU-T G.998.4 7.1.1 Control parameters, 7.1.2 Valid configurations, and 
				8.1.6 Time Stamp."
			DEFVAL { 20 }
			::= { zhoneAdslLineConfProfileExtEntry 29 }

		
		-- 1.3.6.1.4.1.5504.5.4.19.1.30
		zhoneAdslAtucGinpMinDelay OBJECT-TYPE
			SYNTAX Unsigned32 (0..63)
			UNITS "mSecs"
			MAX-ACCESS read-write
			STATUS current
			DESCRIPTION
				"Description."
			DEFVAL { 0 }
			::= { zhoneAdslLineConfProfileExtEntry 30 }

		
		-- 1.3.6.1.4.1.5504.5.4.19.1.31
		zhoneAdslAturGinpMinDelay OBJECT-TYPE
			SYNTAX Unsigned32 (0..63)
			UNITS "mSecs"
			MAX-ACCESS read-write
			STATUS current
			DESCRIPTION
				"Description."
			DEFVAL { 0 }
			::= { zhoneAdslLineConfProfileExtEntry 31 }

		
		-- 1.3.6.1.4.1.5504.5.4.19.1.32
		zhoneAdslAtucGinpMin OBJECT-TYPE
			SYNTAX Unsigned32 (0..127)
			MAX-ACCESS read-write
			STATUS current
			DESCRIPTION
				"ginpMin - The minimum downstream impulse noise protection (INP) against 
				single high impulse noise event (SHINE) in discrete multitone (DMT) 
				symbols. The valid values are all integers from 0 to 63 for system with 
				a sub-carrier spacing of 4.3125 kHz. The valid values are all integers 
				from 0 to 127 for system with a sub-carrier spacing of 8.625 kHz. ITU-T 
				G.998.4 7.1.1 Control parameters and 7.1.2 Valid configurations."
			DEFVAL { 4 }
			::= { zhoneAdslLineConfProfileExtEntry 32 }

		
		-- 1.3.6.1.4.1.5504.5.4.19.1.33
		zhoneAdslAturGinpMin OBJECT-TYPE
			SYNTAX Unsigned32 (0..127)
			UNITS "symbols"
			MAX-ACCESS read-write
			STATUS current
			DESCRIPTION
				"ginpMin - The minimum upstream impulse noise protection (INP) against 
				single high impulse noise event (SHINE) in discrete multitone (DMT) 
				symbols. The valid values are all integers from 0 to 63 for system with 
				a sub-carrier spacing of 4.3125 kHz. The valid values are all integers 
				from 0 to 127 for system with a sub-carrier spacing of 8.625 kHz. ITU-T 
				G.998.4 7.1.1 Control parameters and 7.1.2 Valid configurations."
			DEFVAL { 4 }
			::= { zhoneAdslLineConfProfileExtEntry 33 }

		
		-- 1.3.6.1.4.1.5504.5.4.19.1.34
		zhoneAdslAtucGinpMinRSoverhead OBJECT-TYPE
			SYNTAX Unsigned32 (0..64)
			UNITS "ratio"
			MAX-ACCESS read-write
			STATUS current
			DESCRIPTION
				"gInpMinRSoverhead - This value specifies the downstream bandwidth 
				reserved for RS (reed-solomon) codewords. The minimum guaranteed R/N 
				ratio. The unit is 1/256th and the range is 0..64 (0 to 25%)."
			DEFVAL { 0 }
			::= { zhoneAdslLineConfProfileExtEntry 34 }

		
		-- 1.3.6.1.4.1.5504.5.4.19.1.35
		zhoneAdslAturGinpMinRSoverhead OBJECT-TYPE
			SYNTAX Unsigned32 (0..64)
			UNITS "ratio"
			MAX-ACCESS read-write
			STATUS current
			DESCRIPTION
				"gInpMinRSoverhead - This value specifies the upstream bandwidth 
				reserved for RS (reed-solomon) codewords. The minimum guaranteed R/N 
				ratio. The unit is 1/256th and the range is 0..64 (0 to 25%)."
			DEFVAL { 0 }
			::= { zhoneAdslLineConfProfileExtEntry 35 }

		
		-- 1.3.6.1.4.1.5504.5.4.19.1.36
		zhoneAdslAtucGinpReinCfg OBJECT-TYPE
			SYNTAX Unsigned32 (0..7)
			UNITS "symbols"
			MAX-ACCESS read-write
			STATUS current
			DESCRIPTION
				"gInpReinCfg - The minimum downstream impulse protection against 
				electrical repetitive impulse noise (REIN) in DMT symbols. The valid 
				values are all integers from 0 to 7 for system with a sub-carrier 
				spacing of 4.3125 kHz. The valid values are all integers from 0 to 13 
				for system with a sub-carrier spacing of 8.625 kHz. ITU-T G.998.4 7.1.1 
				Control parameters and 7.1.2 Valid configurations."
			DEFVAL { 0 }
			::= { zhoneAdslLineConfProfileExtEntry 36 }

		
		-- 1.3.6.1.4.1.5504.5.4.19.1.37
		zhoneAdslAturGinpReinCfg OBJECT-TYPE
			SYNTAX Unsigned32 (0..7)
			UNITS "symbols"
			MAX-ACCESS read-write
			STATUS current
			DESCRIPTION
				"gInpReinCfg - The minimum upstream impulse protection against 
				electrical repetitive impulse noise (REIN) in DMT symbols. The valid 
				values are all integers from 0 to 7 for system with a sub-carrier 
				spacing of 4.3125 kHz. The valid values are all integers from 0 to 13 
				for system with a sub-carrier spacing of 8.625 kHz. ITU-T G.998.4 7.1.1 
				Control parameters and 7.1.2 Valid configurations."
			DEFVAL { 0 }
			::= { zhoneAdslLineConfProfileExtEntry 37 }

		
		-- 1.3.6.1.4.1.5504.5.4.19.1.38
		zhoneAdslAtucGinpReinFreq OBJECT-TYPE
			SYNTAX INTEGER
				{
				freq100hz(1),
				freq120hz(2)
				}
			UNITS "Hz"
			MAX-ACCESS read-write
			STATUS current
			DESCRIPTION
				"ginpReinFreq specifies the frequency of REIN inter-arrival time. It is used 
				in the Channel Initialization Policy and on-line reconfiguration procedures. 
				REIN is commonly coupled from electrical power cables appliances drawing power
				from the AC electrical power network, having a repetition rate of twice the 
				AC power frequency (100 or 120 Hz). The valid values are integers 100 hz or 
				120 hz. ITU-T G.998.4 7.1.1 Control parameters and 7.1.2 Valid configurations."
			DEFVAL { freq120hz }
			::= { zhoneAdslLineConfProfileExtEntry 38 }

		
		-- 1.3.6.1.4.1.5504.5.4.19.1.39
		zhoneAdslAturGinpReinFreq OBJECT-TYPE
			SYNTAX INTEGER
				{
				freq100hz(1),
				freq120hz(2)
				}
			UNITS "Hz"
			MAX-ACCESS read-write
			STATUS current
			DESCRIPTION
				"ginpReinFreq specifies the frequency of REIN inter-arrival time. It is used 
				in the Channel Initialization Policy and on-line reconfiguration procedures. 
				REIN is commonly coupled from electrical power cables appliances drawing power
				from the AC electrical power network, having a repetition rate of twice the 
				AC power frequency (100 or 120 Hz). The valid values are integers 100 hz or 
				120 hz. ITU-T G.998.4 7.1.1 Control parameters and 7.1.2 Valid configurations."
			DEFVAL { freq120hz }
			::= { zhoneAdslLineConfProfileExtEntry 39 }

		
		-- 1.3.6.1.4.1.5504.5.4.19.1.40
		zhoneAdslAtucGinpRtxMode OBJECT-TYPE
			SYNTAX INTEGER
				{
				forbidden(1),
				preferred(2),
				forced(3),
				testmode(4)
				}
			UNITS "mode"
			MAX-ACCESS read-write
			STATUS current
			DESCRIPTION
				"gInpRtxMode - Downstream retransmission Mode (RTX MODE). The RTX_MODE 
				is a configuration parameter used to control activation of retransmission
				during initialization. This parameter has 4 valid values:
				 FORBIDDEN: ITU-T G.998.4 retransmission not allowed.
				 PREFERRED: ITU-T G.998.4 retransmission is preferred by the operator. 
				   (i.e., if ITU-T G.998.4 RTX capability is supported by both XTU's, 
				   the XTU's shall select ITU-T G.998.4 operation for this direction).
				 FORCED: Force the use of the ITU-T G.998.4 retransmission.
				   (i.e., if ITU-T G.998.4 RTX capability in this direction is not 
				   supported by both XTU's or not selected by the XTU's, an 
				   initialization failure shall result).
				   NOTE: Due to the optionality of ITU-T G.998.4 retransmission in 
				   upstream direction, the use of FORCED in upstream may lead to 
				   initialization failure, even if the XTU is supporting ITU-T G.998.4 
				   (in downstream).
				 TESTMODE: Force the use of the ITU-T G.998.4 retransmission in the 
				   test mode described in clause 10.4. (i.e., if ITU-T G.998.4 RTX 
				   capability is not supported by both XTU's or not selected by the 
				   XTU's, an initialization failure shall result).
				ITU-T G.998.4 11.1.13 Retransmission Mode (RTX_MODE)"
			DEFVAL { preferred }
			::= { zhoneAdslLineConfProfileExtEntry 40 }

		
		-- 1.3.6.1.4.1.5504.5.4.19.1.41
		zhoneAdslAturGinpRtxMode OBJECT-TYPE
			SYNTAX INTEGER
				{
				forbidden(1),
				preferred(2),
				forced(3),
				testmode(4)
				}
			UNITS "mode"
			MAX-ACCESS read-write
			STATUS current
			DESCRIPTION
				"gInpRtxMode - Upstream retransmission Mode (RTX MODE). The RTX_MODE 
				is a configuration parameter used to control activation of retransmission
				during initialization. This parameter has 4 valid values:
				 FORBIDDEN: ITU-T G.998.4 retransmission not allowed.
				 PREFERRED: ITU-T G.998.4 retransmission is preferred by the operator. 
				   (i.e., if ITU-T G.998.4 RTX capability is supported by both XTU's, 
				   the XTU's shall select ITU-T G.998.4 operation for this direction).
				 FORCED: Force the use of the ITU-T G.998.4 retransmission.
				   (i.e., if ITU-T G.998.4 RTX capability in this direction is not 
				   supported by both XTU's or not selected by the XTU's, an 
				   initialization failure shall result).
				   NOTE: Due to the optionality of ITU-T G.998.4 retransmission in 
				   upstream direction, the use of FORCED in upstream may lead to 
				   initialization failure, even if the XTU is supporting ITU-T G.998.4 
				   (in downstream).
				 TESTMODE: Force the use of the ITU-T G.998.4 retransmission in the 
				   test mode described in clause 10.4. (i.e., if ITU-T G.998.4 RTX 
				   capability is not supported by both XTU's or not selected by the 
				   XTU's, an initialization failure shall result).
				ITU-T G.998.4 11.1.13 Retransmission Mode (RTX_MODE)"
			DEFVAL { preferred }
			::= { zhoneAdslLineConfProfileExtEntry 41 }

		
-- 
-- Objects in zhoneAdslSelt support ADSL SELT (Single-Ended
-- Loop Test). This is a method for measuring the quality
-- of an ADSL line from the CO when no CPE is attached.
-- zhoneAdslSelt is modeled after pdnAdslSeltObjects in
-- the Paradyne SELT mib, PDN-ADSL-SELT-MIB.
-- None of the SELT objects is persistent.
-- 
-- zhoneAdslSeltUnits
--   Supports limited "internationalization" of SELT.
-- 
-- zhoneAdslSeltTable
--   Provides configuration and control of a SELT test.
-- 
-- zhoneAdslSeltLcTable
--   Provides overall loop characterization. How many
--   segments are on the loop, the length of each,
--   the wire guage of each, etc.
-- 
-- zhoneAdslSeltLnfTable
--   Provides loop noise floor measurement, a set of
--   values, one for each ADSL "tone" indicating the
--   noise at that tone.
-- 
		-- 1.3.6.1.4.1.5504.5.4.20
		zhoneAdslSelt OBJECT IDENTIFIER ::= { zhoneDsl 20 }

		
		-- 1.3.6.1.4.1.5504.5.4.20.1
		zhoneAdslSeltUnits OBJECT-TYPE
			SYNTAX INTEGER
				{
				awg(1),
				metric(2),
				metricJapan(3)
				}
			MAX-ACCESS read-write
			STATUS current
			DESCRIPTION
				"This object permits the selection of the metric unit
				to be used when reporting SELT test results.
				(i.e for AWG results are in feet and for 
				metric/metricJapan results are in meters).
				
				This configuration parameter applies to all the SELT
				tests run in the device."
			DEFVAL { awg }
			::= { zhoneAdslSelt 1 }

		
		-- 1.3.6.1.4.1.5504.5.4.20.2
		zhoneAdslSeltTable OBJECT-TYPE
			SYNTAX SEQUENCE OF ZhoneAdslSeltEntry
			MAX-ACCESS not-accessible
			STATUS current
			DESCRIPTION
				"This table alows initiation/termination of
				SELT tests."
			::= { zhoneAdslSelt 2 }

		
		-- 1.3.6.1.4.1.5504.5.4.20.2.1
		zhoneAdslSeltEntry OBJECT-TYPE
			SYNTAX ZhoneAdslSeltEntry
			MAX-ACCESS not-accessible
			STATUS current
			DESCRIPTION
				"Each entry represents an instance of a SELT test
				currently running or ever run (since last system reset)
				on an ADSL interface.
				
				There are entries in this table for every active
				running tests and tests that are in the process
				of being stopped or have terminated already.
				
				There are also entries for ADSL interfaces that
				have not run a test since last since reset; the
				agent will return zhoneAdslSeltStatus=notStarted
				for those cases."
			INDEX { ifIndex }
			::= { zhoneAdslSeltTable 1 }

		
		ZhoneAdslSeltEntry ::=
			SEQUENCE { 
				zhoneAdslSeltCmd
					INTEGER,
				zhoneAdslSeltStatus
					INTEGER,
				zhoneAdslSeltDuration
					Unsigned32,
				zhoneAdslSeltTimeLeft
					Unsigned32,
				zhoneAdslSeltDateAndTimeCompleted
					DateAndTime,
				zhoneAdslSeltDevice
					INTEGER,
				zhoneAdslSeltBridgeTapsSupported
					TruthValue,
				zhoneAdslSeltGaugeExpected
					INTEGER,
				zhoneAdslSeltCable
					INTEGER
			 }

		-- 1.3.6.1.4.1.5504.5.4.20.2.1.1
		zhoneAdslSeltCmd OBJECT-TYPE
			SYNTAX INTEGER
				{
				noOp(1),
				start(2),
				stop(3),
				clearResults(4)
				}
			MAX-ACCESS read-write
			STATUS current
			DESCRIPTION
				"This object corresponds to the list of test operations
				that can be performed.
				
				The possible values are
				    noOp         (1),  -- used when reading the object
				    start        (2),  -- start test
				    stop         (3),  -- stop an initiated test
				    clearResults (4)   -- clears the results of that test
						 
				Reading this object will always return the value 'noOp (1)'.
				
				If SELT test is already running on an ADSL interface, 
				the only possible test command is 'stop (1)'.
				
				The clearResults(4) command clears test results by removing
				an entry in both the zhoneAdslSeltLcTable and the 
				zhoneAdslSeltLnfTable.  After the execution of this command, 
				the appropriate value for zhoneAdslSeltStatus would be
				resultsCleared(5)."
			DEFVAL { noOp }
			::= { zhoneAdslSeltEntry 1 }

		
		-- 1.3.6.1.4.1.5504.5.4.20.2.1.2
		zhoneAdslSeltStatus OBJECT-TYPE
			SYNTAX INTEGER
				{
				inProgress(1),
				stoppedInProgress(2),
				complete(3),
				notStarted(4),
				resultsCleared(5),
				aborted(6),
				timedOut(7),
				unsupported(8),
				portActive(9),
				measurementsInvalid(10)
				}
			MAX-ACCESS read-only
			STATUS current
			DESCRIPTION
				"This object provides status about any SELT test
				running or ever run (since last reset) on an ADSL
				interface. This object can be read by NMS managers
				to determine the status of a test; that is:
				                        
				inProgress (1)        - if the test is currently running.
				
				stoppedInProgress (2) - if a request to stop the test
				                        is still in progress.
				
				complete (3)          - if the test has been run at least 
				                        once since system reset and has 
				                        completed.
				
				notStarted (4)        - if the test has not been run on 
				                        this interface since last system 
				                        reset. 
				
				resultsCleared (5)    - if the entries in the test results table,
				                        Lc and Lnf, were removed as the result
				                        of the execution of the clearResults(4)
				                        zhoneAdslSeltCmd.
				
				aborted (6)           - if the test was aborted by the user before
				                        it could complete. In this case, the Lc
				                        and Lnf tables will have been removed.
				
				timedOut (7)          - if the test was aborted automatically
				                        because it did not complete before the
				                        timeout specified by zhoneAdslSeltDuration.
				                        In this case, the Lc and Lnf tables will
				                        have been removed.
				
				unsupported (8)       - the device does not support SELT.
				
				portActive (9)        - port must be OUT-OF-SERVICE to run SELT.
				
				measurementsInvalid(10)- SELT return invalid measurements."
			::= { zhoneAdslSeltEntry 2 }

		
		-- 1.3.6.1.4.1.5504.5.4.20.2.1.3
		zhoneAdslSeltDuration OBJECT-TYPE
			SYNTAX Unsigned32
			UNITS "seconds"
			MAX-ACCESS read-write
			STATUS current
			DESCRIPTION
				"This object provides the maximum time in seconds that
				the SELT test measurement can take. If the test runs
				longer than this, it will be aborted, and the results
				(if any) will be removed."
			DEFVAL { 600 }
			::= { zhoneAdslSeltEntry 3 }

		
		-- 1.3.6.1.4.1.5504.5.4.20.2.1.4
		zhoneAdslSeltTimeLeft OBJECT-TYPE
			SYNTAX Unsigned32
			UNITS "seconds"
			MAX-ACCESS read-only
			STATUS current
			DESCRIPTION
				"This object provides the approximate time left in seconds
				for the test running on this ADSL interface.
				
				This object will return 0 if no test is actively 
				running on the ADSL interface specified."
			::= { zhoneAdslSeltEntry 4 }

		
		-- 1.3.6.1.4.1.5504.5.4.20.2.1.5
		zhoneAdslSeltDateAndTimeCompleted OBJECT-TYPE
			SYNTAX DateAndTime
			MAX-ACCESS read-only
			STATUS current
			DESCRIPTION
				"This object provides a date and time stamp 
				corresponding to the last completion of a test
				where valid results were obtained.  If no test
				results are available, perhaps in the situation
				where no test has ever been started, this object
				shall return a value that has all the fields set
				to zero."
			::= { zhoneAdslSeltEntry 5 }

		
		-- 1.3.6.1.4.1.5504.5.4.20.2.1.6
		zhoneAdslSeltDevice OBJECT-TYPE
			SYNTAX INTEGER
				{
				other(1),
				conexantG24(2),
				broadcom(3)
				}
			MAX-ACCESS read-only
			STATUS current
			DESCRIPTION
				"This object provides a way to query which device (chip)
				is providing the SELT measurement on this interface.
				other (1)       - a device not in the list below
				conexantG24 (2) - Indicates any Conexant based chipset
				broadcom (3)    - Indicates any Broadcom based chipset"
			::= { zhoneAdslSeltEntry 6 }

		
		-- 1.3.6.1.4.1.5504.5.4.20.2.1.7
		zhoneAdslSeltBridgeTapsSupported OBJECT-TYPE
			SYNTAX TruthValue
			MAX-ACCESS read-only
			STATUS current
			DESCRIPTION
				"This object provides a way to query whether or not the
				measurement device (zhoneAdslSeltDevice) supports SELT
				on loops that have bridge taps. If this object returns
				false, and SELT is run on a loop with bridge taps, the
				SELT results will be unreliable."
			::= { zhoneAdslSeltEntry 7 }

		
		-- 1.3.6.1.4.1.5504.5.4.20.2.1.8
		zhoneAdslSeltGaugeExpected OBJECT-TYPE
			SYNTAX INTEGER
				{
				unknown(1),
				awg19(19),
				awg22(22),
				awg24(24),
				awg26(26),
				metric32(1032),
				metric40(1040),
				metric50(1050),
				metric63(1063),
				metric90(1090),
				metricJapan32(2032),
				metricJapan40(2040),
				metricJapan50(2050),
				metricJapan65(2065),
				metricJapan90(2090)
				}
			MAX-ACCESS read-write
			STATUS current
			DESCRIPTION
				"This object configures the expected wire gauge of the loop.
				The values supported depend on which chip is being used
				to perform the selt measurement. For example, the Conexant
				G24 must be configured as either awg24 or awg26 (or the
				metric equivalents .50mm or .40mm respectively).
				The values are:
				
				unknown  (1),
				
				AWG--
				awg26    (26),
				awg24    (24),
				awg22    (22),
				awg19    (19),
				
				Metric--
				metric32 (1032), -- (0.32mm)
				metric40 (1040), -- (0.40mm)
				metric50 (1050), -- (0.50mm)
				metric63 (1063), -- (0.63mm)
				metric90 (1090), -- (0.90mm)
				
				Metric/Japan--
				metricJapan32 (2032), -- (0.32mm)
				metricJapan40 (2040), -- (0.40mm)
				metricJapan50 (2050), -- (0.50mm)
				metricJapan65 (2065), -- (0.65mm)
				metricJapan90 (2090)  -- (0.90mm)
				"
			DEFVAL { awg26 }
			::= { zhoneAdslSeltEntry 8 }

		
		-- 1.3.6.1.4.1.5504.5.4.20.2.1.9
		zhoneAdslSeltCable OBJECT-TYPE
			SYNTAX INTEGER
				{
				real(1),
				simulatedWithDls90(2),
				simulatedWithDls400(3)
				}
			MAX-ACCESS read-write
			STATUS current
			DESCRIPTION
				"This object configures the selt algorithm with the type of cable
				being tested. For real-world testing with actual wire, this should
				be set to 'real'. In a lab environment, this can be set to match
				the type of loop simulator being used. The values supported depend
				on which chip is being used to perform the selt measurement. Real
				cable is always supported. The Conexant G24 also supports simulated
				cable using a Consultronics/Spirent DLS90 or DLS400 line simulator.
				Other chips may support other options. The values are:
				real (1),
				simulatedWithDls90 (2),
				simulatedWithDls400 (3).
				"
			DEFVAL { real }
			::= { zhoneAdslSeltEntry 9 }

		
		-- 1.3.6.1.4.1.5504.5.4.20.3
		zhoneAdslSeltLcTable OBJECT-TYPE
			SYNTAX SEQUENCE OF ZhoneAdslSeltLcEntry
			MAX-ACCESS not-accessible
			STATUS current
			DESCRIPTION
				"This table posts results for loop characterization tests
				completed. Support for multiple segments was borrowed from
				the Paradyne SELT MIB, but may not be supported, depending
				on the hardware being used to implement SELT.
				
				To conserve memory, LC results are only saved on interfaces
				that have successfully completed a SELT measurement. A GET
				of a table entry for an ifIndex that has not successfully run
				a SELT test will return NO-SUCH-NAME. To determine whether or
				not SELT test results exist for a given ifIndex, query
				zhoneAdslSeltStatus. LC results will only be available if
				the status reads 'complete'."
			::= { zhoneAdslSelt 3 }

		
		-- 1.3.6.1.4.1.5504.5.4.20.3.1
		zhoneAdslSeltLcEntry OBJECT-TYPE
			SYNTAX ZhoneAdslSeltLcEntry
			MAX-ACCESS not-accessible
			STATUS current
			DESCRIPTION
				"Each entry represents the results of a loop
				characterization test performed over an ADSL
				interface."
			INDEX { ifIndex, zhoneAdslSeltLcSegmentIndex }
			::= { zhoneAdslSeltLcTable 1 }

		
		ZhoneAdslSeltLcEntry ::=
			SEQUENCE { 
				zhoneAdslSeltLcSegmentIndex
					Integer32,
				zhoneAdslSeltLcSegmentLength
					Integer32,
				zhoneAdslSeltLcSegmentGauge
					INTEGER,
				zhoneAdslSeltLcSegmentType
					INTEGER,
				zhoneAdslSeltLcDsRate
					Integer32,
				zhoneAdslSeltLcUsRate
					Integer32
			 }

		-- 1.3.6.1.4.1.5504.5.4.20.3.1.1
		zhoneAdslSeltLcSegmentIndex OBJECT-TYPE
			SYNTAX Integer32 (1..10)
			MAX-ACCESS not-accessible
			STATUS current
			DESCRIPTION
				"This object indicates the index of the segment being reported.
				From 1 segment to a possible of 10 segments could be
				identified in the loop topology."
			::= { zhoneAdslSeltLcEntry 1 }

		
		-- 1.3.6.1.4.1.5504.5.4.20.3.1.2
		zhoneAdslSeltLcSegmentLength OBJECT-TYPE
			SYNTAX Integer32
			MAX-ACCESS read-only
			STATUS current
			DESCRIPTION
				"This object indicates an estimate of the segment length
				being reported.
				"
			::= { zhoneAdslSeltLcEntry 2 }

		
		-- 1.3.6.1.4.1.5504.5.4.20.3.1.3
		zhoneAdslSeltLcSegmentGauge OBJECT-TYPE
			SYNTAX INTEGER
				{
				unknown(1),
				awg19(19),
				awg22(22),
				awg24(24),
				awg26(26),
				metric32(1032),
				metric40(1040),
				metric50(1050),
				metric63(1063),
				metric90(1090),
				metricJapan32(2032),
				metricJapan40(2040),
				metricJapan50(2050),
				metricJapan65(2065),
				metricJapan90(2090)
				}
			MAX-ACCESS read-only
			STATUS current
			DESCRIPTION
				"This object indicates the estimated Gauge of the segment
				being reported.  The gauge reported back is based on the
				zhoneAdslSeltUnits configuration parameter passed
				when the test is started. The values are:
				unknown  (1),
				
				AWG--
				awg26    (26),
				awg24    (24),
				awg22    (22),
				awg19    (19),
				
				Metric--
				metric32 (1032), -- (0.32mm)
				metric40 (1040), -- (0.40mm)
				metric50 (1050), -- (0.50mm)
				metric63 (1063), -- (0.63mm)
				metric90 (1090), -- (0.90mm)
				
				Metric/Japan--
				metricJapan32 (2032), -- (0.32mm)
				metricJapan40 (2040), -- (0.40mm)
				metricJapan50 (2050), -- (0.50mm)
				metricJapan65 (2065), -- (0.65mm)
				metricJapan90 (2090)  -- (0.90mm)
				"
			::= { zhoneAdslSeltLcEntry 3 }

		
		-- 1.3.6.1.4.1.5504.5.4.20.3.1.4
		zhoneAdslSeltLcSegmentType OBJECT-TYPE
			SYNTAX INTEGER
				{
				notPresent(1),
				inline(2),
				bridgeTap(3)
				}
			MAX-ACCESS read-only
			STATUS current
			DESCRIPTION
				"This object indicates the segment type being reported."
			::= { zhoneAdslSeltLcEntry 4 }

		
		-- 1.3.6.1.4.1.5504.5.4.20.3.1.5
		zhoneAdslSeltLcDsRate OBJECT-TYPE
			SYNTAX Integer32
			UNITS "Kbps"
			MAX-ACCESS read-only
			STATUS current
			DESCRIPTION
				"Downstream Capacity estimate
				
				This parameter represents a best-effort estimate of the achievable net 
				downstream data rate (in kbit/s) on the loop under test, under the 
				following assumptions:
				- Fast mode (i.e., operation with interleaver depth D=1, and INP=0 
				  (no impulse noise protection));
				- use of Trellis coding;
				- target margin equal to CAP-TARSNRM (see clause B.2.1.4);
				- transmit signal PSD at the U-interface of the xTU-transmitter equal 
				  to CAP-SIGNALPSD
				- noise PSD at the U-interface of the xTU-receiver equal to CAP-NOISEPSD 
				- support of bit loading from 1 to 15 bits included, in steps of 1 bit 
				  increments.
				As the capacity is a best-effort estimate, accuracy for this parameter 
				is Broadcom proprietary."
			::= { zhoneAdslSeltLcEntry 5 }

		
		-- 1.3.6.1.4.1.5504.5.4.20.3.1.6
		zhoneAdslSeltLcUsRate OBJECT-TYPE
			SYNTAX Integer32
			UNITS "Kbps"
			MAX-ACCESS read-only
			STATUS current
			DESCRIPTION
				"Upstream Capacity estimate
				
				This parameter represents a best-effort estimate of the achievable net 
				upstream data rate (in kbit/s) on the loop under test, under the 
				following assumptions:
				- Fast mode (i.e., operation with interleaver depth D=1, and INP=0 
				  (no impulse noise protection));
				- use of Trellis coding;
				- target margin equal to CAP-TARSNRM (see clause B.2.1.4);
				- transmit signal PSD at the U-interface of the xTU-transmitter equal 
				  to CAP-SIGNALPSD
				- noise PSD at the U-interface of the xTU-receiver equal to CAP-NOISEPSD 
				- support of bit loading from 1 to 15 bits included, in steps of 1 bit 
				  increments.
				As the capacity is a best-effort estimate, accuracy for this parameter 
				is Broadcom proprietary."
			::= { zhoneAdslSeltLcEntry 6 }

		
		-- 1.3.6.1.4.1.5504.5.4.20.4
		zhoneAdslSeltLnfTable OBJECT-TYPE
			SYNTAX SEQUENCE OF ZhoneAdslSeltLnfEntry
			MAX-ACCESS not-accessible
			STATUS current
			DESCRIPTION
				"The Loop Noise Floor table provides a set of noise measurements.
				The table is indexed by ifIndex. The noise mesurement consists
				of an array of values, one per sub-carrier. A 'sub-carrier' is
				also known as a 'tone' or a 'bin'. The tones are spaced at
				4.3125 KHz, so there are 512 tones from 0 Hz to 2208 KHz, which
				is the bandwidth of ADSL2+. For a particular SELT implementation,
				the chip used to measure noise may not support all of the tones.
				
				To conserve memory, LNF results are only saved on interfaces
				that have successfully completed a SELT measurement. A GET
				of a table entry for an ifIndex that has not successfully run
				a SELT test will return NO-SUCH-NAME. To determine whether or
				not SELT test results exist for a given ifIndex, query
				zhoneAdslSeltStatus. LNF results will only be available if
				the status reads 'complete'."
			::= { zhoneAdslSelt 4 }

		
		-- 1.3.6.1.4.1.5504.5.4.20.4.1
		zhoneAdslSeltLnfEntry OBJECT-TYPE
			SYNTAX ZhoneAdslSeltLnfEntry
			MAX-ACCESS not-accessible
			STATUS current
			DESCRIPTION
				"Each entry represents the results of a Loop
				Noise Floor test performed over an ADSL interface."
			INDEX { ifIndex }
			::= { zhoneAdslSeltLnfTable 1 }

		
		ZhoneAdslSeltLnfEntry ::=
			SEQUENCE { 
				zhoneAdslSeltLnfInbandNoise
					OCTET STRING,
				zhoneAdslSeltLnfInbandNoise2
					OCTET STRING,
				zhoneAdslSeltLnfInbandNoise3
					OCTET STRING,
				zhoneAdslSeltLnfInbandNoise4
					OCTET STRING,
				zhoneAdslSeltLnfInbandNoise5
					OCTET STRING,
				zhoneAdslSeltLnfInbandNoise6
					OCTET STRING,
				zhoneAdslSeltLnfInbandNoise7
					OCTET STRING,
				zhoneAdslSeltLnfInbandNoise8
					OCTET STRING
			 }

		-- 1.3.6.1.4.1.5504.5.4.20.4.1.2
		zhoneAdslSeltLnfInbandNoise OBJECT-TYPE
			SYNTAX OCTET STRING (SIZE (0..1024))
			UNITS "0.1 dBm/Hz"
			MAX-ACCESS read-only
			STATUS current
			DESCRIPTION
				"This object provides the inband noise of all of the
				sub-carriers on this line. It is an array of 16-bit
				signed integers stored in big-endian format. For
				example, string position 0 is the most-significant
				octet of the first noise value, and string position 1
				is the least-significant byte of the first noise value.
				
				Each value is a signed 16-bit 2's complement number
				scaled as least-significant bit = 1/10 dBm/Hz. e.g.
				an integer value of 35 represents 3.5 dBm/Hz.
				If the measurement is invalid it will read as
				full-scale negative (0x8000)."
			::= { zhoneAdslSeltLnfEntry 2 }

		
		-- 1.3.6.1.4.1.5504.5.4.20.4.1.3
		zhoneAdslSeltLnfInbandNoise2 OBJECT-TYPE
			SYNTAX OCTET STRING (SIZE (0..1024))
			UNITS "0.1 dBm/Hz"
			MAX-ACCESS read-only
			STATUS current
			DESCRIPTION
				"This is a duplicate object of zhoneAdslSeltLnfInbandNoise. It has been added
				to allow for transferring additional tones results for VDSL2 systems which 
				can provide results for up to 4096 tones. Since the system is limited by PDU
				size it was determined that it would be best to transfer results in groups of
				512 tones, which resulted in eight zhoneAdslSeltLnfInbandNoise objects."
			::= { zhoneAdslSeltLnfEntry 3 }

		
		-- 1.3.6.1.4.1.5504.5.4.20.4.1.4
		zhoneAdslSeltLnfInbandNoise3 OBJECT-TYPE
			SYNTAX OCTET STRING (SIZE (0..1024))
			UNITS "0.1 dBm/Hz"
			MAX-ACCESS read-only
			STATUS current
			DESCRIPTION
				"This is a duplicate object of zhoneAdslSeltLnfInbandNoise. It has been added 
				to allow for transferring additional tones results for VDSL2 systems which 
				can provide results for up to 4096 tones. Since the system is limited by PDU
				size it was determined that it would be best to transfer results in groups of
				512 tones, which resulted in eight zhoneAdslSeltLnfInbandNoise objects."
			::= { zhoneAdslSeltLnfEntry 4 }

		
		-- 1.3.6.1.4.1.5504.5.4.20.4.1.5
		zhoneAdslSeltLnfInbandNoise4 OBJECT-TYPE
			SYNTAX OCTET STRING (SIZE (0..1024))
			UNITS "0.1 dBm/Hz"
			MAX-ACCESS read-only
			STATUS current
			DESCRIPTION
				"This is a duplicate object of zhoneAdslSeltLnfInbandNoise. It has been added 
				to allow for transferring additional tones results for VDSL2 systems which 
				can provide results for up to 4096 tones. Since the system is limited by PDU 
				size it was determined that it would be best to transfer results in groups of 
				512 tones, which resulted in eight zhoneAdslSeltLnfInbandNoise objects."
			::= { zhoneAdslSeltLnfEntry 5 }

		
		-- 1.3.6.1.4.1.5504.5.4.20.4.1.6
		zhoneAdslSeltLnfInbandNoise5 OBJECT-TYPE
			SYNTAX OCTET STRING (SIZE (0..1024))
			UNITS "0.1 dBm/Hz"
			MAX-ACCESS read-only
			STATUS current
			DESCRIPTION
				"This is a duplicate object of zhoneAdslSeltLnfInbandNoise. It has been added 
				to allow for transferring additional tones results for VDSL2 systems which 
				can provide results for up to 4096 tones. Since the system is limited by PDU 
				size it was determined that it would be best to transfer results in groups of 
				512 tones, which resulted in eight zhoneAdslSeltLnfInbandNoise objects."
			::= { zhoneAdslSeltLnfEntry 6 }

		
		-- 1.3.6.1.4.1.5504.5.4.20.4.1.7
		zhoneAdslSeltLnfInbandNoise6 OBJECT-TYPE
			SYNTAX OCTET STRING (SIZE (0..1024))
			UNITS "0.1 dBm/Hz"
			MAX-ACCESS read-only
			STATUS current
			DESCRIPTION
				"This is a duplicate object of zhoneAdslSeltLnfInbandNoise. It has been added 
				to allow for transferring additional tones results for VDSL2 systems which 
				can provide results for up to 4096 tones. Since the system is limited by PDU 
				size it was determined that it would be best to transfer results in groups of 
				512 tones, which resulted in eight zhoneAdslSeltLnfInbandNoise objects."
			::= { zhoneAdslSeltLnfEntry 7 }

		
		-- 1.3.6.1.4.1.5504.5.4.20.4.1.8
		zhoneAdslSeltLnfInbandNoise7 OBJECT-TYPE
			SYNTAX OCTET STRING (SIZE (0..1024))
			UNITS "0.1 dBm/Hz"
			MAX-ACCESS read-only
			STATUS current
			DESCRIPTION
				"This is a duplicate object of zhoneAdslSeltLnfInbandNoise. It has been added 
				to allow for transferring additional tones results for VDSL2 systems which 
				can provide results for up to 4096 tones. Since the system is limited by PDU 
				size it was determined that it would be best to transfer results in groups of 
				512 tones, which resulted in eight zhoneAdslSeltLnfInbandNoise objects."
			::= { zhoneAdslSeltLnfEntry 8 }

		
		-- 1.3.6.1.4.1.5504.5.4.20.4.1.9
		zhoneAdslSeltLnfInbandNoise8 OBJECT-TYPE
			SYNTAX OCTET STRING (SIZE (0..1024))
			UNITS "0.1 dBm/Hz"
			MAX-ACCESS read-only
			STATUS current
			DESCRIPTION
				"This is a duplicate object of zhoneAdslSeltLnfInbandNoise. It has been added 
				to allow for transferring additional tones results for VDSL2 systems which 
				can provide results for up to 4096 tones. Since the system is limited by PDU 
				size it was determined that it would be best to transfer results in groups of 
				512 tones, which resulted in eight zhoneAdslSeltLnfInbandNoise objects."
			::= { zhoneAdslSeltLnfEntry 9 }

		
-- 
-- Objects in zhoneAdslDelt support ADSL DELT (Dual-
-- Ended Loop Test). This is a method for measuring
-- the line quality of an ADSL line from the CO when
-- there is a CPE attached. The CPE must also support
-- DELT. DELT is intended to help debug issues where
-- lines will not train. The devices exchange DELT
-- information in early handshakes.
-- 
-- zhoneAdslDelt is modeled after the DELT objects
-- in the IETF adsl2+ mib, which was in draft form
-- at the time that the Zhone version was defined.
-- The IETF draft document used as a model is
-- draft-ietf-adslmib-adsl2-06.txt dated 23 Feb 2006.
-- None of the DELT objects is persistent.
-- 
-- zhoneAdslDeltTable
--   Provides configuration and control of a DELT test.
--   This table contanis DELT control objects from
--   the IETF adsl2LineTable as well as Zhone-specific
--   objects.
-- 
-- zhoneAdsl2SCStatusTable
--   Provides DELT results. This table is the Zhone
--   implementation of selected objects from the IETF
--   adsl2SCStatusTable.
-- 
		-- 1.3.6.1.4.1.5504.5.4.21
		zhoneAdslDelt OBJECT IDENTIFIER ::= { zhoneDsl 21 }

		
		-- 1.3.6.1.4.1.5504.5.4.21.1
		zhoneAdsl2ScalarSCMaxInterfaces OBJECT-TYPE
			SYNTAX Unsigned32
			MAX-ACCESS read-only
			STATUS current
			DESCRIPTION
				"This value determines the upper size of zhoneAdsl2SCStatusTable.
				The maximum number of entries in zhoneAdsl2SCStatusTable is
				equal to two times the value of this attribute. Each interface
				consumes two rows in the table -- one upstream, one downstream."
			::= { zhoneAdslDelt 1 }

		
		-- 1.3.6.1.4.1.5504.5.4.21.2
		zhoneAdsl2ScalarSCAvailInterfaces OBJECT-TYPE
			SYNTAX Unsigned32
			MAX-ACCESS read-only
			STATUS current
			DESCRIPTION
				"This value determines the amount of space that is
				currently available in zhoneAdsl2SCStatusTable.
				The number of entries available in zhoneAdsl2SCStatusTable
				is equal to two times the value of this attribute.
				Each interface consumes two rows in the table -- one
				upstream, one downstream."
			::= { zhoneAdslDelt 2 }

		
		-- 1.3.6.1.4.1.5504.5.4.21.3
		zhoneAdslDeltTable OBJECT-TYPE
			SYNTAX SEQUENCE OF ZhoneAdslDeltEntry
			MAX-ACCESS not-accessible
			STATUS current
			DESCRIPTION
				"This table alows initiation/status of DELT tests."
			::= { zhoneAdslDelt 3 }

		
		-- 1.3.6.1.4.1.5504.5.4.21.3.1
		zhoneAdslDeltEntry OBJECT-TYPE
			SYNTAX ZhoneAdslDeltEntry
			MAX-ACCESS not-accessible
			STATUS current
			DESCRIPTION
				"Each entry represents an instance of a DELT test
				currently running or ever run (since last system reset)
				on an ADSL interface.
				
				There are entries in this table for every active
				running tests and tests that are in the process
				of being stopped or have terminated already.
				
				There are also entries for ADSL interfaces that have not
				run a test since last since reset; the agent will return
				zhoneAdsl2LineCmndConfLdsfFailReason=none for those cases.
				"
			INDEX { ifIndex }
			::= { zhoneAdslDeltTable 1 }

		
		ZhoneAdslDeltEntry ::=
			SEQUENCE { 
				zhoneAdsl2LineCmndConfLdsf
					INTEGER,
				zhoneAdsl2LineCmndConfLdsfFailReason
					INTEGER,
				zhoneAdslDeltDateAndTimeCompleted
					DateAndTime,
				zhoneAdslDeltDevice
					INTEGER
			 }

		-- 1.3.6.1.4.1.5504.5.4.21.3.1.1
		zhoneAdsl2LineCmndConfLdsf OBJECT-TYPE
			SYNTAX INTEGER
				{
				inhibit(0),
				force(1)
				}
			MAX-ACCESS read-write
			STATUS current
			DESCRIPTION
				"Loop diagnostics mode forced (LDSF). Setting this variable
				to 'forced' commands the device to begin loop diagnostic
				procedures. The device resets the variable to 'inhibit'.
				Regardless of the state of zhoneAdsl2LineCmndConfLdsf, the
				device will remain responsive to loop diagnostics initiated
				by the far-end ATU.
				
				As per ITU-T G.997.1, paragraph 7.3.1.1.8, before the operator
				can force loop diagnostics mode, the line must be in the L3
				(IDLE) state. When the operator forces loop diagnostics mode,
				the device will begin loop diagnostic procedures. When loop
				diagnostic procedures have completed (successfully or not),
				the device will set the state of zhoneAdsl2LineCmndConfLdsf
				to 'inhibit', return to and remain in L3 (IDLE) state."
			REFERENCE
				"ITU-T G.997.1, paragraph 7.3.1.1.8"
			DEFVAL { inhibit }
			::= { zhoneAdslDeltEntry 1 }

		
		-- 1.3.6.1.4.1.5504.5.4.21.3.1.2
		zhoneAdsl2LineCmndConfLdsfFailReason OBJECT-TYPE
			SYNTAX INTEGER
				{
				none(1),
				success(2),
				inProgress(3),
				unsupported(4),
				cannotRun(5),
				aborted(6),
				failed(7),
				illegalMode(8),
				adminUp(9),
				tableFull(10),
				noResources(11),
				insufficientCapacity(12),
				crcError(13),
				timeout(14),
				unexpectedContent(15),
				unknown(16),
				noPeerPresent(17)
				}
			MAX-ACCESS read-only
			STATUS current
			DESCRIPTION
				"The status of the recent occasion the loop diagnostics
				mode forced (LDSF) was issued for the associated line.
				Possible values are:
				  none        (1) - The default value in case LDSF was never
				                    requested for the associated line.
				  success     (2) - The recent command completed
				                    successfully.
				  inProgress  (3) - The Loop Diagnostics process is in
				                    progress.
				  unsupported (4) - The NE (Network Element) or the line
				                    card doesn't support LDSF.
				  cannotRun   (5) - The NE cannot initiate the command, due
				                    to a non specific reason.
				  aborted     (6) - The Loop Diagnostics process aborted.
				  failed      (7) - The Loop Diagnostics process failed.
				  illegalMode (8) - The NE cannot initiate the command, due
				                    to the specific mode of the relevant
				                    line.
				  adminUp     (9) - The NE cannot initiate the command, as
				                    the relevant line is administratively
				                    'Up'.
				  tableFull   (10)- The NE cannot initiate the command, due
				                    to reaching the maximum number of rows
				                    in the results table.
				  noResources (11)- The NE cannot initiate the command, due
				                    to lack of internal memory resources.
				  insufficientCapacity (12 ) -Last full initialization failed 
				                    due to insufficient capacity.
				  crcError    (13)- Last full initialization failed due to a
				                    CRC error in one of the received messages.
				  timeout     (14)- Last full initialization failed because the
				                    time duration for a particular initialization
				                    state was exceeeded.
				  unexpectedContent ( 15 ) - Last full initialization failed
				                    due to unexpected content.
				  unknown     (16)- Last full initialization failed due to 
				                    unknown causes.
				  noPeerPresent(17)-Initialization failed because there is no
				                    CPE connection.
				              "
			DEFVAL { none }
			::= { zhoneAdslDeltEntry 2 }

		
		-- 1.3.6.1.4.1.5504.5.4.21.3.1.3
		zhoneAdslDeltDateAndTimeCompleted OBJECT-TYPE
			SYNTAX DateAndTime
			MAX-ACCESS read-only
			STATUS current
			DESCRIPTION
				"This object provides a date and time stamp 
				corresponding to the last completion of a test
				where valid results were obtained.  If no test
				results are available, perhaps in the situation
				where no test has ever been started, this object
				shall return a value that has all the fields set
				to zero."
			::= { zhoneAdslDeltEntry 3 }

		
		-- 1.3.6.1.4.1.5504.5.4.21.3.1.4
		zhoneAdslDeltDevice OBJECT-TYPE
			SYNTAX INTEGER
				{
				other(1),
				conexantG24(2),
				broadcom(3)
				}
			MAX-ACCESS read-only
			STATUS current
			DESCRIPTION
				"This object provides a way to query which device (chip)
				is providing the DELT measurement on this interface.
				other (1)       - a device not in the list below
				conexantG24 (2) - Conexant chipset
				broadcom (3)    - Broadcom chipset"
			::= { zhoneAdslDeltEntry 4 }

		
		-- 1.3.6.1.4.1.5504.5.4.21.4
		zhoneAdsl2SCStatusTable OBJECT-TYPE
			SYNTAX SEQUENCE OF ZhoneAdsl2SCStatusEntry
			MAX-ACCESS not-accessible
			STATUS current
			DESCRIPTION
				"The table zhoneAdsl2SCStatusTable contains status parameters
				of ADSL2 sub-carriers. The following points apply to this
				table :
				1.  The main purpose of this table is to hold the results
				    of a DELT test.
				2.  This table also holds parameters obtained at line
				    initialization time.
				3.  The rows in this table are volatile. That is they are
				    lost if the SNMP agent is rebooted.
				4.  Due to the large OCTET STRING attributes in this table,
				    the worst case memory requirements for this table are
				    very high. The manager may use the row status attribute
				    of this table to delete rows in order to reclaim memory.
				5.  The manager may create rows in this table. The SNMP
				    agent may create rows in this table. Only the manager
				    may delete rows in this table.
				6.  The maximum number of rows allowable in this table is
				    indicated by the scalar attribute
				    zhoneAdsl2ScalarSCMaxInterfaces.
				    The number of rows available in this table is indicated
				    by the scalar attribute zhoneAdsl2ScalarSCAvailInterfaces.
				7.  The SNMP agent is permitted to create rows in this table
				    when a DELT test completes successfully or when line
				    initialization occurs. It is not mandatory for the SNMP
				    agent to create rows in this table, hence it may be
				    necessary for the manager to create rows in this table
				    before any results can be stored.
				8.  If the manager attempts to create a row in this table
				    and there are no more rows available, the creation
				    attempt will fail and the response to the SNMP SET PDU
				    will contain the error noCreation(11).
				9.  If the SNMP agent attempts to create a row in this table
				    and there are no more rows available, the creation
				    attempt will fail and the attribute
				    zhoneAdsl2LineCmndConfLdsfFailReason will indicate the
				    reason for the failure. The failure reason will be either
				    tableFull(10) or noResources(11).
				10. An example of use of this table is as follows:
				    Step 1. : The DELT test is started by setting the
				            : zhoneAdsl2LineCmndConfLdsf from inhibit to force.
				    Step 2. : The DELT test completes and valid data is
				            : available.
				    Step 3. : The row in the zhoneAdsl2SCStatusTable where the
				            : results will be stored does not yet exist so
				            : the SNMP agent attempts to create the row.
				    Step 4. : Due to a low memory condition, a row in the
				            : zhoneAdsl2SCStatusTable table cannot be created
				            : at this time.
				    Step 5. : The reason for the failure, tableFull(10), is
				            : indicated in the zhoneAdsl2LineCmndConfLdsfFailReason
				            : attribute.
				11. Another example of use of this table is as follows:
				    Step 1. : The DELT test is started by setting the
				            : zhoneAdsl2LineCmndConfLdsf from inhibit to force.
				    Step 2. : The DELT test completes and valid data is
				            : available.
				    Step 3. : The row in the zhoneAdsl2SCStatusTable where the
				            : results will be stored does not yet exist so
				            : the SNMP agent attempts to create the row.
				    Step 4. : The row creation is successful.
				    Step 5. : The value of the attribute
				            : zhoneAdsl2LineCmndConfLdsfFailReasonreason is set
				            : to success(2).
				12. Another example of use of this table is as follows:
				    Step 1. : The manager creates a row in zhoneAdsl2SCStatusTable
				            : for a particular ADSL2 line.
				    Step 2. : The DELT test is started on the above mentioned
				            : line by setting the zhoneAdsl2LineCmndConfLdsf from
				            : inhibit to force.
				    Step 3. : The DELT test completes and valid data is
				            : available.
				    Step 4. : The value of the attribute
				            : zhoneAdsl2LineCmndConfLdsfFailReasonreason is set
				            : to success(2)."
			::= { zhoneAdslDelt 4 }

		
		-- 1.3.6.1.4.1.5504.5.4.21.4.1
		zhoneAdsl2SCStatusEntry OBJECT-TYPE
			SYNTAX ZhoneAdsl2SCStatusEntry
			MAX-ACCESS not-accessible
			STATUS current
			DESCRIPTION
				"The table zhoneAdsl2SCStatusEntry contains status parameters
				of ADSL2 sub-carriers.
				The index of this table is an interface index where the
				interface has an ifType of adsl(94) or adsl2(230), plus
				a direction (downstream or upstream)."
			INDEX { ifIndex, zhoneAdsl2SCStatusDirection }
			::= { zhoneAdsl2SCStatusTable 1 }

		
		ZhoneAdsl2SCStatusEntry ::=
			SEQUENCE { 
				zhoneAdsl2SCStatusDirection
					ZhoneAdsl2Direction,
				zhoneAdsl2SCStatusMtime
					Unsigned32,
				zhoneAdsl2SCStatusSnr
					OCTET STRING,
				zhoneAdsl2SCStatusBitsAlloc
					OCTET STRING,
				zhoneAdsl2SCStatusLogMt
					Unsigned32,
				zhoneAdsl2SCStatusLog
					OCTET STRING,
				zhoneAdsl2SCStatusQlnMt
					Unsigned32,
				zhoneAdsl2SCStatusQln
					OCTET STRING,
				zhoneAdsl2SCStatusLnAtten
					Unsigned32,
				zhoneAdsl2SCStatusSigAtten
					Unsigned32,
				zhoneAdsl2SCStatusSnrMargin
					Integer32,
				zhoneAdsl2SCStatusAttainableRate
					Unsigned32,
				zhoneAdsl2SCStatusActAtp
					Integer32,
				zhoneAdsl2SCStatusRowStatus
					RowStatus
			 }

		-- 1.3.6.1.4.1.5504.5.4.21.4.1.1
		zhoneAdsl2SCStatusDirection OBJECT-TYPE
			SYNTAX ZhoneAdsl2Direction
			MAX-ACCESS not-accessible
			STATUS current
			DESCRIPTION
				"The direction of the sub-carrier either upstream or
				downstream."
			::= { zhoneAdsl2SCStatusEntry 1 }

		
		-- 1.3.6.1.4.1.5504.5.4.21.4.1.2
		zhoneAdsl2SCStatusMtime OBJECT-TYPE
			SYNTAX Unsigned32
			UNITS "symbols"
			MAX-ACCESS read-only
			STATUS current
			DESCRIPTION
				"SNR Measurement Time.  The number of symbols used to
				measure the SNR values on the respective transmission
				direction.  It should correspond to the value specified in the
				recommendation (e.g., the number of symbols in 1 second
				time interval for G.992.3).  This parameter corresponds to
				1 second in loop diagnostic procedure and should be updated
				otherwise."
			REFERENCE
				"ITU-T G.997.1, paragraph 7.5.1.20.1 (SNRMTds)
				and paragraph 7.5.1.20.3 (SNRMTus)"
			::= { zhoneAdsl2SCStatusEntry 2 }

		
		-- 1.3.6.1.4.1.5504.5.4.21.4.1.3
		zhoneAdsl2SCStatusSnr OBJECT-TYPE
			SYNTAX OCTET STRING (SIZE (0..512))
			MAX-ACCESS read-only
			STATUS current
			DESCRIPTION
				"The SNR Margin per sub-carrier, expressing the ratio between
				the received signal power and received noise power per
				subscriber.  It is an array of 512 octets, designed for
				supporting up to 512 (downstream) sub-carriers.
				The number of utilized octets on downstream direction depends
				on NSCds, and on upstream direction it depends on NSCus.  This
				value is referred here as NSC.
				Octet i (0 <= i < NSC) is set to a value in the range 0 to
				254 to indicate that the respective downstream or upstream sub-
				carrier i has SNR of: (-32 + zhoneAdsl2SCStatusSnr(i)/2) in dB
				i.e., -32 to 95dB). In other words, the least-significant bit
				of each octet is 0.5 dB, and there is a -32 dB bias.
				The special value 255 means that no measurement could be done
				for the subcarrier, probably because it is out of the PSD mask
				passband or that the noise PSD is out of range to be represented.
				Each value in this array is 8 bits wide."
			REFERENCE
				"ITU-T G.997.1, paragraph 7.5.1.20.2 (SNRpsds)
				and paragraph 7.5.1.20.4 (SNRpsus)"
			::= { zhoneAdsl2SCStatusEntry 3 }

		
		-- 1.3.6.1.4.1.5504.5.4.21.4.1.4
		zhoneAdsl2SCStatusBitsAlloc OBJECT-TYPE
			SYNTAX OCTET STRING (SIZE (0..256))
			MAX-ACCESS read-only
			STATUS current
			DESCRIPTION
				"The bits allocation per sub-carrier.  An array of 256 octets
				512 nibbles), designed for supporting up to 512 (downstream)
				sub-carriers.
				The number of utilized nibbles on downstream direction depends
				on NSCds, and on upstream direction it depends on NSCus.  This
				value is referred here as NSC.
				Nibble i (0 <= i < NSC) is set to a value in the range 0
				to 15 to indicate that the respective downstream or upstream
				sub-carrier i has the same amount of bits allocation."
			REFERENCE
				"ITU-T G.997.1, paragraph 7.5.1.21.1 (BITSpsds)
				and paragraph 7.5.1.21.2 (BITSpsus)"
			::= { zhoneAdsl2SCStatusEntry 4 }

		
		-- 1.3.6.1.4.1.5504.5.4.21.4.1.5
		zhoneAdsl2SCStatusLogMt OBJECT-TYPE
			SYNTAX Unsigned32
			MAX-ACCESS read-only
			STATUS current
			DESCRIPTION
				"The number of symbols used to measure the H(f) logarithmic
				measurement values for the respective transmission direction.
				This parameter should correspond to the value specified in the
				recommendation (e.g., the number of symbols in 1 second
				time interval for G.992.3).  This parameter corresponds to 1
				second in loop diagnostic procedure and should be updated in
				initialization."
			REFERENCE
				"ITU-T G.997.1, paragraph 7.5.1.18.3 (HLOGMTds)
				and paragraph 7.5.1.18.7 (HLOGMTus)"
			::= { zhoneAdsl2SCStatusEntry 5 }

		
		-- 1.3.6.1.4.1.5504.5.4.21.4.1.6
		zhoneAdsl2SCStatusLog OBJECT-TYPE
			SYNTAX OCTET STRING (SIZE (0..1024))
			MAX-ACCESS read-only
			STATUS current
			DESCRIPTION
				"An array of up to 512 real H(f) logarithmic representation
				values in dB for the respective transmission direction.  It is
				designed to support up to 512 (downstream) sub-carriers
				The number of utilized values on downstream direction depends
				on NSCds, and on upstream direction it depends on NSCus.  This
				value is referred here as NSC.
				Each array entry represents the real Hlog(f = i*Df) value for a
				particular sub-carrier index i, (0 <= i < NSC).
				The real Hlog(f) value is represented as (6-m(i)/10), with m(i)
				in the range 0 to 1022.  A special value m=1023 indicates that
				no measurement could be done for the subcarrier because it is
				out of the passband or that the attenuation is out of range to
				be represented.  This parameter is applicable in loop diagnostic
				procedure and initialization.
				Each value in this array is 16 bits wide and is stored
				in big endian format."
			REFERENCE
				"ITU-T G.997.1, paragraph 7.5.1.18.4 (HLOGpsds)
				and paragraph 7.5.1.18.8 (HLOGpsus)"
			::= { zhoneAdsl2SCStatusEntry 6 }

		
		-- 1.3.6.1.4.1.5504.5.4.21.4.1.7
		zhoneAdsl2SCStatusQlnMt OBJECT-TYPE
			SYNTAX Unsigned32
			MAX-ACCESS read-only
			STATUS current
			DESCRIPTION
				"The number of symbols used to measure the Quiet Line Noise
				values on the respective transmission direction.   This
				parameter should correspond to the value specified in the
				recommendation (e.g., the number of symbols in 1 second time
				interval for G.992.3).  This parameter corresponds to 1 second
				in loop diagnostic procedure and should be updated in
				initialization."
			REFERENCE
				"ITU-T G.997.1, paragraph 7.5.1.19.1 (QLNMTds)
				and paragraph 7.5.1.19.3 (QLNMTus)"
			::= { zhoneAdsl2SCStatusEntry 7 }

		
		-- 1.3.6.1.4.1.5504.5.4.21.4.1.8
		zhoneAdsl2SCStatusQln OBJECT-TYPE
			SYNTAX OCTET STRING (SIZE (0..512))
			UNITS "dBm/Hz"
			MAX-ACCESS read-only
			STATUS current
			DESCRIPTION
				"An array of up to 512 real Quiet Line Noise values in dBm/Hz
				for the respective transmission direction.  It is designed for
				up to 512 (downstream) sub-carriers
				The number of utilized values on downstream direction depends
				on NSCds, and on upstream direction it depends on NSCus.  This
				value is referred here as NSC.
				Each array entry represents the QLN(f = i*Df) value for a
				particular sub-carrier index i, (0 <= i < NSC).
				The QLN(f) is represented as ( -23-n(i)/2), with n(i) in the
				range 0 to 254.  A special value n(i)=255 indicates that no
				measurement could be done for the subcarrier because it is out
				of the passband or that the noise PSD is out of range to be
				represented.
				This parameter is applicable in loop diagnostic procedure and
				initialization.  Each value in this array is 8 bits wide."
			REFERENCE
				"ITU-T G.997.1, paragraph 7.5.1.19.2 (QLNpsds)
				and paragraph 7.5.1.19.4 (QLNpsus)"
			::= { zhoneAdsl2SCStatusEntry 8 }

		
		-- 1.3.6.1.4.1.5504.5.4.21.4.1.9
		zhoneAdsl2SCStatusLnAtten OBJECT-TYPE
			SYNTAX Unsigned32 (0..1270 | 2147483646 | 2147483647)
			MAX-ACCESS read-only
			STATUS current
			DESCRIPTION
				"When referring to the downstream direction, it is the measured
				difference in the total power transmitted by the ATU-C and the
				total power received by the ATU-R over all sub-carriers during
				diagnostics mode.
				When referring to the upstream direction, it is the measured
				difference in the total power transmitted by the ATU-R and the
				total power received by the ATU-C over all sub-carriers during
				diagnostics mode.
				It ranges from 0 to 1270 units of 0.1 dB (Physical values are
				0 to 127 dB).
				A special value of 0x7FFFFFFF (2147483647) indicates the line
				attenuation is out of range to be represented.
				A special value of 0x7FFFFFFE (2147483646) indicates the line
				This object reflects the value of the parameter following the
				most recent DELT performed on the associated line.  Once
				the DELT process is over, the parameter no longer changes
				until the row is deleted or a new DELT process is initiated."
			REFERENCE
				"ITU-T G.997.1, paragraph 7.5.1.6 (LATNds)
				and paragraph 7.5.1.7 (LATNus)"
			::= { zhoneAdsl2SCStatusEntry 9 }

		
		-- 1.3.6.1.4.1.5504.5.4.21.4.1.10
		zhoneAdsl2SCStatusSigAtten OBJECT-TYPE
			SYNTAX Unsigned32 (0..1270 | 2147483646 | 2147483647)
			UNITS "0.1 dB"
			MAX-ACCESS read-only
			STATUS current
			DESCRIPTION
				"When referring to the downstream direction, it is the measured
				difference in the total power transmitted by the
				ATU-C and the total power received by the ATU-R over all sub
				carriers during Showtime after the diagnostics mode.
				When referring to the upstream direction, it is the measured
				difference in the total power transmitted by the
				ATU-R and the total power received by the ATU-C over all sub
				carriers during Showtime after the diagnostics mode.
				It ranges from 0 to 1270 units of 0.1 dB (Physical values
				are 0 to 127 dB).
				A special value of 0x7FFFFFFF (2147483647) indicates the
				signal attenuation is out of range to be represented.
				A special value of 0x7FFFFFFE (2147483646) indicates the
				signal attenuation measurement is unavailable.
				This object reflects the value of the parameter following the
				most recent DELT performed on the associated line.  Once
				the DELT process is over, the parameter no longer changes
				until the row is deleted or a new DELT process is initiated."
			REFERENCE
				"ITU-T G.997.1, paragraph 7.5.1.8 (SATNds)
				and paragraph 7.5.1.9 (SATNus)"
			::= { zhoneAdsl2SCStatusEntry 10 }

		
		-- 1.3.6.1.4.1.5504.5.4.21.4.1.11
		zhoneAdsl2SCStatusSnrMargin OBJECT-TYPE
			SYNTAX Integer32 (-640..630 | 2147483646 | 2147483647)
			UNITS "0.1 dB"
			MAX-ACCESS read-only
			STATUS current
			DESCRIPTION
				"SNR Margin is the maximum increase in dB of the noise power
				received at the ATU (ATU-R on downstream direction and ATU-C
				on upstream direction), such that the BER requirements are met
				for all bearer channels received at the ATU.  It ranges from
				640 to 630 units of 0.1 dB (Physical values are -64 to
				63 dB).
				A special value of 0x7FFFFFFF (2147483647) indicates the
				SNR Margin is out of range to be represented.
				A special value of 0x7FFFFFFE (2147483646) indicates the
				SNR Margin measurement is currently unavailable.
				This object reflects the value of the parameter following the
				most recent DELT performed on the associated line.  Once
				the DELT process is over, the parameter no longer changes
				until the row is deleted or a new DELT process is initiated."
			REFERENCE
				"ITU-T G.997.1, paragraph 7.5.1.10 (SNRMds)
				and paragraph 7.5.1.11 (SNRMus)"
			::= { zhoneAdsl2SCStatusEntry 11 }

		
		-- 1.3.6.1.4.1.5504.5.4.21.4.1.12
		zhoneAdsl2SCStatusAttainableRate OBJECT-TYPE
			SYNTAX Unsigned32
			UNITS "bits/second"
			MAX-ACCESS read-only
			STATUS current
			DESCRIPTION
				"Maximum Attainable Data Rate.  The maximum net data rate
				currently attainable by the ATU-C transmitter and ATU-R
				receiver (when referring to downstream direction) or by the
				ATU-R transmitter and ATU-C receiver (when referring to
				upstream direction).  Value is coded in bits/s.
				This object reflects the value of the parameter following the
				most recent DELT performed on the associated line.  Once
				the DELT process is over, the parameter no longer changes
				until the row is deleted or a new DELT process is initiated."
			REFERENCE
				"ITU-T G.997.1, paragraph 7.5.1.12 (ATTNDRds)
				and paragraph 7.5.1.13 (ATTNDRus)"
			::= { zhoneAdsl2SCStatusEntry 12 }

		
		-- 1.3.6.1.4.1.5504.5.4.21.4.1.13
		zhoneAdsl2SCStatusActAtp OBJECT-TYPE
			SYNTAX Integer32
			UNITS "0.1 dB"
			MAX-ACCESS read-only
			STATUS current
			DESCRIPTION
				"Actual Aggregate Transmit Power from the ATU (ATU-R on
				downstream direction and ATU-C on upstream direction), at the
				instant of measurement.  It ranges from -310 to 310 units of
				0.1 dB (Physical values are -31 to 31 dBm).  A value of all
				1's indicates the measurement is out of range to be
				represented.
				This object reflects the value of the parameter following the
				most recent DELT performed on the associated line.  Once
				the DELT process is over, the parameter no longer changes
				until the row is deleted or a new DELT process is initiated."
			REFERENCE
				"ITU-T G.997.1, paragraph 7.5.1.14 (ACTPSDds)
				and paragraph 7.5.1.15 (ACTPSDus)"
			::= { zhoneAdsl2SCStatusEntry 13 }

		
		-- 1.3.6.1.4.1.5504.5.4.21.4.1.14
		zhoneAdsl2SCStatusRowStatus OBJECT-TYPE
			SYNTAX RowStatus
			MAX-ACCESS read-create
			STATUS current
			DESCRIPTION
				"Row Status.  The manager may create and delete rows
				of this table. Please see the description of
				zhoneAdsl2SCStatusTable above for more details."
			::= { zhoneAdsl2SCStatusEntry 14 }

		
-- 
-- Objects in zhoneDslDpbo support ITU-T G.997.1, paragraph 7.3.1.2.13 
-- Downstream Power Back-Off Shaped (DPBOSHAPED).
-- 
-- zhoneDslDpboProfileTable allows configuration of the following
-- ITU-T G.997.1, paragraph 7.3.1.2.13 Downstream Power Back-Off 
-- profile parameters:
--   DPBOESEL  - E-Side Electrical Length
--   DPBOESCMA - E-Side Cable Model Parm A 
--   DPBOESCMB - E-Side Cable Model Parm B
--   DPBOESCMC - E-Side Cable Model Parm C
--   DPBOMUS   - Minimum Usable Signal
--   DPBOFMIN  - Minimum frequency
--   DPBOFMAX  - Maximum frequency
-- 
-- zhoneDslDpboEpsdTable allows configuration of the ITU-T G.997.1, 
-- paragraph 7.3.1.2.13 Downstream Power Back-Off DPBO Assumed exchange 
-- PSD mask (DPBOEPSD) breakpoints for the associated DPBO profile. 
-- There is a maximum of 16 breakpoints. This set of breakpoints define
-- the PSD mask that is assumed to be permitted at the exchange. Each 
-- breakpoint supports the following parameters:
--   DPBOEPSD Freq  - Assumed exchange PSD mask (DPBOEPSD) Frequency
--   DPBOEPSD Level - Assumed exchange PSD mask (DPBOEPSD) Level
-- 
-- zhoneDslDpboPsdMaskTable allows configuration of the ITU-T G.997.1, 
-- paragraph 7.3.1.2.13 Downstream Power Back-Off DPBO maximum PSD 
-- mask downstream (DPBOPSDMASKds) breakpoints for the associated DPBO 
-- profile. There is a maximum of 16 breakpoints. Each breakpoint 
-- supports the following parameters:
--   DPBOPSDMASKds Freq  - max PSD mask ds (DPBOPSDMASKds) Frequency
--   DPBOPSDMASKds Level - max PSD mask ds (DPBOPSDMASKds) Level
-- 
-- zhoneDslDpboLfoTable allows configuration of the ITU-T G.997.1, 
-- paragraph 7.3.1.2.13 Downstream Power Back-Off DPBO low frequency 
-- override (DPBOLFO) breakpoints for the associated DPBO profile. 
-- There is a maximum of 16 breakpoints. This set of breakpoints define
-- the PSD mask that overrides DPBO at low frequencies. Each breakpoint 
-- supports the following parameters:
--   DPBOLFO Freq  - DPBO low frequency override (DPBOLFO) Frequency
--   DPBOLFO Level - DPBO low frequency override (DPBOLFO) Level
-- 
		-- 1.3.6.1.4.1.5504.5.4.22
		zhoneDslDpbo OBJECT IDENTIFIER ::= { zhoneDsl 22 }

		
		-- 1.3.6.1.4.1.5504.5.4.22.1
		zhoneDslDpboProfileTable OBJECT-TYPE
			SYNTAX SEQUENCE OF ZhoneDslDpboProfileEntry
			MAX-ACCESS not-accessible
			STATUS current
			DESCRIPTION
				"zhoneDslDpboProfileTable allows configuration of the following
				ITU-T G.997.1, paragraph 7.3.1.2.13 Downstream Power Back-Off 
				profile parameters:
				  DPBOESEL  - E-Side Electrical Length
				  DPBOESCMA - E-Side Cable Model Parm A 
				  DPBOESCMB - E-Side Cable Model Parm B
				  DPBOESCMC - E-Side Cable Model Parm C
				  DPBOMUS   - Minimum Usable Signal
				  DPBOFMIN  - Minimum frequency
				  DPBOFMAX  - Maximum frequency"
			REFERENCE
				"ITU-T G.997.1, paragraph 7.3.1.2.13 Downstream Power Back-Off"
			::= { zhoneDslDpbo 1 }

		
		-- 1.3.6.1.4.1.5504.5.4.22.1.1
		zhoneDslDpboProfileEntry OBJECT-TYPE
			SYNTAX ZhoneDslDpboProfileEntry
			MAX-ACCESS not-accessible
			STATUS current
			DESCRIPTION
				"Each zhoneDslDpboProfileEntry represents one ITU-T G.997.1, paragraph 
				7.3.1.2.13 Downstream Power Back-Off parameter profile entry."
			REFERENCE
				"ITU-T G.997.1, paragraph 7.3.1.2.13 Downstream Power Back-Off"
			INDEX { zhoneDslDpboProfileIndex }
			::= { zhoneDslDpboProfileTable 1 }

		
		ZhoneDslDpboProfileEntry ::=
			SEQUENCE { 
				zhoneDslDpboProfileIndex
					Unsigned32,
				zhoneDslDpboProfileName
					ZhoneAdminString,
				zhoneDslDpboEsel
					Unsigned32,
				zhoneDslDpboEscmA
					Unsigned32,
				zhoneDslDpboEscmB
					Unsigned32,
				zhoneDslDpboEscmC
					Unsigned32,
				zhoneDslDpboFmax
					Unsigned32,
				zhoneDslDpboFmin
					Unsigned32,
				zhoneDslDpboMus
					Integer32
			 }

-- 
-- 
		-- 1.3.6.1.4.1.5504.5.4.22.1.1.1
		zhoneDslDpboProfileIndex OBJECT-TYPE
			SYNTAX Unsigned32 (0..6)
			UNITS "Unsigned32"
			MAX-ACCESS not-accessible
			STATUS current
			DESCRIPTION
				"An unsigned integer containing the zhoneDslDpboProfileEntry index. This
				index is common to zhoneDslDpboProfile, zhoneDslDpboEpsd, zhoneDslDpboPsdMask,
				and zhoneDslDpboLfo. The valid table index range is one to six. A zero index 
				value is valid only in zhoneDslDpboProfile and zhoneDslDpboFallbackProfile to 
				disable the DPBO feature."
			::= { zhoneDslDpboProfileEntry 1 }

		
-- 
		-- 1.3.6.1.4.1.5504.5.4.22.1.1.2
		zhoneDslDpboProfileName OBJECT-TYPE
			SYNTAX ZhoneAdminString
			UNITS "STRING"
			MAX-ACCESS read-write
			STATUS current
			DESCRIPTION
				"An 36 byte octet string containing the DPBO profile name."
			::= { zhoneDslDpboProfileEntry 2 }

		
		-- 1.3.6.1.4.1.5504.5.4.22.1.1.3
		zhoneDslDpboEsel OBJECT-TYPE
			SYNTAX Unsigned32 (0..2555)
			UNITS "0.1 dB"
			MAX-ACCESS read-write
			STATUS current
			DESCRIPTION
				"DpboEsel: E-side electrical length (DPBOESEL)
				
				Range: 0 ~ 2555
				0 is disabled
				units: 0.1 dB
				Effective Range: 0 ~ 255.5 dB
				Default: 0
				
				The DBPOESEL configuration parameter defines the assumed electrical 
				length of cables (E-side cables) connecting exchange based DSL 
				services to a remote flexibility point (cabinet), that hosts the 
				xTU-C that is subject to spectrally shaped downstream power back-off 
				depending on this length. For this parameter the electrical length is 
				defined as the loss (in dB) of an equivalent length of hypothetical 
				cable at a reference frequency defined by the network operator or in 
				spectrum management regulations. DPBOESEL shall be coded as an unsigned
				integer representing an electrical length from 0 dB to 255.5 dB in 
				steps of 0.1 dB. All values in the range are valid."
			REFERENCE
				"ITU-T G.997.1, paragraph 7.3.1.2.13 Downstream Power Back-Off"
			DEFVAL { 0 }
			::= { zhoneDslDpboProfileEntry 3 }

		
		-- 1.3.6.1.4.1.5504.5.4.22.1.1.4
		zhoneDslDpboEscmA OBJECT-TYPE
			SYNTAX Unsigned32 (0..640)
			UNITS "1/256 dB"
			MAX-ACCESS read-write
			STATUS current
			DESCRIPTION
				"DpboEscmA: E-Side Cable Model A (DPBOESCMA)
				
				Range: 0 ~ 640
				Units: 1/256 dB
				Effective Range: -1 ~ 1.5 dB
				Default: 0
				
				The DPBOESCMA configuration parameter is one of three scalars that 
				defines a cable model that describes the frequency dependent loss of 
				E-side cables using the formula: 
				
				ESCM(f) = (DPBOESCMA + DPBOESCMB * SQRT(f) + DPBOESCMC * f ) * DPBOESEL 
				   where ESCM is expressed in dB and f is expressed in MHz. 
				
				Parameters DPBOESCMA, DPBOESCMB, DPBOESCMC are coded as unsigned 
				integers representing a scalar value from -1 to 1.5 in steps of 
				1/256 dB. All values in the range are valid."
			REFERENCE
				"ITU-T G.997.1, paragraph 7.3.1.2.13 Downstream Power Back-Off"
			DEFVAL { 0 }
			::= { zhoneDslDpboProfileEntry 4 }

		
		-- 1.3.6.1.4.1.5504.5.4.22.1.1.5
		zhoneDslDpboEscmB OBJECT-TYPE
			SYNTAX Unsigned32 (0..640)
			UNITS "1/256 dB"
			MAX-ACCESS read-write
			STATUS current
			DESCRIPTION
				"DpboEscmB: E-Side Cable Model B (DPBOESCMB)
				
				Range: 0 ~ 640
				Units: 1/256 dB
				Effective Range: -1 ~ 1.5 dB
				Default: 0
				
				The DPBOESCMB configuration parameter is one of three scalars that 
				defines a cable model that describes the frequency dependent loss of 
				E-side cables using the formula: 
				
				ESCM(f) = (DPBOESCMA + DPBOESCMB * SQRT(f) + DPBOESCMC * f ) * DPBOESEL 
				   where ESCM is expressed in dB and f is expressed in MHz. 
				
				Parameters DPBOESCMA, DPBOESCMB, DPBOESCMC are coded as unsigned 
				integers representing a scalar value from -1 to 1.5 in steps of 
				1/256 dB. All values in the range are valid."
			REFERENCE
				"ITU-T G.997.1, paragraph 7.3.1.2.13 Downstream Power Back-Off"
			DEFVAL { 0 }
			::= { zhoneDslDpboProfileEntry 5 }

		
		-- 1.3.6.1.4.1.5504.5.4.22.1.1.6
		zhoneDslDpboEscmC OBJECT-TYPE
			SYNTAX Unsigned32 (0..640)
			UNITS "1/256 dB"
			MAX-ACCESS read-write
			STATUS current
			DESCRIPTION
				"DpboEscmC: E-Side Cable Model C (DPBOESCMC)
				
				Range: 0 ~ 640
				Units: 1/256 dB
				Effective Range: -1 ~ 1.5 dB
				Default: 0
				
				The DPBOESCMC configuration parameter is one of three scalars that 
				defines a cable model that describes the frequency dependent loss of 
				E-side cables using the formula: 
				
				ESCM(f) = (DPBOESCMA + DPBOESCMB * SQRT(f) + DPBOESCMC * f ) * DPBOESEL 
				   where ESCM is expressed in dB and f is expressed in MHz. 
				
				Parameters DPBOESCMA, DPBOESCMB, DPBOESCMC are coded as unsigned 
				integers representing a scalar value from -1 to 1.5 in steps of 
				1/256 dB. All values in the range are valid."
			REFERENCE
				"ITU-T G.997.1, paragraph 7.3.1.2.13 Downstream Power Back-Off"
			DEFVAL { 0 }
			::= { zhoneDslDpboProfileEntry 6 }

		
		-- 1.3.6.1.4.1.5504.5.4.22.1.1.7
		zhoneDslDpboFmax OBJECT-TYPE
			SYNTAX Unsigned32 (32..6956)
			UNITS "4.3125 kHz"
			MAX-ACCESS read-write
			STATUS current
			DESCRIPTION
				"DpboFmax: DPBO span maximum frequency (DPBOFMAX)
				
				Range: 32 ~ 6956
				Units: 4.3125 kHz
				Effective Range: 138 ~ 29997.75 kHz
				Default: 32
				
				The DPBOFMAX configuration parameter defines the maximum frequency at 
				which DPBO may be applied. It ranges from 138 kHz to 29997.75 kHz in 
				steps of 4.3125 kHz."
			REFERENCE
				"ITU-T G.997.1, paragraph 7.3.1.2.13 Downstream Power Back-Off"
			DEFVAL { 32 }
			::= { zhoneDslDpboProfileEntry 7 }

		
		-- 1.3.6.1.4.1.5504.5.4.22.1.1.8
		zhoneDslDpboFmin OBJECT-TYPE
			SYNTAX Unsigned32 (0..2048)
			UNITS "4.3125 kHz"
			MAX-ACCESS read-write
			STATUS current
			DESCRIPTION
				"DpboFmin: DPBO span minimum frequency (DPBOFMIN)
				
				Range: 0 ~ 2048
				Units: 4.3125 kHz
				Effective Range: 0 ~ 8832 kHz
				Default: 0
				
				The DPBOFMIN configuration parameter defines the minimum frequency 
				from which the DPBO shall be applied. It ranges from 0 kHz to 8832 
				kHz in steps of 4.3125 kHz."
			REFERENCE
				"ITU-T G.997.1, paragraph 7.3.1.2.13 Downstream Power Back-Off"
			DEFVAL { 0 }
			::= { zhoneDslDpboProfileEntry 8 }

		
		-- 1.3.6.1.4.1.5504.5.4.22.1.1.9
		zhoneDslDpboMus OBJECT-TYPE
			SYNTAX Integer32 (-1275..0)
			UNITS "0.1 dBm/Hz"
			MAX-ACCESS read-write
			STATUS current
			DESCRIPTION
				"DpboMus: Assumed minimum usable signal (DPBOMUS)
				
				Range: -1275 ~ 0
				Units: 0.1 dBm/Hz
				Effective Range: -127.5 ~ 0 kHz
				Default: -1275
				
				The DPBOMUS configuration parameter defines the assumed Minimum Usable
				receive PSD mask (in dBm/Hz) for exchange based services, used to 
				modify parameter DPBOFMAX. It represents a PSD mask level from 0 dBm/Hz 
				to -127.5 dBm/Hz in steps of 0.1 dB. All values in the range are valid. 
				NOTE: The PSD mask level is 3.5 dB above the signal PSD level."
			REFERENCE
				"ITU-T G.997.1, paragraph 7.3.1.2.13 Downstream Power Back-Off"
			DEFVAL { -1275 }
			::= { zhoneDslDpboProfileEntry 9 }

		
		-- 1.3.6.1.4.1.5504.5.4.22.2
		zhoneDslDpboEpsdTable OBJECT-TYPE
			SYNTAX SEQUENCE OF ZhoneDslDpboEpsdEntry
			MAX-ACCESS not-accessible
			STATUS current
			DESCRIPTION
				"zhoneDslDpboEpsdTable allows configuration of the ITU-T G.997.1, 
				paragraph 7.3.1.2.13 Downstream Power Back-Off DPBO Assumed exchange 
				PSD mask (DPBOEPSD) breakpoints for the associated DPBO profile. 
				There is a maximum of 16 breakpoints. This set of breakpoints define
				the PSD mask that is assumed to be permitted at the exchange. Each 
				breakpoint supports the following parameters:
				  DPBOEPSD Freq  - Assumed exchange PSD mask (DPBOEPSD) Frequency
				  DPBOEPSD Level - Assumed exchange PSD mask (DPBOEPSD) Level"
			REFERENCE
				"ITU-T G.997.1, paragraph 7.3.1.2.13 Downstream Power Back-Off"
			::= { zhoneDslDpbo 2 }

		
		-- 1.3.6.1.4.1.5504.5.4.22.2.1
		zhoneDslDpboEpsdEntry OBJECT-TYPE
			SYNTAX ZhoneDslDpboEpsdEntry
			MAX-ACCESS not-accessible
			STATUS current
			DESCRIPTION
				"Each zhoneDslDpboEpsdEntry represents a set of ITU-T G.997.1, 
				paragraph 7.3.1.2.13 Downstream Power Back-Off DPBO Assumed exchange 
				PSD mask (DPBOEPSD) breakpoints. Each Entry in this table corresponds 
				directly with the DPBO Profile using the same index."
			REFERENCE
				"ITU-T G.997.1, paragraph 7.3.1.2.13 Downstream Power Back-Off"
			INDEX { zhoneDslDpboProfileIndex }
			::= { zhoneDslDpboEpsdTable 1 }

		
		ZhoneDslDpboEpsdEntry ::=
			SEQUENCE { 
				zhoneDslDpboEpsdFreq1
					Integer32,
				zhoneDslDpboEpsdLevel1
					Integer32,
				zhoneDslDpboEpsdFreq2
					Integer32,
				zhoneDslDpboEpsdLevel2
					Integer32,
				zhoneDslDpboEpsdFreq3
					Integer32,
				zhoneDslDpboEpsdLevel3
					Integer32,
				zhoneDslDpboEpsdFreq4
					Integer32,
				zhoneDslDpboEpsdLevel4
					Integer32,
				zhoneDslDpboEpsdFreq5
					Integer32,
				zhoneDslDpboEpsdLevel5
					Integer32,
				zhoneDslDpboEpsdFreq6
					Integer32,
				zhoneDslDpboEpsdLevel6
					Integer32,
				zhoneDslDpboEpsdFreq7
					Integer32,
				zhoneDslDpboEpsdLevel7
					Integer32,
				zhoneDslDpboEpsdFreq8
					Integer32,
				zhoneDslDpboEpsdLevel8
					Integer32,
				zhoneDslDpboEpsdFreq9
					Integer32,
				zhoneDslDpboEpsdLevel9
					Integer32,
				zhoneDslDpboEpsdFreq10
					Integer32,
				zhoneDslDpboEpsdLevel10
					Integer32,
				zhoneDslDpboEpsdFreq11
					Integer32,
				zhoneDslDpboEpsdLevel11
					Integer32,
				zhoneDslDpboEpsdFreq12
					Integer32,
				zhoneDslDpboEpsdLevel12
					Integer32,
				zhoneDslDpboEpsdFreq13
					Integer32,
				zhoneDslDpboEpsdLevel13
					Integer32,
				zhoneDslDpboEpsdFreq14
					Integer32,
				zhoneDslDpboEpsdLevel14
					Integer32,
				zhoneDslDpboEpsdFreq15
					Integer32,
				zhoneDslDpboEpsdLevel15
					Integer32,
				zhoneDslDpboEpsdFreq16
					Integer32,
				zhoneDslDpboEpsdLevel16
					Integer32
			 }

		-- 1.3.6.1.4.1.5504.5.4.22.2.1.1
		zhoneDslDpboEpsdFreq1 OBJECT-TYPE
			SYNTAX Integer32 (0..29998)
			UNITS "1 KHz"
			MAX-ACCESS read-write
			STATUS current
			DESCRIPTION
				"Assumed exchange PSD mask (DPBOEPSD) Breakpoint Frequency 1. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 1 }

		
		-- 1.3.6.1.4.1.5504.5.4.22.2.1.2
		zhoneDslDpboEpsdLevel1 OBJECT-TYPE
			SYNTAX Integer32 (-1275..0)
			UNITS "0.1 dBm/Hz"
			MAX-ACCESS read-write
			STATUS current
			DESCRIPTION
				"Assumed exchange PSD mask (DPBOEPSD) Breakpoint Level 1.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 2 }

		
		-- 1.3.6.1.4.1.5504.5.4.22.2.1.3
		zhoneDslDpboEpsdFreq2 OBJECT-TYPE
			SYNTAX Integer32 (0..29998)
			UNITS "1 KHz"
			MAX-ACCESS read-write
			STATUS current
			DESCRIPTION
				"Assumed exchange PSD mask (DPBOEPSD) Breakpoint Frequency 2. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 3 }

		
		-- 1.3.6.1.4.1.5504.5.4.22.2.1.4
		zhoneDslDpboEpsdLevel2 OBJECT-TYPE
			SYNTAX Integer32 (-1275..0)
			UNITS "0.1 dBm/Hz"
			MAX-ACCESS read-write
			STATUS current
			DESCRIPTION
				"Assumed exchange PSD mask (DPBOEPSD) Breakpoint Level 2.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 4 }

		
		-- 1.3.6.1.4.1.5504.5.4.22.2.1.5
		zhoneDslDpboEpsdFreq3 OBJECT-TYPE
			SYNTAX Integer32 (0..29998)
			UNITS "1 KHz"
			MAX-ACCESS read-write
			STATUS current
			DESCRIPTION
				"Assumed exchange PSD mask (DPBOEPSD) Breakpoint Frequency 3. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 5 }

		
		-- 1.3.6.1.4.1.5504.5.4.22.2.1.6
		zhoneDslDpboEpsdLevel3 OBJECT-TYPE
			SYNTAX Integer32 (-1275..0)
			UNITS "0.1 dBm/Hz"
			MAX-ACCESS read-write
			STATUS current
			DESCRIPTION
				"Assumed exchange PSD mask (DPBOEPSD) Breakpoint Level 3.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 6 }

		
		-- 1.3.6.1.4.1.5504.5.4.22.2.1.7
		zhoneDslDpboEpsdFreq4 OBJECT-TYPE
			SYNTAX Integer32 (0..29998)
			UNITS "1 KHz"
			MAX-ACCESS read-write
			STATUS current
			DESCRIPTION
				"Assumed exchange PSD mask (DPBOEPSD) Breakpoint Frequency 4. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 7 }

		
		-- 1.3.6.1.4.1.5504.5.4.22.2.1.8
		zhoneDslDpboEpsdLevel4 OBJECT-TYPE
			SYNTAX Integer32 (-1275..0)
			UNITS "0.1 dBm/Hz"
			MAX-ACCESS read-write
			STATUS current
			DESCRIPTION
				"Assumed exchange PSD mask (DPBOEPSD) Breakpoint Level 4.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 8 }

		
		-- 1.3.6.1.4.1.5504.5.4.22.2.1.9
		zhoneDslDpboEpsdFreq5 OBJECT-TYPE
			SYNTAX Integer32 (0..29998)
			UNITS "1 KHz"
			MAX-ACCESS read-write
			STATUS current
			DESCRIPTION
				"Assumed exchange PSD mask (DPBOEPSD) Breakpoint Frequency 5. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 9 }

		
		-- 1.3.6.1.4.1.5504.5.4.22.2.1.10
		zhoneDslDpboEpsdLevel5 OBJECT-TYPE
			SYNTAX Integer32 (-1275..0)
			UNITS "0.1 dBm/Hz"
			MAX-ACCESS read-write
			STATUS current
			DESCRIPTION
				"Assumed exchange PSD mask (DPBOEPSD) Breakpoint Level 5.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 10 }

		
		-- 1.3.6.1.4.1.5504.5.4.22.2.1.11
		zhoneDslDpboEpsdFreq6 OBJECT-TYPE
			SYNTAX Integer32 (0..29998)
			UNITS "1 KHz"
			MAX-ACCESS read-write
			STATUS current
			DESCRIPTION
				"Assumed exchange PSD mask (DPBOEPSD) Breakpoint Frequency 6. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 11 }

		
		-- 1.3.6.1.4.1.5504.5.4.22.2.1.12
		zhoneDslDpboEpsdLevel6 OBJECT-TYPE
			SYNTAX Integer32 (-1275..0)
			UNITS "0.1 dBm/Hz"
			MAX-ACCESS read-write
			STATUS current
			DESCRIPTION
				"Assumed exchange PSD mask (DPBOEPSD) Breakpoint Level 6.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 12 }

		
		-- 1.3.6.1.4.1.5504.5.4.22.2.1.13
		zhoneDslDpboEpsdFreq7 OBJECT-TYPE
			SYNTAX Integer32 (0..29998)
			UNITS "1 KHz"
			MAX-ACCESS read-write
			STATUS current
			DESCRIPTION
				"Assumed exchange PSD mask (DPBOEPSD) Breakpoint Frequency 7. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 13 }

		
		-- 1.3.6.1.4.1.5504.5.4.22.2.1.14
		zhoneDslDpboEpsdLevel7 OBJECT-TYPE
			SYNTAX Integer32 (-1275..0)
			UNITS "0.1 dBm/Hz"
			MAX-ACCESS read-write
			STATUS current
			DESCRIPTION
				"Assumed exchange PSD mask (DPBOEPSD) Breakpoint Level 7.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 14 }

		
		-- 1.3.6.1.4.1.5504.5.4.22.2.1.15
		zhoneDslDpboEpsdFreq8 OBJECT-TYPE
			SYNTAX Integer32 (0..29998)
			UNITS "1 KHz"
			MAX-ACCESS read-write
			STATUS current
			DESCRIPTION
				"Assumed exchange PSD mask (DPBOEPSD) Breakpoint Frequency 8. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 15 }

		
		-- 1.3.6.1.4.1.5504.5.4.22.2.1.16
		zhoneDslDpboEpsdLevel8 OBJECT-TYPE
			SYNTAX Integer32 (-1275..0)
			UNITS "0.1 dBm/Hz"
			MAX-ACCESS read-write
			STATUS current
			DESCRIPTION
				"Assumed exchange PSD mask (DPBOEPSD) Breakpoint Level 8.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 16 }

		
		-- 1.3.6.1.4.1.5504.5.4.22.2.1.17
		zhoneDslDpboEpsdFreq9 OBJECT-TYPE
			SYNTAX Integer32 (0..29998)
			UNITS "1 KHz"
			MAX-ACCESS read-write
			STATUS current
			DESCRIPTION
				"Assumed exchange PSD mask (DPBOEPSD) Breakpoint Frequency 9. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 17 }

		
		-- 1.3.6.1.4.1.5504.5.4.22.2.1.18
		zhoneDslDpboEpsdLevel9 OBJECT-TYPE
			SYNTAX Integer32 (-1275..0)
			UNITS "0.1 dBm/Hz"
			MAX-ACCESS read-write
			STATUS current
			DESCRIPTION
				"Assumed exchange PSD mask (DPBOEPSD) Breakpoint Level 9.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 18 }

		
		-- 1.3.6.1.4.1.5504.5.4.22.2.1.19
		zhoneDslDpboEpsdFreq10 OBJECT-TYPE
			SYNTAX Integer32 (0..29998)
			UNITS "1 KHz"
			MAX-ACCESS read-write
			STATUS current
			DESCRIPTION
				"Assumed exchange PSD mask (DPBOEPSD) Breakpoint Frequency 10. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 19 }

		
		-- 1.3.6.1.4.1.5504.5.4.22.2.1.20
		zhoneDslDpboEpsdLevel10 OBJECT-TYPE
			SYNTAX Integer32 (-1275..0)
			UNITS "0.1 dBm/Hz"
			MAX-ACCESS read-write
			STATUS current
			DESCRIPTION
				"Assumed exchange PSD mask (DPBOEPSD) Breakpoint Level 10.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 20 }

		
		-- 1.3.6.1.4.1.5504.5.4.22.2.1.21
		zhoneDslDpboEpsdFreq11 OBJECT-TYPE
			SYNTAX Integer32 (0..29998)
			UNITS "1 KHz"
			MAX-ACCESS read-write
			STATUS current
			DESCRIPTION
				"Assumed exchange PSD mask (DPBOEPSD) Breakpoint Frequency 11. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 21 }

		
		-- 1.3.6.1.4.1.5504.5.4.22.2.1.22
		zhoneDslDpboEpsdLevel11 OBJECT-TYPE
			SYNTAX Integer32 (-1275..0)
			UNITS "0.1 dBm/Hz"
			MAX-ACCESS read-write
			STATUS current
			DESCRIPTION
				"Assumed exchange PSD mask (DPBOEPSD) Breakpoint Level 11.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 22 }

		
		-- 1.3.6.1.4.1.5504.5.4.22.2.1.23
		zhoneDslDpboEpsdFreq12 OBJECT-TYPE
			SYNTAX Integer32 (0..29998)
			UNITS "1 KHz"
			MAX-ACCESS read-write
			STATUS current
			DESCRIPTION
				"Assumed exchange PSD mask (DPBOEPSD) Breakpoint Frequency 12. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 23 }

		
		-- 1.3.6.1.4.1.5504.5.4.22.2.1.24
		zhoneDslDpboEpsdLevel12 OBJECT-TYPE
			SYNTAX Integer32 (-1275..0)
			UNITS "0.1 dBm/Hz"
			MAX-ACCESS read-write
			STATUS current
			DESCRIPTION
				"Assumed exchange PSD mask (DPBOEPSD) Breakpoint Level 12.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 24 }

		
		-- 1.3.6.1.4.1.5504.5.4.22.2.1.25
		zhoneDslDpboEpsdFreq13 OBJECT-TYPE
			SYNTAX Integer32 (0..29998)
			UNITS "1 KHz"
			MAX-ACCESS read-write
			STATUS current
			DESCRIPTION
				"Assumed exchange PSD mask (DPBOEPSD) Breakpoint Frequency 13. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 25 }

		
		-- 1.3.6.1.4.1.5504.5.4.22.2.1.26
		zhoneDslDpboEpsdLevel13 OBJECT-TYPE
			SYNTAX Integer32 (-1275..0)
			UNITS "0.1 dBm/Hz"
			MAX-ACCESS read-write
			STATUS current
			DESCRIPTION
				"Assumed exchange PSD mask (DPBOEPSD) Breakpoint Level 13.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 26 }

		
		-- 1.3.6.1.4.1.5504.5.4.22.2.1.27
		zhoneDslDpboEpsdFreq14 OBJECT-TYPE
			SYNTAX Integer32 (0..29998)
			UNITS "1 KHz"
			MAX-ACCESS read-write
			STATUS current
			DESCRIPTION
				"Assumed exchange PSD mask (DPBOEPSD) Breakpoint Frequency 14. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 27 }

		
		-- 1.3.6.1.4.1.5504.5.4.22.2.1.28
		zhoneDslDpboEpsdLevel14 OBJECT-TYPE
			SYNTAX Integer32 (-1275..0)
			UNITS "0.1 dBm/Hz"
			MAX-ACCESS read-write
			STATUS current
			DESCRIPTION
				"Assumed exchange PSD mask (DPBOEPSD) Breakpoint Level 14.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 28 }

		
		-- 1.3.6.1.4.1.5504.5.4.22.2.1.29
		zhoneDslDpboEpsdFreq15 OBJECT-TYPE
			SYNTAX Integer32 (0..29998)
			UNITS "1 KHz"
			MAX-ACCESS read-write
			STATUS current
			DESCRIPTION
				"Assumed exchange PSD mask (DPBOEPSD) Breakpoint Frequency 15. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 29 }

		
		-- 1.3.6.1.4.1.5504.5.4.22.2.1.30
		zhoneDslDpboEpsdLevel15 OBJECT-TYPE
			SYNTAX Integer32 (-1275..0)
			UNITS "0.1 dBm/Hz"
			MAX-ACCESS read-write
			STATUS current
			DESCRIPTION
				"Assumed exchange PSD mask (DPBOEPSD) Breakpoint Level 15.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 30 }

		
		-- 1.3.6.1.4.1.5504.5.4.22.2.1.31
		zhoneDslDpboEpsdFreq16 OBJECT-TYPE
			SYNTAX Integer32 (0..65535)
			UNITS "1 KHz"
			MAX-ACCESS read-write
			STATUS current
			DESCRIPTION
				"Assumed exchange PSD mask (DPBOEPSD) Breakpoint Frequency 16. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboEpsdEntry 31 }

		
		-- 1.3.6.1.4.1.5504.5.4.22.2.1.32
		zhoneDslDpboEpsdLevel16 OBJECT-TYPE
			SYNTAX Integer32 (-1275..0)
			UNITS "0.1 dBm/Hz"
			MAX-ACCESS read-write
			STATUS current
			DESCRIPTION
				"Assumed exchange PSD mask (DPBOEPSD) Breakpoint Level 16.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboEpsdEntry 32 }

		
		-- 1.3.6.1.4.1.5504.5.4.22.3
		zhoneDslDpboPsdMaskTable OBJECT-TYPE
			SYNTAX SEQUENCE OF ZhoneDslDpboPsdMaskEntry
			MAX-ACCESS not-accessible
			STATUS current
			DESCRIPTION
				"zhoneDslDpboPsdMaskTable allows configuration of the ITU-T G.997.1, 
				paragraph 7.3.1.2.13 Downstream Power Back-Off DPBO maximum PSD 
				mask downstream (DPBOPSDMASKds) breakpoints for the associated DPBO 
				profile. There is a maximum of 16 breakpoints. 
				
				Each breakpoint 
				supports the following parameters:
				  DPBOPSDMASKds Freq  - max PSD mask ds (DPBOPSDMASKds) Frequency
				  DPBOPSDMASKds Level - max PSD mask ds (DPBOPSDMASKds) Level"
			REFERENCE
				"ITU-T G.997.1, paragraph 7.3.1.2.13 Downstream Power Back-Off"
			::= { zhoneDslDpbo 3 }

		
		-- 1.3.6.1.4.1.5504.5.4.22.3.1
		zhoneDslDpboPsdMaskEntry OBJECT-TYPE
			SYNTAX ZhoneDslDpboPsdMaskEntry
			MAX-ACCESS not-accessible
			STATUS current
			DESCRIPTION
				"Each zhoneDslDpboPsdMaskEntry represents a set of ITU-T G.997.1, 
				paragraph 7.3.1.2.13 Downstream Power Back-Off DPBO maximum PSD 
				mask downstream (DPBOPSDMASKds) breakpoints. Each Entry in this 
				table corresponds directly with the DPBO Profile using the same 
				index."
			REFERENCE
				"ITU-T G.997.1, paragraph 7.3.1.2.13 Downstream Power Back-Off"
			INDEX { zhoneDslDpboProfileIndex }
			::= { zhoneDslDpboPsdMaskTable 1 }

		
		ZhoneDslDpboPsdMaskEntry ::=
			SEQUENCE { 
				zhoneDslDpboPsdMaskFreq1
					Integer32,
				zhoneDslDpboPsdMaskLevel1
					Integer32,
				zhoneDslDpboPsdMaskFreq2
					Integer32,
				zhoneDslDpboPsdMaskLevel2
					Integer32,
				zhoneDslDpboPsdMaskFreq3
					Integer32,
				zhoneDslDpboPsdMaskLevel3
					Integer32,
				zhoneDslDpboPsdMaskFreq4
					Integer32,
				zhoneDslDpboPsdMaskLevel4
					Integer32,
				zhoneDslDpboPsdMaskFreq5
					Integer32,
				zhoneDslDpboPsdMaskLevel5
					Integer32,
				zhoneDslDpboPsdMaskFreq6
					Integer32,
				zhoneDslDpboPsdMaskLevel6
					Integer32,
				zhoneDslDpboPsdMaskFreq7
					Integer32,
				zhoneDslDpboPsdMaskLevel7
					Integer32,
				zhoneDslDpboPsdMaskFreq8
					Integer32,
				zhoneDslDpboPsdMaskLevel8
					Integer32,
				zhoneDslDpboPsdMaskFreq9
					Integer32,
				zhoneDslDpboPsdMaskLevel9
					Integer32,
				zhoneDslDpboPsdMaskFreq10
					Integer32,
				zhoneDslDpboPsdMaskLevel10
					Integer32,
				zhoneDslDpboPsdMaskFreq11
					Integer32,
				zhoneDslDpboPsdMaskLevel11
					Integer32,
				zhoneDslDpboPsdMaskFreq12
					Integer32,
				zhoneDslDpboPsdMaskLevel12
					Integer32,
				zhoneDslDpboPsdMaskFreq13
					Integer32,
				zhoneDslDpboPsdMaskLevel13
					Integer32,
				zhoneDslDpboPsdMaskFreq14
					Integer32,
				zhoneDslDpboPsdMaskLevel14
					Integer32,
				zhoneDslDpboPsdMaskFreq15
					Integer32,
				zhoneDslDpboPsdMaskLevel15
					Integer32,
				zhoneDslDpboPsdMaskFreq16
					Integer32,
				zhoneDslDpboPsdMaskLevel16
					Integer32
			 }

		-- 1.3.6.1.4.1.5504.5.4.22.3.1.1
		zhoneDslDpboPsdMaskFreq1 OBJECT-TYPE
			SYNTAX Integer32 (0..29998)
			UNITS "1 KHz"
			MAX-ACCESS read-write
			STATUS current
			DESCRIPTION
				"Maximum PSD mask downstream (DPBOPSDMASKds) breakpoint Frequency 1. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 1 }

		
		-- 1.3.6.1.4.1.5504.5.4.22.3.1.2
		zhoneDslDpboPsdMaskLevel1 OBJECT-TYPE
			SYNTAX Integer32 (-1275..0)
			UNITS "0.1 dBm/Hz"
			MAX-ACCESS read-write
			STATUS current
			DESCRIPTION
				"Maximum PSD mask downstream (DPBOPSDMASKds) breakpoint Level 1.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 2 }

		
		-- 1.3.6.1.4.1.5504.5.4.22.3.1.3
		zhoneDslDpboPsdMaskFreq2 OBJECT-TYPE
			SYNTAX Integer32 (0..29998)
			UNITS "1 KHz"
			MAX-ACCESS read-write
			STATUS current
			DESCRIPTION
				"Maximum PSD mask downstream (DPBOPSDMASKds) breakpoint Frequency 2. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 3 }

		
		-- 1.3.6.1.4.1.5504.5.4.22.3.1.4
		zhoneDslDpboPsdMaskLevel2 OBJECT-TYPE
			SYNTAX Integer32 (-1275..0)
			UNITS "0.1 dBm/Hz"
			MAX-ACCESS read-write
			STATUS current
			DESCRIPTION
				"Maximum PSD mask downstream (DPBOPSDMASKds) breakpoint Level 2.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 4 }

		
		-- 1.3.6.1.4.1.5504.5.4.22.3.1.5
		zhoneDslDpboPsdMaskFreq3 OBJECT-TYPE
			SYNTAX Integer32 (0..29998)
			UNITS "1 KHz"
			MAX-ACCESS read-write
			STATUS current
			DESCRIPTION
				"Maximum PSD mask downstream (DPBOPSDMASKds) breakpoint Frequency 3. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 5 }

		
		-- 1.3.6.1.4.1.5504.5.4.22.3.1.6
		zhoneDslDpboPsdMaskLevel3 OBJECT-TYPE
			SYNTAX Integer32 (-1275..0)
			UNITS "0.1 dBm/Hz"
			MAX-ACCESS read-write
			STATUS current
			DESCRIPTION
				"Maximum PSD mask downstream (DPBOPSDMASKds) breakpoint Level 3.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 6 }

		
		-- 1.3.6.1.4.1.5504.5.4.22.3.1.7
		zhoneDslDpboPsdMaskFreq4 OBJECT-TYPE
			SYNTAX Integer32 (0..29998)
			UNITS "1 KHz"
			MAX-ACCESS read-write
			STATUS current
			DESCRIPTION
				"Maximum PSD mask downstream (DPBOPSDMASKds) breakpoint Frequency 4. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 7 }

		
		-- 1.3.6.1.4.1.5504.5.4.22.3.1.8
		zhoneDslDpboPsdMaskLevel4 OBJECT-TYPE
			SYNTAX Integer32 (-1275..0)
			UNITS "0.1 dBm/Hz"
			MAX-ACCESS read-write
			STATUS current
			DESCRIPTION
				"Maximum PSD mask downstream (DPBOPSDMASKds) breakpoint Level 4.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 8 }

		
		-- 1.3.6.1.4.1.5504.5.4.22.3.1.9
		zhoneDslDpboPsdMaskFreq5 OBJECT-TYPE
			SYNTAX Integer32 (0..29998)
			UNITS "1 KHz"
			MAX-ACCESS read-write
			STATUS current
			DESCRIPTION
				"Maximum PSD mask downstream (DPBOPSDMASKds) breakpoint Frequency 5. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 9 }

		
		-- 1.3.6.1.4.1.5504.5.4.22.3.1.10
		zhoneDslDpboPsdMaskLevel5 OBJECT-TYPE
			SYNTAX Integer32 (-1275..0)
			UNITS "0.1 dBm/Hz"
			MAX-ACCESS read-write
			STATUS current
			DESCRIPTION
				"Maximum PSD mask downstream (DPBOPSDMASKds) breakpoint Level 5.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 10 }

		
		-- 1.3.6.1.4.1.5504.5.4.22.3.1.11
		zhoneDslDpboPsdMaskFreq6 OBJECT-TYPE
			SYNTAX Integer32 (0..29998)
			UNITS "1 KHz"
			MAX-ACCESS read-write
			STATUS current
			DESCRIPTION
				"Maximum PSD mask downstream (DPBOPSDMASKds) breakpoint Frequency 6. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 11 }

		
		-- 1.3.6.1.4.1.5504.5.4.22.3.1.12
		zhoneDslDpboPsdMaskLevel6 OBJECT-TYPE
			SYNTAX Integer32 (-1275..0)
			UNITS "0.1 dBm/Hz"
			MAX-ACCESS read-write
			STATUS current
			DESCRIPTION
				"Maximum PSD mask downstream (DPBOPSDMASKds) breakpoint Level 6.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 12 }

		
		-- 1.3.6.1.4.1.5504.5.4.22.3.1.13
		zhoneDslDpboPsdMaskFreq7 OBJECT-TYPE
			SYNTAX Integer32 (0..29998)
			UNITS "1 KHz"
			MAX-ACCESS read-write
			STATUS current
			DESCRIPTION
				"Maximum PSD mask downstream (DPBOPSDMASKds) breakpoint Frequency 7. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 13 }

		
		-- 1.3.6.1.4.1.5504.5.4.22.3.1.14
		zhoneDslDpboPsdMaskLevel7 OBJECT-TYPE
			SYNTAX Integer32 (-1275..0)
			UNITS "0.1 dBm/Hz"
			MAX-ACCESS read-write
			STATUS current
			DESCRIPTION
				"Maximum PSD mask downstream (DPBOPSDMASKds) breakpoint Level 7.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 14 }

		
		-- 1.3.6.1.4.1.5504.5.4.22.3.1.15
		zhoneDslDpboPsdMaskFreq8 OBJECT-TYPE
			SYNTAX Integer32 (0..29998)
			UNITS "1 KHz"
			MAX-ACCESS read-write
			STATUS current
			DESCRIPTION
				"Maximum PSD mask downstream (DPBOPSDMASKds) breakpoint Frequency 8. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 15 }

		
		-- 1.3.6.1.4.1.5504.5.4.22.3.1.16
		zhoneDslDpboPsdMaskLevel8 OBJECT-TYPE
			SYNTAX Integer32 (-1275..0)
			UNITS "0.1 dBm/Hz"
			MAX-ACCESS read-write
			STATUS current
			DESCRIPTION
				"Maximum PSD mask downstream (DPBOPSDMASKds) breakpoint Level 8.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 16 }

		
		-- 1.3.6.1.4.1.5504.5.4.22.3.1.17
		zhoneDslDpboPsdMaskFreq9 OBJECT-TYPE
			SYNTAX Integer32 (0..29998)
			UNITS "1 KHz"
			MAX-ACCESS read-write
			STATUS current
			DESCRIPTION
				"Maximum PSD mask downstream (DPBOPSDMASKds) breakpoint Frequency 9. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 17 }

		
		-- 1.3.6.1.4.1.5504.5.4.22.3.1.18
		zhoneDslDpboPsdMaskLevel9 OBJECT-TYPE
			SYNTAX Integer32 (-1275..0)
			UNITS "0.1 dBm/Hz"
			MAX-ACCESS read-write
			STATUS current
			DESCRIPTION
				"Maximum PSD mask downstream (DPBOPSDMASKds) breakpoint Level 9.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 18 }

		
		-- 1.3.6.1.4.1.5504.5.4.22.3.1.19
		zhoneDslDpboPsdMaskFreq10 OBJECT-TYPE
			SYNTAX Integer32 (0..29998)
			UNITS "1 KHz"
			MAX-ACCESS read-write
			STATUS current
			DESCRIPTION
				"Maximum PSD mask downstream (DPBOPSDMASKds) breakpoint Frequency 
				10. For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 19 }

		
		-- 1.3.6.1.4.1.5504.5.4.22.3.1.20
		zhoneDslDpboPsdMaskLevel10 OBJECT-TYPE
			SYNTAX Integer32 (-1275..0)
			UNITS "0.1 dBm/Hz"
			MAX-ACCESS read-write
			STATUS current
			DESCRIPTION
				"Maximum PSD mask downstream (DPBOPSDMASKds) breakpoint Level 10.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 20 }

		
		-- 1.3.6.1.4.1.5504.5.4.22.3.1.21
		zhoneDslDpboPsdMaskFreq11 OBJECT-TYPE
			SYNTAX Integer32 (0..29998)
			UNITS "1 KHz"
			MAX-ACCESS read-write
			STATUS current
			DESCRIPTION
				"Maximum PSD mask downstream (DPBOPSDMASKds) breakpoint Frequency 
				11. For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 21 }

		
		-- 1.3.6.1.4.1.5504.5.4.22.3.1.22
		zhoneDslDpboPsdMaskLevel11 OBJECT-TYPE
			SYNTAX Integer32 (-1275..0)
			UNITS "0.1 dBm/Hz"
			MAX-ACCESS read-write
			STATUS current
			DESCRIPTION
				"Maximum PSD mask downstream (DPBOPSDMASKds) breakpoint Level 11.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 22 }

		
		-- 1.3.6.1.4.1.5504.5.4.22.3.1.23
		zhoneDslDpboPsdMaskFreq12 OBJECT-TYPE
			SYNTAX Integer32 (0..29998)
			UNITS "1 KHz"
			MAX-ACCESS read-write
			STATUS current
			DESCRIPTION
				"Maximum PSD mask downstream (DPBOPSDMASKds) breakpoint Frequency 
				12. For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 23 }

		
		-- 1.3.6.1.4.1.5504.5.4.22.3.1.24
		zhoneDslDpboPsdMaskLevel12 OBJECT-TYPE
			SYNTAX Integer32 (-1275..0)
			UNITS "0.1 dBm/Hz"
			MAX-ACCESS read-write
			STATUS current
			DESCRIPTION
				"Maximum PSD mask downstream (DPBOPSDMASKds) breakpoint Level 12.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 24 }

		
		-- 1.3.6.1.4.1.5504.5.4.22.3.1.25
		zhoneDslDpboPsdMaskFreq13 OBJECT-TYPE
			SYNTAX Integer32 (0..29998)
			UNITS "1 KHz"
			MAX-ACCESS read-write
			STATUS current
			DESCRIPTION
				"Maximum PSD mask downstream (DPBOPSDMASKds) breakpoint Frequency 
				13. For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 25 }

		
		-- 1.3.6.1.4.1.5504.5.4.22.3.1.26
		zhoneDslDpboPsdMaskLevel13 OBJECT-TYPE
			SYNTAX Integer32 (-1275..0)
			UNITS "0.1 dBm/Hz"
			MAX-ACCESS read-write
			STATUS current
			DESCRIPTION
				"Maximum PSD mask downstream (DPBOPSDMASKds) breakpoint Level 13.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 26 }

		
		-- 1.3.6.1.4.1.5504.5.4.22.3.1.27
		zhoneDslDpboPsdMaskFreq14 OBJECT-TYPE
			SYNTAX Integer32 (0..29998)
			UNITS "1 KHz"
			MAX-ACCESS read-write
			STATUS current
			DESCRIPTION
				"Maximum PSD mask downstream (DPBOPSDMASKds) breakpoint Frequency 
				14. For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 27 }

		
		-- 1.3.6.1.4.1.5504.5.4.22.3.1.28
		zhoneDslDpboPsdMaskLevel14 OBJECT-TYPE
			SYNTAX Integer32 (-1275..0)
			UNITS "0.1 dBm/Hz"
			MAX-ACCESS read-write
			STATUS current
			DESCRIPTION
				"Maximum PSD mask downstream (DPBOPSDMASKds) breakpoint Level 14.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 28 }

		
		-- 1.3.6.1.4.1.5504.5.4.22.3.1.29
		zhoneDslDpboPsdMaskFreq15 OBJECT-TYPE
			SYNTAX Integer32 (0..29998)
			UNITS "1 KHz"
			MAX-ACCESS read-write
			STATUS current
			DESCRIPTION
				"Maximum PSD mask downstream (DPBOPSDMASKds) breakpoint Frequency 
				15. For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 29 }

		
		-- 1.3.6.1.4.1.5504.5.4.22.3.1.30
		zhoneDslDpboPsdMaskLevel15 OBJECT-TYPE
			SYNTAX Integer32 (-1275..0)
			UNITS "0.1 dBm/Hz"
			MAX-ACCESS read-write
			STATUS current
			DESCRIPTION
				"Maximum PSD mask downstream (DPBOPSDMASKds) breakpoint Level 15.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 30 }

		
		-- 1.3.6.1.4.1.5504.5.4.22.3.1.31
		zhoneDslDpboPsdMaskFreq16 OBJECT-TYPE
			SYNTAX Integer32 (0..29998)
			UNITS "1 KHz"
			MAX-ACCESS read-write
			STATUS current
			DESCRIPTION
				"Maximum PSD mask downstream (DPBOPSDMASKds) breakpoint Frequency 
				16. For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboPsdMaskEntry 31 }

		
		-- 1.3.6.1.4.1.5504.5.4.22.3.1.32
		zhoneDslDpboPsdMaskLevel16 OBJECT-TYPE
			SYNTAX Integer32 (-1275..0)
			UNITS "0.1 dBm/Hz"
			MAX-ACCESS read-write
			STATUS current
			DESCRIPTION
				"Maximum PSD mask downstream (DPBOPSDMASKds) breakpoint Level 16.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboPsdMaskEntry 32 }

		
		-- 1.3.6.1.4.1.5504.5.4.22.4
		zhoneDslDpboLfoTable OBJECT-TYPE
			SYNTAX SEQUENCE OF ZhoneDslDpboLfoEntry
			MAX-ACCESS not-accessible
			STATUS current
			DESCRIPTION
				"zhoneDslDpboLfoTable allows configuration of the ITU-T G.997.1, 
				paragraph 7.3.1.2.13 Downstream Power Back-Off DPBO low frequency 
				override (DPBOLFO) breakpoints for the associated DPBO profile. 
				There is a maximum of 16 breakpoints. This set of breakpoints define
				the PSD mask that overrides DPBO at low frequencies. Each breakpoint 
				supports the following parameters:
				  DPBOLFO Freq  - DPBO low frequency override (DPBOLFO) Frequency
				  DPBOLFO Level - DPBO low frequency override (DPBOLFO) Level
				"
			REFERENCE
				"ITU-T G.997.1, paragraph 7.3.1.2.13 Downstream Power Back-Off"
			::= { zhoneDslDpbo 4 }

		
		-- 1.3.6.1.4.1.5504.5.4.22.4.1
		zhoneDslDpboLfoEntry OBJECT-TYPE
			SYNTAX ZhoneDslDpboLfoEntry
			MAX-ACCESS not-accessible
			STATUS current
			DESCRIPTION
				"Each zhoneDslDpboProfileEntry represents a set of ITU-T G.997.1, 
				paragraph 7.3.1.2.13 Downstream Power Back-Off DPBO low frequency 
				override (DPBOLFO) breakpoints. Each Entry in this table corresponds 
				directly with the DPBO Profile using the same index.
				"
			REFERENCE
				"ITU-T G.997.1, paragraph 7.3.1.2.13 Downstream Power Back-Off"
			INDEX { zhoneDslDpboProfileIndex }
			::= { zhoneDslDpboLfoTable 1 }

		
		ZhoneDslDpboLfoEntry ::=
			SEQUENCE { 
				zhoneDslDpboLfoFreq1
					Integer32,
				zhoneDslDpboLfoLevel1
					Integer32,
				zhoneDslDpboLfoFreq2
					Integer32,
				zhoneDslDpboLfoLevel2
					Integer32,
				zhoneDslDpboLfoFreq3
					Integer32,
				zhoneDslDpboLfoLevel3
					Integer32,
				zhoneDslDpboLfoFreq4
					Integer32,
				zhoneDslDpboLfoLevel4
					Integer32,
				zhoneDslDpboLfoFreq5
					Integer32,
				zhoneDslDpboLfoLevel5
					Integer32,
				zhoneDslDpboLfoFreq6
					Integer32,
				zhoneDslDpboLfoLevel6
					Integer32,
				zhoneDslDpboLfoFreq7
					Integer32,
				zhoneDslDpboLfoLevel7
					Integer32,
				zhoneDslDpboLfoFreq8
					Integer32,
				zhoneDslDpboLfoLevel8
					Integer32,
				zhoneDslDpboLfoFreq9
					Integer32,
				zhoneDslDpboLfoLevel9
					Integer32,
				zhoneDslDpboLfoFreq10
					Integer32,
				zhoneDslDpboLfoLevel10
					Integer32,
				zhoneDslDpboLfoFreq11
					Integer32,
				zhoneDslDpboLfoLevel11
					Integer32,
				zhoneDslDpboLfoFreq12
					Integer32,
				zhoneDslDpboLfoLevel12
					Integer32,
				zhoneDslDpboLfoFreq13
					Integer32,
				zhoneDslDpboLfoLevel13
					Integer32,
				zhoneDslDpboLfoFreq14
					Integer32,
				zhoneDslDpboLfoLevel14
					Integer32,
				zhoneDslDpboLfoFreq15
					Integer32,
				zhoneDslDpboLfoLevel15
					Integer32,
				zhoneDslDpboLfoFreq16
					Integer32,
				zhoneDslDpboLfoLevel16
					Integer32
			 }

		-- 1.3.6.1.4.1.5504.5.4.22.4.1.1
		zhoneDslDpboLfoFreq1 OBJECT-TYPE
			SYNTAX Integer32 (0..29998)
			UNITS "1 KHz"
			MAX-ACCESS read-write
			STATUS current
			DESCRIPTION
				"DPBO low frequency override (DPBOLFO) breakpoint Frequency 1. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 1 }

		
		-- 1.3.6.1.4.1.5504.5.4.22.4.1.2
		zhoneDslDpboLfoLevel1 OBJECT-TYPE
			SYNTAX Integer32 (-1275..0)
			UNITS "0.1 dBm/Hz"
			MAX-ACCESS read-write
			STATUS current
			DESCRIPTION
				"DPBO low frequency override (DPBOLFO) breakpoint Level 1.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 2 }

		
		-- 1.3.6.1.4.1.5504.5.4.22.4.1.3
		zhoneDslDpboLfoFreq2 OBJECT-TYPE
			SYNTAX Integer32 (0..29998)
			UNITS "1 KHz"
			MAX-ACCESS read-write
			STATUS current
			DESCRIPTION
				"DPBO low frequency override (DPBOLFO) breakpoint Frequency 2. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 3 }

		
		-- 1.3.6.1.4.1.5504.5.4.22.4.1.4
		zhoneDslDpboLfoLevel2 OBJECT-TYPE
			SYNTAX Integer32 (-1275..0)
			UNITS "0.1 dBm/Hz"
			MAX-ACCESS read-write
			STATUS current
			DESCRIPTION
				"DPBO low frequency override (DPBOLFO) breakpoint Level 2.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 4 }

		
		-- 1.3.6.1.4.1.5504.5.4.22.4.1.5
		zhoneDslDpboLfoFreq3 OBJECT-TYPE
			SYNTAX Integer32 (0..29998)
			UNITS "1 KHz"
			MAX-ACCESS read-write
			STATUS current
			DESCRIPTION
				"DPBO low frequency override (DPBOLFO) breakpoint Frequency 3. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 5 }

		
		-- 1.3.6.1.4.1.5504.5.4.22.4.1.6
		zhoneDslDpboLfoLevel3 OBJECT-TYPE
			SYNTAX Integer32 (-1275..0)
			UNITS "0.1 dBm/Hz"
			MAX-ACCESS read-write
			STATUS current
			DESCRIPTION
				"DPBO low frequency override (DPBOLFO) breakpoint Level 3.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 6 }

		
		-- 1.3.6.1.4.1.5504.5.4.22.4.1.7
		zhoneDslDpboLfoFreq4 OBJECT-TYPE
			SYNTAX Integer32 (0..29998)
			UNITS "1 KHz"
			MAX-ACCESS read-write
			STATUS current
			DESCRIPTION
				"DPBO low frequency override (DPBOLFO) breakpoint Frequency 4. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 7 }

		
		-- 1.3.6.1.4.1.5504.5.4.22.4.1.8
		zhoneDslDpboLfoLevel4 OBJECT-TYPE
			SYNTAX Integer32 (-1275..0)
			UNITS "0.1 dBm/Hz"
			MAX-ACCESS read-write
			STATUS current
			DESCRIPTION
				"DPBO low frequency override (DPBOLFO) breakpoint Level 4.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 8 }

		
		-- 1.3.6.1.4.1.5504.5.4.22.4.1.9
		zhoneDslDpboLfoFreq5 OBJECT-TYPE
			SYNTAX Integer32 (0..29998)
			UNITS "1 KHz"
			MAX-ACCESS read-write
			STATUS current
			DESCRIPTION
				"DPBO low frequency override (DPBOLFO) breakpoint Frequency 5. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 9 }

		
		-- 1.3.6.1.4.1.5504.5.4.22.4.1.10
		zhoneDslDpboLfoLevel5 OBJECT-TYPE
			SYNTAX Integer32 (-1275..0)
			UNITS "0.1 dBm/Hz"
			MAX-ACCESS read-write
			STATUS current
			DESCRIPTION
				"DPBO low frequency override (DPBOLFO) breakpoint Level 5.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 10 }

		
		-- 1.3.6.1.4.1.5504.5.4.22.4.1.11
		zhoneDslDpboLfoFreq6 OBJECT-TYPE
			SYNTAX Integer32 (0..29998)
			UNITS "1 KHz"
			MAX-ACCESS read-write
			STATUS current
			DESCRIPTION
				"DPBO low frequency override (DPBOLFO) breakpoint Frequency 6. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 11 }

		
		-- 1.3.6.1.4.1.5504.5.4.22.4.1.12
		zhoneDslDpboLfoLevel6 OBJECT-TYPE
			SYNTAX Integer32 (-1275..0)
			UNITS "0.1 dBm/Hz"
			MAX-ACCESS read-write
			STATUS current
			DESCRIPTION
				"DPBO low frequency override (DPBOLFO) breakpoint Level 6.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 12 }

		
		-- 1.3.6.1.4.1.5504.5.4.22.4.1.13
		zhoneDslDpboLfoFreq7 OBJECT-TYPE
			SYNTAX Integer32 (0..29998)
			UNITS "1 KHz"
			MAX-ACCESS read-write
			STATUS current
			DESCRIPTION
				"DPBO low frequency override (DPBOLFO) breakpoint Frequency 7. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 13 }

		
		-- 1.3.6.1.4.1.5504.5.4.22.4.1.14
		zhoneDslDpboLfoLevel7 OBJECT-TYPE
			SYNTAX Integer32 (-1275..0)
			UNITS "0.1 dBm/Hz"
			MAX-ACCESS read-write
			STATUS current
			DESCRIPTION
				"DPBO low frequency override (DPBOLFO) breakpoint Level 7.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 14 }

		
		-- 1.3.6.1.4.1.5504.5.4.22.4.1.15
		zhoneDslDpboLfoFreq8 OBJECT-TYPE
			SYNTAX Integer32 (0..29998)
			UNITS "1 KHz"
			MAX-ACCESS read-write
			STATUS current
			DESCRIPTION
				"DPBO low frequency override (DPBOLFO) breakpoint Frequency 8. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 15 }

		
		-- 1.3.6.1.4.1.5504.5.4.22.4.1.16
		zhoneDslDpboLfoLevel8 OBJECT-TYPE
			SYNTAX Integer32 (-1275..0)
			UNITS "0.1 dBm/Hz"
			MAX-ACCESS read-write
			STATUS current
			DESCRIPTION
				"DPBO low frequency override (DPBOLFO) breakpoint Level 8.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 16 }

		
		-- 1.3.6.1.4.1.5504.5.4.22.4.1.17
		zhoneDslDpboLfoFreq9 OBJECT-TYPE
			SYNTAX Integer32 (0..29998)
			UNITS "1 KHz"
			MAX-ACCESS read-write
			STATUS current
			DESCRIPTION
				"DPBO low frequency override (DPBOLFO) breakpoint Frequency 9. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 17 }

		
		-- 1.3.6.1.4.1.5504.5.4.22.4.1.18
		zhoneDslDpboLfoLevel9 OBJECT-TYPE
			SYNTAX Integer32 (-1275..0)
			UNITS "0.1 dBm/Hz"
			MAX-ACCESS read-write
			STATUS current
			DESCRIPTION
				"DPBO low frequency override (DPBOLFO) breakpoint Level 9.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 18 }

		
		-- 1.3.6.1.4.1.5504.5.4.22.4.1.19
		zhoneDslDpboLfoFreq10 OBJECT-TYPE
			SYNTAX Integer32 (0..29998)
			UNITS "1 KHz"
			MAX-ACCESS read-write
			STATUS current
			DESCRIPTION
				"DPBO low frequency override (DPBOLFO) breakpoint Frequency 10. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 19 }

		
		-- 1.3.6.1.4.1.5504.5.4.22.4.1.20
		zhoneDslDpboLfoLevel10 OBJECT-TYPE
			SYNTAX Integer32 (-1275..0)
			UNITS "0.1 dBm/Hz"
			MAX-ACCESS read-write
			STATUS current
			DESCRIPTION
				"DPBO low frequency override (DPBOLFO) breakpoint Level 10.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 20 }

		
		-- 1.3.6.1.4.1.5504.5.4.22.4.1.21
		zhoneDslDpboLfoFreq11 OBJECT-TYPE
			SYNTAX Integer32 (0..29998)
			UNITS "1 KHz"
			MAX-ACCESS read-write
			STATUS current
			DESCRIPTION
				"DPBO low frequency override (DPBOLFO) breakpoint Frequency 11. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 21 }

		
		-- 1.3.6.1.4.1.5504.5.4.22.4.1.22
		zhoneDslDpboLfoLevel11 OBJECT-TYPE
			SYNTAX Integer32 (-1275..0)
			UNITS "0.1 dBm/Hz"
			MAX-ACCESS read-write
			STATUS current
			DESCRIPTION
				"DPBO low frequency override (DPBOLFO) breakpoint Level 11.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 22 }

		
		-- 1.3.6.1.4.1.5504.5.4.22.4.1.23
		zhoneDslDpboLfoFreq12 OBJECT-TYPE
			SYNTAX Integer32 (0..29998)
			UNITS "1 KHz"
			MAX-ACCESS read-write
			STATUS current
			DESCRIPTION
				"DPBO low frequency override (DPBOLFO) breakpoint Frequency 12. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 23 }

		
		-- 1.3.6.1.4.1.5504.5.4.22.4.1.24
		zhoneDslDpboLfoLevel12 OBJECT-TYPE
			SYNTAX Integer32 (-1275..0)
			UNITS "0.1 dBm/Hz"
			MAX-ACCESS read-write
			STATUS current
			DESCRIPTION
				"DPBO low frequency override (DPBOLFO) breakpoint Level 12.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 24 }

		
		-- 1.3.6.1.4.1.5504.5.4.22.4.1.25
		zhoneDslDpboLfoFreq13 OBJECT-TYPE
			SYNTAX Integer32 (0..29998)
			UNITS "1 KHz"
			MAX-ACCESS read-write
			STATUS current
			DESCRIPTION
				"DPBO low frequency override (DPBOLFO) breakpoint Frequency 13. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 25 }

		
		-- 1.3.6.1.4.1.5504.5.4.22.4.1.26
		zhoneDslDpboLfoLevel13 OBJECT-TYPE
			SYNTAX Integer32 (-1275..0)
			UNITS "0.1 dBm/Hz"
			MAX-ACCESS read-write
			STATUS current
			DESCRIPTION
				"DPBO low frequency override (DPBOLFO) breakpoint Level 13.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 26 }

		
		-- 1.3.6.1.4.1.5504.5.4.22.4.1.27
		zhoneDslDpboLfoFreq14 OBJECT-TYPE
			SYNTAX Integer32 (0..29998)
			UNITS "1 KHz"
			MAX-ACCESS read-write
			STATUS current
			DESCRIPTION
				"DPBO low frequency override (DPBOLFO) breakpoint Frequency 14. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 27 }

		
		-- 1.3.6.1.4.1.5504.5.4.22.4.1.28
		zhoneDslDpboLfoLevel14 OBJECT-TYPE
			SYNTAX Integer32 (-1275..0)
			UNITS "0.1 dBm/Hz"
			MAX-ACCESS read-write
			STATUS current
			DESCRIPTION
				"DPBO low frequency override (DPBOLFO) breakpoint Level 14.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 28 }

		
		-- 1.3.6.1.4.1.5504.5.4.22.4.1.29
		zhoneDslDpboLfoFreq15 OBJECT-TYPE
			SYNTAX Integer32 (0..29998)
			UNITS "1 KHz"
			MAX-ACCESS read-write
			STATUS current
			DESCRIPTION
				"DPBO low frequency override (DPBOLFO) breakpoint Frequency 15. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 29 }

		
		-- 1.3.6.1.4.1.5504.5.4.22.4.1.30
		zhoneDslDpboLfoLevel15 OBJECT-TYPE
			SYNTAX Integer32 (-1275..0)
			UNITS "0.1 dBm/Hz"
			MAX-ACCESS read-write
			STATUS current
			DESCRIPTION
				"DPBO low frequency override (DPBOLFO) breakpoint Level 15.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 30 }

		
		-- 1.3.6.1.4.1.5504.5.4.22.4.1.31
		zhoneDslDpboLfoFreq16 OBJECT-TYPE
			SYNTAX Integer32 (0..29998)
			UNITS "1 KHz"
			MAX-ACCESS read-write
			STATUS current
			DESCRIPTION
				"DPBO low frequency override (DPBOLFO) breakpoint Frequency 16. 
				For convenience, this value is set in KHz. A zero frequency 
				value disables the breakpoint.
				
				Range: 0 ~ 29998
				Units: 1 KHz
				Effective Range: 0 ~ 29.998 MHz
				Default: 0
				
				Please note the following when setting this parameter:
				
				ADSL2+ : 
				Maximum 2.208 MHz 
				Spacing between tones 4.3125 kHz 
				Number of tone bins 0 ~ 511
				
				VDSL2 (8a/b/c/d profiles)
				Maximum 8.5 MHz 
				Spacing between tones 4.3125 kHz 
				Number of tone bins 0 ~ 1971
				
				VDSL2 (12a/b profiles)
				Maximum 8.5 MHz 
				Spacing between tones 4.3125 kHz 
				Number of tone bins 0 ~ 1971
				
				VDSL2 (17a profile)
				Maximum 17.664 MHz 
				Spacing between tones 4.3125 kHz 
				Number of tone bins 0 ~ 4095
				
				VDSL2 (30a profile)
				Maximum 29.99775 MHz
				Spacing between tones 8.6250 kHz 
				Number of tone bins 0 ~ 3478"
			REFERENCE
				"ITU-T G.997.1, paragraph 7.3.1.2.13 Downstream Power Back-Off"
			DEFVAL { 0 }
			::= { zhoneDslDpboLfoEntry 31 }

		
		-- 1.3.6.1.4.1.5504.5.4.22.4.1.32
		zhoneDslDpboLfoLevel16 OBJECT-TYPE
			SYNTAX Integer32 (-1275..0)
			UNITS "0.1 dBm/Hz"
			MAX-ACCESS read-write
			STATUS current
			DESCRIPTION
				"DPBO low frequency override (DPBOLFO) breakpoint Level 16.
				
				Range: -1275 ~ 0
				Units: 0.1 dBm/Hz
				Effective Range: -127.5 ~ 0 dB
				Default: 0"
			REFERENCE
				"ITU-T G.997.1, paragraph 7.3.1.2.13 Downstream Power Back-Off"
			DEFVAL { 0 }
			::= { zhoneDslDpboLfoEntry 32 }

		
	
	END

--
-- phyDsl.mib
--
