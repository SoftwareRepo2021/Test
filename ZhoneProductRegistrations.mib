--
-- ZhoneProductRegistrations.mib
-- MIB generated by MG-SOFT Visual MIB Builder Version 3.0 Build 285
-- Thursday, November 21, 2013 at 10:38:00
--

	ZhoneProductRegistrations DEFINITIONS ::= BEGIN
 
		IMPORTS
			MODULE-IDENTITY, OBJECT-IDENTITY			
				FROM SNMPv2-SMI			
			zhoneRegistrations, zhoneRegPls, zhoneRegCpe, zhoneRegMux, zhoneRegSechtor, 
			zhoneRegMalc, zhoneModules			
				FROM Zhone;
	
	
		-- 1.3.6.1.4.1.5504.6.1
		zhoneRegistrationsModule MODULE-IDENTITY 
			LAST-UPDATED "201310041411Z"		-- October 04, 2013 at 14:11 GMT
			ORGANIZATION 
				"Zhone Technologies"
			CONTACT-INFO 
				"  Postal: 
				Zhone Technologies, Inc.
				@ Zhone Way
				7001 Oakport Street
				Oakland, CA  94621
				USA
				Toll-Free: +1 877-ZHONE20 (+1 877-946-6320)
				Tel: +1-510-777-7000
				Fax: +1-510-777-7001
				E-mail: support@zhone.com"
			DESCRIPTION 
				"This mib describes the per product registrations that are then
				used for the sysObjectId field.
				
				The format is  1.3.6.1.4.1.5504.1.x.y.z where 5504 is our 
				enterprise ID. 
				
				X is the product type so:
				        X = 1 - PLS
				        X = 2 - CPE
				        X = 3 - MUX
				
				Y is the product model type:
				        Y = 1 - BAN (for the PLS product)
				              Etc.
				
				        Y = 1 - IAD-50 (for CPE equipment)
				                  Etc.
				           
				
				Z is just an incremental field which needs to be documented 
				what value maps to which product model.
				
				For example, an IAD-50 could be .1.3.6.1.4.1.5504.1.2.1.1. A 
				new model of the iad-50 that for some reason we would want 
				to differentiate functionality would be
				 .1.3.6.1.4.1.5504.2.1.2.
				"
			REVISION "201311211030Z"		-- November 21, 2013 at 10:30 GMT
			DESCRIPTION 
				"Add 8 port mx1U160. "
			REVISION "201303071035Z"		-- March 07, 2013 at 10:35 GMT
			DESCRIPTION 
				"Fix MX 160-16p registration."
			REVISION "201208011611Z"		-- August 01, 2012 at 16:11 GMT
			DESCRIPTION 
				"Add znidNextGen node for ZNID-26xx products."
			REVISION "201111301156Z"		-- November 30, 2011 at 11:56 GMT
			DESCRIPTION 
				"add mx1Ux80 TP-RJ45 new modules"
			REVISION "201108150713Z"		-- August 15, 2011 at 07:13 GMT
			DESCRIPTION 
				"Change description of mx1U19x family."
			REVISION "201105130514Z"		-- May 13, 2011 at 05:14 GMT
			DESCRIPTION 
				"Add mx1U19x family"
			REVISION "201009231440Z"		-- September 23, 2010 at 14:40 GMT
			DESCRIPTION 
				"Add znidNextGen OIDs for 21xx, 24xx, 
				94xx, 97xx and FiberJack models."
			REVISION "201008031012Z"		-- August 03, 2010 at 10:12 GMT
			DESCRIPTION 
				"Add the MX1Ux6x and MX1Ux80 products"
			REVISION "201002111538Z"		-- February 11, 2010 at 15:38 GMT
			DESCRIPTION 
				"Added mx319."
			REVISION "200908131404Z"		-- August 13, 2009 at 14:04 GMT
			DESCRIPTION 
				"Add znid and znidNextGen nodes."
			REVISION "200810281344Z"		-- October 28, 2008 at 13:44 GMT
			DESCRIPTION 
				"Add SysObjectID values for Raptor-XP-170 flavors"
			REVISION "200711151208Z"		-- November 15, 2007 at 12:08 GMT
			DESCRIPTION 
				"Added RaptorXP and MalcXP indoor and outdoor units"
			REVISION "200710311313Z"		-- October 31, 2007 at 13:13 GMT
			DESCRIPTION 
				"V01.00.37 - Add SkyZhone 1xxx, EtherXtend 30xxx, 
				and EtherXtend 31xxx nodes."
			REVISION "200706271154Z"		-- June 27, 2007 at 11:54 GMT
			DESCRIPTION 
				"V01.00.36 - Add node FiberSLAM 101."
			REVISION "200706111612Z"		-- June 11, 2007 at 16:12 GMT
			DESCRIPTION 
				"V01.00.35 - Change gigaMux100 node identity name to
				FiberSLAM 105."
			REVISION "200705111600Z"		-- May 11, 2007 at 16:00 GMT
			DESCRIPTION 
				"- Add new card type raptorXP160 in zhoneRegistrations->zhoneRegMalc->raptorXP, 
				- Obsolete the following card types:
				 
				r100adsl2Pxxx/r100adsl2pgm
				r100adsl2Pxxx/r100adsl2pgte
				m100/m100adsl2pgm
				m100/m100Vdsl2xxx - the whole tree
				r100Vdsl2xx - the whole tree
				"
			REVISION "200705091056Z"		-- May 09, 2007 at 10:56 GMT
			DESCRIPTION 
				"Added card types malcXP350A and raptorXP350A"
			REVISION "200704031048Z"		-- April 03, 2007 at 10:48 GMT
			DESCRIPTION 
				"V01.00.32 - Add nodes for Raptor XP and
				MALC XP family definitions.  Add raptorXP105A
				and malcXP150A leaves."
			REVISION "200703091413Z"		-- March 09, 2007 at 14:13 GMT
			DESCRIPTION 
				"V01.00.31 - Add Raptor-XP-150-A definition."
			REVISION "200610261517Z"		-- October 26, 2006 at 15:17 GMT
			DESCRIPTION 
				"Added zhoneRegMalcNextGen node."
			REVISION "200608312002Z"		-- August 31, 2006 at 20:02 GMT
			DESCRIPTION 
				"V01.00.29 - Add m100Adsl2pAnxB"
			REVISION "200607131607Z"		-- July 13, 2006 at 16:07 GMT
			DESCRIPTION 
				"V01.00.28 - Add r100Adsl2pAnxB"
			REVISION "200605221601Z"		-- May 22, 2006 at 16:01 GMT
			DESCRIPTION 
				"V01.00.27 - Correct case of new onbject names"
			REVISION "200605051542Z"		-- May 05, 2006 at 15:42 GMT
			DESCRIPTION 
				"V01.00.26 - Add r100Adsl2pGte"
			REVISION "200604281336Z"		-- April 28, 2006 at 13:36 GMT
			DESCRIPTION 
				"V01.00.25 - Add m100Vdsl2Gm"
			REVISION "200604271323Z"		-- April 27, 2006 at 13:23 GMT
			DESCRIPTION 
				"V01.00.24 - Add r100Vdsl2Gm"
			REVISION "200604241206Z"		-- April 24, 2006 at 12:06 GMT
			DESCRIPTION 
				"V01.00.23 - Add m100Adsl2pGm"
			REVISION "200604181743Z"		-- April 18, 2006 at 17:43 GMT
			DESCRIPTION 
				" "
			REVISION "200603271114Z"		-- March 27, 2006 at 11:14 GMT
			DESCRIPTION 
				"V01.00.20 - Add new ethX products."
			REVISION "200512091414Z"		-- December 09, 2005 at 14:14 GMT
			DESCRIPTION 
				"V01.00.19 - added M100 product tree."
			REVISION "200409081728Z"		-- September 08, 2004 at 17:28 GMT
			DESCRIPTION 
				"V01.00.18 -- Add r100Adsl2PGigE definition."
			REVISION "200408301107Z"		-- August 30, 2004 at 11:07 GMT
			DESCRIPTION 
				"V01.00.17 -- Add zrg8xx series."
			REVISION "200405251230Z"		-- May 25, 2004 at 12:30 GMT
			DESCRIPTION 
				"V01.00.17 -- Add zrg6xx series."
			REVISION "200405211425Z"		-- May 21, 2004 at 14:25 GMT
			DESCRIPTION 
				"V01.00.16 - Add r100adsl2p family of products."
			REVISION "200405211326Z"		-- May 21, 2004 at 13:26 GMT
			DESCRIPTION 
				"add zrg700 ODU"
			REVISION "200404060145Z"		-- April 06, 2004 at 01:45 GMT
			DESCRIPTION 
				"V01.00.14 - Add isc303 product."
			REVISION "200403171054Z"		-- March 17, 2004 at 10:54 GMT
			DESCRIPTION 
				"V01.00.13 - Add IDU/ODU for 
				ZRG300 and ZRG500 products"
			REVISION "200403021400Z"		-- March 02, 2004 at 14:00 GMT
			DESCRIPTION 
				"V01.00.12 - Add raptor50LP product"
			REVISION "200310311426Z"		-- October 31, 2003 at 14:26 GMT
			DESCRIPTION 
				"V01.00.11 - Add Zhone Residential
				Gateway (ZRG) products."
			REVISION "200307101219Z"		-- July 10, 2003 at 12:19 GMT
			DESCRIPTION 
				"V01.00.11 - Added ZEDGE 6200 products"
			REVISION "200305161704Z"		-- May 16, 2003 at 17:04 GMT
			DESCRIPTION 
				"V01.00.10 - add raptor100LP product.
				Modified raptor100A description."
			REVISION "200302111458Z"		-- February 11, 2003 at 14:58 GMT
			DESCRIPTION 
				"V01.00.09 - Added REBEL MALC oids."
			REVISION "200210231018Z"		-- October 23, 2002 at 10:18 GMT
			DESCRIPTION 
				"V01.00.08 -- change malc100 to malc319"
			REVISION "200210100943Z"		-- October 10, 2002 at 09:43 GMT
			DESCRIPTION 
				"V01.00.07 - add malc100 product"
			REVISION "200210100942Z"		-- October 10, 2002 at 09:42 GMT
			DESCRIPTION 
				"V01.00.06 -- added for skyzhone"
			REVISION "200106261704Z"		-- June 26, 2001 at 17:04 GMT
			DESCRIPTION 
				"V01.00.05 - Added malc19 and malc23 Product to the malc product family
				"
			REVISION "200106071159Z"		-- June 07, 2001 at 11:59 GMT
			DESCRIPTION 
				"V01.00.04 - Expanded 23GHz family to 4 sub-bands 
				per product.  Corrected name of 5.7GHz family."
			REVISION "200105151153Z"		-- May 15, 2001 at 11:53 GMT
			DESCRIPTION 
				"V01.00.03 - changed zhoneRegZwt to zhoneRegWtn.
				Added sysObjId's for skyzhone155 and skyzhone8x."
			REVISION "200102011310Z"		-- February 01, 2001 at 13:10 GMT
			DESCRIPTION 
				"V01.00.02 - added sysObjectID assignments for Sechtor 100 models."
			REVISION "200009281648Z"		-- September 28, 2000 at 16:48 GMT
			DESCRIPTION 
				"V01.00.01 - added Wireless Transport Node product type and the DS3  
				           Wireless Transport Node product model."
			REVISION "200009121055Z"		-- September 12, 2000 at 10:55 GMT
			DESCRIPTION 
				"V01.00.00 - Initial Release"
			::= { zhoneModules 1 }

		
	
--
-- Node definitions
--
	
		-- 1.3.6.1.4.1.5504.1.1.1
		ban-2000 OBJECT-IDENTITY
			STATUS current
			DESCRIPTION 
				"BAN-2000 sysObjectId."
			::= { zhoneRegPls 1 }

		
		-- 1.3.6.1.4.1.5504.1.2.1
		zedge64 OBJECT-IDENTITY
			STATUS current
			DESCRIPTION 
				"zedge64 CPE equipment product registrations. The zedge64 has four flavours with diffrenet features so four child node are created under this node.
				The oid of these child node will be the sysObjectId of the corresponding product."
			::= { zhoneRegCpe 1 }

		
		-- 1.3.6.1.4.1.5504.1.2.1.1
		zedge64-SHDSL-FXS OBJECT-IDENTITY
			STATUS current
			DESCRIPTION 
				"zedge64-SHDSL-FXS sysObjectId."
			::= { zedge64 1 }

		
		-- 1.3.6.1.4.1.5504.1.2.1.2
		zedge64-SHDSL-BRI OBJECT-IDENTITY
			STATUS current
			DESCRIPTION 
				"zedge64-SHDSL-BRI sysObjectId."
			::= { zedge64 2 }

		
		-- 1.3.6.1.4.1.5504.1.2.1.3
		zedge64-T1-FXS OBJECT-IDENTITY
			STATUS current
			DESCRIPTION 
				"zedge64-T1-FXS sysObjectId."
			::= { zedge64 3 }

		
		-- 1.3.6.1.4.1.5504.1.2.1.4
		zedge64-E1-FXS OBJECT-IDENTITY
			STATUS current
			DESCRIPTION 
				"zedge64-E1-FXS sysObjectId."
			::= { zedge64 4 }

		
		-- 1.3.6.1.4.1.5504.1.2.2
		zedge6200 OBJECT-IDENTITY
			STATUS current
			DESCRIPTION 
				"zedge6200 CPE equipment product registrations. The zedge6200 has 3 flavours with diffrenet features so 3 child nodes are created under this node.
				The oid of these child node will be the sysObjectId of the corresponding product."
			::= { zhoneRegCpe 2 }

		
		-- 1.3.6.1.4.1.5504.1.2.2.1
		zedge6200-IP-T1 OBJECT-IDENTITY
			STATUS current
			DESCRIPTION 
				"zedge6200(ipIad) sysObjectId."
			::= { zedge6200 1 }

		
		-- 1.3.6.1.4.1.5504.1.2.2.2
		zedge6200-IP-EM OBJECT-IDENTITY
			STATUS current
			DESCRIPTION 
				"zedge6200EM sysObjectId."
			::= { zedge6200 2 }

		
		-- 1.3.6.1.4.1.5504.1.2.2.3
		zedge6200-IP-FXS OBJECT-IDENTITY
			STATUS current
			DESCRIPTION 
				"zedge6200FXS sysObjectId."
			::= { zedge6200 3 }

		
		-- 1.3.6.1.4.1.5504.1.2.3
		zrg3xx OBJECT-IDENTITY
			STATUS current
			DESCRIPTION 
				"Zhone Residential Gateway ADSL 300 series."
			::= { zhoneRegCpe 3 }

		
		-- 1.3.6.1.4.1.5504.1.2.3.1
		zrg300-IDU OBJECT-IDENTITY
			STATUS current
			DESCRIPTION 
				"1 Lifeline Pots port.
				2 Derived voice FXS ports.
				1 Ethernet port.
				0-4 video decoders.
				Indoor Unit."
			::= { zrg3xx 1 }

		
		-- 1.3.6.1.4.1.5504.1.2.3.2
		zrg300-ODU OBJECT-IDENTITY
			STATUS current
			DESCRIPTION 
				"1 Lifeline Pots port.
				2 Derived voice FXS ports.
				1 Ethernet port.
				0-4 video decoders.
				Outdoor Unit."
			::= { zrg3xx 2 }

		
		-- 1.3.6.1.4.1.5504.1.2.4
		zrg5xx OBJECT-IDENTITY
			STATUS current
			DESCRIPTION 
				"Zhone Residential Gateway VDSL 500 series."
			::= { zhoneRegCpe 4 }

		
		-- 1.3.6.1.4.1.5504.1.2.4.1
		zrg500-IDU OBJECT-IDENTITY
			STATUS current
			DESCRIPTION 
				"1 Lifeline Pots port.
				2 Derived voice FXS ports.
				1 Ethernet port.
				0-4 video decoders.
				Indoor Unit.
				"
			::= { zrg5xx 1 }

		
		-- 1.3.6.1.4.1.5504.1.2.4.2
		zrg500-ODU OBJECT-IDENTITY
			STATUS current
			DESCRIPTION 
				"1 Lifeline Pots port.
				2 Derived voice FXS ports.
				1 Ethernet port.
				0-4 video decoders.
				Outdoor Unit."
			::= { zrg5xx 2 }

		
		-- 1.3.6.1.4.1.5504.1.2.5
		zrg7xx OBJECT-IDENTITY
			STATUS current
			DESCRIPTION 
				"Zhone Residential Gateway PON 700 series."
			::= { zhoneRegCpe 5 }

		
		-- 1.3.6.1.4.1.5504.1.2.5.1
		zrg700-IDU OBJECT-IDENTITY
			STATUS current
			DESCRIPTION 
				"4 voice ports
				1 multicast video port
				1 ethernet channel"
			::= { zrg7xx 1 }

		
		-- 1.3.6.1.4.1.5504.1.2.5.2
		zrg700-ODU OBJECT-IDENTITY
			STATUS current
			DESCRIPTION 
				"4 voice ports
				1 multicast video port
				1 ethernet channel"
			::= { zrg7xx 2 }

		
		-- 1.3.6.1.4.1.5504.1.2.6
		zrg6xx OBJECT-IDENTITY
			STATUS current
			DESCRIPTION 
				"Zhone Resedential Gateway 600 series."
			::= { zhoneRegCpe 6 }

		
		-- 1.3.6.1.4.1.5504.1.2.6.1
		zrg600-IDU OBJECT-IDENTITY
			STATUS current
			DESCRIPTION 
				"Description."
			::= { zrg6xx 1 }

		
		-- 1.3.6.1.4.1.5504.1.2.6.2
		zrg600-ODU OBJECT-IDENTITY
			STATUS current
			DESCRIPTION 
				"Description."
			::= { zrg6xx 2 }

		
		-- 1.3.6.1.4.1.5504.1.2.7
		zrg8xx OBJECT-IDENTITY
			STATUS current
			DESCRIPTION 
				"Description."
			::= { zhoneRegCpe 7 }

		
		-- 1.3.6.1.4.1.5504.1.2.7.1
		zrg800-IDU OBJECT-IDENTITY
			STATUS current
			DESCRIPTION 
				"Zrg800 is like a PON (zrg700) with the addition of video 
				set-top boards like those on the zrg3xx.
				
				It has a PON uplink, a local 10/100 network, 2 built-in 
				video decoders, and a 2-port Circuit Emulation board."
			::= { zrg8xx 1 }

		
		-- 1.3.6.1.4.1.5504.1.2.7.2
		zrg800-ODU OBJECT-IDENTITY
			STATUS current
			DESCRIPTION 
				"Zrg800 is like a PON (zrg700) with the addition of video 
				set-top boards like those on the zrg3xx.
				
				It has a PON uplink, a local 10/100 network, 2 built-in 
				video decoders, and a 2-port Circuit Emulation board."
			::= { zrg8xx 2 }

		
		-- 1.3.6.1.4.1.5504.1.2.8
		ethXtendxx OBJECT-IDENTITY
			STATUS current
			DESCRIPTION 
				"Zhone Ethernet First Mile CPE devices."
			::= { zhoneRegCpe 8 }

		
		-- 1.3.6.1.4.1.5504.1.2.8.1
		ethXtendShdsl OBJECT-IDENTITY
			STATUS current
			DESCRIPTION 
				"Zhone Ethernet First Mile runnig on SHDSL."
			::= { ethXtendxx 1 }

		
		-- 1.3.6.1.4.1.5504.1.2.8.2
		ethXtendT1E1 OBJECT-IDENTITY
			STATUS current
			DESCRIPTION 
				"Zhone Ethernet First Mile running on T1 or E1."
			::= { ethXtendxx 2 }

		
		-- 1.3.6.1.4.1.5504.1.2.8.3
		ethXtend30xx OBJECT-IDENTITY
			STATUS current
			DESCRIPTION 
				"Zhone Ethernet First Mile over SHDSL 30xx 
				product family."
			::= { ethXtendxx 3 }

		
		-- 1.3.6.1.4.1.5504.1.2.8.4
		ethXtend31xx OBJECT-IDENTITY
			STATUS current
			DESCRIPTION 
				"Zhone Ethernet First Mile over SHDSL with
				T1/E1 PWE 31xx product family."
			::= { ethXtendxx 4 }

		
		-- 1.3.6.1.4.1.5504.1.2.8.5
		ethXtend32xx OBJECT-IDENTITY
			STATUS current
			DESCRIPTION 
				"Zhone Ethernet First Mile over SHDSL with
				Voice Ports 32xx product family."
			::= { ethXtendxx 5 }

		
		-- 1.3.6.1.4.1.5504.1.2.9
		znid OBJECT-IDENTITY
			STATUS current
			DESCRIPTION 
				"Zhone Network Interface Device (ZNID) heritage 
				product family."
			::= { zhoneRegCpe 9 }

		
		-- 1.3.6.1.4.1.5504.1.2.9.1
		znid42xx OBJECT-IDENTITY
			STATUS current
			DESCRIPTION 
				"Zhone Network Interface Device (ZNID) heritage 
				product family which includes the 421x and 422x 
				models in the heritage housing."
			::= { znid 1 }

		
		-- 1.3.6.1.4.1.5504.1.2.9.1.2
		znidGPON42xx OBJECT-IDENTITY
			STATUS current
			DESCRIPTION 
				"Zhone Network Interface Device (ZNID) heritage 
				GPON 421x and 422x RFOG products."
			::= { znid42xx 2 }

		
		-- 1.3.6.1.4.1.5504.1.2.9.1.3
		znidEth422x OBJECT-IDENTITY
			STATUS current
			DESCRIPTION 
				"Zhone Network Interface Device (ZNID) heritage 
				Active Ethernet 422x products."
			::= { znid42xx 3 }

		
		-- 1.3.6.1.4.1.5504.1.2.9.2
		znid420x OBJECT-IDENTITY
			STATUS current
			DESCRIPTION 
				"Zhone Network Interface Device (ZNID) heritage 
				420x product family in the next generation housing."
			::= { znid 2 }

		
		-- 1.3.6.1.4.1.5504.1.2.9.2.1
		znidGPON420x OBJECT-IDENTITY
			STATUS current
			DESCRIPTION 
				"Zhone Network Interface Device (ZNID) heritage 
				GPON 420x products in the next generation 
				housing."
			::= { znid420x 1 }

		
		-- 1.3.6.1.4.1.5504.1.2.10
		znidNextGen OBJECT-IDENTITY
			STATUS current
			DESCRIPTION 
				"Zhone Network Interface Device (ZNID) next generation
				product family."
			::= { zhoneRegCpe 10 }

		
		-- 1.3.6.1.4.1.5504.1.2.10.1
		znidNextGen22xx OBJECT-IDENTITY
			STATUS current
			DESCRIPTION 
				"Zhone Network Interface Device (ZNID) next generation 
				indoor 22xx product family."
			::= { znidNextGen 1 }

		
		-- 1.3.6.1.4.1.5504.1.2.10.1.1
		znidNextGenGE22xx OBJECT-IDENTITY
			STATUS current
			DESCRIPTION 
				"Zhone Network Interface Device (ZNID) next generation
				22xx Indoor Active GigE products."
			::= { znidNextGen22xx 1 }

		
		-- 1.3.6.1.4.1.5504.1.2.10.2
		znidNextGen42xx OBJECT-IDENTITY
			STATUS current
			DESCRIPTION 
				"Zhone Network Interface Device (ZNID) next generation
				42xx product family."
			::= { znidNextGen 2 }

		
		-- 1.3.6.1.4.1.5504.1.2.10.2.1
		znidNextGenGPON42xx OBJECT-IDENTITY
			STATUS current
			DESCRIPTION 
				"Zhone Network Interface Device (ZNID) next generation
				Outdoor 42xx GPON products."
			::= { znidNextGen42xx 1 }

		
		-- 1.3.6.1.4.1.5504.1.2.10.2.2
		znidNextGenGE42xx OBJECT-IDENTITY
			STATUS current
			DESCRIPTION 
				"Zhone Network Interface Device (ZNID) next generation
				Outdoor 42xx Active GigE products."
			::= { znidNextGen42xx 2 }

		
		-- 1.3.6.1.4.1.5504.1.2.10.3
		znidNextGen9xxx OBJECT-IDENTITY
			STATUS current
			DESCRIPTION 
				"Zhone Network Interface Device (ZNID) next generation
				9xxx product family."
			::= { znidNextGen 3 }

		
		-- 1.3.6.1.4.1.5504.1.2.10.3.1
		znidNextGenGPON9xxx OBJECT-IDENTITY
			STATUS current
			DESCRIPTION 
				"Zhone Network Interface Device (ZNID) next generation
				9xxx Outdoor GPON products."
			::= { znidNextGen9xxx 1 }

		
		-- 1.3.6.1.4.1.5504.1.2.10.3.2
		znidNextGenGE9xxx OBJECT-IDENTITY
			STATUS current
			DESCRIPTION 
				"Zhone Network Interface Device (ZNID) next generation
				9xxx Outdoor Active GigE products."
			::= { znidNextGen9xxx 2 }

		
		-- 1.3.6.1.4.1.5504.1.2.10.3.3
		znidNextGenGPON94xx OBJECT-IDENTITY
			STATUS current
			DESCRIPTION 
				"Zhone Network Interface Device (ZNID) next generation
				94xx Outdoor GPON Pseudo-Wire Emulation products."
			::= { znidNextGen9xxx 3 }

		
		-- 1.3.6.1.4.1.5504.1.2.10.3.4
		znidNextGenGE94xx OBJECT-IDENTITY
			STATUS current
			DESCRIPTION 
				"Zhone Network Interface Device (ZNID) next generation
				94xx Outdoor Active GigE Pseudo-Wire Emulation products."
			::= { znidNextGen9xxx 4 }

		
		-- 1.3.6.1.4.1.5504.1.2.10.3.5
		znidNextGenGPON97xx OBJECT-IDENTITY
			STATUS current
			DESCRIPTION 
				"Zhone Network Interface Device (ZNID) next generation
				97xx Outdoor GPON VDSL products."
			::= { znidNextGen9xxx 5 }

		
		-- 1.3.6.1.4.1.5504.1.2.10.3.6
		znidNextGenGE97xx OBJECT-IDENTITY
			STATUS current
			DESCRIPTION 
				"Zhone Network Interface Device (ZNID) next generation
				97xx Outdoor Active GigE VDSL products."
			::= { znidNextGen9xxx 6 }

		
		-- 1.3.6.1.4.1.5504.1.2.10.4
		fiberJack OBJECT-IDENTITY
			STATUS current
			DESCRIPTION 
				"Integrated GPON Uplink Module."
			::= { znidNextGen 4 }

		
		-- 1.3.6.1.4.1.5504.1.2.10.5
		znidNextGen21xx OBJECT-IDENTITY
			STATUS current
			DESCRIPTION 
				"Zhone Network Interface Device (ZNID) next generation 
				indoor 21xx product family."
			::= { znidNextGen 5 }

		
		-- 1.3.6.1.4.1.5504.1.2.10.5.1
		znidNextGenGPON21xx OBJECT-IDENTITY
			STATUS current
			DESCRIPTION 
				"Zhone Network Interface Device (ZNID) next generation
				21xx Indoor GPON products without voice."
			::= { znidNextGen21xx 1 }

		
		-- 1.3.6.1.4.1.5504.1.2.10.5.2
		znidNextGenGE21xx OBJECT-IDENTITY
			STATUS current
			DESCRIPTION 
				"Zhone Network Interface Device (ZNID) next generation
				21xx Indoor Active GigE products without voice."
			::= { znidNextGen21xx 2 }

		
		-- 1.3.6.1.4.1.5504.1.2.10.6
		znidNextGen24xx OBJECT-IDENTITY
			STATUS current
			DESCRIPTION 
				"Zhone Network Interface Device (ZNID) next generation 
				indoor 24xx product family."
			::= { znidNextGen 6 }

		
		-- 1.3.6.1.4.1.5504.1.2.10.6.1
		znidNextGenGPON24xx OBJECT-IDENTITY
			STATUS current
			DESCRIPTION 
				"Zhone Network Interface Device (ZNID) next generation
				24xx Indoor GPON products."
			::= { znidNextGen24xx 1 }

		
		-- 1.3.6.1.4.1.5504.1.2.10.6.2
		znidNextGenGE24xx OBJECT-IDENTITY
			STATUS current
			DESCRIPTION 
				"Zhone Network Interface Device (ZNID) next generation
				24xx Indoor Active GigE products."
			::= { znidNextGen24xx 2 }

		
		-- 1.3.6.1.4.1.5504.1.2.10.7
		znidNextGen26xx OBJECT-IDENTITY
			STATUS current
			DESCRIPTION 
				"Zhone Network Interface Device (ZNID) 26xx series Indoor 26xx product family."
			::= { znidNextGen 7 }

		
		-- 1.3.6.1.4.1.5504.1.2.10.7.1
		znidNextGenGPON26xx OBJECT-IDENTITY
			STATUS current
			DESCRIPTION 
				"Zhone Network Interface Device (ZNID) 26xx series Indoor GPON products."
			::= { znidNextGen26xx 1 }

		
		-- 1.3.6.1.4.1.5504.1.2.10.7.2
		znidNextGenGE26xx OBJECT-IDENTITY
			STATUS current
			DESCRIPTION 
				"Zhone Network Interface Device (ZNID) 26xx series Indoor Active GigE products."
			::= { znidNextGen26xx 2 }

		
		-- 1.3.6.1.4.1.5504.1.3.1
		z-plex10B OBJECT-IDENTITY
			STATUS current
			DESCRIPTION 
				"Z-Plex10B CPE equipment product registrations. 
				The z-plex has two flavours with diffrenet features so two child node are created
				under this node.The oid of these child node will be the sysObjectId of the corresponding z-plex product."
			::= { zhoneRegMux 1 }

		
		-- 1.3.6.1.4.1.5504.1.3.1.1
		z-plex10B-FXS-FXO OBJECT-IDENTITY
			STATUS current
			DESCRIPTION 
				"z-plex10B-FXS-FXO sysObjectId."
			::= { z-plex10B 1 }

		
		-- 1.3.6.1.4.1.5504.1.3.1.2
		z-plex10B-FXS OBJECT-IDENTITY
			STATUS current
			DESCRIPTION 
				"z-plex10B-FXS sysObjectId."
			::= { z-plex10B 2 }

		
		-- 1.3.6.1.4.1.5504.1.4.1
		sechtor-100 OBJECT-IDENTITY
			STATUS current
			DESCRIPTION 
				"Sechtor-100 sysObjectId."
			::= { zhoneRegSechtor 1 }

		
		-- 1.3.6.1.4.1.5504.1.4.1.1
		s100-ATM-SM-16T1 OBJECT-IDENTITY
			STATUS current
			DESCRIPTION 
				"sysObjectID for S100-ATM-SM-16T1."
			::= { sechtor-100 1 }

		
		-- 1.3.6.1.4.1.5504.1.4.1.2
		s100-ATM-SM-16E1 OBJECT-IDENTITY
			STATUS current
			DESCRIPTION 
				"sysObjectID for S100-ATM-SM-16E1."
			::= { sechtor-100 2 }

		
		-- 1.3.6.1.4.1.5504.1.4.2
		sechtor-300 OBJECT-IDENTITY
			STATUS current
			DESCRIPTION 
				"Sechtor-300 sysObjectId."
			::= { zhoneRegSechtor 2 }

		
		-- 1.3.6.1.4.1.5504.1.5
		zhoneRegWtn OBJECT-IDENTITY
			STATUS current
			DESCRIPTION 
				"Zhone Wireless Transport Registration."
			::= { zhoneRegistrations 5 }

		
		-- 1.3.6.1.4.1.5504.1.5.1
		node5700Mhz OBJECT-IDENTITY
			STATUS current
			DESCRIPTION 
				"sysObjectId Family for Wireless Transport Node with 5.7Ghz radio."
			::= { zhoneRegWtn 1 }

		
		-- 1.3.6.1.4.1.5504.1.5.1.1
		skyZhone45 OBJECT-IDENTITY
			STATUS current
			DESCRIPTION 
				"Unit contains a built in (not modular) ds3 interface on the
				wireline side."
			::= { node5700Mhz 1 }

		
		-- 1.3.6.1.4.1.5504.1.5.1.1.1
		oduTypeA OBJECT-IDENTITY
			STATUS current
			DESCRIPTION 
				"Unit transmits at 5735Mhz, receives at 5260Mhz (channel 1).
				Also known as ODU type A."
			::= { skyZhone45 1 }

		
		-- 1.3.6.1.4.1.5504.1.5.1.1.2
		oduTypeB OBJECT-IDENTITY
			STATUS current
			DESCRIPTION 
				"Unit transmits at 5260Mhz, receives at 5735Mhz (channel 1).
				Also known as ODU type B."
			::= { skyZhone45 2 }

		
		-- 1.3.6.1.4.1.5504.1.5.2
		node23000Mhz OBJECT-IDENTITY
			STATUS current
			DESCRIPTION 
				"sysObjectId Family for Wireless Transport Node with 23Ghz radio
				in accordance with ITU-R F.637-3 Specifications."
			::= { zhoneRegWtn 2 }

		
		-- 1.3.6.1.4.1.5504.1.5.2.1
		skyZhone8e1 OBJECT-IDENTITY
			STATUS current
			DESCRIPTION 
				"Variant of transport node with E1/T1 interface which operates a link at frequency bands
				21.8-22.4Ghz and 23.0-23.6Ghz.  14Mhz Channel separation."
			::= { node23000Mhz 1 }

		
		-- 1.3.6.1.4.1.5504.1.5.2.1.1
		oduTypeE1A OBJECT-IDENTITY
			STATUS current
			DESCRIPTION 
				"Unit transmits at 21200-21500Mhz, receives at 22400-22700Mhz."
			::= { skyZhone8e1 1 }

		
		-- 1.3.6.1.4.1.5504.1.5.2.1.2
		oduTypeE1B OBJECT-IDENTITY
			STATUS current
			DESCRIPTION 
				"Unit transmits at 22400-22700Mhz, receives at 21200-21500Mhz."
			::= { skyZhone8e1 2 }

		
		-- 1.3.6.1.4.1.5504.1.5.2.2
		skyZhone8e2 OBJECT-IDENTITY
			STATUS current
			DESCRIPTION 
				"Variant of transport node with E1/T1 interface which operates a link at frequency bands
				21.8-22.4Ghz and 23.0-23.6Ghz.  14Mhz Channel separation."
			::= { node23000Mhz 2 }

		
		-- 1.3.6.1.4.1.5504.1.5.2.2.1
		oduTypeE2A OBJECT-IDENTITY
			STATUS current
			DESCRIPTION 
				"Unit transmits at 21500-21800Mhz, receives at 22700-23000Mhz."
			::= { skyZhone8e2 1 }

		
		-- 1.3.6.1.4.1.5504.1.5.2.2.2
		oduTypeE2B OBJECT-IDENTITY
			STATUS current
			DESCRIPTION 
				"Unit transmits at 22700-23000Mhz, receives at 21500-21800Mhz."
			::= { skyZhone8e2 2 }

		
		-- 1.3.6.1.4.1.5504.1.5.2.3
		skyZhone8e3 OBJECT-IDENTITY
			STATUS current
			DESCRIPTION 
				"Variant of transport node with E1/T1 interface which operates a link at frequency bands
				21.8-22.4Ghz and 23.0-23.6Ghz.  14Mhz Channel separation."
			::= { node23000Mhz 3 }

		
		-- 1.3.6.1.4.1.5504.1.5.2.3.1
		oduTypeE3A OBJECT-IDENTITY
			STATUS current
			DESCRIPTION 
				"Unit transmits at 21800-22100Mhz, receives at 23000-23300Mhz."
			::= { skyZhone8e3 1 }

		
		-- 1.3.6.1.4.1.5504.1.5.2.3.2
		oduTypeE3B OBJECT-IDENTITY
			STATUS current
			DESCRIPTION 
				"Unit transmits at 23000-23300Mhz, receives at 21800-22100Mhz."
			::= { skyZhone8e3 2 }

		
		-- 1.3.6.1.4.1.5504.1.5.2.4
		skyZhone8e4 OBJECT-IDENTITY
			STATUS current
			DESCRIPTION 
				"Variant of transport node with E1/T1 interface which operates a link at frequency bands
				21.8-22.4Ghz and 23.0-23.6Ghz.  14Mhz Channel separation."
			::= { node23000Mhz 4 }

		
		-- 1.3.6.1.4.1.5504.1.5.2.4.1
		oduTypeE4A OBJECT-IDENTITY
			STATUS current
			DESCRIPTION 
				"Unit transmits at 22100-22400Mhz, receives at 23300-23600Mhz."
			::= { skyZhone8e4 1 }

		
		-- 1.3.6.1.4.1.5504.1.5.2.4.2
		oduTypeE4B OBJECT-IDENTITY
			STATUS current
			DESCRIPTION 
				"Unit transmits at 23300-23600Mhz, receives at 22100-22400Mhz."
			::= { skyZhone8e4 2 }

		
		-- 1.3.6.1.4.1.5504.1.5.2.5
		skyZhone8t1 OBJECT-IDENTITY
			STATUS current
			DESCRIPTION 
				"Variant of transport node with E1/T1 interface which operates a link at frequency bands
				21.8-22.4Ghz and 23.0-23.6Ghz.  14Mhz Channel separation."
			::= { node23000Mhz 5 }

		
		-- 1.3.6.1.4.1.5504.1.5.2.5.1
		oduTypeT1A OBJECT-IDENTITY
			STATUS current
			DESCRIPTION 
				"Unit transmits at 21200-21500Mhz, receives at 22400-22700Mhz."
			::= { skyZhone8t1 1 }

		
		-- 1.3.6.1.4.1.5504.1.5.2.5.2
		oduTypeT1B OBJECT-IDENTITY
			STATUS current
			DESCRIPTION 
				"Unit transmits at 22400-22700Mhz, receives at 21200-21500Mhz."
			::= { skyZhone8t1 2 }

		
		-- 1.3.6.1.4.1.5504.1.5.2.6
		skyZhone8t2 OBJECT-IDENTITY
			STATUS current
			DESCRIPTION 
				"Variant of transport node with E1/T1 interface which operates a link at frequency bands
				21.8-22.4Ghz and 23.0-23.6Ghz.  14Mhz Channel separation."
			::= { node23000Mhz 6 }

		
		-- 1.3.6.1.4.1.5504.1.5.2.6.1
		oduTypeT2A OBJECT-IDENTITY
			STATUS current
			DESCRIPTION 
				"Unit transmits at 21500-21800Mhz, receives at 22700-23000Mhz."
			::= { skyZhone8t2 1 }

		
		-- 1.3.6.1.4.1.5504.1.5.2.6.2
		oduTypeT2B OBJECT-IDENTITY
			STATUS current
			DESCRIPTION 
				"Unit transmits at 22700-23000Mhz, receives at 21500-21800Mhz."
			::= { skyZhone8t2 2 }

		
		-- 1.3.6.1.4.1.5504.1.5.2.7
		skyZhone8t3 OBJECT-IDENTITY
			STATUS current
			DESCRIPTION 
				"Variant of transport node with E1/T1 interface which operates a link at frequency bands
				21.8-22.4Ghz and 23.0-23.6Ghz.  14Mhz Channel separation."
			::= { node23000Mhz 7 }

		
		-- 1.3.6.1.4.1.5504.1.5.2.7.1
		oduTypeT3A OBJECT-IDENTITY
			STATUS current
			DESCRIPTION 
				"Unit transmits at 21800-22100Mhz, receives at 23000-23300Mhz."
			::= { skyZhone8t3 1 }

		
		-- 1.3.6.1.4.1.5504.1.5.2.7.2
		oduTypeT3B OBJECT-IDENTITY
			STATUS current
			DESCRIPTION 
				"Unit transmits at 23000-23300Mhz, receives at 21800-22100Mhz."
			::= { skyZhone8t3 2 }

		
		-- 1.3.6.1.4.1.5504.1.5.2.8
		skyZhone8t4 OBJECT-IDENTITY
			STATUS current
			DESCRIPTION 
				"Variant of transport node with E1/T1 interface which operates a link at frequency bands
				21.8-22.4Ghz and 23.0-23.6Ghz.  14Mhz Channel separation."
			::= { node23000Mhz 8 }

		
		-- 1.3.6.1.4.1.5504.1.5.2.8.1
		oduTypeT4A OBJECT-IDENTITY
			STATUS current
			DESCRIPTION 
				"Unit transmits at 22100-22400Mhz, receives at 23300-23600Mhz."
			::= { skyZhone8t4 1 }

		
		-- 1.3.6.1.4.1.5504.1.5.2.8.2
		oduTypeT4B OBJECT-IDENTITY
			STATUS current
			DESCRIPTION 
				"Unit transmits at 23300-23600Mhz, receives at 22100-22400Mhz."
			::= { skyZhone8t4 2 }

		
		-- 1.3.6.1.4.1.5504.1.5.2.9
		skyZhone155s1 OBJECT-IDENTITY
			STATUS current
			DESCRIPTION 
				"Variant of transport node with STM-1 interface which operates a link at frequency bands
				21.2-21.8Ghz and 22.4-23Ghz.  28Mhz Channel separation."
			::= { node23000Mhz 9 }

		
		-- 1.3.6.1.4.1.5504.1.5.2.9.1
		oduTypeS1A OBJECT-IDENTITY
			STATUS current
			DESCRIPTION 
				"Unit transmits at 21200-21500Mhz, receives at 22400-22700Mhz."
			::= { skyZhone155s1 1 }

		
		-- 1.3.6.1.4.1.5504.1.5.2.9.2
		oduTypeS1B OBJECT-IDENTITY
			STATUS current
			DESCRIPTION 
				"Unit transmits at 22400-22700Mhz, receives at 21200-21500Mhz."
			::= { skyZhone155s1 2 }

		
		-- 1.3.6.1.4.1.5504.1.5.2.10
		skyZhone155s2 OBJECT-IDENTITY
			STATUS current
			DESCRIPTION 
				"Variant of transport node with STM-1 interface which operates a link at frequency bands
				21.8-22.4Ghz and 23.0-23.6Ghz.  28Mhz Channel separation."
			::= { node23000Mhz 10 }

		
		-- 1.3.6.1.4.1.5504.1.5.2.10.1
		oduTypeS2A OBJECT-IDENTITY
			STATUS current
			DESCRIPTION 
				"Unit transmits at 21500-21800Mhz, receives at 22700-23000Mhz."
			::= { skyZhone155s2 1 }

		
		-- 1.3.6.1.4.1.5504.1.5.2.10.2
		oduTypeS2B OBJECT-IDENTITY
			STATUS current
			DESCRIPTION 
				"Unit transmits at 22700-23000Mhz, receives at 21500-21800Mhz."
			::= { skyZhone155s2 2 }

		
		-- 1.3.6.1.4.1.5504.1.5.2.11
		skyZhone155s3 OBJECT-IDENTITY
			STATUS current
			DESCRIPTION 
				"Variant of transport node with STM-1 interface which operates a link at frequency bands
				21.2-21.8Ghz and 22.4-23Ghz.  28Mhz Channel separation."
			::= { node23000Mhz 11 }

		
		-- 1.3.6.1.4.1.5504.1.5.2.11.1
		oduTypeS3A OBJECT-IDENTITY
			STATUS current
			DESCRIPTION 
				"Unit transmits at 21800-22100Mhz, receives at 23000-23300Mhz."
			::= { skyZhone155s3 1 }

		
		-- 1.3.6.1.4.1.5504.1.5.2.11.2
		oduTypeS3B OBJECT-IDENTITY
			STATUS current
			DESCRIPTION 
				"Unit transmits at 23000-23300Mhz, receives at 21800-22100Mhz."
			::= { skyZhone155s3 2 }

		
		-- 1.3.6.1.4.1.5504.1.5.2.12
		skyZhone155s4 OBJECT-IDENTITY
			STATUS current
			DESCRIPTION 
				"Variant of transport node with STM-1 interface which operates a link at frequency bands
				21.8-22.4Ghz and 23.0-23.6Ghz.  28Mhz Channel separation."
			::= { node23000Mhz 12 }

		
		-- 1.3.6.1.4.1.5504.1.5.2.12.1
		oduTypeS4A OBJECT-IDENTITY
			STATUS current
			DESCRIPTION 
				"Unit transmits at 22100-22400Mhz, receives at 23300-23600Mhz."
			::= { skyZhone155s4 1 }

		
		-- 1.3.6.1.4.1.5504.1.5.2.12.2
		oduTypeS4B OBJECT-IDENTITY
			STATUS current
			DESCRIPTION 
				"Unit transmits at 23300-23600Mhz, receives at 22100-22400Mhz."
			::= { skyZhone155s4 2 }

		
		-- 1.3.6.1.4.1.5504.1.5.3
		skyZhone1xxx OBJECT-IDENTITY
			STATUS current
			DESCRIPTION 
				"SkyZhone 802.11 a/b/g/n Wifi Access Points product
				family."
			::= { zhoneRegWtn 3 }

		
		-- 1.3.6.1.4.1.5504.1.6.1
		malc19 OBJECT-IDENTITY
			STATUS current
			DESCRIPTION 
				"Multiple Access Loop Concentrator with 19 inch rack mount
				cabinet product identifier."
			::= { zhoneRegMalc 1 }

		
		-- 1.3.6.1.4.1.5504.1.6.2
		malc23 OBJECT-IDENTITY
			STATUS current
			DESCRIPTION 
				"Multiple Access Loop Concentrator with 23 inch rack mount
				cabinet product identifier."
			::= { zhoneRegMalc 2 }

		
		-- 1.3.6.1.4.1.5504.1.6.3
		malc319 OBJECT-IDENTITY
			STATUS current
			DESCRIPTION 
				"Multiple Access Loop Concentrator with 10 inch rack mount
				cabinet product identifier."
			::= { zhoneRegMalc 3 }

		
		-- 1.3.6.1.4.1.5504.1.6.4
		raptor319A OBJECT-IDENTITY
			STATUS current
			DESCRIPTION 
				"Raptor MALC with 10 inch rack mount cabinet 
				product identifier.  The Raptor differs 
				from the standard MALC in that it does not 
				have any subscriber voice capability."
			::= { zhoneRegMalc 4 }

		
		-- 1.3.6.1.4.1.5504.1.6.5
		raptor319I OBJECT-IDENTITY
			STATUS current
			DESCRIPTION 
				"Raptor MALC with IP termination, with 10 inch rack 
				mount cabinet product identifier.  The Raptor differs 
				from the standard MALC in that it does not have any
				subscriber voice capability."
			::= { zhoneRegMalc 5 }

		
		-- 1.3.6.1.4.1.5504.1.6.6
		raptor719A OBJECT-IDENTITY
			STATUS current
			DESCRIPTION 
				"Raptor MALC with 19 inch rack mount cabinet 
				product identifier.  The Raptor differs 
				from the standard MALC in that it does not 
				have any subscriber voice capability."
			::= { zhoneRegMalc 6 }

		
		-- 1.3.6.1.4.1.5504.1.6.7
		raptor719I OBJECT-IDENTITY
			STATUS current
			DESCRIPTION 
				"Raptor MALC with IP termination, with 10 inch rack 
				mount cabinet product identifier.  The Raptor differs 
				from the standard MALC in that it does not 
				have any subscriber voice capability."
			::= { zhoneRegMalc 7 }

		
		-- 1.3.6.1.4.1.5504.1.6.8
		raptor723A OBJECT-IDENTITY
			STATUS current
			DESCRIPTION 
				"Raptor MALC with 23 inch rack mount cabinet 
				product identifier.  The Raptor differs 
				from the standard MALC in that it does not 
				have any subscriber voice capability."
			::= { zhoneRegMalc 8 }

		
		-- 1.3.6.1.4.1.5504.1.6.9
		raptor723I OBJECT-IDENTITY
			STATUS current
			DESCRIPTION 
				"Raptor MALC with IP termination, with 10 inch rack 
				mount cabinet product identifier.  The Raptor differs 
				from the standard MALC in that it does not 
				have any subscriber voice capability."
			::= { zhoneRegMalc 9 }

		
		-- 1.3.6.1.4.1.5504.1.6.10
		raptor100A OBJECT-IDENTITY
			STATUS current
			DESCRIPTION 
				"RAPTOR-100A in a single board configuration.
				The RAPTOR 100A is a single-board MALC with
				up to 4 T1/E1 IMA/UNI uplinks and 24 ADSL
				lines. It is offered with or without a
				splitter daughter-board. The RAPTOR-100A does
				not offer any subscriber voice services."
			::= { zhoneRegMalc 10 }

		
		-- 1.3.6.1.4.1.5504.1.6.11
		raptor100I OBJECT-IDENTITY
			STATUS current
			DESCRIPTION 
				"Raptor MALC in single-board configuration 
				with IP termination product identifier.  
				The Raptor differs from the standard MALC 
				in that it does not have any subscriber 
				voice capability."
			::= { zhoneRegMalc 11 }

		
		-- 1.3.6.1.4.1.5504.1.6.12
		raptor100LP OBJECT-IDENTITY
			STATUS current
			DESCRIPTION 
				"RAPTOR-100 Line Powered in a single board configuration.
				The RAPTOR-100 Line-Powered is a single-board MALC with
				up to four GSHDSL uplinks and 16 ADSL lines. It is
				offered with or without a splitter daughter-board.
				The RAPTOR-100 LP does not offer any subscriber voice
				services."
			::= { zhoneRegMalc 12 }

		
		-- 1.3.6.1.4.1.5504.1.6.13
		raptor50Gshdsl OBJECT-IDENTITY
			STATUS current
			DESCRIPTION 
				"RAPTOR-100 Line Powered in a single board configuration.
				The RAPTOR-100 Line-Powered is a single-board MALC with
				up to four GSHDSL uplinks and 16 ADSL lines. It is
				offered with or without a splitter daughter-board.
				The RAPTOR-100 LP does not offer any subscriber voice
				services."
			::= { zhoneRegMalc 13 }

		
		-- 1.3.6.1.4.1.5504.1.6.14
		isc303 OBJECT-IDENTITY
			STATUS current
			DESCRIPTION 
				"ISC-303 ADSL subsystem based on modified legacy ISC-303
				TDM platform.  The ISC-303 ADSL system provides up to
				60 ADSL ports spread over 24 line cards.  The system
				is fed by two T1 lines.  The T1 IMA uplink operates on
				half of the eCTU card and the ADSL operates on half of
				each of the ADSL line cards.  This system does not
				offer any subscriber voice services."
			::= { zhoneRegMalc 14 }

		
		-- 1.3.6.1.4.1.5504.1.6.15
		r100adsl2Pxxx OBJECT-IDENTITY
			STATUS current
			DESCRIPTION 
				"R100 ADSL2P family of products."
			::= { zhoneRegMalc 15 }

		
		-- 1.3.6.1.4.1.5504.1.6.15.1
		r100adsl2pip OBJECT-IDENTITY
			STATUS current
			DESCRIPTION 
				"R100 ADSL2P IP."
			::= { r100adsl2Pxxx 1 }

		
		-- 1.3.6.1.4.1.5504.1.6.15.2
		r100adsl2phdsl4 OBJECT-IDENTITY
			STATUS current
			DESCRIPTION 
				"R100 ADSL2P HDSL4."
			::= { r100adsl2Pxxx 2 }

		
		-- 1.3.6.1.4.1.5504.1.6.15.3
		r100adsl2pt1ima OBJECT-IDENTITY
			STATUS current
			DESCRIPTION 
				"R100 ADSL2P T1IMA."
			::= { r100adsl2Pxxx 3 }

		
		-- 1.3.6.1.4.1.5504.1.6.15.4
		r100adsl2pgige OBJECT-IDENTITY
			STATUS current
			DESCRIPTION 
				"R100 ADSL2P GigE."
			::= { r100adsl2Pxxx 4 }

		
		-- 1.3.6.1.4.1.5504.1.6.15.5
		r100adsl2pgm OBJECT-IDENTITY
			STATUS obsolete
			DESCRIPTION 
				"R100 Adsl2P Gm"
			::= { r100adsl2Pxxx 5 }

		
		-- 1.3.6.1.4.1.5504.1.6.15.6
		r100adsl2pgte OBJECT-IDENTITY
			STATUS obsolete
			DESCRIPTION 
				"R100 ADSL2P GTE"
			::= { r100adsl2Pxxx 6 }

		
		-- 1.3.6.1.4.1.5504.1.6.15.7
		r100adsl2panxb OBJECT-IDENTITY
			STATUS current
			DESCRIPTION 
				"R100  ADSL2P  ANXB"
			::= { r100adsl2Pxxx 7 }

		
		-- 1.3.6.1.4.1.5504.1.6.16
		m100 OBJECT-IDENTITY
			STATUS current
			DESCRIPTION 
				"M100."
			::= { zhoneRegMalc 16 }

		
		-- 1.3.6.1.4.1.5504.1.6.16.1
		m100adsl2pxxx OBJECT-IDENTITY
			STATUS current
			DESCRIPTION 
				"M100 ADSL2P."
			::= { m100 1 }

		
		-- 1.3.6.1.4.1.5504.1.6.16.1.1
		m100adsl2pgige OBJECT-IDENTITY
			STATUS current
			DESCRIPTION 
				"M100 ADSL2P GigE."
			::= { m100adsl2pxxx 1 }

		
		-- 1.3.6.1.4.1.5504.1.6.16.1.2
		m100adsl2pgm OBJECT-IDENTITY
			STATUS obsolete
			DESCRIPTION 
				"M100 Adsl2p Gm"
			::= { m100adsl2pxxx 2 }

		
		-- 1.3.6.1.4.1.5504.1.6.16.1.3
		m100Adsl2pAnxB OBJECT-IDENTITY
			STATUS current
			DESCRIPTION 
				"MALC 100 ADSL2P ANXB"
			::= { m100adsl2pxxx 3 }

		
		-- 1.3.6.1.4.1.5504.1.6.16.2
		m100Vdsl2xxx OBJECT-IDENTITY
			STATUS obsolete
			DESCRIPTION 
				"M100 Vdsl2"
			::= { m100 2 }

		
		-- 1.3.6.1.4.1.5504.1.6.16.2.1
		m100vdsl2gm OBJECT-IDENTITY
			STATUS obsolete
			DESCRIPTION 
				"M100 Vdsl2 Gm"
			::= { m100Vdsl2xxx 1 }

		
		-- 1.3.6.1.4.1.5504.1.6.17
		r100Vdsl2xx OBJECT-IDENTITY
			STATUS obsolete
			DESCRIPTION 
				"Raptor 100 Vdsl2 series"
			::= { zhoneRegMalc 17 }

		
		-- 1.3.6.1.4.1.5504.1.6.17.1
		r100vdsl2gm OBJECT-IDENTITY
			STATUS obsolete
			DESCRIPTION 
				"R100 VDSL2 GM"
			::= { r100Vdsl2xx 1 }

		
		-- 1.3.6.1.4.1.5504.1.6.18
		fiberSlam OBJECT-IDENTITY
			STATUS current
			DESCRIPTION 
				"FiberSLAM series."
			::= { zhoneRegMalc 18 }

		
		-- 1.3.6.1.4.1.5504.1.6.18.1
		fs105 OBJECT-IDENTITY
			STATUS current
			DESCRIPTION 
				"fiberslam-105 provides datacom (2xGigE, 2x10/100)
				and telecom (16xT1/E1, 3xDS3/E3) traffic
				mapping over SONET/SDH at 2.5Gbps."
			::= { fiberSlam 1 }

		
		-- 1.3.6.1.4.1.5504.1.6.18.2
		fs101 OBJECT-IDENTITY
			STATUS current
			DESCRIPTION 
				"fiberslam-101 provides datacom (2xGigE, 2x10/100) and 
				telecom (16xT1/E1) traffic mapping over SONET/SDH at 2.5Gbps."
			::= { fiberSlam 2 }

		
		-- 1.3.6.1.4.1.5504.1.6.19
		raptorXP OBJECT-IDENTITY
			STATUS current
			DESCRIPTION 
				"Raptor XP family"
			::= { zhoneRegMalc 19 }

		
		-- 1.3.6.1.4.1.5504.1.6.19.1
		raptorXP150A OBJECT-IDENTITY
			STATUS current
			DESCRIPTION 
				"Raptor-XP-150-A, the Raptor Adsl2 board"
			::= { raptorXP 1 }

		
		-- 1.3.6.1.4.1.5504.1.6.19.1.1
		raptorXP150A_ISP OBJECT-IDENTITY
			STATUS current
			DESCRIPTION 
				"Raptor-150A Indoor Unit"
			::= { raptorXP150A 1 }

		
		-- 1.3.6.1.4.1.5504.1.6.19.1.2
		raptorXP150A_OSP OBJECT-IDENTITY
			STATUS current
			DESCRIPTION 
				"Raptor-150A Outdoor Unit"
			::= { raptorXP150A 2 }

		
		-- 1.3.6.1.4.1.5504.1.6.19.2
		raptorXP350A OBJECT-IDENTITY
			STATUS current
			DESCRIPTION 
				"Raptor-XP-350-A, the Raptor Adsl2 T1/E1 board"
			::= { raptorXP 2 }

		
		-- 1.3.6.1.4.1.5504.1.6.19.2.1
		raptorXP350A_ISP OBJECT-IDENTITY
			STATUS current
			DESCRIPTION 
				"Raptor-XP-350A Indoor Unit"
			::= { raptorXP350A 1 }

		
		-- 1.3.6.1.4.1.5504.1.6.19.2.2
		raptorXP350A_OSP OBJECT-IDENTITY
			STATUS current
			DESCRIPTION 
				"Raptor-XP-350A Outdoor Unit"
			::= { raptorXP350A 2 }

		
		-- 1.3.6.1.4.1.5504.1.6.19.3
		raptorXP160 OBJECT-IDENTITY
			STATUS current
			DESCRIPTION 
				"Raptor-XP-160, the Raptor Vdsl2 board"
			::= { raptorXP 3 }

		
		-- 1.3.6.1.4.1.5504.1.6.19.3.1
		raptorXP160_ISP OBJECT-IDENTITY
			STATUS current
			DESCRIPTION 
				"Raptor-XP-160 Indoor Unit"
			::= { raptorXP160 1 }

		
		-- 1.3.6.1.4.1.5504.1.6.19.3.2
		raptorXP160_OSP OBJECT-IDENTITY
			STATUS current
			DESCRIPTION 
				"Raptor-XP-160 Outdoor Unit"
			::= { raptorXP160 2 }

		
		-- 1.3.6.1.4.1.5504.1.6.19.4
		raptorXP170 OBJECT-IDENTITY
			STATUS current
			DESCRIPTION 
				"Raptor-XP-170, the Raptor SHDSL board"
			::= { raptorXP 4 }

		
		-- 1.3.6.1.4.1.5504.1.6.19.4.1
		raptorXP170_WC OBJECT-IDENTITY
			STATUS current
			DESCRIPTION 
				"Raptor-XP-170 with Wetting Current"
			::= { raptorXP170 1 }

		
		-- 1.3.6.1.4.1.5504.1.6.19.4.1.1
		raptorXP170_ISP_WC OBJECT-IDENTITY
			STATUS current
			DESCRIPTION 
				"Raptor-XP-170 Indoor Unit with Wetting Current"
			::= { raptorXP170_WC 1 }

		
		-- 1.3.6.1.4.1.5504.1.6.19.4.1.2
		raptorXP170_OSP_WC OBJECT-IDENTITY
			STATUS current
			DESCRIPTION 
				"Raptor-XP-170 Outdoor Unit with Wetting Current"
			::= { raptorXP170_WC 2 }

		
		-- 1.3.6.1.4.1.5504.1.6.19.4.2
		raptorXP170_WC_SD OBJECT-IDENTITY
			STATUS current
			DESCRIPTION 
				"Raptor-XP-170 with Wetting Current and SELT/DELT"
			::= { raptorXP170 2 }

		
		-- 1.3.6.1.4.1.5504.1.6.19.4.2.1
		raptorXP170_ISP_WC_SD OBJECT-IDENTITY
			STATUS current
			DESCRIPTION 
				"Raptor-XP-170 Indoor Unit with Wetting Current and SELT/DELT"
			::= { raptorXP170_WC_SD 1 }

		
		-- 1.3.6.1.4.1.5504.1.6.19.4.2.2
		raptorXP170_OSP_WC_SD OBJECT-IDENTITY
			STATUS current
			DESCRIPTION 
				"Raptor-XP-170 Outdoor Unit with Wetting Current and SELT/DELT"
			::= { raptorXP170_WC_SD 2 }

		
		-- 1.3.6.1.4.1.5504.1.6.19.4.3
		raptorXP170_LP OBJECT-IDENTITY
			STATUS current
			DESCRIPTION 
				"Raptor-XP-170 with Line Power"
			::= { raptorXP170 3 }

		
		-- 1.3.6.1.4.1.5504.1.6.19.4.3.1
		raptorXP170_ISP_LP OBJECT-IDENTITY
			STATUS current
			DESCRIPTION 
				"Raptor-XP-170 Indoor Unit with Line Power"
			::= { raptorXP170_LP 1 }

		
		-- 1.3.6.1.4.1.5504.1.6.19.4.3.2
		raptorXP170_OSP_LP OBJECT-IDENTITY
			STATUS current
			DESCRIPTION 
				"Raptor-XP-170 Outdoor Unit with Line Power"
			::= { raptorXP170_LP 2 }

		
		-- 1.3.6.1.4.1.5504.1.6.19.4.4
		raptorXP170_LP_SD OBJECT-IDENTITY
			STATUS current
			DESCRIPTION 
				"Raptor-XP-170 with Line Power and SELT/DELT"
			::= { raptorXP170 4 }

		
		-- 1.3.6.1.4.1.5504.1.6.19.4.4.1
		raptorXP170_ISP_LP_SD OBJECT-IDENTITY
			STATUS current
			DESCRIPTION 
				"Raptor-XP-170 Indoor Unit with Line Power and SELT/DELT"
			::= { raptorXP170_LP_SD 1 }

		
		-- 1.3.6.1.4.1.5504.1.6.19.4.4.2
		raptorXP170_OSP_LP_SD OBJECT-IDENTITY
			STATUS current
			DESCRIPTION 
				"Raptor-XP-170 Outdoor Unit with Line Power and SELT/DELT"
			::= { raptorXP170_LP_SD 2 }

		
		-- 1.3.6.1.4.1.5504.1.6.20
		malcXP OBJECT-IDENTITY
			STATUS current
			DESCRIPTION 
				"Malc-XP family"
			::= { zhoneRegMalc 20 }

		
		-- 1.3.6.1.4.1.5504.1.6.20.1
		malcXP150A OBJECT-IDENTITY
			STATUS current
			DESCRIPTION 
				"Malc-XP-150-A, the Raptor Adsl2 POTS board"
			::= { malcXP 1 }

		
		-- 1.3.6.1.4.1.5504.1.6.20.1.1
		malcXP150A_ISP OBJECT-IDENTITY
			STATUS current
			DESCRIPTION 
				"MalcXP150A Indoor Unit"
			::= { malcXP150A 1 }

		
		-- 1.3.6.1.4.1.5504.1.6.20.1.2
		malcXP150A_OSP OBJECT-IDENTITY
			STATUS current
			DESCRIPTION 
				"MalcXP150A Outdoor Unit"
			::= { malcXP150A 2 }

		
		-- 1.3.6.1.4.1.5504.1.6.20.4
		malcXP350A OBJECT-IDENTITY
			STATUS current
			DESCRIPTION 
				"Malc-XP-350-A, the Raptor Adsl2 POTS T1/E1 board"
			::= { malcXP 4 }

		
		-- 1.3.6.1.4.1.5504.1.6.20.4.1
		malcXP350A_ISP OBJECT-IDENTITY
			STATUS current
			DESCRIPTION 
				"Malc-XP-350A Indoor Unit"
			::= { malcXP350A 1 }

		
		-- 1.3.6.1.4.1.5504.1.6.20.4.2
		malcXP350A_OSP OBJECT-IDENTITY
			STATUS current
			DESCRIPTION 
				"Malc-XP-350A Outdoor Unit"
			::= { malcXP350A 2 }

		
		-- 1.3.6.1.4.1.5504.1.6.20.5
		malcXP160 OBJECT-IDENTITY
			STATUS current
			DESCRIPTION 
				"Malc-XP-160, the Raptor Vdsl2 POTS board"
			::= { malcXP 5 }

		
		-- 1.3.6.1.4.1.5504.1.6.20.5.1
		malcXP160_ISP OBJECT-IDENTITY
			STATUS current
			DESCRIPTION 
				"Malc-XP-160 Indoor Unit"
			::= { malcXP160 1 }

		
		-- 1.3.6.1.4.1.5504.1.6.20.5.2
		malcXP160_OSP OBJECT-IDENTITY
			STATUS current
			DESCRIPTION 
				"Malc-XP-160 Outdoor Unit"
			::= { malcXP160 2 }

		
		-- 1.3.6.1.4.1.5504.1.7
		zhoneRegMxNextGen OBJECT-IDENTITY
			STATUS current
			DESCRIPTION 
				"Next Generation MALC"
			::= { zhoneRegistrations 7 }

		
		-- 1.3.6.1.4.1.5504.1.7.1
		mx19 OBJECT-IDENTITY
			STATUS current
			DESCRIPTION 
				"Mx Next Gen 19 inch."
			::= { zhoneRegMxNextGen 1 }

		
		-- 1.3.6.1.4.1.5504.1.7.2
		mx23 OBJECT-IDENTITY
			STATUS current
			DESCRIPTION 
				"Mx Next Gen 23 inch."
			::= { zhoneRegMxNextGen 2 }

		
		-- 1.3.6.1.4.1.5504.1.7.3
		mx319 OBJECT-IDENTITY
			STATUS current
			DESCRIPTION 
				"Mx Next Gen 3U 19 inch."
			::= { zhoneRegMxNextGen 3 }

		
		-- 1.3.6.1.4.1.5504.1.7.4
		mx1U OBJECT-IDENTITY
			STATUS current
			DESCRIPTION 
				"MX1U Product Family"
			::= { zhoneRegMxNextGen 4 }

		
		-- 1.3.6.1.4.1.5504.1.7.4.1
		mx1Ux6x OBJECT-IDENTITY
			STATUS current
			DESCRIPTION 
				"MX1U x6x Product Family"
			::= { mx1U 1 }

		
		-- 1.3.6.1.4.1.5504.1.7.4.1.1
		mx1U16x OBJECT-IDENTITY
			STATUS current
			DESCRIPTION 
				"MX1U 16x Product Family"
			::= { mx1Ux6x 1 }

		
		-- 1.3.6.1.4.1.5504.1.7.4.1.1.1
		mx1U160 OBJECT-IDENTITY
			STATUS current
			DESCRIPTION 
				"MX 160 - 24 VDSL2, 4 FE/GE"
			::= { mx1U16x 1 }

		
		-- 1.3.6.1.4.1.5504.1.7.4.1.1.2
		mx1U161 OBJECT-IDENTITY
			STATUS current
			DESCRIPTION 
				"MX 161 - 24 VDSL2, 24 POTS SPLT (600 Ohm), 4 FE/GE"
			::= { mx1U16x 2 }

		
		-- 1.3.6.1.4.1.5504.1.7.4.1.1.3
		mx1U162 OBJECT-IDENTITY
			STATUS current
			DESCRIPTION 
				"MX 162 - 24 VDSL2, 24 POTS SPLT (900 Ohm), 4 FE/GE"
			::= { mx1U16x 3 }

		
		-- 1.3.6.1.4.1.5504.1.7.4.1.1.4
		mx160-16p OBJECT-IDENTITY
			STATUS current
			DESCRIPTION 
				"MX x6x/MX 160-16p - 16 VDSL2, 2 FE/GE"
			::= { mx1U16x 4 }

		
		-- 1.3.6.1.4.1.5504.1.7.4.1.1.5
		mx160-8p OBJECT-IDENTITY
			STATUS current
			DESCRIPTION 
				"MX 160-LT-8p - 8 VDSL2, 2 FE/GE"
			::= { mx1U16x 5 }

		
		-- 1.3.6.1.4.1.5504.1.7.4.1.2
		mx1U26x OBJECT-IDENTITY
			STATUS current
			DESCRIPTION 
				"MX1U 26x Product Family"
			::= { mx1Ux6x 2 }

		
		-- 1.3.6.1.4.1.5504.1.7.4.1.2.1
		mx1U260 OBJECT-IDENTITY
			STATUS current
			DESCRIPTION 
				"MX 260 - 24 VDSL2, 3 FE/GE, 1 GPON"
			::= { mx1U26x 1 }

		
		-- 1.3.6.1.4.1.5504.1.7.4.1.2.2
		mx1U261 OBJECT-IDENTITY
			STATUS current
			DESCRIPTION 
				"MX 261 - 24 VDSL2, 24 POTS SPLT (600 Ohm), 3 FE/GE, 1 GPON"
			::= { mx1U26x 2 }

		
		-- 1.3.6.1.4.1.5504.1.7.4.1.2.3
		mx1U262 OBJECT-IDENTITY
			STATUS current
			DESCRIPTION 
				"MX 262 - 24 VDSL2, 24 POTS SPLT (900 Ohm), 3 FE/GE, 1 GPON"
			::= { mx1U26x 3 }

		
		-- 1.3.6.1.4.1.5504.1.7.4.2
		mx1Ux80 OBJECT-IDENTITY
			STATUS current
			DESCRIPTION 
				"MX1U x80 Product Family"
			::= { mx1U 2 }

		
		-- 1.3.6.1.4.1.5504.1.7.4.2.1
		mx1U180 OBJECT-IDENTITY
			STATUS current
			DESCRIPTION 
				"MX 180 - 24 FE, 2 FE/GE"
			::= { mx1Ux80 1 }

		
		-- 1.3.6.1.4.1.5504.1.7.4.2.2
		mx1U280 OBJECT-IDENTITY
			STATUS current
			DESCRIPTION 
				"MX 280 - 24 FE, 2 FE/GE, 1 GPON"
			::= { mx1Ux80 2 }

		
		-- 1.3.6.1.4.1.5504.1.7.4.2.3
		mx1U180_TP_RJ45 OBJECT-IDENTITY
			STATUS current
			DESCRIPTION 
				"MX 180 TP-RJ45 - 24 FE, 4 FE/GE"
			::= { mx1Ux80 3 }

		
		-- 1.3.6.1.4.1.5504.1.7.4.2.4
		mx1U280_TP_RJ45 OBJECT-IDENTITY
			STATUS current
			DESCRIPTION 
				"MX 280 TP-RJ45 - 24 FE, 3 FE/GE, 1 GPON"
			::= { mx1Ux80 4 }

		
		-- 1.3.6.1.4.1.5504.1.7.4.2.5
		mx1U180_LT_TP_RJ45 OBJECT-IDENTITY
			STATUS current
			DESCRIPTION 
				"MX 180 LT-TP-RJ45 - 24 FE, 4 FE/GE"
			::= { mx1Ux80 5 }

		
		-- 1.3.6.1.4.1.5504.1.7.4.2.6
		mx1U280_LT_TP_RJ45 OBJECT-IDENTITY
			STATUS current
			DESCRIPTION 
				"MX 280 LT-TP-RJ45 - 24 FE, 3 FE/GE, 1 GPON"
			::= { mx1Ux80 6 }

		
		-- 1.3.6.1.4.1.5504.1.7.4.3
		mx1U19x OBJECT-IDENTITY
			STATUS current
			DESCRIPTION 
				"MXK 19x Product Family"
			::= { mx1U 3 }

		
		-- 1.3.6.1.4.1.5504.1.7.4.3.1
		mx1U194 OBJECT-IDENTITY
			STATUS current
			DESCRIPTION 
				"MXK 194 - 4 GPON OLT, 8 FE/GE"
			::= { mx1U19x 1 }

		
		-- 1.3.6.1.4.1.5504.1.7.4.3.2
		mx1U198 OBJECT-IDENTITY
			STATUS current
			DESCRIPTION 
				"MXK 198 - 8 GPON OLT, 8 FE/GE"
			::= { mx1U19x 2 }

		
		-- 1.3.6.1.4.1.5504.1.7.4.3.3
		mx1U194_10GE OBJECT-IDENTITY
			STATUS current
			DESCRIPTION 
				"MXK 194-10GE - 4 GPON OLT, 8 FE/GE, 2 10GE"
			::= { mx1U19x 3 }

		
		-- 1.3.6.1.4.1.5504.1.7.4.3.4
		mx1U198_10GE OBJECT-IDENTITY
			STATUS current
			DESCRIPTION 
				"MXK 198-10GE - 8 GPON OLT, 8 FE/GE, 2 10GE"
			::= { mx1U19x 4 }

		
		-- 1.3.6.1.4.1.5504.1.7.4.3.5
		mx1U194_TOP OBJECT-IDENTITY
			STATUS current
			DESCRIPTION 
				"MXK 194-TOP - 4 GPON OLT, 8 FE/GE, TOP"
			::= { mx1U19x 5 }

		
		-- 1.3.6.1.4.1.5504.1.7.4.3.6
		mx1U198_TOP OBJECT-IDENTITY
			STATUS current
			DESCRIPTION 
				"MXK 198-TOP - 8 GPON OLT, 8 FE/GE, TOP"
			::= { mx1U19x 6 }

		
		-- 1.3.6.1.4.1.5504.1.7.4.3.7
		mx1U194_10GE_TOP OBJECT-IDENTITY
			STATUS current
			DESCRIPTION 
				"MXK 194-10GE-TOP - 4 GPON OLT, 8 FE/GE, 2 10GE, TOP"
			::= { mx1U19x 7 }

		
		-- 1.3.6.1.4.1.5504.1.7.4.3.8
		mx1U198_10GE_TOP OBJECT-IDENTITY
			STATUS current
			DESCRIPTION 
				"MXK 198-10GE-TOP - 8 GPON OLT, 8 FE/GE, 2 10GE, TOP"
			::= { mx1U19x 8 }

		
		-- 1.3.6.1.4.1.5504.1.7.4.4
		mx1Ux5x OBJECT-IDENTITY
			STATUS current
			DESCRIPTION 
				"Description."
			::= { mx1U 4 }

		
		-- 1.3.6.1.4.1.5504.1.7.4.4.1
		mx1U15x OBJECT-IDENTITY
			STATUS current
			DESCRIPTION 
				"Description."
			::= { mx1Ux5x 1 }

		
		-- 1.3.6.1.4.1.5504.1.7.4.4.1.1
		mx1U150 OBJECT-IDENTITY
			STATUS current
			DESCRIPTION 
				"Description."
			::= { mx1U15x 1 }

		
		-- 1.3.6.1.4.1.5504.1.7.4.4.1.2
		mx1U151 OBJECT-IDENTITY
			STATUS current
			DESCRIPTION 
				"Description."
			::= { mx1U15x 2 }

		
		-- 1.3.6.1.4.1.5504.1.7.4.4.1.3
		mx1U152 OBJECT-IDENTITY
			STATUS current
			DESCRIPTION 
				"Description."
			::= { mx1U15x 3 }

		
		-- 1.3.6.1.4.1.5504.1.7.4.5
		mx1U180Ge OBJECT-IDENTITY
			STATUS current
			DESCRIPTION 
				"MX1U 180 GE Product Family"
			::= { mx1U 5 }

		
		-- 1.3.6.1.4.1.5504.1.7.4.5.1
		mx1U180_GE_LT_SFP OBJECT-IDENTITY
			STATUS current
			DESCRIPTION 
				" MX 180 GE-LT-SFP - 28 FE/GE, 2 10 G"
			::= { mx1U180Ge 1 }

		
		-- 1.3.6.1.4.1.5504.1.7.4.5.2
		mx1U180_GE_LT_RJ45 OBJECT-IDENTITY
			STATUS current
			DESCRIPTION 
				"MX 180 GE-LT-RJ45 - 28 FE/GE, 2 10 G"
			::= { mx1U180Ge 2 }

		
		-- 1.3.6.1.4.1.5504.1.7.5
		mxp1U OBJECT-IDENTITY
			STATUS current
			DESCRIPTION 
				"MXP1U Product Family"
			::= { zhoneRegMxNextGen 5 }

		
		-- 1.3.6.1.4.1.5504.1.7.5.1
		mxp1Ux60 OBJECT-IDENTITY
			STATUS current
			DESCRIPTION 
				"MXP1U x60 Product Family"
			::= { mxp1U 1 }

		
		-- 1.3.6.1.4.1.5504.1.7.5.1.1
		mxp1U160Family OBJECT-IDENTITY
			STATUS current
			DESCRIPTION 
				"MXP1U 160 Product Family"
			::= { mxp1Ux60 1 }

		
		-- 1.3.6.1.4.1.5504.1.7.5.1.1.1
		mxp1U160 OBJECT-IDENTITY
			STATUS current
			DESCRIPTION 
				"MXP 160 - 24 VDSL2, 24 POTS VOIP, 4 FE/GE"
			::= { mxp1U160Family 1 }

		
		-- 1.3.6.1.4.1.5504.1.7.5.1.2
		mxp1U260Family OBJECT-IDENTITY
			STATUS current
			DESCRIPTION 
				"MXP1U 260 Product Family"
			::= { mxp1Ux60 2 }

		
		-- 1.3.6.1.4.1.5504.1.7.5.1.2.1
		mxp1U260 OBJECT-IDENTITY
			STATUS current
			DESCRIPTION 
				"MXP 260 - 24 VDSL2, 24 POTS VOIP, 3 FE/GE, 1 GPON"
			::= { mxp1U260Family 1 }

		
		-- 1.3.6.1.4.1.5504.1.7.5.2
		mxp1Ux80 OBJECT-IDENTITY
			STATUS current
			DESCRIPTION 
				"MXP1U x80 Product Family"
			::= { mxp1U 2 }

		
		-- 1.3.6.1.4.1.5504.1.7.5.2.1
		mxp1U180 OBJECT-IDENTITY
			STATUS current
			DESCRIPTION 
				"MXP 180 - 24 FE, 24 POTS VOIP, 2 FE/GE"
			::= { mxp1Ux80 1 }

		
		-- 1.3.6.1.4.1.5504.1.7.5.2.2
		mxp1U280 OBJECT-IDENTITY
			STATUS current
			DESCRIPTION 
				"MXP 280 - 24 FE, 24 POTS VOIP, 2 FE/GE, 1 GPON"
			::= { mxp1Ux80 2 }

		
		-- 1.3.6.1.4.1.5504.1.7.5.2.3
		mxp1U180_TP_RJ45 OBJECT-IDENTITY
			STATUS current
			DESCRIPTION 
				"MXP 180 TP-RJ45 - 24 FE, 24 POTS VOIP, 4 FE/GE"
			::= { mxp1Ux80 3 }

		
		-- 1.3.6.1.4.1.5504.1.7.5.2.4
		mxp1U280_TP_RJ45 OBJECT-IDENTITY
			STATUS current
			DESCRIPTION 
				"MXP 280 TP-RJ45 - 24 FE, 24 POTS VOIP, 3 FE/GE, 1 GPON"
			::= { mxp1Ux80 4 }

		
		-- 1.3.6.1.4.1.5504.1.7.5.3
		mxp1Ux5x OBJECT-IDENTITY
			STATUS current
			DESCRIPTION 
				"Description."
			::= { mxp1U 3 }

		
		-- 1.3.6.1.4.1.5504.1.7.5.3.1
		mxp1U15xFamily OBJECT-IDENTITY
			STATUS current
			DESCRIPTION 
				"Description."
			::= { mxp1Ux5x 1 }

		
		-- 1.3.6.1.4.1.5504.1.7.5.3.1.1
		mxp1U150 OBJECT-IDENTITY
			STATUS current
			DESCRIPTION 
				"Description."
			::= { mxp1U15xFamily 1 }


		-- 1.3.6.1.4.1.5504.1.7.6
  		mx19-ha OBJECT-IDENTITY
          		STATUS current
          		DESCRIPTION
                  		"Mx Next Gen 19 inch with high-availability set."
          		::= { zhoneRegMxNextGen 6 }


		-- 1.3.6.1.4.1.5504.1.7.7
  		mx23-ha OBJECT-IDENTITY
          		STATUS current
          		DESCRIPTION
                  		"Mx Next Gen 23 inch with high-availability set."
          		::= { zhoneRegMxNextGen 7 }


  		-- 1.3.6.1.4.1.5504.1.7.8
  		mx319-ha OBJECT-IDENTITY
          		STATUS current
          		DESCRIPTION
                  		"Mx Next Gen 3U 19 inch with high-availability set."
          		::= { zhoneRegMxNextGen 8 }


  		-- 1.3.6.1.4.1.5504.1.8
  		zhoneRegMxK OBJECT-IDENTITY
          		STATUS current
          		DESCRIPTION
                  		"MXK Family"
          		::= { zhoneRegistrations 8 }


  		-- 1.3.6.1.4.1.5504.1.8.1
  		mxk1419 OBJECT-IDENTITY
          		STATUS current
          		DESCRIPTION
                  		"MXK 14U, 19 inch CHASSIS, 14 SERVICE SLOTS"
          		::= { zhoneRegMxK 1 }


  		-- 1.3.6.1.4.1.5504.1.8.2
  		mxk1421 OBJECT-IDENTITY
          		STATUS current
          		DESCRIPTION
                  		"MXK 14U, 21 inch CHASSIS, 16 SERVICE SLOTS"
          		::= { zhoneRegMxK 2 }


  		-- 1.3.6.1.4.1.5504.1.8.3
  		mxk219 OBJECT-IDENTITY
          		STATUS current
          		DESCRIPTION
                  		"MXK 2U, 19 inch CHASSIS, 2 SERVICE SLOTS"
          		::= { zhoneRegMxK 3 }


  		-- 1.3.6.1.4.1.5504.1.8.6
  		mxk1419-ha OBJECT-IDENTITY
          		STATUS current
          		DESCRIPTION
                  		"MXK 14U, 19 inch CHASSIS, 14 SERVICE SLOTS with high-availability set"
          	::= { zhoneRegMxK 6 }


  		-- 1.3.6.1.4.1.5504.1.8.7
  		mxk1421-ha OBJECT-IDENTITY
          		STATUS current
          		DESCRIPTION
                  		"MXK 14U, 21 inch CHASSIS, 16 SERVICE SLOTS with high-availability set"
          	::= { zhoneRegMxK 7 }


  		-- 1.3.6.1.4.1.5504.1.8.8
  		mxk219-ha OBJECT-IDENTITY
          		STATUS current
          		DESCRIPTION
                  		"MXK 2U, 19 inch CHASSIS, 2 SERVICE SLOTS with high-availability set"
          	::= { zhoneRegMxK 8 }
		
	
	END

--
-- ZhoneProductRegistrations.mib
--
