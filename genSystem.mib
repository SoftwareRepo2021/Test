--
-- genSystem.mib
-- MIB generated by MG-SOFT Visual MIB Builder Version 3.0 Build 285
-- Friday, September 02, 2016 at 00:01:57
--

	ZHONE-SYSTEM-MIB DEFINITIONS ::= BEGIN
 
		IMPORTS
			IANAifType			
				FROM IANAifType-MIB			
			ifIndex, InterfaceIndexOrZero			
				FROM IF-MIB			
			SnmpAdminString			
				FROM SNMP-FRAMEWORK-MIB			
			OBJECT-GROUP, NOTIFICATION-GROUP			
				FROM SNMPv2-CONF			
			TimeTicks, IpAddress, Integer32, Unsigned32, Counter32, 
			OBJECT-TYPE, MODULE-IDENTITY, OBJECT-IDENTITY, NOTIFICATION-TYPE			
				FROM SNMPv2-SMI			
			TruthValue, DateAndTime, TEXTUAL-CONVENTION			
				FROM SNMPv2-TC			
			ipIfLgId, ipIfVpi, ipIfVci, ipIfAddr			
				FROM ZHONE-COM-IP-REC-MIB			
			zhoneShelfNumber, zhoneSlotNumber, pportNumber, subPortNumber			
				FROM ZHONE-INTERFACE-TRANSLATION-MIB			
			zhone, zhoneSystem, zhoneShelfIndex, zhoneSlotIndex, zhoneTrapModules, 
			zhoneModules, zhoneShelfIndex, zhoneSlotIndex			
				FROM Zhone			
			ZhoneAdminString, ZhoneRowStatus, ZhoneShelfValue, ZhoneSlotValue, ZhoneFileName, 
			ZhoneIfType, ZhoneCountryCode, ZhoneCardLineType, ZhoneCardType, ZhoneAlarmSeverity, 
			ZhoneAlarmTypeId			
				FROM Zhone-TC;
	
	
-- 
-- 
-- 
-- 
-- 
-- 
-- 
-- 
-- 
-- 
-- 
-- 
-- 
-- 
-- 
-- 
-- 
-- Command to generate protection layer:
--  /vob/zhonetools/bin/pahrser.pl rfc2514.mib rfc1907.mib \
-- iftype.mib rfc2233.mib Zhone.mib Zhone-TC.mib genSystem.mib
-- 
-- Command to generate mib handler (this example put all output
-- in a file called fileSystemHdlr.c but you can use any filename):
-- /vob/EPILOGUE/binaries/emissary/solaris/mibcomp Zhone.mib \
-- Zhone-TC.mib iftype.mib rfc1907.mib rfc2233.mib rfc2571.mib \
-- rfc2514.mib comIpRD.mib comIpRec.mib genIntfTranslationTable.mib \
-- -stub -o fileSystemHdlrs.c genSystem.mib
-- 
		-- 1.3.6.1.4.1.5504.6.2
		zhoneSystemModule MODULE-IDENTITY 
			LAST-UPDATED "201511291200Z"		-- November 29, 2015 at 12:00 GMT
			ORGANIZATION 
				"Zhone Technologies, Inc."
			CONTACT-INFO 
				"  Postal: 
				Zhone Technologies, Inc.
				@ Zhone Way
				7001 Oakport Street
				Oakland, CA  94621
				USA
				Toll-Free: +1 877-ZHONE20 (+1 877-946-6320)
				Tel: +1-510-777-7000
				Fax: +1-510-777-7001
				E-mail: support@zhone.com"
			DESCRIPTION 
				"This module contains the system generic variables that are
				complete for the entire system. Note that some functional
				entities are maintained in their own mib as they will be
				included only when their functionality is included for that
				particular Zhone platform."
			REVISION "201609012346Z"		-- September 01, 2016 at 23:46 GMT
			DESCRIPTION 
				"Added new object zhoneTrapProfilesIndexes and 
				include it in zhoneGenericSetClear trap"
			REVISION "201603291740Z"		-- March 29, 2016 at 17:40 GMT
			DESCRIPTION 
				"Add snmp v3 engine id unique part"
			REVISION "201510132021Z"		-- October 13, 2015 at 20:21 GMT
			DESCRIPTION 
				"Modified zhoneUserAdmin description"
			REVISION "201509111658Z"		-- September 11, 2015 at 16:58 GMT
			DESCRIPTION 
				"Add zhoneGenericSetClear trap and associated bindings."
			REVISION "201507090903Z"		-- July 09, 2015 at 09:03 GMT
			DESCRIPTION 
				"Remove currentVers in Card_Stats profile, code was not working anyway"
			REVISION "201410300626Z"		-- October 30, 2014 at 06:26 GMT
			DESCRIPTION 
				"Add option bondautodetect."
			REVISION "201405122359Z"		-- May 12, 2014 at 23:59 GMT
			DESCRIPTION 
				"Added new fields zhoneSystemOutletTemperatureHighThreshold & 
				zhoneSystemOutletTemperatureLowThreshold to the zhoneSystemConfiguration group"
			REVISION "201404132318Z"		-- April 13, 2014 at 23:18 GMT
			DESCRIPTION 
				"Added persistentLogging support"
			REVISION "201402030329Z"		-- February 03, 2014 at 03:29 GMT
			DESCRIPTION 
				"Changed the sysProfOptions from cfmoff to cfmon."
			REVISION "201311262245Z"		-- November 26, 2013 at 22:45 GMT
			DESCRIPTION 
				"Added new option bit flag: cfmoff and added new snmpv3includingZMS enum in snmpversion."
			REVISION "201306211544Z"		-- June 21, 2013 at 15:44 GMT
			DESCRIPTION 
				"added new option bitflags: enablexcardlinkagg and fiberlan"
			REVISION "201305161723Z"		-- May 16, 2013 at 17:23 GMT
			DESCRIPTION 
				"Added bits nol3bridgetable+ipg88bits+disdefpktrules bits to zhoneSystemConfigurationOptions field"
			REVISION "201212270429Z"		-- December 27, 2012 at 04:29 GMT
			DESCRIPTION 
				"Added zhoneSntpDaylightSavingStart & zhoneSntpDaylightSavingEnd fields to n
				tp-config-profile"
			REVISION "201210181311Z"		-- October 18, 2012 at 13:11 GMT
			DESCRIPTION 
				"Addd snmpVersion object."
			REVISION "201204101128Z"		-- April 10, 2012 at 11:28 GMT
			DESCRIPTION 
				"1. Change range of zhoneSystemConfigurationReservedVlanIdStart.
				2. Add comments to zhoneSystemConfigurationReservedVlanIdCount."
			REVISION "201203260932Z"		-- March 26, 2012 at 09:32 GMT
			DESCRIPTION 
				"1. Add reserved VLAN IDs to system profile.
				2. Add GROUPs to eliminate warning messages"
			REVISION "201203201600Z"		-- March 20, 2012 at 16:00 GMT
			DESCRIPTION 
				"Add utc time trap binding"
			REVISION "201112201756Z"		-- December 20, 2011 at 17:56 GMT
			DESCRIPTION 
				"Add backup/restore options to zhoneSysSwAdmin"
			REVISION "201112081200Z"		-- December 08, 2011 at 12:00 GMT
			DESCRIPTION 
				"Add radiusThenCraft value to zhoneSystemUserAuthMethod OID."
			REVISION "201102171334Z"		-- February 17, 2011 at 13:34 GMT
			DESCRIPTION 
				"Added zhoneSnmpErrorStatusTable.
				Added cardIsStandbyWithActiveLinks(5)
				to zhoneSysCardRedundancyOperStatus."
			REVISION "201102080655Z"		-- February 08, 2011 at 06:55 GMT
			DESCRIPTION 
				"Double length of zhoneSysSwRemoteFilePath to allow for CPE 
				Config Manager combined base-path, specific-path and 
				specific-config-filename for downloading."
			REVISION "201005181000Z"		-- May 18, 2010 at 10:00 GMT
			DESCRIPTION 
				"Added cpeMgr stub under zhone.zhoneGeneric.zhoneSystem.  
				This will be used by CPE Configuration Manager and other 
				cpeMgr releated objects."
			REVISION "200904231448Z"		-- April 23, 2009 at 14:48 GMT
			DESCRIPTION 
				"zhoneSystemWebInterface is changed
				from read-only to read-write"
			REVISION "200904200928Z"		-- April 20, 2009 at 09:28 GMT
			DESCRIPTION 
				"Add zhoneSystemConfigurationOptions"
			REVISION "200904141707Z"		-- April 14, 2009 at 17:07 GMT
			DESCRIPTION 
				"Deprecate ZhoneZmsBlockCli trap."
			REVISION "200810232257Z"		-- October 23, 2008 at 22:57 GMT
			DESCRIPTION 
				"Changed MTAC names to TAC."
			REVISION "200810071238Z"		-- October 07, 2008 at 12:38 GMT
			DESCRIPTION 
				"Add configScriptActivate and configDatabaseActivate
				values to the zhoneSysSwAdmin object."
			REVISION "200809171320Z"		-- September 17, 2008 at 13:20 GMT
			DESCRIPTION 
				"Add webInterface field to system prof"
			REVISION "200807102015Z"		-- July 10, 2008 at 20:15 GMT
			DESCRIPTION 
				"Expand vpiVciRamge enum to include vpi-15-vci127"
			REVISION "200806081115Z"		-- June 08, 2008 at 11:15 GMT
			DESCRIPTION 
				"V01.24.00 - add zhoneSystemSecureFTP."
			REVISION "200712141520Z"		-- December 14, 2007 at 15:20 GMT
			DESCRIPTION 
				"V01.23.00 - Add redundancyUnsafe trap"
			REVISION "200711021110Z"		-- November 02, 2007 at 11:10 GMT
			DESCRIPTION 
				"V01.22.00 Add vbnrt5rt95cbr."
			REVISION "200703261624Z"		-- March 26, 2007 at 16:24 GMT
			DESCRIPTION 
				"V01.21.00 - add zhoneSysCardInitString"
			REVISION "200611291511Z"		-- November 29, 2006 at 15:11 GMT
			DESCRIPTION 
				"V01.20.00 - added zhoneSystemUserAuthMethod and zhoneSystemRadiusAuthIndex."
			REVISION "200610171457Z"		-- October 17, 2006 at 14:57 GMT
			DESCRIPTION 
				"Add zhoneSysCardLineVoltage and zhoneSysCardVpiVciRange"
			REVISION "200606161314Z"		-- June 16, 2006 at 13:14 GMT
			DESCRIPTION 
				"V01.18.00 - add zhoneAlarmLevelsEnabled."
			REVISION "200605220952Z"		-- May 22, 2006 at 09:52 GMT
			DESCRIPTION 
				"V01.17.00 - Change Feature Flag for File System
				and Software Upgrade keywords."
			REVISION "200605171634Z"		-- May 17, 2006 at 16:34 GMT
			DESCRIPTION 
				"V01.16.00 - missing the letter t in zhoneSoftwareUpgrade."
			REVISION "200603151236Z"		-- March 15, 2006 at 12:36 GMT
			DESCRIPTION 
				"V01.15.00 - add zhoneFileTable and
				zhoneSoftwareUpgrade objects."
			REVISION "200505120913Z"		-- May 12, 2005 at 09:13 GMT
			DESCRIPTION 
				"V01.14.00 - Added comment regarding support of card-line-type change for packet voice cards.
				"
			REVISION "200501181443Z"		-- January 18, 2005 at 14:43 GMT
			DESCRIPTION 
				"V01.14.00 -  Add zhoneTrapConfigSyncReset
				trap and supporting object bindings."
			REVISION "200407021230Z"		-- July 02, 2004 at 12:30 GMT
			DESCRIPTION 
				"V01.13.00
				Modified Video_System_Profile to carry more
				EPG information, needed by zrg family."
			REVISION "200402181500Z"		-- February 18, 2004 at 15:00 GMT
			DESCRIPTION 
				"V01.12.00
				Added zhoneTrapAlarmAction, zhoneTrapAlarmId
				and zhoneTrapAlarmSeverity."
			REVISION "200312041418Z"		-- December 04, 2003 at 14:18 GMT
			DESCRIPTION 
				"Addition of the zhoneCallDetailRecConfiguration object."
			REVISION "200311081430Z"		-- November 08, 2003 at 14:30 GMT
			DESCRIPTION 
				"V01.11.25 - Added zhoneZmsBlockCliChange trap."
			REVISION "200304231626Z"		-- April 23, 2003 at 16:26 GMT
			DESCRIPTION 
				"v01.11.24 - Changed feature flag access to video system profile from MALC_VIDEO to ATM_IP_MULTICAST."
			REVISION "200303191035Z"		-- March 19, 2003 at 10:35 GMT
			DESCRIPTION 
				"V01.11.23 - Added RowStatus to VideoSystemConfigurationEntry"
			REVISION "200302201100Z"		-- February 20, 2003 at 11:00 GMT
			DESCRIPTION 
				"V01.11.22 - Added video system profile."
			REVISION "200211191115Z"		-- November 19, 2002 at 11:15 GMT
			DESCRIPTION 
				"V01.11.21 - add bulk statistics objects"
			REVISION "200210291533Z"		-- October 29, 2002 at 15:33 GMT
			DESCRIPTION 
				"V01.11.20 - change zhoneSysRebootCardType to use ZhoneCardType from Zhone-TC.mib"
			REVISION "200210241836Z"		-- October 24, 2002 at 18:36 GMT
			DESCRIPTION 
				"V01.11.19 - use zhone-tc for cardtype"
			REVISION "200210181603Z"		-- October 18, 2002 at 16:03 GMT
			DESCRIPTION 
				"V01.11.18 - Changed zhoneSysCardLineType
				to use TC ZhoneCardLineType."
			REVISION "200209231536Z"		-- September 23, 2002 at 15:36 GMT
			DESCRIPTION 
				"V01.11.17 Added zhoneSntpConfiguration"
			REVISION "200206111704Z"		-- June 11, 2002 at 17:04 GMT
			DESCRIPTION 
				"V01.11.16 - Added malcT1E1Tdm, malcAdslAc6, malcAdslAc6Post, malcAdslAc6Splt, malcAdslAc6AnxB and malcAdslAc6AnxBSplt. Changed malcAdslAc5B to malcAdslAc5AnxB."
			REVISION "200206111401Z"		-- June 11, 2002 at 14:01 GMT
			DESCRIPTION 
				"V01.11.15 - Add support for image flash, file upload/download and dump/restore"
			REVISION "200206030857Z"		-- June 03, 2002 at 08:57 GMT
			DESCRIPTION 
				"V01.11.14 - Added zhoneSystemVoiceBandwidthCheck to zhoneSystemConfiguration"
			REVISION "200205241240Z"		-- May 24, 2002 at 12:40 GMT
			DESCRIPTION 
				"V01.11.13 - Added malcAdslAc5B card type"
			REVISION "200205091742Z"		-- May 09, 2002 at 17:42 GMT
			DESCRIPTION 
				"V01.11.12 - Added zhoneSystemRevertiveClockSource to zhoneSystemConfiguration"
			REVISION "200203221512Z"		-- March 22, 2002 at 15:12 GMT
			DESCRIPTION 
				"V01.11.11 - Added malcOc3 card type"
			REVISION "200201101609Z"		-- January 10, 2002 at 16:09 GMT
			DESCRIPTION 
				"V01.11.10 - Added Console Logging variable to make the consol logging feature persistent"
			REVISION "200201101604Z"		-- January 10, 2002 at 16:04 GMT
			DESCRIPTION 
				"V01.11.09 - Clarify description of zhoneCardRedundnacyTable that the row cannot be deleted, but is autmatically deleted with a corresponding delete of zhoneSysCardSoftwareConfigTable"
			REVISION "200111261559Z"		-- November 26, 2001 at 15:59 GMT
			DESCRIPTION 
				"V01.11.08 - Add ATM qos configuration values for malc uplink."
			REVISION "200111161819Z"		-- November 16, 2001 at 18:19 GMT
			DESCRIPTION 
				"V01.11.07 - Added malcAdslAc5(5010) card type."
			REVISION "200111011714Z"		-- November 01, 2001 at 17:14 GMT
			DESCRIPTION 
				"V01.11.06 - Updated description for cardAtmConfiguration"
			REVISION "200110291219Z"		-- October 29, 2001 at 12:19 GMT
			DESCRIPTION 
				"V01.11.05 - Updated description for cardAtmConfiguration"
			REVISION "200110252009Z"		-- October 25, 2001 at 20:09 GMT
			DESCRIPTION 
				"V01.11.04 - Change system clock tx clock mode to read-only and add description."
			REVISION "200110221710Z"		-- October 22, 2001 at 17:10 GMT
			DESCRIPTION 
				"V01.11.03 - Add tdmT1e1 card type"
			REVISION "200110191137Z"		-- October 19, 2001 at 11:37 GMT
			DESCRIPTION 
				"V01.11.02 - Add system clock status fields."
			REVISION "200110181030Z"		-- October 18, 2001 at 10:30 GMT
			DESCRIPTION 
				"V01.11.01 - Added e3 and t3 to card-line-type."
			REVISION "200110171351Z"		-- October 17, 2001 at 13:51 GMT
			DESCRIPTION 
				"V01.11.00 - Added system clock PERSISTENT profile table."
			REVISION "200110051208Z"		-- October 05, 2001 at 12:08 GMT
			DESCRIPTION 
				"V01.10.07 - Added malcDs3 card type."
			REVISION "200110021119Z"		-- October 02, 2001 at 11:19 GMT
			DESCRIPTION 
				"V01.10.06 - Added cardAtmConfiguration"
			REVISION "200109251450Z"		-- September 25, 2001 at 14:50 GMT
			DESCRIPTION 
				"V01.10.05 - Add two new line types for card."
			REVISION "200108301745Z"		-- August 30, 2001 at 17:45 GMT
			DESCRIPTION 
				"V01.10.04 - add e1-ima and t1-ima new line types."
			REVISION "200108221443Z"		-- August 22, 2001 at 14:43 GMT
			DESCRIPTION 
				"V01.10.03 - Added zhoneSysCardLineType."
			REVISION "200108101337Z"		-- August 10, 2001 at 13:37 GMT
			DESCRIPTION 
				"V01.10.02 - Added Atm Trnk Card Types."
			REVISION "200108011620Z"		-- August 01, 2001 at 16:20 GMT
			DESCRIPTION 
				"V01.10.01 -Corrected Mark up order for Card Redundancy.."
			REVISION "200108011620Z"		-- August 01, 2001 at 16:20 GMT
			DESCRIPTION 
				"V01.10.00 - Replace enum list with ZhoneCountryCode
				textual convention for zhoneSystemConfigurationCountryRegion."
			REVISION "200107301532Z"		-- July 30, 2001 at 15:32 GMT
			DESCRIPTION 
				"V01.09.00 - Add zhoneTrapPortType and zhoneTrapPortTypeExtension to the zhoneTrapsTable."
			REVISION "200106061753Z"		-- June 06, 2001 at 17:53 GMT
			DESCRIPTION 
				"V01.08.00 - add zhoneTrapsGatewayTrapServerAddress"
			REVISION "200105251531Z"		-- May 25, 2001 at 15:31 GMT
			DESCRIPTION 
				"V01.07.00 -- Card Redundancy"
			REVISION "200105170959Z"		-- May 17, 2001 at 09:59 GMT
			DESCRIPTION 
				"V01.06.00 - add primaryClockSource"
			REVISION "200104271116Z"		-- April 27, 2001 at 11:16 GMT
			DESCRIPTION 
				"V01.05.07 - add atmTrnkCr under zhoneSwCardType,
				    zhoneSysCardSwType, zhoneSysRebootCardType."
			REVISION "200102181555Z"		-- February 18, 2001 at 15:55 GMT
			DESCRIPTION 
				"V01.05.06 - add zhoneSystemConfigurationCountryRegion under
				zhoneSystemConfiguration."
			REVISION "200102161312Z"		-- February 16, 2001 at 13:12 GMT
			DESCRIPTION 
				"V01.05.05 -- add new trap for zhone SNMP sub agent timeout"
			REVISION "200102121906Z"		-- February 12, 2001 at 19:06 GMT
			DESCRIPTION 
				"V01.05.04 - change zhoneAdminCommunityName index to IMPLIED"
			REVISION "200101221414Z"		-- January 22, 2001 at 14:14 GMT
			DESCRIPTION 
				"V01.05.03 - Add MALC card types."
			REVISION "200101161344Z"		-- January 16, 2001 at 13:44 GMT
			DESCRIPTION 
				"V01.05.02 - Fix some comments"
			REVISION "200012011216Z"		-- December 01, 2000 at 12:16 GMT
			DESCRIPTION 
				"V01.05.01 - Change markup to reflect latest MIB layout."
			REVISION "200011111227Z"		-- November 11, 2000 at 12:27 GMT
			DESCRIPTION 
				"V01.05.00 - New fields:
				            date and system time
				            user definition table
				            sw download entries.
				            Also changed trap seq. number
				            to be read-only from
				            read-create."
			REVISION "200011071209Z"		-- November 07, 2000 at 12:09 GMT
			DESCRIPTION 
				"V01.04.00 - Added catWtn for Wireless."
			REVISION "200010171936Z"		-- October 17, 2000 at 19:36 GMT
			DESCRIPTION 
				"V01.03.00 - Added trapResetSequenceNumber to zhoneTrapFlags."
			REVISION "200009151707Z"		-- September 15, 2000 at 17:07 GMT
			DESCRIPTION 
				"V01.02.00 - Added the Zhone CPE connection down/up Traps"
			REVISION "200009121802Z"		-- September 12, 2000 at 18:02 GMT
			DESCRIPTION 
				"V01.01.00 - Added the config synch user name and password"
			REVISION "200009121801Z"		-- September 12, 2000 at 18:01 GMT
			DESCRIPTION 
				"V01.00.00 - Initial Release"
			::= { zhoneModules 2 }

		
	
--
-- Textual conventions
--
	
		ZhoneRedundancyWeight ::= TEXTUAL-CONVENTION
			STATUS current
			DESCRIPTION 
				"Preference values for redundancy
				"
			SYNTAX INTEGER
				{
				neverActive(1),
				noPreference(2),
				slightPreference(3),
				mediumPreference(4),
				highPreference(5)
				}

		ZhoneLocalTimeZone ::= TEXTUAL-CONVENTION
			STATUS current
			DESCRIPTION 
				"World time zones:
				  internationalDateLineWest (GMT-12:00 hrs) 
				  nome (GMT-11:00)
				  hawaii(GMT-10:00)
				  yukon(GMT-9:00)
				  pacific(GMT-8:00)
				  mountain(GMT-7:00)
				  central(GMT-6:00)
				  eastern(GMT-5:00)
				  atlantic(GMT-4:00)
				  newfoundland(GMT-3:30)
				  brasilia(GMT-3:00)
				  azores(GMT-2:00),
				  westAfrica(GMT-1:00)
				  gmt(GMT/UTC)
				  centralEuropean(GMT+1:00)
				  easternEurope(GMT+2:00)
				  baghdad(GMT+3:00)
				  tehran(GMT+3:30)
				  uae(GMT+4:00)
				  afghanistan(GMT+4:30)
				  islamabad(GMT+5:00)
				  india(GMT+5:30)
				  kathmandu(GMT+5:45)
				  dhaka(GMT+6:00)
				  rangoon(GMT+6:30)
				  bangkok(GMT+7:00)
				  chinaCoast(GMT+8:00)
				  japan(GMT+9:00)
				  australia(GMT+9:30)
				  guam(GMT+10:00)
				  magadan(GMT+11:00)
				  newZealand(GMT+12:00)
				  rawakiIslands(GMT+13:00)
				  lineIslands(GMT+14:00)"
			SYNTAX INTEGER
				{
				internationalDateLineWest(1),
				nome(2),
				hawaii(3),
				yukon(4),
				pacific(5),
				mountain(6),
				central(7),
				eastern(8),
				atlantic(9),
				newfoundland(10),
				brasilia(11),
				azores(12),
				westAfrica(13),
				gmt(14),
				centralEuropean(15),
				easternEurope(16),
				baghdad(17),
				tehran(18),
				uae(19),
				afghanistan(20),
				islamabad(21),
				india(22),
				kathmandu(23),
				dhaka(24),
				rangoon(25),
				bangkok(26),
				chinaCoast(27),
				japan(28),
				australia(29),
				guam(30),
				magadan(31),
				newZealand(32),
				rawakiIslands(33),
				lineIslands(34)
				}

	
--
-- Node definitions
--
	
		-- 1.3.6.1.4.1.5504.3.1.1
		zhoneZms OBJECT-IDENTITY
			STATUS current
			DESCRIPTION 
				"The following variables are associated with the state of
				existence and connectivity with the Zhone Management System
				(ZMS)."
			::= { zhoneSystem 1 }

		
-- 
		-- 1.3.6.1.4.1.5504.3.1.1.1
		zhoneZmsExists OBJECT-TYPE
			SYNTAX TruthValue
			MAX-ACCESS read-write
			STATUS current
			DESCRIPTION
				"Identifies whether or not this device is being managed by the Zhone
				Management System. This is only settable by the management system and
				NOT by the CLI as it indicates existence of the manager. Different
				operations are performed based on this setting (i.e. no configuration
				synchronization processing is performed if there is no Zhone Management
				System).
				
				Default value is 'false'."
			::= { zhoneZms 1 }

		
-- 
		-- 1.3.6.1.4.1.5504.3.1.1.2
		zhoneZmsConnectionStatus OBJECT-TYPE
			SYNTAX INTEGER
				{
				active(1),
				inactive(2)
				}
			MAX-ACCESS read-write
			STATUS current
			DESCRIPTION
				"The status of the connection between this device and the Zhone 
				Management System, if one exists. This value can either be set 
				directly by ZMS or by the device internally when a SNMP request
				is processed from the ZMS. For devices that are being proxied by 
				another entity, since they are not being polled by ZMS, will 
				set this state according to the communication channel state
				between this device and the connected entity.
				
				Default value is 'inactive'."
			::= { zhoneZms 2 }

		
-- 
		-- 1.3.6.1.4.1.5504.3.1.1.3
		zhoneZmsIpAddress OBJECT-TYPE
			SYNTAX IpAddress
			MAX-ACCESS read-write
			STATUS current
			DESCRIPTION
				"This is the ZMS IP address for which configuration synchronization 
				messages and any other special handling is performed. This can
				be set either via CLI or ZMS."
			::= { zhoneZms 3 }

		
		-- 1.3.6.1.4.1.5504.3.1.1.4
		zhoneZmsBlockCli OBJECT-TYPE
			SYNTAX TruthValue
			MAX-ACCESS read-write
			STATUS current
			DESCRIPTION
				"If TRUE, CLI only allows 'show' commands and cannot
				modify/add any data records. This is used by ZMS
				to prevent race conditions and to allow only single
				access to system resources especially during 
				problem analysis times.
				
				Default value is 'false'."
			::= { zhoneZms 4 }

		
-- The Zhone Trap information is information used to provide a 
-- reliable trap mechanism between the device and the Zhone
-- Management System. There are two trap flows utilized between the 
-- device and any fault management system. The first is used for most 
-- traps generated by the device where an incremental sequence number
-- is used. It is then up to the FMS to indicated any traps that
-- it missed asking for retransmission starting at a particular
-- sequence number. The other type is an Acknowledged trap where
-- only one trap will be outstanding at one time. This will
-- be a separate sequence number than the unacknowledged flow.
-- 
		-- 1.3.6.1.4.1.5504.3.1.2
		zhoneTraps OBJECT-IDENTITY
			STATUS current
			DESCRIPTION 
				"This is the trap information related to
				handling device to ZMS traps. "
			::= { zhoneSystem 2 }

		
-- The Table defining the list of trap destinations and associated trap 
-- message exchange handling.
-- 
		-- 1.3.6.1.4.1.5504.3.1.2.1
		zhoneTrapsTable OBJECT-TYPE
			SYNTAX SEQUENCE OF ZhoneTrapsEntry
			MAX-ACCESS not-accessible
			STATUS current
			DESCRIPTION
				"Zhone Traps Table
				"
			::= { zhoneTraps 1 }

		
		-- 1.3.6.1.4.1.5504.3.1.2.1.1
		zhoneTrapsEntry OBJECT-TYPE
			SYNTAX ZhoneTrapsEntry
			MAX-ACCESS not-accessible
			STATUS current
			DESCRIPTION
				"An entry per trap destination."
			INDEX { zhoneTrapsDestination }
			::= { zhoneTrapsTable 1 }

		
		ZhoneTrapsEntry ::=
			SEQUENCE { 
				zhoneTrapsDestination
					IpAddress,
				zhoneTrapsCommunityName
					ZhoneAdminString,
				zhoneTrapsSequenceNumber
					Unsigned32,
				zhoneTrapsResendSequenceNumber
					Integer32,
				zhoneTrapsAckedSequenceNumber
					Unsigned32,
				zhoneTrapsSeverity
					INTEGER,
				zhoneTrapsAllowedCategories
					BITS,
				zhoneTrapsAdminStatus
					INTEGER,
				zhoneTrapsRowStatus
					ZhoneRowStatus,
				zhoneTrapsGatewayTrapServerAddress
					ZhoneAdminString
			 }

-- 
		-- 1.3.6.1.4.1.5504.3.1.2.1.1.1
		zhoneTrapsDestination OBJECT-TYPE
			SYNTAX IpAddress
			MAX-ACCESS not-accessible
			STATUS current
			DESCRIPTION
				"The location to be send traps."
			::= { zhoneTrapsEntry 1 }

		
-- 
		-- 1.3.6.1.4.1.5504.3.1.2.1.1.2
		zhoneTrapsCommunityName OBJECT-TYPE
			SYNTAX ZhoneAdminString
			MAX-ACCESS read-create
			STATUS current
			DESCRIPTION
				"Community name to be sent in all traps sent to this destination. This 
				field is defaulted to NULL so a null string will be sent to the
				destination."
			::= { zhoneTrapsEntry 2 }

		
		-- 1.3.6.1.4.1.5504.3.1.2.1.1.3
		zhoneTrapsSequenceNumber OBJECT-TYPE
			SYNTAX Unsigned32
			MAX-ACCESS read-only
			STATUS current
			DESCRIPTION
				"Next sequence number to be sent as part of a trap
				generated by the device. The sequence number has two uses. In
				one case,it is the sequence number of the non-acknowledge traps
				and has a range of 0-2147483647. While the acknowledge sequence
				number range is 2147483648-4294967295. This field wraps to 
				the appropriate '0' value (0 or 2147483648) for it's range."
			::= { zhoneTrapsEntry 3 }

		
-- 
		-- 1.3.6.1.4.1.5504.3.1.2.1.1.4
		zhoneTrapsResendSequenceNumber OBJECT-TYPE
			SYNTAX Integer32
			MAX-ACCESS read-create
			STATUS current
			DESCRIPTION
				"This is set by the ZMS in order
				to have the device resend saved traps because one
				or more were lost in transmission. The device will 
				resend traps starting at this sequence number. Note
				that due to resource constraints not all traps may
				be available to be resent. The first trap resent will
				indicate that this is a resent and whether or not
				any traps were deleted/lost. 
				
				This is used only on the unacknowledge trap flow. This is
				the only indication of whether or not any traps have
				been acknowledged.
				
				The value returned is always 0 as setting this field
				only causes restarting of the traps with this number."
			DEFVAL { 0 }
			::= { zhoneTrapsEntry 4 }

		
-- 
		-- 1.3.6.1.4.1.5504.3.1.2.1.1.5
		zhoneTrapsAckedSequenceNumber OBJECT-TYPE
			SYNTAX Unsigned32
			MAX-ACCESS read-create
			STATUS current
			DESCRIPTION
				"Acknowledged trap sequence number. This field is set 
				by the ZMS in order to acknowledge a trap sent
				by the device with the Request Acknowledge flag
				set to YES. There will be only one trap will be 
				outstanding on this flow (acknowledged flow)at one time so
				this should be the last sequence number sent. If not, it
				is ignored."
			::= { zhoneTrapsEntry 5 }

		
-- 
		-- 1.3.6.1.4.1.5504.3.1.2.1.1.6
		zhoneTrapsSeverity OBJECT-TYPE
			SYNTAX INTEGER
				{
				critical(1),
				severe(2),
				moderate(3),
				low(4)
				}
			MAX-ACCESS read-create
			STATUS current
			DESCRIPTION
				"The Trap severity level which at this level or higher, traps will
				be sent to this destination."
			DEFVAL { low }
			::= { zhoneTrapsEntry 6 }

		
-- 
		-- 1.3.6.1.4.1.5504.3.1.2.1.1.7
		zhoneTrapsAllowedCategories OBJECT-TYPE
			SYNTAX BITS
				{
				catAdmin(0),
				catLine(1),
				catVoice(2),
				catIP(3),
				catRip(4),
				catRadio(5)
				}
			MAX-ACCESS read-create
			STATUS current
			DESCRIPTION
				"Array of allowed categories to be sent to this particular
				trap destination. This field is not currently implemented
				and is reserved for future use."
			::= { zhoneTrapsEntry 7 }

		
-- 
		-- 1.3.6.1.4.1.5504.3.1.2.1.1.8
		zhoneTrapsAdminStatus OBJECT-TYPE
			SYNTAX INTEGER
				{
				enabled(1),
				disabled(2)
				}
			MAX-ACCESS read-create
			STATUS current
			DESCRIPTION
				"Whether traps should be enabled or disabled for this particular
				IP address."
			DEFVAL { enabled }
			::= { zhoneTrapsEntry 8 }

		
		-- 1.3.6.1.4.1.5504.3.1.2.1.1.9
		zhoneTrapsRowStatus OBJECT-TYPE
			SYNTAX ZhoneRowStatus
			MAX-ACCESS read-create
			STATUS current
			DESCRIPTION
				"Row status in order to create the entry for this 
				destination. There are no required fields on a create
				besides the obvious index of the ip address of the 
				destination."
			::= { zhoneTrapsEntry 9 }

		
-- 
		-- 1.3.6.1.4.1.5504.3.1.2.1.1.10
		zhoneTrapsGatewayTrapServerAddress OBJECT-TYPE
			SYNTAX ZhoneAdminString
			MAX-ACCESS read-create
			STATUS current
			DESCRIPTION
				"The Gateway Trap Server Address is used to locate the Gateway.
				Trap Server. This field is defaulted 0,0,0."
			DEFVAL { "none" }
			::= { zhoneTrapsEntry 10 }

		
-- The following define common trap OIDs to be used in all traps sent
-- to the fault manager service.
--  
		-- 1.3.6.1.4.1.5504.3.1.2.2
		zhoneTrapVersion OBJECT-TYPE
			SYNTAX INTEGER { version1(1) }
			MAX-ACCESS accessible-for-notify
			STATUS current
			DESCRIPTION
				"Version number of the format of the trap. Any changes to
				the common area of a trap require a bump of this number."
			::= { zhoneTraps 2 }

		
		-- 1.3.6.1.4.1.5504.3.1.2.3
		zhoneTrapFlags OBJECT-TYPE
			SYNTAX BITS
				{
				trapAcknowledge(0),
				trapOutOfSequence(1),
				trapResetSequenceNumber(2)
				}
			MAX-ACCESS accessible-for-notify
			STATUS current
			DESCRIPTION
				"This variable is sent with all traps and contains flags related
				to this trap. 
				
				trapAcknolwedge: If this bit is set, it indicates to the ZMS 
				                 that the trap must be acknowledged.
				                 Acknowledgement is accomplished by the ZMS 
				                 sending a SET request to the variable 
				                 zhoneTrapsAckedSequenceNumber in the 
				                 zhoneTrapsTable. See the trap sequence number
				                 field description (value is 2147483648 and 
				                 higher.
				trapOutOfSequence: If set, it indicates that this trap is being
				                 sent out of sequence from what the trap
				                 receiver is expecting. The specific occurence is
				                 when the trap receiver detects lost traps and
				                 requests resending of traps starting from a
				                 specific sequence number (see 
				                 zhoneTrapsResendSequenceNumber) but the system
				                 does not have all these traps. Example:
				- traps 400-600 sent to the trap receiver.
				                 - trap 500 is lost
				                 - trap receiver requests resend of traps 500 and
				                   up.
				                 - system only has 550-600 saved in memory.
				                 - trap 550 resent with trapOutOfSequence set.
				                 - trap 551 and above resent with trapOutOfSequence
				                   reset.
				trapResetSequenceNumber: If set, the sender of this trap has
				reset the trap sequence number for this trap
				destination. It is indicating to the ZMS to
				also reset its sequence numbers."
			::= { zhoneTraps 3 }

		
		-- 1.3.6.1.4.1.5504.3.1.2.4
		zhoneTrapShelf OBJECT-TYPE
			SYNTAX ZhoneShelfValue
			MAX-ACCESS accessible-for-notify
			STATUS current
			DESCRIPTION
				"This variable is sent with all traps. This contains the
				value of the shelf that originated the trap."
			::= { zhoneTraps 4 }

		
		-- 1.3.6.1.4.1.5504.3.1.2.5
		zhoneTrapSlot OBJECT-TYPE
			SYNTAX ZhoneSlotValue
			MAX-ACCESS accessible-for-notify
			STATUS current
			DESCRIPTION
				"This variable is sent with all traps. This contains the
				value of the slot that originated the trap."
			::= { zhoneTraps 5 }

		
		-- 1.3.6.1.4.1.5504.3.1.2.6
		zhoneTrapPort OBJECT-TYPE
			SYNTAX Integer32 (0..2147483647)
			MAX-ACCESS accessible-for-notify
			STATUS current
			DESCRIPTION
				"This variable is sent with all traps. This contains the
				value of the port that originated the trap. If this is a
				system or card level trap (no port is associated with the trap),
				this value is 0."
			::= { zhoneTraps 6 }

		
		-- 1.3.6.1.4.1.5504.3.1.2.7
		zhoneTrapSubPort OBJECT-TYPE
			SYNTAX Integer32 (0..2147483647)
			MAX-ACCESS accessible-for-notify
			STATUS current
			DESCRIPTION
				"This variable is sent with all traps. This contains the
				value of the subport that originated the trap. If this is a
				system or card level trap (no port is associated with the trap),
				this value is 0. It may also be 0 if not subports are associated
				with this physical port such as in the case of an ethernet port."
			::= { zhoneTraps 7 }

		
		-- 1.3.6.1.4.1.5504.3.1.2.8
		zhoneTrapProviderId OBJECT-TYPE
			SYNTAX Integer32
			MAX-ACCESS accessible-for-notify
			STATUS current
			DESCRIPTION
				"Unique  service provider ID.  This value is used 
				throughout the management system to link objects with 
				customers or service providers."
			::= { zhoneTraps 8 }

		
		-- 1.3.6.1.4.1.5504.3.1.2.9
		zhoneTrapText OBJECT-TYPE
			SYNTAX SnmpAdminString (SIZE (0..80))
			MAX-ACCESS accessible-for-notify
			STATUS current
			DESCRIPTION
				"Any text associated with this trap. NULL is allowed"
			::= { zhoneTraps 9 }

		
		-- 1.3.6.1.4.1.5504.3.1.2.10
		zhoneTrapPortType OBJECT-TYPE
			SYNTAX IANAifType
			MAX-ACCESS accessible-for-notify
			STATUS current
			DESCRIPTION
				"This is the If Type. It is used to uniquely identify a port."
			::= { zhoneTraps 10 }

		
		-- 1.3.6.1.4.1.5504.3.1.2.11
		zhoneTrapPortTypeExtension OBJECT-TYPE
			SYNTAX ZhoneIfType
			MAX-ACCESS accessible-for-notify
			STATUS current
			DESCRIPTION
				"This is the If Type Extension. It is used to uniquely identify a port."
			::= { zhoneTraps 11 }

		
		-- 1.3.6.1.4.1.5504.3.1.2.12
		zhoneTrapAlarmAction OBJECT-TYPE
			SYNTAX INTEGER
				{
				set(1),
				clear(2),
				informational(3)
				}
			MAX-ACCESS accessible-for-notify
			STATUS current
			DESCRIPTION
				"This is the alarm action type for products supporting the
				alarm manager functionality."
			::= { zhoneTraps 12 }

		
		-- 1.3.6.1.4.1.5504.3.1.2.13
		zhoneTrapAlarmId OBJECT-TYPE
			SYNTAX ZhoneAlarmTypeId
			MAX-ACCESS accessible-for-notify
			STATUS current
			DESCRIPTION
				"For products supporting the alarm manager functionality,
				this is the alarm id a particular trap is setting or
				clearing."
			::= { zhoneTraps 13 }

		
		-- 1.3.6.1.4.1.5504.3.1.2.14
		zhoneTrapAlarmSeverity OBJECT-TYPE
			SYNTAX ZhoneAlarmSeverity
			MAX-ACCESS accessible-for-notify
			STATUS current
			DESCRIPTION
				"For products supporting the alarm manager functionality,
				this is the alarm severity a particular trap is setting
				or clearing."
			::= { zhoneTraps 14 }

		
		-- 1.3.6.1.4.1.5504.3.1.2.15
		zhoneTrapConfigSyncResetInterval OBJECT-TYPE
			SYNTAX Unsigned32
			MAX-ACCESS accessible-for-notify
			STATUS current
			DESCRIPTION
				"The ConfigSync reset check is run in 6 minute intervals.
				This object represents the interval number and starts
				with interval number 1 at system bootup and will reset
				to 1 whenever the sytem reboots."
			::= { zhoneTraps 15 }

		
		-- 1.3.6.1.4.1.5504.3.1.2.16
		zhoneTrapConfigSyncResetCount OBJECT-TYPE
			SYNTAX Unsigned32
			MAX-ACCESS accessible-for-notify
			STATUS current
			DESCRIPTION
				"This count is the number of times the device has had to
				reset ConfigSync.  Resetting configsync on the device 
				consists of closing the FTP data and control sockets,
				setting the configsyncstatus to syncerror, cleaning up
				any pending configsync records, resetting the
				ConfigSync state machine to the initial state, and 
				throwing a ConfigSyncReset Trap."
			::= { zhoneTraps 16 }

		
		-- 1.3.6.1.4.1.5504.3.1.2.17
		zhoneTrapConfigSyncResetLastFtpTime OBJECT-TYPE
			SYNTAX Unsigned32
			MAX-ACCESS accessible-for-notify
			STATUS current
			DESCRIPTION
				"Last time device sent a ConfigSync Ftp command to ZMS.
				Measured using the Unix time() function.
				The internal representation of time is the number of
				seconds elapsed since 00:00 Universal time on
				January 1, 1970 in the Gregorian calendar
				(Julian day 2440587.5), with time stored as a 32 bit
				signed integer (long in the original C implementation)."
			::= { zhoneTraps 17 }

		
		-- 1.3.6.1.4.1.5504.3.1.2.18
		zhoneTrapConfigSyncResetCurrentTime OBJECT-TYPE
			SYNTAX Unsigned32
			MAX-ACCESS accessible-for-notify
			STATUS current
			DESCRIPTION
				"Current device time returned using Unix time() function.
				The internal representation of time is the number of
				seconds elapsed since 00:00 Universal time on
				January 1, 1970 in the Gregorian calendar
				(Julian day 2440587.5), with time stored as a 32 bit
				signed integer (long in the original C implementation)."
			::= { zhoneTraps 18 }

		
		-- 1.3.6.1.4.1.5504.3.1.2.19
		zhoneTrapUtcTime OBJECT-TYPE
			SYNTAX Unsigned32
			UNITS "seconds"
			MAX-ACCESS accessible-for-notify
			STATUS current
			DESCRIPTION
				"Number of seconds since Jan. 1, 1970 GMT, when this trap 
				was sent from the device."
			::= { zhoneTraps 19 }

		
		-- 1.3.6.1.4.1.5504.3.1.2.20
		zhoneTrapIfName OBJECT-TYPE
			SYNTAX SnmpAdminString
			MAX-ACCESS accessible-for-notify
			STATUS current
			DESCRIPTION
				"Describes the ifName of the entity"
			::= { zhoneTraps 20 }

		
		-- 1.3.6.1.4.1.5504.3.1.2.21
		zhoneTrapProfileId OBJECT-TYPE
			SYNTAX Unsigned32
			MAX-ACCESS accessible-for-notify
			STATUS obsolete
			DESCRIPTION
				"Describes the profile id of the entity"
			::= { zhoneTraps 21 }

		
		-- 1.3.6.1.4.1.5504.3.1.2.22
		zhoneTrapName OBJECT-TYPE
			SYNTAX SnmpAdminString
			MAX-ACCESS accessible-for-notify
			STATUS current
			DESCRIPTION
				"Describes the trap name"
			::= { zhoneTraps 22 }

		
		-- 1.3.6.1.4.1.5504.3.1.2.23
		zhoneTrapDescZms OBJECT-TYPE
			SYNTAX SnmpAdminString
			MAX-ACCESS accessible-for-notify
			STATUS current
			DESCRIPTION
				"Trap description"
			::= { zhoneTraps 23 }

		
		-- 1.3.6.1.4.1.5504.3.1.2.24
		zhoneTrapDescCli OBJECT-TYPE
			SYNTAX SnmpAdminString
			MAX-ACCESS accessible-for-notify
			STATUS current
			DESCRIPTION
				"Trap description"
			::= { zhoneTraps 24 }

		
		-- 1.3.6.1.4.1.5504.3.1.2.25
		zhoneTrapProfilesIndexes OBJECT-TYPE
			SYNTAX OCTET STRING (SIZE (0..127))
			MAX-ACCESS accessible-for-notify
			STATUS current
			DESCRIPTION
				"Describes the profile indexes. If the profile has multiple indexes,
				the index values would be delimited by a period.
				Ex. 1.1 for voip-server-entry 1/1"
			::= { zhoneTraps 25 }

		
-- The Configuration Synchronization related information is provided
-- to allow the device to synchronize non-SNMP changes with the
-- Zhone Management System.
-- 
		-- 1.3.6.1.4.1.5504.3.1.3
		zhoneConfigSync OBJECT-IDENTITY
			STATUS current
			DESCRIPTION 
				"Configuration Synchronization information."
			::= { zhoneSystem 3 }

		
-- 
		-- 1.3.6.1.4.1.5504.3.1.3.1
		zhoneConfigSyncExists OBJECT-TYPE
			SYNTAX TruthValue
			MAX-ACCESS read-only
			STATUS current
			DESCRIPTION
				"Indicates whether or not there exists records to be
				sent to the ZMS config synch manager for changes
				that have been made by CLI/HTTP to the data base."
			::= { zhoneConfigSync 1 }

		
-- 
		-- 1.3.6.1.4.1.5504.3.1.3.2
		zhoneConfigSyncOverflow OBJECT-TYPE
			SYNTAX TruthValue
			MAX-ACCESS read-only
			STATUS current
			DESCRIPTION
				"Indicates whether or not the device had to discard
				update data base records due to resource constraints.
				If TRUE, traps will be sent to the ZMS Config Synch
				Manager indicating a download of the entire data
				base is required."
			::= { zhoneConfigSync 2 }

		
-- 
		-- 1.3.6.1.4.1.5504.3.1.3.3
		zhoneConfigSyncPriority OBJECT-TYPE
			SYNTAX INTEGER
				{
				none(1),
				low(2),
				medium(3),
				high(4)
				}
			MAX-ACCESS read-only
			STATUS current
			DESCRIPTION
				"Indicates the highest priority configuration synchronization trap 
				outstanding. This flag is set to none at boot time and whenever a file
				of synchronization changes has been sent to ZMS. If a parameter change
				has been made to either the same or lower prioirty, the device does
				not have to send a change notification to ZMS. Higher priority
				fields must immediately cause traps to be sent to ZMS."
			::= { zhoneConfigSync 3 }

		
-- 
		-- 1.3.6.1.4.1.5504.3.1.3.4
		zhoneConfigSyncAction OBJECT-TYPE
			SYNTAX INTEGER
				{
				noAction(1),
				createList(2),
				createFullList(3)
				}
			MAX-ACCESS read-write
			STATUS current
			DESCRIPTION
				"Used by ZMS when it wants to create a list
				of config synch records. It must first write the
				filename expected and then set the action. The
				create_list action allows the device to determine
				whether the complete database (synchoverflow 
				occured) needs to be sent or only those records
				that have been modified. create_full_list 
				specifies that ZMS would like to receive the
				complete database."
			::= { zhoneConfigSync 4 }

		
-- 
		-- 1.3.6.1.4.1.5504.3.1.3.5
		zhoneConfigSyncFileName OBJECT-TYPE
			SYNTAX ZhoneFileName
			MAX-ACCESS read-write
			STATUS current
			DESCRIPTION
				"File Name to be used when creating the config
				synch records."
			::= { zhoneConfigSync 5 }

		
-- 
		-- 1.3.6.1.4.1.5504.3.1.3.6
		zhoneConfigSyncStatus OBJECT-TYPE
			SYNTAX INTEGER
				{
				syncComplete(1),
				syncPending(2),
				syncError(3),
				syncInitializing(4)
				}
			MAX-ACCESS read-only
			STATUS current
			DESCRIPTION
				"Used by Config Sync Acgent when processing a request
				to create a list of config synch records."
			::= { zhoneConfigSync 6 }

		
-- 
		-- 1.3.6.1.4.1.5504.3.1.3.7
		zhoneConfigSyncUserName OBJECT-TYPE
			SYNTAX ZhoneAdminString
			MAX-ACCESS read-write
			STATUS current
			DESCRIPTION
				"User Name to be used when sending the config
				synch records.
				
				When read, the last user name is returned. "
			::= { zhoneConfigSync 7 }

		
-- 
		-- 1.3.6.1.4.1.5504.3.1.3.8
		zhoneConfigSyncUserPassword OBJECT-TYPE
			SYNTAX ZhoneAdminString
			MAX-ACCESS read-write
			STATUS current
			DESCRIPTION
				"Password to be used when sending the config
				synch records. For use in FTP authentication.
				
				When read, always returns the NULL string"
			::= { zhoneConfigSync 8 }

		
-- The parameters listed below are associated with the administration
-- and security of this device from a CLI, SNMP, and HTTP reference.
-- 
		-- 1.3.6.1.4.1.5504.3.1.4
		zhoneAdmin OBJECT-IDENTITY
			STATUS current
			DESCRIPTION 
				"Zhone Authorization parameters."
			::= { zhoneSystem 4 }

		
-- The Community Table determines access to the device. Incoming
-- SNMP requests are first validated for their community name and
-- their access right determined. An optional additional level
-- of security is provided by allowing specification of only certain
-- IP addresses. This can be specified on a per community name
-- basis. This function is provided by the use of an access list
-- (i.e. IP address list) table whose entries can be used by 
-- multiple community name tables.
-- 
		-- 1.3.6.1.4.1.5504.3.1.4.1
		zhoneAdminCommunityTable OBJECT-TYPE
			SYNTAX SEQUENCE OF ZhoneAdminCommunityEntry
			MAX-ACCESS not-accessible
			STATUS current
			DESCRIPTION
				"Zhone proprietary Community Table."
			::= { zhoneAdmin 1 }

		
		-- 1.3.6.1.4.1.5504.3.1.4.1.1
		zhoneAdminCommunityEntry OBJECT-TYPE
			SYNTAX ZhoneAdminCommunityEntry
			MAX-ACCESS not-accessible
			STATUS current
			DESCRIPTION
				"A community name access to this system."
			INDEX { IMPLIED zhoneAdminCommunityName }
			::= { zhoneAdminCommunityTable 1 }

		
		ZhoneAdminCommunityEntry ::=
			SEQUENCE { 
				zhoneAdminCommunityName
					ZhoneAdminString,
				zhoneAdminCommunityAccess
					INTEGER,
				zhoneAdminCommunityAccessListIndex
					Integer32,
				zhoneAdminCommunityRowStatus
					ZhoneRowStatus
			 }

-- 
		-- 1.3.6.1.4.1.5504.3.1.4.1.1.1
		zhoneAdminCommunityName OBJECT-TYPE
			SYNTAX ZhoneAdminString (SIZE (1..32))
			MAX-ACCESS not-accessible
			STATUS current
			DESCRIPTION
				"The community name that has access to this system.
				
				Maximum length for community name string is 32 characters."
			::= { zhoneAdminCommunityEntry 1 }

		
-- 
		-- 1.3.6.1.4.1.5504.3.1.4.1.1.2
		zhoneAdminCommunityAccess OBJECT-TYPE
			SYNTAX INTEGER
				{
				noAccess(1),
				read(2),
				readAndWrite(3),
				admin(4)
				}
			MAX-ACCESS read-create
			STATUS current
			DESCRIPTION
				"The Access Rights for this particular community name. An access of read-write-admin
				allows access to those tables with a higher level of security such as the
				community table. Gets to this table will return E_NOSUCHINSTANCE unless
				the accessrights is read-write-admin. 
				
				noAccess - this community name does not have any access to this device.
				read - allows read access to all fields except admin access fields such
				            as this community table.
				readAndWrite - allow read and write access to all fields except admin access
				            fields such as this community table.
				admin - read and write access to all fields on this device."
			DEFVAL { read }
			::= { zhoneAdminCommunityEntry 2 }

		
-- 
		-- 1.3.6.1.4.1.5504.3.1.4.1.1.3
		zhoneAdminCommunityAccessListIndex OBJECT-TYPE
			SYNTAX Integer32 (0..50)
			MAX-ACCESS read-create
			STATUS current
			DESCRIPTION
				"The AccessList Table index indicating which IP addresses are
				allowed to use this community name. If the value is
				0, no address checking is performed and all SNMP requests are
				allowed with the access right as specified in this table."
			DEFVAL { '0'b }
			::= { zhoneAdminCommunityEntry 3 }

		
		-- 1.3.6.1.4.1.5504.3.1.4.1.1.4
		zhoneAdminCommunityRowStatus OBJECT-TYPE
			SYNTAX ZhoneRowStatus
			MAX-ACCESS read-create
			STATUS current
			DESCRIPTION
				"Row status in order to create the entry for this 
				destination."
			::= { zhoneAdminCommunityEntry 4 }

		
-- The access list table is a proprietary table defined by 
-- Zhone for the use of defining which IP addresses are
-- allowed to send SNMP requests. The community name
-- table references, if applicable, an access list index
-- which along with any defined IP address indexes define
-- the total list of acceptable IP addresses. See the community
-- name table for further description.
-- 
		-- 1.3.6.1.4.1.5504.3.1.4.2
		zhoneNextAdminAccessIndex OBJECT-TYPE
			SYNTAX Integer32 (1..50)
			MAX-ACCESS read-only
			STATUS current
			DESCRIPTION
				"The next available zhoneAdminAccessListIndex that can 
				be used by the manager when creating a access list
				entry.  A Get request to this field causes the current 
				number to be returned and the value to be incremented
				for the next requester.
				
				Once this value reaches 50, processing examines the
				entire list for possible free entries and provides the 
				lowest number available. If no entries are free, an
				error is returned.
				"
			::= { zhoneAdmin 2 }

		
		-- 1.3.6.1.4.1.5504.3.1.4.3
		zhoneAdminAccessListTable OBJECT-TYPE
			SYNTAX SEQUENCE OF ZhoneAdminAccessListEntry
			MAX-ACCESS not-accessible
			STATUS current
			DESCRIPTION
				"Access List Table Definition."
			::= { zhoneAdmin 3 }

		
		-- 1.3.6.1.4.1.5504.3.1.4.3.1
		zhoneAdminAccessListEntry OBJECT-TYPE
			SYNTAX ZhoneAdminAccessListEntry
			MAX-ACCESS not-accessible
			STATUS current
			DESCRIPTION
				"Zhone Access List Entry Definition."
			INDEX { zhoneAdminAccessListIndex, zhoneAdminAccessListIpAddress }
			::= { zhoneAdminAccessListTable 1 }

		
		ZhoneAdminAccessListEntry ::=
			SEQUENCE { 
				zhoneAdminAccessListIndex
					Integer32,
				zhoneAdminAccessListIpAddress
					IpAddress,
				zhoneAdminAccessRowStatus
					ZhoneRowStatus
			 }

-- 
		-- 1.3.6.1.4.1.5504.3.1.4.3.1.1
		zhoneAdminAccessListIndex OBJECT-TYPE
			SYNTAX Integer32 (1..50)
			MAX-ACCESS not-accessible
			STATUS current
			DESCRIPTION
				"The index into this table. There is a maximum support of
				a total of 50 access lists. 0 is not supported as it 
				indicates that no IP address validation should be 
				performed."
			::= { zhoneAdminAccessListEntry 1 }

		
-- 
		-- 1.3.6.1.4.1.5504.3.1.4.3.1.2
		zhoneAdminAccessListIpAddress OBJECT-TYPE
			SYNTAX IpAddress
			MAX-ACCESS not-accessible
			STATUS current
			DESCRIPTION
				"The IP address is used as a index into this table and 
				indicates whether SNMP requests originating from this
				address will be accepted."
			::= { zhoneAdminAccessListEntry 2 }

		
		-- 1.3.6.1.4.1.5504.3.1.4.3.1.3
		zhoneAdminAccessRowStatus OBJECT-TYPE
			SYNTAX ZhoneRowStatus
			MAX-ACCESS read-create
			STATUS current
			DESCRIPTION
				"Row status in order to create the entry for this 
				destination."
			::= { zhoneAdminAccessListEntry 3 }

		
-- The parameters listed below are associated with the user administration
-- on this device whether the access is via ZLI or telnet.
-- 
		-- 1.3.6.1.4.1.5504.3.1.4.4
		zhoneUser OBJECT-IDENTITY
			STATUS current
			DESCRIPTION 
				"Zhone User parameters."
			::= { zhoneAdmin 4 }

		
		-- 1.3.6.1.4.1.5504.3.1.4.4.1
		zhoneUserIdNext OBJECT-TYPE
			SYNTAX Integer32 (1..20)
			MAX-ACCESS read-only
			STATUS current
			DESCRIPTION
				"The next available zhoneUserId that can 
				be used by the manager when creating a user
				entry.  A Get request to this field causes the current 
				number to be returned and the value to be incremented
				to the next available ID for the next requester use.
				
				A maximum of 20 login accounts are allowed per system."
			::= { zhoneUser 1 }

		
		-- 1.3.6.1.4.1.5504.3.1.4.4.2
		zhoneUserTotalFailedLogins OBJECT-TYPE
			SYNTAX Counter32
			MAX-ACCESS read-only
			STATUS current
			DESCRIPTION
				"The number of failed logins performed by any user whether
				this be for invalid user id or valid user id but an invalid
				password."
			::= { zhoneUser 2 }

		
-- The following table defines the users allowed to login on the zli.
-- In addition to the user name and password, an access level for this user
-- and the prompt to be used is specified. Any access to this table requires
-- admin access level via either the community name or zli.
-- 
		-- 1.3.6.1.4.1.5504.3.1.4.4.3
		zhoneUserTable OBJECT-TYPE
			SYNTAX SEQUENCE OF ZhoneUserEntry
			MAX-ACCESS not-accessible
			STATUS current
			DESCRIPTION
				"ZLI user information."
			::= { zhoneUser 3 }

		
		-- 1.3.6.1.4.1.5504.3.1.4.4.3.1
		zhoneUserEntry OBJECT-TYPE
			SYNTAX ZhoneUserEntry
			MAX-ACCESS not-accessible
			STATUS current
			DESCRIPTION
				"A row exists for each user that can login on this system."
			INDEX { zhoneUserId }
			::= { zhoneUserTable 1 }

		
		ZhoneUserEntry ::=
			SEQUENCE { 
				zhoneUserId
					Integer32,
				zhoneUserName
					ZhoneAdminString,
				zhoneUserPassword
					ZhoneAdminString,
				zhoneUserPrompt
					ZhoneAdminString,
				zhoneUserAccessLevel
					BITS,
				zhoneUserAdmin
					INTEGER,
				zhoneUserLogins
					Counter32,
				zhoneUserFailedLogins
					Counter32,
				zhoneUserRowStatus
					ZhoneRowStatus
			 }

		-- 1.3.6.1.4.1.5504.3.1.4.4.3.1.1
		zhoneUserId OBJECT-TYPE
			SYNTAX Integer32 (1..20)
			MAX-ACCESS not-accessible
			STATUS current
			DESCRIPTION
				"The id used to identify this particular user. This value
				is only used for access to this table and is not externally
				shown."
			::= { zhoneUserEntry 1 }

		
		-- 1.3.6.1.4.1.5504.3.1.4.4.3.1.2
		zhoneUserName OBJECT-TYPE
			SYNTAX ZhoneAdminString
			MAX-ACCESS read-create
			STATUS current
			DESCRIPTION
				"The user name allowed to login to this system."
			::= { zhoneUserEntry 2 }

		
		-- 1.3.6.1.4.1.5504.3.1.4.4.3.1.3
		zhoneUserPassword OBJECT-TYPE
			SYNTAX ZhoneAdminString
			MAX-ACCESS read-create
			STATUS current
			DESCRIPTION
				"The password to be used for logging in to the system.
				
				This field is returned as an encrypted field."
			::= { zhoneUserEntry 3 }

		
		-- 1.3.6.1.4.1.5504.3.1.4.4.3.1.4
		zhoneUserPrompt OBJECT-TYPE
			SYNTAX ZhoneAdminString
			MAX-ACCESS read-create
			STATUS current
			DESCRIPTION
				"The prompt to be used after this user has logged in to
				the system."
			DEFVAL { "zSH> " }
			::= { zhoneUserEntry 4 }

		
		-- 1.3.6.1.4.1.5504.3.1.4.4.3.1.5
		zhoneUserAccessLevel OBJECT-TYPE
			SYNTAX BITS
				{
				userAccessAdmin(0),
				userAccessVoice(1),
				userAccessData(2),
				userAccessManuf(3),
				userAccessDatabase(4),
				userAccessSystems(5),
				userAccessTool(6),
				userAccessDebug(7)
				}
			MAX-ACCESS read-create
			STATUS current
			DESCRIPTION
				"Array of access levels that a user may have. This is an OR
				field where a user may have access to different subsystems.
				Only exception is Admin access level which allows access to
				all functions in the system.
				
				userAccessAdmin - allows access to all entities of the system.
				
				userAccessVoice - allows access to voice specific configuration
				                  and information.
				
				userAccessData - allows access to the data (i.e. IP)
				                 configuration and information.
				
				userAccessManuf - allows access to the manufacturing components
				                  of the system.
				
				userAccessDatabase - allows access to the database allowing
				                  write access. For any access except admin,
				                  this value must be set to allow any changes
				                  to be saved by this user.
				
				userAccessSystems - allows access to the system information.
				
				userAccessTool - allows access to system tools which help
				                 administer the system.
				
				userAccessDebug - allows access to Zhone Debug commands. This
				                  access should rarely be specified.
				
				There is No default value and a value must be specified for the
				user entry to be created.
				
				"
			::= { zhoneUserEntry 5 }

		
		-- 1.3.6.1.4.1.5504.3.1.4.4.3.1.6
		zhoneUserAdmin OBJECT-TYPE
			SYNTAX INTEGER
				{
				enabled(1),
				disabled(2)
				}
			MAX-ACCESS read-create
			STATUS current
			DESCRIPTION
				"Allows access to add, modify and delete users."
			DEFVAL { enabled }
			::= { zhoneUserEntry 6 }

		
		-- 1.3.6.1.4.1.5504.3.1.4.4.3.1.7
		zhoneUserLogins OBJECT-TYPE
			SYNTAX Counter32
			MAX-ACCESS read-only
			STATUS current
			DESCRIPTION
				"The number of successful logins performed by this user."
			::= { zhoneUserEntry 7 }

		
		-- 1.3.6.1.4.1.5504.3.1.4.4.3.1.8
		zhoneUserFailedLogins OBJECT-TYPE
			SYNTAX Counter32
			MAX-ACCESS read-only
			STATUS current
			DESCRIPTION
				"The number of failed logins performed by this user.
				
				A user would have had entered a this user name but entered
				an invalid password. Invalid user names are not tracked but
				are included in the total count described above."
			::= { zhoneUserEntry 8 }

		
		-- 1.3.6.1.4.1.5504.3.1.4.4.3.1.9
		zhoneUserRowStatus OBJECT-TYPE
			SYNTAX ZhoneRowStatus
			MAX-ACCESS read-create
			STATUS current
			DESCRIPTION
				"Row status in order to create the entry for this 
				user.
				
				In order to successfully create a user record, the following
				variables are required:
				
				      zhoneUserName
				      zhoneUserPassword
				      zhoneUserAccessLevel
				"
			::= { zhoneUserEntry 9 }

		
		-- 1.3.6.1.4.1.5504.3.1.5
		zhoneSystemConfiguration OBJECT-IDENTITY
			STATUS current
			DESCRIPTION 
				"System configuration parameters"
			::= { zhoneSystem 5 }

		
-- 
		-- 1.3.6.1.4.1.5504.3.1.5.1
		zhoneSystemConfigurationNumShelves OBJECT-TYPE
			SYNTAX Integer32
			UNITS "shelves"
			MAX-ACCESS read-only
			STATUS current
			DESCRIPTION
				"The number of shelves physically in the system"
			::= { zhoneSystemConfiguration 1 }

		
-- 
		-- 1.3.6.1.4.1.5504.3.1.5.2
		zhoneSystemConfigurationShelvesArray OBJECT-TYPE
			SYNTAX OCTET STRING (SIZE (32))
			MAX-ACCESS read-only
			STATUS current
			DESCRIPTION
				"Bit array from 0-255 (32 8-bit bytes) that are 
				present in the system."
			::= { zhoneSystemConfiguration 2 }

		
-- 
		-- 1.3.6.1.4.1.5504.3.1.5.3
		zhoneSystemConfigurationNumCards OBJECT-TYPE
			SYNTAX Integer32
			MAX-ACCESS read-only
			STATUS current
			DESCRIPTION
				"The total number of cards in the system (physcially).
				The number per shelf is defined in the shelf mib."
			::= { zhoneSystemConfiguration 3 }

		
-- 
		-- 1.3.6.1.4.1.5504.3.1.5.4
		zhoneSystemConfigurationIpAddress OBJECT-TYPE
			SYNTAX IpAddress
			MAX-ACCESS read-write
			STATUS current
			DESCRIPTION
				"The IP address of this device. Independent of the
				different IP interfaces configured and what is active,a manager
				uses this address as how to address the device. This address
				may OR may not be an IP address of an existing IP 
				interface. Deletion of a matching IP interface does not
				cause this address to be modified or deleted.
				
				A manager may communicate with the device using any of the
				configured IP interface addresses. However, any failures
				such as physical line outages or the card status is inactive,
				may result in failures to the manager requests (i.e. timeout).
				
				This value is defaulted to 0."
			::= { zhoneSystemConfiguration 4 }

		
-- 
		-- 1.3.6.1.4.1.5504.3.1.5.5
		zhoneSystemConfigurationAlternateIpAddress OBJECT-TYPE
			SYNTAX IpAddress
			MAX-ACCESS read-write
			STATUS current
			DESCRIPTION
				"A second IP address of this device. Independent of the
				different IP interfaces configured and what is active,a manager
				uses this address as how to address the device. This address
				may OR may not be an IP address of an existing IP 
				interface. Deletion of a matching IP interface does not
				cause this address to be modified or deleted.
				
				A manager may communicate with the device using any of the
				configured IP interface addresses. However, any failures
				such as physical line outages or the card status is inactive,
				may result in failures to the manager requests (i.e. timeout).
				
				This value is defaulted to 0 and in some cases, may never
				be configured."
			::= { zhoneSystemConfiguration 5 }

		
		-- 1.3.6.1.4.1.5504.3.1.5.6
		zhoneSystemConfigurationDateAndTime OBJECT-TYPE
			SYNTAX DateAndTime
			MAX-ACCESS read-write
			STATUS current
			DESCRIPTION
				"The date and time of the system, specified in local time.
				
				Only a community name having 'admin' priviledges will be
				allowed to modify this value. Although any valid community 
				name is allowed to read it.
				
				If an NTP server has been configured in zhoneSntpConfiguration, 
				then manual setting of the date and time is not allowed, and 
				a set attempt on zhoneSystemConfigurationDateAndTime will
				result in a generic error."
			::= { zhoneSystemConfiguration 6 }

		
-- 
		-- 1.3.6.1.4.1.5504.3.1.5.7
		zhoneSystemConfigurationCountryRegion OBJECT-TYPE
			SYNTAX ZhoneCountryCode
			MAX-ACCESS read-write
			STATUS current
			DESCRIPTION
				"The country or region where this system is operating in. This
				variable is used to adjust system settings for different
				functional modules. For example, both DSP tones and TDM
				compounding are country-specific settings that can be
				determined by this variable.
				
				This value is defaulted to 'us'."
			DEFVAL { us }
			::= { zhoneSystemConfiguration 7 }

		
		-- 1.3.6.1.4.1.5504.3.1.5.8
		zhonePrimaryClockSource OBJECT-TYPE
			SYNTAX InterfaceIndexOrZero
			MAX-ACCESS read-write
			STATUS deprecated
			DESCRIPTION
				"The ifIndex of the interface from which clock can be derived.
				Only oc3, ds1, and ds3 interfaces can be used for this.
				                                
				This interface will be used to drive the 8khz backplane
				signal.
				                                
				The interface must be set to loop or local timing in order for
				it to be considered as the primary clock source.  It must
				also be administratively turned on and be in an operational state.
				                                
				Only one interface in the system can be the primary clock source
				at any given time.
				                                
				                                
				NOTE: This value has been deprecated and should not be used. If
				specified, the system will use this interface as the clock source
				and will ignore the provisioning specified in the
				zhoneSystemClockTable."
			DEFVAL { 0 }
			::= { zhoneSystemConfiguration 8 }

		
		-- 1.3.6.1.4.1.5504.3.1.5.9
		zhoneSystemConfigurationRingSource OBJECT-TYPE
			SYNTAX INTEGER
				{
				internalRingSourceLabel(1),
				externalRingSourceLabel(2)
				}
			MAX-ACCESS read-write
			STATUS current
			DESCRIPTION
				"Ring voltage source selection (internal or external): 
				(1)Select internal ring generator (located within TAC)
				as source for ring voltage to line cards. 
				(2) Select external ring generator (input connector 
				located on TAC) as source for ring voltage to line cards.
				"
			DEFVAL { internalRingSourceLabel }
			::= { zhoneSystemConfiguration 9 }

		
		-- 1.3.6.1.4.1.5504.3.1.5.10
		zhoneSystemCurrentClockSource OBJECT-TYPE
			SYNTAX InterfaceIndexOrZero
			MAX-ACCESS read-only
			STATUS current
			DESCRIPTION
				"The current interface that is being used for the clock source.
				
				A value of 0 is returned if there are no available interfaces 
				in the zhoneSystemClockTable that have a 
				zhoneSystemClockAvailibilityStatus of active even the system
				clock table is not empty."
			::= { zhoneSystemConfiguration 10 }

		
		-- 1.3.6.1.4.1.5504.3.1.5.11
		zhoneSystemSecondaryClockSource OBJECT-TYPE
			SYNTAX InterfaceIndexOrZero
			MAX-ACCESS read-only
			STATUS current
			DESCRIPTION
				"The interface that would next be used for the system clock source
				if the zhoneSystemCurrentClockSource becomes inactive,
				it's elgibility is changed,is being used for the clock source.
				
				A value of 0 is returned if there are no other available interfaces 
				in the zhoneSystemClockTable that have a 
				zhoneSystemAvailabilityStatus of active even the system clock table
				is not empty.
				"
			::= { zhoneSystemConfiguration 11 }

		
		-- 1.3.6.1.4.1.5504.3.1.5.12
		zhoneSystemClockTable OBJECT-TYPE
			SYNTAX SEQUENCE OF ZhoneSystemClockEntry
			MAX-ACCESS not-accessible
			STATUS current
			DESCRIPTION
				"Table of physical ports that could be used as the clock
				source for other physical ports (i.e. DSL, DS1/DS3, and sonet).
				
				Entries are added to this table automatically by the system
				software whenever a card is activated for the first time.
				Ports that can supply clock will be added to this table
				with the default eligibility being set to FALSE (i.e not
				eligible to be a clock source). Current port types that will
				be added to this table are: DS1/E1, DS3/E3, and Sonet). Note
				that only physical ports are added so for example, a DS3 
				would be added but not any of the associated DS1 interfaces.
				
				A manager provisions entries in this table to be eligible
				to be a clock source and the associated weight that is 
				provisioned is used to determine the preference order
				for the clock source.
				
				A manager which specifies the DEPRECATED zhonePrimaryClockSource
				overrides entries in this table and will be used as the
				system clock source as long as the interface is active."
			::= { zhoneSystemConfiguration 12 }

		
		-- 1.3.6.1.4.1.5504.3.1.5.12.1
		zhoneSystemClockEntry OBJECT-TYPE
			SYNTAX ZhoneSystemClockEntry
			MAX-ACCESS not-accessible
			STATUS current
			DESCRIPTION
				"A row in the system clock table. Each row represents a 
				possible clock source by it's associated ifIndex."
			INDEX { ifIndex }
			::= { zhoneSystemClockTable 1 }

		
		ZhoneSystemClockEntry ::=
			SEQUENCE { 
				zhoneSystemClockEligibility
					TruthValue,
				zhoneSystemClockWeight
					Integer32,
				zhoneSystemClockAvailabilityStatus
					INTEGER,
				zhoneSystemClockTxClockMode
					INTEGER
			 }

		-- 1.3.6.1.4.1.5504.3.1.5.12.1.1
		zhoneSystemClockEligibility OBJECT-TYPE
			SYNTAX TruthValue
			MAX-ACCESS read-write
			STATUS current
			DESCRIPTION
				"The eligibility field indicates whether the system should
				include this physical port as a possible clock source."
			DEFVAL { false }
			::= { zhoneSystemClockEntry 1 }

		
		-- 1.3.6.1.4.1.5504.3.1.5.12.1.2
		zhoneSystemClockWeight OBJECT-TYPE
			SYNTAX Integer32 (1..10)
			MAX-ACCESS read-write
			STATUS current
			DESCRIPTION
				"The weight to be used to indicate the preference for
				each eligible port which is currently active 
				(zhoneSystemClockElgibilityStatus = active) to be used as
				the system clock source.
				
				Multiple interfaces may have the same weight and if so, the system
				will choose which interface to be chosen as the clock source.
				
				Changing the weight will have an immediate affect. For example,
				changing an interface to the highest priority will immediately
				make the interface the zhoneSystemCurrentClockSource unless
				the weight of the current source has that same weight."
			DEFVAL { 5 }
			::= { zhoneSystemClockEntry 2 }

		
		-- 1.3.6.1.4.1.5504.3.1.5.12.1.3
		zhoneSystemClockAvailabilityStatus OBJECT-TYPE
			SYNTAX INTEGER
				{
				inactive(1),
				active(2)
				}
			MAX-ACCESS read-only
			STATUS current
			DESCRIPTION
				"The status for whether this port can be usd as a clock source.
								
				A port can be active only on all of the following conditions
				are true:
								
				1. zhoneSystemClockEligibility is true.
				2. the interface is up and running (both ifAdminStatus and
				ifOperStatus are up).
								
				When this value is 'active', this port is included in a pool
				ordered by weights for whether it should be the clock source."
			::= { zhoneSystemClockEntry 3 }

		
		-- 1.3.6.1.4.1.5504.3.1.5.12.1.4
		zhoneSystemClockTxClockMode OBJECT-TYPE
			SYNTAX INTEGER
				{
				other(1),
				provisionedTiming(2),
				localTiming(3),
				loopTiming(4),
				throughTiming(5)
				}
			MAX-ACCESS read-only
			STATUS current
			DESCRIPTION
				"The transmit clock source is provisioned in the profile
				corresponding to the line type.  The choices are loop, 
				local, or through.  zhoneSystemClockTxClockMode shows 
				the current transmit clock source as possibly modified 
				by the clock manager. If the line selected as system 
				clock source is provisioned in through mode, its 
				zhoneSystemClockTxClockMode value is set to loopTiming 
				while it is the source.  If there is no eligible clock
				source, zhoneSystemClockTxClockMode for all lines are 
				set to localTiming.
				
				provisionedTiming  is reserved for internal use and will
				never be seen as the status of transmit clock mode.
				
				localTiming indicates that a local clock source is used
				or that an external clock is attached to the box
				containing the interface.
				
				loopTiming indicates that the recovered receive clock
				is used as the transmit clock.
				
				throughTiming indicates that transmit clock is derived
				from the recovered receive clock of another interface."
			::= { zhoneSystemClockEntry 4 }

		
		-- 1.3.6.1.4.1.5504.3.1.5.13
		zhoneSystemConsoleLogging OBJECT-TYPE
			SYNTAX INTEGER
				{
				enabled(1),
				disabled(2)
				}
			MAX-ACCESS read-write
			STATUS current
			DESCRIPTION
				"An option to enable or disable logging of system messages onto the console."
			DEFVAL { enabled }
			::= { zhoneSystemConfiguration 13 }

		
		-- 1.3.6.1.4.1.5504.3.1.5.14
		zhoneSystemRevertiveClockSource OBJECT-TYPE
			SYNTAX TruthValue
			MAX-ACCESS read-write
			STATUS current
			DESCRIPTION
				"Indicates whether revertive behavior of the system clock is desired. 
				If set to TRUE, the system will automatically revert to the higher 
				weighted clock when it becomes available again.  Used by systems that
				have the Clock Manager enabled."
			DEFVAL { true }
			::= { zhoneSystemConfiguration 14 }

		
-- 
		-- 1.3.6.1.4.1.5504.3.1.5.15
		zhoneSystemVoiceBandwidthCheck OBJECT-TYPE
			SYNTAX TruthValue
			MAX-ACCESS read-write
			STATUS current
			DESCRIPTION
				"Turns ON (true) of OFF (false) ATM bandwidth checks
				for new voice calls going through the system.  The
				bandwidth check is based on the configuration of
				the Rx and Tx traffic descriptors used for the ATM
				VC/CID that the call is going across.  If rtVBR is
				being used then the SCR is used for the bandwidth
				calculation cell rate.  If CBR is being used then
				the PCR is used for the bandwidth calculation cell
				rate.  For any other service category, a call is
				always allowed and the voice quality is not
				guaranteed.  The bandwidth calculation looks like
				this (assume approx 180 AAL2 cells used for a
				voice stream):
				
				if ((rxCellRate - (180 * numActiveCallsOn VC)) < 180)
				{
				    /* reject call */
				}
				else if ((txCellRate - (180 * numActiveCallsOnVC)) < 180)
				{
				    /* reject call */
				}
				else
				{
				    /* proceed with call */
				}
				"
			DEFVAL { false }
			::= { zhoneSystemConfiguration 15 }

		
-- 
		-- 1.3.6.1.4.1.5504.3.1.5.16
		zhoneAlarmLevelsEnabled OBJECT-TYPE
			SYNTAX BITS
				{
				critical(0),
				major(1),
				minor(2),
				warning(3)
				}
			MAX-ACCESS read-write
			STATUS current
			DESCRIPTION
				"Bit field indicating which combination of the 4 alarm
				levels are enabled.  User can disable alarms based
				on alarm severity level."
			::= { zhoneSystemConfiguration 16 }

		
-- 
		-- 1.3.6.1.4.1.5504.3.1.5.17
		zhoneSystemUserAuthMethod OBJECT-TYPE
			SYNTAX INTEGER
				{
				local(1),
				radius(2),
				radiusThenLocal(3),
				radiusThenCraft(4)
				}
			MAX-ACCESS read-write
			STATUS current
			DESCRIPTION
				"This object determines how users access to the device is authenticated.
				A value of local indicates that user should be authenticated using
				locally provisioned user-profile profiles. A value of radius 
				indicates that only RADIUS authentication should be used. A value
				of radiusThenLocal indicates that the user should be authenticated
				first by using RADIUS authentication and if that fails, then by local
				user-profile profiles. A value of radiusThenCraft indicates that the 
				user should be authenticated first by using RADIUS authentication and 
				if that fails, then only on the local craft port authentication by local 
				user-profile profiles is allowed but all other ports will be denied 
				access."
			DEFVAL { local }
			::= { zhoneSystemConfiguration 17 }

		
-- 
		-- 1.3.6.1.4.1.5504.3.1.5.18
		zhoneSystemRadiusAuthIndex OBJECT-TYPE
			SYNTAX Integer32
			MAX-ACCESS read-write
			STATUS current
			DESCRIPTION
				"This object contains the index of the Radius Server profile to
				be used if RADIUS authentication is desired."
			::= { zhoneSystemConfiguration 18 }

		
		-- 1.3.6.1.4.1.5504.3.1.5.19
		zhoneSystemSecureFTP OBJECT-TYPE
			SYNTAX INTEGER
				{
				enabled(1),
				disabled(2)
				}
			MAX-ACCESS read-write
			STATUS current
			DESCRIPTION
				"Secure FTP (SFTP) control."
			DEFVAL { disabled }
			::= { zhoneSystemConfiguration 19 }

		
		-- 1.3.6.1.4.1.5504.3.1.5.20
		zhoneSystemWebInterface OBJECT-TYPE
			SYNTAX INTEGER
				{
				enabled(1),
				disabled(2)
				}
			MAX-ACCESS read-write
			STATUS current
			DESCRIPTION
				"Specifies whether the Web GUI Interface is enabled for this system."
			DEFVAL { enabled }
			::= { zhoneSystemConfiguration 20 }

		
		-- 1.3.6.1.4.1.5504.3.1.5.21
		zhoneSystemConfigurationOptions OBJECT-TYPE
			SYNTAX BITS
				{
				cvlanonly(0),
				nol3bridgetable(1),
				ipg88bits(2),
				disdefpktrules(3),
				enablexcardlinkagg(4),
				fiberlan(5),
				cfmon(6),
				bondautodetect(7)
				}
			MAX-ACCESS read-write
			STATUS current
			DESCRIPTION
				"System options in bit-mask format."
			::= { zhoneSystemConfiguration 21 }

		
-- 
		-- 1.3.6.1.4.1.5504.3.1.5.22
		zhoneSystemConfigurationReservedVlanIdStart OBJECT-TYPE
			SYNTAX Unsigned32 (0..4090)
			MAX-ACCESS read-write
			STATUS current
			DESCRIPTION
				"Starting VLAN ID of the reserved VLAN ID block.
				
				The reserved VLAN ID block starts with the reservedVlanIdStart and
				ends with reservedVlanIdStart + reservedVlanIdCount;
				
				No bridge, host, or IP can use a VLAN ID in the reserved VLANs."
			DEFVAL { 0 }
			::= { zhoneSystemConfiguration 22 }

		
-- 
		-- 1.3.6.1.4.1.5504.3.1.5.23
		zhoneSystemConfigurationReservedVlanIdCount OBJECT-TYPE
			SYNTAX Unsigned32 (0..2048)
			MAX-ACCESS read-write
			STATUS current
			DESCRIPTION
				"Number of reserved VLAN IDs in the reserved VLAN ID block.
				
				A zero value disables these reserved VLANs and operation
				reverts to normal VLAN ID reservation.
				
				The reserved VLAN ID block starts with the reservedVlanIdStart and
				ends with reservedVlanIdStart + reservedVlanIdCount;
				
				No bridge, host, or IP can use a VLAN ID in the reserved VLANs.
				
				For GPON OLTs, the number of GEM Ports per OLT cannot exceed 
				this number."
			DEFVAL { 0 }
			::= { zhoneSystemConfiguration 23 }

		
		-- 1.3.6.1.4.1.5504.3.1.5.24
		zhoneSystemSnmpVersion OBJECT-TYPE
			SYNTAX INTEGER
				{
				snmpv2(1),
				snmpv3(2),
				snmpv3includingZMS(3)
				}
			MAX-ACCESS read-write
			STATUS current
			DESCRIPTION
				"Version of SNMP the supported by the device."
			::= { zhoneSystemConfiguration 24 }

		
		-- 1.3.6.1.4.1.5504.3.1.5.25
		zhoneSystemPersistentLogging OBJECT-TYPE
			SYNTAX INTEGER
				{
				enabled(1),
				disabled(2)
				}
			MAX-ACCESS read-write
			STATUS current
			DESCRIPTION
				"An option to enable or disable persistent logging of system messages onto the console."
			DEFVAL { disabled }
			::= { zhoneSystemConfiguration 25 }

		
		-- 1.3.6.1.4.1.5504.3.1.5.26
		zhoneSystemOutletTemperatureHighThreshold OBJECT-TYPE
			SYNTAX Integer32 (35..75)
			MAX-ACCESS read-write
			STATUS current
			DESCRIPTION
				"Specifies the outlet sensor high temperature threshold.
				Minor, Major & Critical alarms will be raised when outlet 
				sensor temperature reaches X, X+5 & X+10 respectively. 
				
				X is the value of this field. 
				Allowed range for MXK & MX1U products is 35 to 65 
				Allowed range for MX1uU10Lt is 35 to 75"
			DEFVAL { 65 }
			::= { zhoneSystemConfiguration 26 }

		
		-- 1.3.6.1.4.1.5504.3.1.5.27
		zhoneSystemOutletTemperatureLowThreshold OBJECT-TYPE
			SYNTAX Integer32 (-40..0)
			MAX-ACCESS read-write
			STATUS current
			DESCRIPTION
				"Specifies the outlet sensor low temperature threshold. 
				Minor alarm will be raised when outlet sensor reaches the 
				temperatue configured in this field"
			DEFVAL { -12 }
			::= { zhoneSystemConfiguration 27 }

		
		-- 1.3.6.1.4.1.5504.3.1.5.28
		zhoneSystemSnmpV3EngineId OBJECT-TYPE
			SYNTAX Unsigned32
			MAX-ACCESS read-only
			STATUS current
			DESCRIPTION
				"The engine ID used for snmp version 3 access includes
				the backplane serial number of the chassis. For HA
				systems, we store this (the shelf 1 serial
				number) for use when shelf 2 is active.
				"
			DEFVAL { 0 }
			::= { zhoneSystemConfiguration 28 }

		
		-- 1.3.6.1.4.1.5504.3.1.6
		zhoneSoftwareLoadTable OBJECT-TYPE
			SYNTAX SEQUENCE OF ZhoneSoftwareLoadEntry
			MAX-ACCESS not-accessible
			STATUS current
			DESCRIPTION
				"This table is used by the system to determine the
				default code image to load for each card type.  
				
				Each card, when it requests a software load, will either
				receive an upgrade version of software, a specific 
				version of software, or receive the known current
				version of the software.  This table is used to 
				determine the code image to load in the default case.
				
				This table is not used for non-BAN hardware."
			::= { zhoneSystem 6 }

		
		-- 1.3.6.1.4.1.5504.3.1.6.1
		zhoneSoftwareLoadEntry OBJECT-TYPE
			SYNTAX ZhoneSoftwareLoadEntry
			MAX-ACCESS not-accessible
			STATUS current
			DESCRIPTION
				"Table of software code image names for each card type
				in a BAN."
			INDEX { zhoneSwCardType }
			::= { zhoneSoftwareLoadTable 1 }

		
		ZhoneSoftwareLoadEntry ::=
			SEQUENCE { 
				zhoneSwCardType
					ZhoneCardType,
				zhoneSwCardSwFileName
					ZhoneFileName,
				zhoneSwLoadRowStatus
					ZhoneRowStatus
			 }

		-- 1.3.6.1.4.1.5504.3.1.6.1.1
		zhoneSwCardType OBJECT-TYPE
			SYNTAX ZhoneCardType
			MAX-ACCESS not-accessible
			STATUS current
			DESCRIPTION
				"Type of card requesting software load this card type
				the same used in the Card Resources MIB.
				"
			::= { zhoneSoftwareLoadEntry 1 }

		
-- 
		-- 1.3.6.1.4.1.5504.3.1.6.1.2
		zhoneSwCardSwFileName OBJECT-TYPE
			SYNTAX ZhoneFileName
			MAX-ACCESS read-create
			STATUS current
			DESCRIPTION
				"Name of code image to loaded by software load
				services for the card type requesting a load
				if a specific load version is not requested.
				
				Required for RowCreate"
			::= { zhoneSoftwareLoadEntry 2 }

		
		-- 1.3.6.1.4.1.5504.3.1.6.1.3
		zhoneSwLoadRowStatus OBJECT-TYPE
			SYNTAX ZhoneRowStatus
			MAX-ACCESS read-create
			STATUS current
			DESCRIPTION
				"Row status in order to create the entry for this 
				destination.
				
				zhoneCardSwFileName is required for row creation."
			::= { zhoneSoftwareLoadEntry 3 }

		
-- The device will store an error string, along with 
-- the current request_id and IP source address along 
-- with the current time to be stored in a new row in 
-- this error mib. This mib can then be accessed (via 
-- an INDEX of ip address, request_id) with a 'get' 
-- operation by the cli or zms to get the appropriate 
-- error code. Once the value is 'gotten', the row is 
-- destroyed. The time stamp is maintained so that old 
-- rows are removed after 2 minutes so as not to tie 
-- up any unnecessary resources. This is used to 
-- extend the limited SNMP error codes and fully define
-- to the user what error occured.
-- 
-- Note that there may be more than one entry in this
-- table with the same reqid and IP address as a 
-- single SNMP PDU may have multiple errors.
-- 
		-- 1.3.6.1.4.1.5504.3.1.7
		zhoneSnmpErrorTable OBJECT-TYPE
			SYNTAX SEQUENCE OF ZhoneSnmpErrorEntry
			MAX-ACCESS not-accessible
			STATUS current
			DESCRIPTION
				"Zhone SNMP error information."
			::= { zhoneSystem 7 }

		
		-- 1.3.6.1.4.1.5504.3.1.7.1
		zhoneSnmpErrorEntry OBJECT-TYPE
			SYNTAX ZhoneSnmpErrorEntry
			MAX-ACCESS not-accessible
			STATUS current
			DESCRIPTION
				"A single entry in the error table which describes an 
				problem detected by the mib handler."
			INDEX { zhoneSnmpErrorIpAddress, zhoneSnmpErrorReqId }
			::= { zhoneSnmpErrorTable 1 }

		
		ZhoneSnmpErrorEntry ::=
			SEQUENCE { 
				zhoneSnmpErrorIpAddress
					IpAddress,
				zhoneSnmpErrorReqId
					Unsigned32,
				zhoneSnmpErrorDisplayString
					OCTET STRING,
				zhoneSnmpErrorTime
					TimeTicks
			 }

		-- 1.3.6.1.4.1.5504.3.1.7.1.1
		zhoneSnmpErrorIpAddress OBJECT-TYPE
			SYNTAX IpAddress
			MAX-ACCESS not-accessible
			STATUS current
			DESCRIPTION
				"The IP address of the requesting station for which this
				error is applicable."
			::= { zhoneSnmpErrorEntry 1 }

		
		-- 1.3.6.1.4.1.5504.3.1.7.1.2
		zhoneSnmpErrorReqId OBJECT-TYPE
			SYNTAX Unsigned32
			MAX-ACCESS not-accessible
			STATUS current
			DESCRIPTION
				"SNMP request ID of failed error. "
			::= { zhoneSnmpErrorEntry 2 }

		
		-- 1.3.6.1.4.1.5504.3.1.7.1.3
		zhoneSnmpErrorDisplayString OBJECT-TYPE
			SYNTAX OCTET STRING (SIZE (0..120))
			MAX-ACCESS read-write
			STATUS current
			DESCRIPTION
				"The actual text string to show to the user."
			::= { zhoneSnmpErrorEntry 3 }

		
		-- 1.3.6.1.4.1.5504.3.1.7.1.4
		zhoneSnmpErrorTime OBJECT-TYPE
			SYNTAX TimeTicks
			MAX-ACCESS read-only
			STATUS current
			DESCRIPTION
				"System time that the error occurred. This is used so
				the system will remove any old entries (older
				than 2 minutes) as it is unlikely that the cli or
				management station will require errors after that
				long of a period."
			::= { zhoneSnmpErrorEntry 4 }

		
-- Contains information for the software downloads for
-- Zhone Management System. Access to this table is only allowed with
-- admin access community names from snmp or admin access allowed user 
-- names.
-- 
		-- 1.3.6.1.4.1.5504.3.1.8
		zhoneSoftwareDownload OBJECT-IDENTITY
			STATUS current
			DESCRIPTION 
				"Software Download information utilized by all Zhone
				devices in order to obtain software images on to
				local storage.
				
				In lower-end devices, the download itself may be 
				stored directly into a boot area which is automatically
				used upon restart of the system.
				
				The login/password information may be ignored if the device
				only supports tftp. Sets to these fields will be accepted so
				the request may continue."
			::= { zhoneSystem 8 }

		
		-- 1.3.6.1.4.1.5504.3.1.8.1
		zhoneSysSwLogin OBJECT-TYPE
			SYNTAX ZhoneAdminString
			MAX-ACCESS read-write
			STATUS current
			DESCRIPTION
				"The login to be used on the remote system when 
				downloading the image.
				
				This value is maintained throughout (i.e. persisted) and
				can be used for additional/future download requests.
				
				This login is used for both zli 'update-image' commands and
				snmp/zms requests using this mib.
				
				The login is defaulted to NULL the first time the system is 
				booted and is maintained across sw download requests and
				reboots. That is, the value is not cleared upon completion and
				can be reused by the manager..
				
				When read, the last value used is returned."
			::= { zhoneSoftwareDownload 1 }

		
		-- 1.3.6.1.4.1.5504.3.1.8.2
		zhoneSysSwPassword OBJECT-TYPE
			SYNTAX ZhoneAdminString
			MAX-ACCESS read-write
			STATUS current
			DESCRIPTION
				"The password to be used on the remote system when 
				downloading the image.
				
				This value is maintained throughout (i.e. persisted) and
				can be used for additional/future download requests.
				
				This password is used for both zli 'update-image' commands and
				snmp/zms requests using this mib.
				
				The password is defaulted to NULL the first time the system is 
				booted and is maintained across sw download requests and
				reboots. That is, the value is not cleared upon completion and
				can be reused by the manager..
				
				When read, a NULL value is always returned."
			::= { zhoneSoftwareDownload 2 }

		
		-- 1.3.6.1.4.1.5504.3.1.8.3
		zhoneSysSwPriLoadServer OBJECT-TYPE
			SYNTAX IpAddress
			MAX-ACCESS read-write
			STATUS current
			DESCRIPTION
				"The IP address of the primary software load server.
				If the value of the zhoneSysSwPriLoadServer is set to 
				0.0.0.0 then no primary load server is available.
				
				If the system is unable to load the software file
				from the Primary Load Server, the system should
				attemmpt to load the software from the the Secondary
				Load Server (zhoneSysSecLoadServer).
				
				This value must be set on each download request."
			::= { zhoneSoftwareDownload 3 }

		
		-- 1.3.6.1.4.1.5504.3.1.8.4
		zhoneSysSwSecLoadServer OBJECT-TYPE
			SYNTAX IpAddress
			MAX-ACCESS read-write
			STATUS current
			DESCRIPTION
				"The IP address of the secondary or back-up software
				load server, if there is no secondary server this
				should be set to 0.0.0.0"
			::= { zhoneSoftwareDownload 4 }

		
		-- 1.3.6.1.4.1.5504.3.1.8.5
		zhoneSysSwRemoteFilePath OBJECT-TYPE
			SYNTAX OCTET STRING (SIZE (0..128))
			MAX-ACCESS read-write
			STATUS current
			DESCRIPTION
				"The path on the remote system for the image to be loaded."
			::= { zhoneSoftwareDownload 5 }

		
		-- 1.3.6.1.4.1.5504.3.1.8.6
		zhoneSysSwLocalFilePath OBJECT-TYPE
			SYNTAX ZhoneFileName
			MAX-ACCESS read-write
			STATUS current
			DESCRIPTION
				"The path on the system for the image to be stored."
			::= { zhoneSoftwareDownload 6 }

		
		-- 1.3.6.1.4.1.5504.3.1.8.7
		zhoneSysSwAdmin OBJECT-TYPE
			SYNTAX INTEGER
				{
				downLoadSw(1),
				abortDownLoadSw(2),
				delete(3),
				imageFlashActive(4),
				imageFlashStandby(5),
				downLoadFile(6),
				upLoadFile(7),
				dumpFile(8),
				dumpNetwork(9),
				restore(10),
				configScriptActivate(11),
				configDatabaseActivate(12),
				backupDatabase(13),
				restoreDatabase(14)
				}
			MAX-ACCESS read-write
			STATUS current
			DESCRIPTION
				" (1) downloadSw: Download the image from the Primary load 
				Server. If that fails, try to download from secondary 
				load server. This value is only allowed if the zhoneSysSwStatus
				field is NOT downLoadSwInProgress.
				
				(2) abortDownLoadSw: abort an in-progress download. This value
				is only allowed if the zhoneSysSwStatus is downLoadSwInProgress.
				
				(3) delete: deletes the filename specified in 
				zhoneSysSwLocalFilePath. This is used by the manager to
				manage the amount of storage space used by the
				system for sw load images. A delete will fail if
				the file is specified in either a: default sw entry,
				specific software entry, or an upgrade software entry.
				
				This is only supported on devices having a file-system.
				
				(4) imageFlashActive: flashes the raw file specified in the
				zhoneSysSwLocalFilePath.  This is used to update the raw 
				boot area of the flash of the active infoserver.
				
				(5) imageFlashStandby: flashes the raw file specified in the
				zhoneSysSwLocalFilePath.  This is used to update the raw 
				boot area of the flash of the active infoserver.
				
				(6) downLoadFile: Download a file from the Primary load 
				Server. If that fails, try to download from secondary 
				load server. This value is only allowed if the zhoneSysSwStatus
				field is NOT operationInProgress.
				
				(7) upLoadFile: Upload a file to the Primary load 
				Server. The file must already exists on the load server
				This value is only allowed if the zhoneSysSwStatus
				field is NOT operationInProgress.
				
				(8) dumpFile: dump the database to a local file.
				
				(9) dumpNetwork: dump the database to the primary load
				server. The file must already exists on the load server
				This value is only allowed if the zhoneSysSwStatus
				field is NOT operationInProgress.
				
				(10) restore
				
				(11) configScriptActivate: activate the configuration
				script file specified in the zhoneSysSwLocalFilePath.
				This value is only allowed if the zhoneSysSwStatus is
				NOT operationInProgress nor downloadSwInProgress.
				
				(12) configDatabaseActivate: activate the contents of a
				database file specified in the zhoneSysSwLocalFilePath.
				This value is only allowed if the zhoneSysSwStatus is
				NOT operationInProgress nor downloadSwInProgress.
				Activation of a new database may result in a reset of
				the system.
				
				(13) backupDatabase: backup device by uploading database 
				file to zhoneSysSwLocalFilePath.
				
				(14) restoreDatabase: restore device database from 
				zhoneSysSwLocalFilePath. This command will reboot device 
				with restored database.
				"
			::= { zhoneSoftwareDownload 7 }

		
		-- 1.3.6.1.4.1.5504.3.1.8.8
		zhoneSysSwStatus OBJECT-TYPE
			SYNTAX INTEGER
				{
				downLoadSwUnknown(1),
				downLoadSwInProgress(2),
				downLoadSwAborted(3),
				downLoadSwFailed(4),
				downLoadSwSuccessful(5),
				deleteFileNotFound(6),
				deleteFileInUse(7),
				deleteSuccessful(8),
				operationInProgress(9),
				operationAborted(10),
				operationFailed(11),
				operationSuccessful(12)
				}
			MAX-ACCESS read-only
			STATUS current
			DESCRIPTION
				" 
				(1) downLoadSwUnknown: No state known. This is the value if
				no sw download had been requested since the system was
				initialized or a delete command is in progress.
				
				(2) downloadSwInProgres: Download currently in progress.
				
				(3) downLoadSwAborted: abort command processed. Sw not loaded.
				
				(4) downLoadSwFailed: FTP/TFTP request failed to  both the primary
				and secondary server.
				
				(5) downLoadSwSuccessful: SW successfully downloaded from 
				either the primary or secondary server.
				
				(6) deleteFileNotFound: The file specified in 
				zhoneSysSwLocalFilePath cannot be found on the device.
				
				(7) deleteFileInUse: The file specified in 
				zhoneSysSwLocalFilePath is currently specified in
				a sw configuration record.
				
				(8) deleteSuccessful: The file was successfully deleted.
				
				The following are the generic status for the imageFlash,
				uploadFile, downloadFile, dump and restore operations.
				(9) operationInProgres: operation currently in progress.
				
				(10) operationAborted: abort command processed. Sw not loaded.
				
				(11) operationFailed: operation failed
				
				(12) operationSuccessful: operation successfully
				"
			::= { zhoneSoftwareDownload 8 }

		
-- Contains information for the reboot of the system or cards of the system.
-- 
		-- 1.3.6.1.4.1.5504.3.1.9
		zhoneSoftwareReboot OBJECT-IDENTITY
			STATUS current
			DESCRIPTION 
				"Reboot for system or particular type of cards. Common use
				is  after software downloads but can be used anytime.
				
				Initiating a reboot requires admin access level security."
			::= { zhoneSystem 9 }

		
		-- 1.3.6.1.4.1.5504.3.1.9.1
		zhoneSysRebootAdmin OBJECT-TYPE
			SYNTAX INTEGER
				{
				systemReboot(1),
				rebootByCardType(2)
				}
			MAX-ACCESS read-write
			STATUS current
			DESCRIPTION
				" systemReboot: reboot all the cards
				
				rebootByCardType : reboot all cards of a particular card 
				              Type (specified by zhoneSysRebootCardType).
				       	    "
			::= { zhoneSoftwareReboot 1 }

		
		-- 1.3.6.1.4.1.5504.3.1.9.2
		zhoneSysRebootCardType OBJECT-TYPE
			SYNTAX ZhoneCardType
			MAX-ACCESS read-write
			STATUS current
			DESCRIPTION
				"The numerical representation of what unit/card type
				has to be rebooted."
			::= { zhoneSoftwareReboot 2 }

		
		-- 1.3.6.1.4.1.5504.3.1.10
		zhoneSysCardSoftwareConfigTable OBJECT-TYPE
			SYNTAX SEQUENCE OF ZhoneSysCardSoftwareConfigEntry
			MAX-ACCESS not-accessible
			STATUS current
			DESCRIPTION
				"The software configuration for this card. For every
				card (i.e. shelf/slot) in the system, an entry must
				be created in order for the card to get loaded with
				software along with the card software enable flag
				set to true. 
				
				At a minimum, the system will check to see if the
				zhoneSysCardSwEnable value is TRUE to indicate the
				card can be loaded. If the value is true, the scenario
				to determine which software to load is:
				
				        - if zhoneSysCardUpgradeFileName is set and
				              the zhoneSysSwUpgradeEnable flag is
				              set to true, load this software.
				        - if zhoneSysCardSpecificFileName is set, load
				             this software.
				        - if a default file name is specified for this
				              card type, the software specified in 
				              zhoneSwCardFileName will be used.
				
				        - Otherwise, a trap is generated for the first
				          time this error occurs."
			::= { zhoneSystem 10 }

		
		-- 1.3.6.1.4.1.5504.3.1.10.1
		zhoneSysCardSoftwareConfigEntry OBJECT-TYPE
			SYNTAX ZhoneSysCardSoftwareConfigEntry
			MAX-ACCESS not-accessible
			STATUS current
			DESCRIPTION
				"An entry for a particular card. An entry is added by
				the manager in order for a card to be available for
				loading. If an entry does not exist for a card, no load
				is possible."
			INDEX { zhoneShelfIndex, zhoneSlotIndex }
			::= { zhoneSysCardSoftwareConfigTable 1 }

		
		ZhoneSysCardSoftwareConfigEntry ::=
			SEQUENCE { 
				zhoneSysCardSpecificSwFileName
					ZhoneFileName,
				zhoneSysCardSwSpecificVers
					ZhoneAdminString,
				zhoneSysCardUpgradeSwFileName
					ZhoneFileName,
				zhoneSysCardSwUpgradeVers
					ZhoneAdminString,
				zhoneSysCardSwType
					ZhoneCardType,
				zhoneSysCardSwEnable
					TruthValue,
				zhoneSysCardSwUpgradeEnable
					TruthValue,
				zhoneSysCardRowStatus
					ZhoneRowStatus,
				zhoneSysCardLineType
					ZhoneCardLineType,
				zhoneSysCardAtmConfiguration
					INTEGER,
				zhoneSysCardLineVoltage
					INTEGER,
				zhoneSysCardVpiVciRange
					INTEGER,
				zhoneSysCardInitString
					OCTET STRING,
				zhoneSysCardWettingCurrent
					INTEGER
			 }

-- 
-- 
		-- 1.3.6.1.4.1.5504.3.1.10.1.1
		zhoneSysCardSpecificSwFileName OBJECT-TYPE
			SYNTAX ZhoneFileName
			MAX-ACCESS read-create
			STATUS current
			DESCRIPTION
				"The file or code image name of the specific software 
				version that should be loaded by the unit/card for 
				operation. If a failure occurs when trying to boot
				an upgrade version, the system will automatically
				revert to a 'good' software version which is either
				the zhoneSysCardSpecificSwFileName if non-NULL or the
				default for this card type if it is NULL.
				
				The operation will vary if the unit is a BAN card or 
				a standalone device.
				 
				BAN: In the case of a BAN the card will load the 
				indicated module and set cardSwStatus as appropriate.
				If the cardSpecificFileName is set to NULL then the card 
				will load the image indicated by the 
				zhoneSoftwareLoadTable in the system mib.
				
				STANDALONE: If the card is a Zedge,Sechtor, or similar
				device, the system will first check if there is a local 
				copy of the code image indicated, if there is, the 
				card will load from the local copy.  If the local copy 
				is not the same revision as zhoneSysCardSpecificSwFileName 
				the card will load this file. "
			DEFVAL { " " }
			::= { zhoneSysCardSoftwareConfigEntry 1 }

		
-- 
-- 
		-- 1.3.6.1.4.1.5504.3.1.10.1.2
		zhoneSysCardSwSpecificVers OBJECT-TYPE
			SYNTAX ZhoneAdminString
			MAX-ACCESS read-only
			STATUS current
			DESCRIPTION
				"The software version of the file name specified in
				zhoneSysCardSpecificSwFileName. 
				
				If the revision is not known or the file name is
				NULL, this should return an empty string."
			::= { zhoneSysCardSoftwareConfigEntry 2 }

		
-- 
-- 
		-- 1.3.6.1.4.1.5504.3.1.10.1.3
		zhoneSysCardUpgradeSwFileName OBJECT-TYPE
			SYNTAX ZhoneFileName
			MAX-ACCESS read-create
			STATUS current
			DESCRIPTION
				"The file name of the software version that should be 
				loaded by the unit/card into the upgrade region of 
				the card/unit memory or storage.
				
				This file takes precendence over the current sw file
				name and is used to attempt to upgrade the software 
				on the system or card. If a user determines that the
				software upgrade version is acceptable, this value
				should be set in the CurrSwFileName.
				"
			DEFVAL { "  " }
			::= { zhoneSysCardSoftwareConfigEntry 3 }

		
-- 
-- 
		-- 1.3.6.1.4.1.5504.3.1.10.1.4
		zhoneSysCardSwUpgradeVers OBJECT-TYPE
			SYNTAX ZhoneAdminString
			MAX-ACCESS read-only
			STATUS current
			DESCRIPTION
				"The software version specified in the zhoneSysCardUpgrade
				FileName variable in this table that will be loaded
				on the next card reboot. 
				
				This object complies to the Zhone software revision
				syntax."
			::= { zhoneSysCardSoftwareConfigEntry 4 }

		
-- 
-- 
		-- 1.3.6.1.4.1.5504.3.1.10.1.5
		zhoneSysCardSwType OBJECT-TYPE
			SYNTAX ZhoneCardType
			MAX-ACCESS read-create
			STATUS current
			DESCRIPTION
				"The card type for the card in this shelf/slot.
				
				When initially created, this value is defaulted to
				'unknown'. When the card requests a load, the value in
				this field is compared to the requesting card type. If
				the value is 'unknown' and a load can be serviced 
				(i.e. the card is swenabled, and a sw is specified
				in either the upgrade, specific, or default for this
				type fields), the value is updated to the requesting
				card type. Otherwise, the type in this field is
				compared to the requesting card type. If it matches,
				a load based on the other parameters is attempted.
				Otherwise, the load request is rejected and the
				initial request causes a trap to be generated.
				
				This processing is provided to ensure a card is not
				accidentally installed which attempts to load or
				start provisioning for a non-matching card type. 
				
				The user may switch to a different card type than
				currently executing by setting this value to the new
				card type after the old card has been removed."
			::= { zhoneSysCardSoftwareConfigEntry 5 }

		
-- 
-- 
		-- 1.3.6.1.4.1.5504.3.1.10.1.6
		zhoneSysCardSwEnable OBJECT-TYPE
			SYNTAX TruthValue
			MAX-ACCESS read-create
			STATUS current
			DESCRIPTION
				"Whether or not the card has been enabled to be loaded.
				If this value is false, no sw will be loaded, otherwise
				the logic flow defined in the table description
				will be exercised for determining which software to load."
			DEFVAL { false }
			::= { zhoneSysCardSoftwareConfigEntry 6 }

		
-- 
		-- 1.3.6.1.4.1.5504.3.1.10.1.7
		zhoneSysCardSwUpgradeEnable OBJECT-TYPE
			SYNTAX TruthValue
			MAX-ACCESS read-create
			STATUS current
			DESCRIPTION
				"This field indicates whether the zhoneSysCardUpgradeSwFileName
				should be used as the software image when the card
				requests a software load. This value can either be
				set directly or may be set indirectly via changes to
				the cardSwAdmin field in the card mib.
				"
			DEFVAL { false }
			::= { zhoneSysCardSoftwareConfigEntry 7 }

		
		-- 1.3.6.1.4.1.5504.3.1.10.1.8
		zhoneSysCardRowStatus OBJECT-TYPE
			SYNTAX ZhoneRowStatus
			MAX-ACCESS read-create
			STATUS current
			DESCRIPTION
				"The row status used to create or delete an entry
				for a card (i.e. shelf/slot). No entries are required
				to be included in a table create as all entries have
				default settings."
			::= { zhoneSysCardSoftwareConfigEntry 8 }

		
		-- 1.3.6.1.4.1.5504.3.1.10.1.9
		zhoneSysCardLineType OBJECT-TYPE
			SYNTAX ZhoneCardLineType
			MAX-ACCESS read-create
			STATUS current
			DESCRIPTION
				"This field is used to identify which line types for
				different cards
								
				For normal e1/t1 cards only t1 and e1 (uni mode)
				line types are supported.
								
				For MALC t1Ima Uplink card, e1, t1, e1-ima, and
				t1-ima line types are supported
								
				For MALC ds3 Uplink card, e3 and t3 line types
				are supported.
				
				For MALC t1e1tdm Uplink card, only t1UniGr303,
				t1ImaGr303, e1UniV52 and e1ImaV52 are supported.
				MalcT1E1Tdm cards have 16 T1/E1 ports.  The first
				8 ports are ATM, the second 8 are TDM.  These 4
				values indicate both the layer 1 line type (e1Uni,
				e1Ima, t1Uni, t1Ima) for the ATM ports and the
				layer 3 signalling (gr303 and V5.2) for the TDM ports.
				
				For malcXdsl48 with optional pots card, unknown, 
				adsl-pots and adsl-pots-pv are allowed.
				
				For malcPots48 with unknown, pots and pots-pv are allowed.
				
				
				All other cards only support unknown.
								
				Default value for MALC t1Ima uplink will be
				t1 line type if the line type was not stored
				in the Real Time Clock (RTC).  Otherwise it
				will be the value stored in the RTC.
								
				Default value for MALC ds3 Uplink will be
				t3 line type if the line type was not stored
				in the Real Time Clock (RTC).  Otherwise it
				will be the value stored in the RTC.
				
				Default for MalcT1E1Tdm is t1UniGr303.
								
				This field is only set upon row-creation.
				Modifications to this value after row creation
				will only be allowed for packet voice capable cards."
			DEFVAL { unknown }
			::= { zhoneSysCardSoftwareConfigEntry 9 }

		
		-- 1.3.6.1.4.1.5504.3.1.10.1.10
		zhoneSysCardAtmConfiguration OBJECT-TYPE
			SYNTAX INTEGER
				{
				notApplicable(1),
				cellRelayOnly(2),
				cellRelayAndManagement(3),
				dataTerm(4),
				voiceGateway(5),
				hybridLowAal5Data(6),
				hybridDefault(7),
				hybridHighAal5Data(8),
				vbnrt95rt5(9),
				vbnrt80rt15(10),
				vbnrt65rt30(11),
				vbnrt50rt45(12),
				vbnrt35rt60(13),
				vbnrt20rt75(14),
				vbnrt5rt95(15),
				vbnrt5rt95cbr(16),
				manual(99)
				}
			MAX-ACCESS read-create
			STATUS current
			DESCRIPTION
				"This field specifies how internal resources are distributed 
				between aal5 resources and aal2/cell relay resources based 
				on the core use of this card.  This field is applicable for BAN 
				AtmTrnk, AtmAal25 and AtmTrnkCr Cards. For AtmAal25 card, it 
				also specifies how much of the AAL2/Cell Relay BW will be utilized 
				for RTVBR and UBR.
				
				For AtmTrnkCr card valid value is cellRelayOnly. It implies
				100% BW is available for cellRelay and none for AAL5. All 
				cell relay traffic is RTVBR.
				
				For AtmTrnk card valid values are cellRelayOnly, cellRelayAndManagement,
				dataTerm, hybridLowAal5Data, hybridDefault and hybridHighAal5Data.
				All cell relay traffic is RTVBR and all AAL5 traffic is UBR.
				Out of total available BW on AtmTrnk card:
				for cellRelayOnly Cell Relay BW is 100% and AAL5 BW is 0%. 
				for cellRelayAndManagement Cell Relay BW is 95% and AAL5 BW is 5%.
				for dataTerm Cell Relay BW is 5% and AAL5 BW is 95%.
				for hybridLowAal5Data Cell Relay BW is 75% and AAL5 BW is 25%.
				for hybridDefault Cell Relay BW is 60% and AAL5 BW is 40%.
				for hybridHighAal5Data Cell Relay BW is 25% and AAL5 BW is 75%.
				
				For AtmAal25 card valid values are cellRelayOnly, cellRelayAndManagement,
				dataTerm, voiceGateway, hybridLowAal5Data, hybridDefault and 
				hybridHighAal5Data. All AAL5 traffic is UBR and AAL2/Cell Relay
				traffic can be RTVBR or UBR.
				Out of total available BW on AtmAal25 card:
				for cellRelayOnly AAL2/Cell Relay BW is 100% and AAL5 BW is 0%.
				50% of AAL2/Cell Relay BW is for RTVBR.
				for cellRelayAndManagement AAL2/Cell Relay BW is 95% and AAL5 BW is 5%.
				50% of AAL2/Cell Relay BW is for RTVBR.
				for dataTerm AAL2/Cell Relay BW is 5% and AAL5 BW is 95%.
				50% of AAL2/Cell Relay BW is for RTVBR.
				for voiceGateway AAL2/Cell Relay BW is 95% and AAL5 BW is 5%.
				95% of AAL2/Cell Relay BW is for RTVBR.
				for hybridLowAal5Data AAL2/Cell Relay BW is 75% and AAL5 BW is 25%.
				95% of AAL2/Cell Relay BW is for RTVBR.
				for hybridDefault AAL2/Cell Relay BW is 60% and AAL5 BW is 40%.
				75% of AAL2/Cell Relay BW is for RTVBR.
				for hybridHighAal5Data AAL2/Cell Relay BW is 25% and AAL5 BW is 75%.
				50% of AAL2/Cell Relay BW is for RTVBR.
				
				For malc uplink cards (t1/e1, t3/e3 ima), the following qos values 
				and its associated BW can be configured:
				
				qos name        ubr%     vbr%     vbrrt%
				
				vbnrt95rt5      0        95       5
				vbnrt80rt15     5        80       15
				vbnrt65rt30     5        65       30
				vbnrt50rt45     5        50       45
				vbnrt35rt60     5        35       60
				vbnrt20rt75     5        20       75
				vbnrt5rt95      5        5        95
				vbnrt5rt95cbr   5        5        95
				
				For all other cards valid value is notApplicable.
				This field cannot be updated after row creation.
				manual configuration is not supported in this
				release.
				"
			DEFVAL { notApplicable }
			::= { zhoneSysCardSoftwareConfigEntry 10 }

		
		-- 1.3.6.1.4.1.5504.3.1.10.1.11
		zhoneSysCardLineVoltage OBJECT-TYPE
			SYNTAX INTEGER
				{
				not-used(1),
				lv-60-volts(2),
				lv-68-volts(3),
				lv-95-volts(4),
				lv-100-volts(5),
				lv-110-volts(6)
				}
			MAX-ACCESS read-create
			STATUS current
			DESCRIPTION
				"Sepcifies the voltage supplied to all lines (ports) 
				of this card, Used on ISDN line cards."
			DEFVAL { not-used }
			::= { zhoneSysCardSoftwareConfigEntry 11 }

		
		-- 1.3.6.1.4.1.5504.3.1.10.1.12
		zhoneSysCardVpiVciRange OBJECT-TYPE
			SYNTAX INTEGER
				{
				not-applicable(1),
				vpi-15-vci-63(2),
				vpi-7-vci-127(3),
				vpi-15-vci-127(4)
				}
			MAX-ACCESS read-create
			STATUS current
			DESCRIPTION
				"The maximum vpi and vci values that may be used for 
				this card."
			DEFVAL { not-applicable }
			::= { zhoneSysCardSoftwareConfigEntry 12 }

		
-- 
		-- 1.3.6.1.4.1.5504.3.1.10.1.13
		zhoneSysCardInitString OBJECT-TYPE
			SYNTAX OCTET STRING (SIZE (0..256))
			MAX-ACCESS read-create
			STATUS current
			DESCRIPTION
				"Ascii string containing tokens separated by ',' or ' '
				which is used to configure special non-standard operations.
				This string is blank for normal operation."
			::= { zhoneSysCardSoftwareConfigEntry 13 }

		
		-- 1.3.6.1.4.1.5504.3.1.10.1.14
		zhoneSysCardWettingCurrent OBJECT-TYPE
			SYNTAX INTEGER
				{
				disabled(1),
				standard(2)
				}
			MAX-ACCESS read-create
			STATUS current
			DESCRIPTION
				"Sepcifies weather wetting current is disabled 
				or enabled(standard)."
			::= { zhoneSysCardSoftwareConfigEntry 14 }

		
		-- 1.3.6.1.4.1.5504.3.1.11
		zhoneCardRedundancy OBJECT IDENTIFIER ::= { zhoneSystem 11 }

		
		-- 1.3.6.1.4.1.5504.3.1.11.1
		nextCardRedundancyGroupId OBJECT-TYPE
			SYNTAX Integer32
			MAX-ACCESS read-only
			STATUS current
			DESCRIPTION
				"Returns the next unused card Redundancy Group Id."
			::= { zhoneCardRedundancy 1 }

		
		-- 1.3.6.1.4.1.5504.3.1.11.2
		zhoneSysCardRedundancyTable OBJECT-TYPE
			SYNTAX SEQUENCE OF ZhoneSysCardRedundancyEntry
			MAX-ACCESS not-accessible
			STATUS current
			DESCRIPTION
				"This table is used to group redundant cards and provide a mechanism 
				to indicate which card, if any, is preferred to be active.   
								
				A weight is assigned to each card to indicate a preference for which 
				card should be active.  In the absence of any preference (e.g., weights 
				for all cards are equal), then the card with the lowest shelf/slot 
				number will become active.
								
				Notes:
				(1) A row for this table cannot exist without a corresponding entry in
				the zhoneSysCardSoftwareConfigTable.   Thus, a row-create cannot occur
				on the this table until a corresponding row-create is performed on the
				zhoneSysCardSoftwareConfigTable.  When a row-delete is performed on
				the zhoneSysCardSoftwareConfigTable, that action automatically performs 
				a row delete on the relevant entry in this table.
				(2) Row deletes are disallowed on the zhoneCardRedundancy table.
				"
			::= { zhoneCardRedundancy 2 }

		
		-- 1.3.6.1.4.1.5504.3.1.11.2.1
		zhoneSysCardRedundancyEntry OBJECT-TYPE
			SYNTAX ZhoneSysCardRedundancyEntry
			MAX-ACCESS not-accessible
			STATUS current
			DESCRIPTION
				"An entry for a particular card."
			INDEX { zhoneSysCardRedundancyGroupId, zhoneShelfIndex, zhoneSlotIndex }
			::= { zhoneSysCardRedundancyTable 1 }

		
		ZhoneSysCardRedundancyEntry ::=
			SEQUENCE { 
				zhoneSysCardRedundancyGroupId
					Integer32,
				zhoneSysCardRedundancyWeight
					ZhoneRedundancyWeight,
				zhoneSysCardRedundancyHoldActive
					TruthValue,
				zhoneSysCardRedundancyOperStatus
					INTEGER,
				zhoneSysCardRedundancyRowStatus
					ZhoneRowStatus
			 }

-- 
-- 
		-- 1.3.6.1.4.1.5504.3.1.11.2.1.1
		zhoneSysCardRedundancyGroupId OBJECT-TYPE
			SYNTAX Integer32 (1..2147483647)
			MAX-ACCESS accessible-for-notify
			STATUS current
			DESCRIPTION
				"The unique redundancy group to which the card is assigned."
			::= { zhoneSysCardRedundancyEntry 1 }

		
-- 
-- 
		-- 1.3.6.1.4.1.5504.3.1.11.2.1.2
		zhoneSysCardRedundancyWeight OBJECT-TYPE
			SYNTAX ZhoneRedundancyWeight
			MAX-ACCESS read-create
			STATUS current
			DESCRIPTION
				"A weight given to this card in determining whether 
				this card should become Active on system boot.  
				"
			DEFVAL { noPreference }
			::= { zhoneSysCardRedundancyEntry 2 }

		
-- 
-- 
		-- 1.3.6.1.4.1.5504.3.1.11.2.1.3
		zhoneSysCardRedundancyHoldActive OBJECT-TYPE
			SYNTAX TruthValue
			MAX-ACCESS read-create
			STATUS current
			DESCRIPTION
				"When set to true, this indicates that the card, when 
				Active, should remain in the Active state regardless 
				of any system events.   This effectively disables 
				redundancy for the card group.
								
				Note the the holdActive attribute can be simultaneously
				set for multiple cards in the same redundancy group.
								
				Not supported in the initial release.
				"
			DEFVAL { false }
			::= { zhoneSysCardRedundancyEntry 3 }

		
		-- 1.3.6.1.4.1.5504.3.1.11.2.1.4
		zhoneSysCardRedundancyOperStatus OBJECT-TYPE
			SYNTAX INTEGER
				{
				noStatus(1),
				cardIsActive(2),
				cardIsStandby(3),
				cardIsNotRedundant(4),
				cardIsStandbyWithActiveLinks(5)
				}
			MAX-ACCESS read-only
			STATUS current
			DESCRIPTION
				"Indicates the status of the card.   Note that a noStatus value means
				that the  card is in a non-operational state, such as booting or fault."
			::= { zhoneSysCardRedundancyEntry 4 }

		
		-- 1.3.6.1.4.1.5504.3.1.11.2.1.5
		zhoneSysCardRedundancyRowStatus OBJECT-TYPE
			SYNTAX ZhoneRowStatus
			MAX-ACCESS read-create
			STATUS current
			DESCRIPTION
				"The row status used to create or delete an entry
				for card redundancy. No entries are required to 
				be included in a table create as all entries have
				default settings."
			::= { zhoneSysCardRedundancyEntry 5 }

		
		-- 1.3.6.1.4.1.5504.3.1.12
		zhoneSntpConfiguration OBJECT-IDENTITY
			STATUS current
			DESCRIPTION 
				"Configuration of parameters for SNTP.  The SLMS node will act as
				an SNTP Client and synchronize the time and date from the network
				as specified in this table.
				
				This table has one entry, which is automatically generated by 
				the system at boot time."
			::= { zhoneSystem 12 }

		
		-- 1.3.6.1.4.1.5504.3.1.12.1
		zhoneSntpPrimaryServerIpAddr OBJECT-TYPE
			SYNTAX IpAddress
			MAX-ACCESS read-write
			STATUS current
			DESCRIPTION
				"The IP address of the Primary NTP Server from which the date/time
				will be synchronized."
			::= { zhoneSntpConfiguration 1 }

		
		-- 1.3.6.1.4.1.5504.3.1.12.2
		zhoneSntpSecondaryServerIpAddr OBJECT-TYPE
			SYNTAX IpAddress
			MAX-ACCESS read-write
			STATUS current
			DESCRIPTION
				"The IP address of the Secondary NTP Server from which the date/time
				will be synchronized.  Whenever the Primary NTP Server is not available,
				the Secondary NTP Server will be used."
			::= { zhoneSntpConfiguration 2 }

		
		-- 1.3.6.1.4.1.5504.3.1.12.3
		zhoneSntpLocalTimeZone OBJECT-TYPE
			SYNTAX ZhoneLocalTimeZone
			MAX-ACCESS read-write
			STATUS current
			DESCRIPTION
				"Indicates the local time zone."
			DEFVAL { 14 }
			::= { zhoneSntpConfiguration 3 }

		
		-- 1.3.6.1.4.1.5504.3.1.12.4
		zhoneSntpDaylightSavingTime OBJECT-TYPE
			SYNTAX TruthValue
			MAX-ACCESS read-write
			STATUS current
			DESCRIPTION
				"Indicates whether Daylight Savings time is currently in affect."
			DEFVAL { false }
			::= { zhoneSntpConfiguration 4 }

		
		-- 1.3.6.1.4.1.5504.3.1.12.5
		zhoneSntpDaylightSavingStart OBJECT-TYPE
			SYNTAX OCTET STRING (SIZE (0..11))
			UNITS "characters"
			MAX-ACCESS read-write
			STATUS current
			DESCRIPTION
				"Indicates the daylight savings start time. The start time should be of the
				format mm:dd:hh:mm"
			::= { zhoneSntpConfiguration 5 }

		
		-- 1.3.6.1.4.1.5504.3.1.12.6
		zhoneSntpDaylightSavingEnd OBJECT-TYPE
			SYNTAX OCTET STRING (SIZE (0..11))
			UNITS "characters"
			MAX-ACCESS read-write
			STATUS current
			DESCRIPTION
				"Indicates the daylight savings end time. The start time should be of the fo
				rmat mm:dd:hh:mm"
			::= { zhoneSntpConfiguration 6 }

		
		-- 1.3.6.1.4.1.5504.3.1.13
		zhoneAdslPotsBypassRelay OBJECT-IDENTITY
			STATUS current
			DESCRIPTION 
				"The objects contained in this ojbect identity are scalar
				objects used for provisioning and viewing the Adsl Pots 
				LPF Bypass Relays."
			::= { zhoneSystem 13 }

		
		-- 1.3.6.1.4.1.5504.3.1.13.1
		zhoneAdslPotsMaxActiveBypassRelays OBJECT-TYPE
			SYNTAX Integer32 (1..32)
			MAX-ACCESS read-only
			STATUS current
			DESCRIPTION
				"Maximum number of Adsl Pots LPF Bypass Relays that
				can be active on any one card at any given time.  This number
				is determined by the device and is calculated based upon
				power consumption of the relays.
				
				For example, if this value is set to 8, each Adsl Pots Splitter
				w/Bypass Relay card can have 8 relays set to closed at any given
				time.		
				
				This object is only valid for Adsl Pots Splitter
				cards containing the Pots LBF Relays."
			::= { zhoneAdslPotsBypassRelay 1 }

		
		-- 1.3.6.1.4.1.5504.3.1.13.2
		zhoneAdslPotsBypassRelayResetAll  OBJECT-TYPE
			SYNTAX INTEGER
				{
				unchanged(1),
				reset(2)
				}
			MAX-ACCESS read-write
			STATUS current
			DESCRIPTION
				"Enables the operator to force all Pots Bypass Relays
				in the system back to a normal state.
				
				This object is only valid for Adsl Pots Splitter
				cards containing the Bypass Relays."
			::= { zhoneAdslPotsBypassRelay 2 }

		
		-- 1.3.6.1.4.1.5504.3.1.14
		zhoneBulkStatsSystemConfiguration OBJECT-IDENTITY
			STATUS current
			DESCRIPTION 
				"System wide configuration of bulk statistics, including ftp parameters
				and enabling/disabling bulk statistics collection for the system.
				"
			::= { zhoneSystem 14 }

		
		-- 1.3.6.1.4.1.5504.3.1.14.1
		zhoneBulkStatsSystemCollectionEnabled OBJECT-TYPE
			SYNTAX TruthValue
			MAX-ACCESS read-write
			STATUS current
			DESCRIPTION
				"Indicates whether bulk stats collection has been enabled for the 
				system.  If false,  no collection is done.  If true, the system
				will collect the stats identified in the zhoneBulkStatCollectionTable."
			DEFVAL { false }
			::= { zhoneBulkStatsSystemConfiguration 1 }

		
		-- 1.3.6.1.4.1.5504.3.1.14.2
		zhoneBulkStatsSystemFtpAddress OBJECT-TYPE
			SYNTAX IpAddress
			MAX-ACCESS read-write
			STATUS current
			DESCRIPTION
				"The IP address of the FTP Server to which the collected stats will
				be sent."
			::= { zhoneBulkStatsSystemConfiguration 2 }

		
		-- 1.3.6.1.4.1.5504.3.1.14.3
		zhoneBulkStatsSystemFtpLogin OBJECT-TYPE
			SYNTAX ZhoneAdminString
			MAX-ACCESS read-write
			STATUS current
			DESCRIPTION
				"The FTP login name to be used for initiating the FTP file transfer 
				of the collected bulk statistics."
			::= { zhoneBulkStatsSystemConfiguration 3 }

		
		-- 1.3.6.1.4.1.5504.3.1.14.4
		zhoneBulkStatsSystemFtpPassword OBJECT-TYPE
			SYNTAX ZhoneAdminString
			MAX-ACCESS read-write
			STATUS current
			DESCRIPTION
				"The FTP password to be used for initiating the FTP file transfer 
				of the collected bulk statistics."
			::= { zhoneBulkStatsSystemConfiguration 4 }

		
		-- 1.3.6.1.4.1.5504.3.1.14.5
		zhoneBulkStatsSystemFtpDirPath OBJECT-TYPE
			SYNTAX ZhoneFileName
			MAX-ACCESS read-write
			STATUS current
			DESCRIPTION
				"This specifies the directory path on the FTP server into which the 
				bulk statistics files will be transferred.   
				
				The device will use this in a cd command, therefore a trailing '/'
				is not required.
				
				The ftp filename is constructed as follows:
				    <device-ip>_<timestamp>   
				           where timestamp is YYYY.DD.MM.HH.MM in device local time.
				For example:
				    172.16.80.291_2002.11.06.14.37
				
				"
			::= { zhoneBulkStatsSystemConfiguration 5 }

		
		-- 1.3.6.1.4.1.5504.3.1.14.6
		zhoneBulkStatsSystemOperStatus OBJECT-TYPE
			SYNTAX INTEGER
				{
				collectionInProgress(1),
				collectionComplete(2),
				collectionPeriodOverrun(3),
				collectionAbortedNoDiskSpace(4),
				collectionAbortedFileIoFailure(5),
				collectionCompleteFtpFailure(6)
				}
			MAX-ACCESS read-only
			STATUS current
			DESCRIPTION
				"The operational status of the current collection interval.
				Valid values are:
				
				collectionInProgress:
				  - Collection for the current interval has started
				collectionComplete:
				  - Collection for the current interval has completed, and the resulting 
				    file has been transferred via ftp to the specified host.
				collectionPeriodOverrun:
				  - Collection for the previous interval has not completed prior to the 
				    start of the current collection interval.   In this case, the collection
				    for the previous interval continues and the current interval is skipped.
				    This is an indication that either the system/network is too busy and/or
				    there are too many statistics being collected.
				collectionAbortedNoDiskSpace:
				  - Collection for the current interval has been aborted due to insufficient
				    disk space on the device.   The current interval is skipped.
				collectionAbortedFileIoFailure:
				  - Collection for the current interval has been aborted due to a file IO
				    (write) error on the device.   The current interval is skipped.
				collectionCompleteFtpFailure:
				  - Collection for the current interval has completed, but the resulting 
				    file could not be transferred via ftp to the specified host.  The file
				    is queued for retry.
				
				
				The operStatus is only pertinent if bulk stats have been enabled."
			::= { zhoneBulkStatsSystemConfiguration 6 }

		
		-- 1.3.6.1.4.1.5504.3.1.15
		zhoneBulkStatCollection OBJECT IDENTIFIER ::= { zhoneSystem 15 }

		
		-- 1.3.6.1.4.1.5504.3.1.15.1
		nextBulkStatCollectionId OBJECT-TYPE
			SYNTAX Integer32
			MAX-ACCESS read-only
			STATUS current
			DESCRIPTION
				"Returns the next unused bulk statistics collection id."
			::= { zhoneBulkStatCollection 1 }

		
		-- 1.3.6.1.4.1.5504.3.1.15.2
		zhoneBulkStatCollectionTable OBJECT-TYPE
			SYNTAX SEQUENCE OF ZhoneBulkStatCollectionEntry
			MAX-ACCESS not-accessible
			STATUS current
			DESCRIPTION
				"This table is used to identify the statistics to be collected in bulk.
				Each row in the table represents a statistic to be collected."
			::= { zhoneBulkStatCollection 2 }

		
		-- 1.3.6.1.4.1.5504.3.1.15.2.1
		zhoneBulkStatCollectionEntry OBJECT-TYPE
			SYNTAX ZhoneBulkStatCollectionEntry
			MAX-ACCESS not-accessible
			STATUS current
			DESCRIPTION
				"Defines an entry in the zhoneBulkStatCollectionTable."
			INDEX { zhoneBulkStatCollectionId }
			::= { zhoneBulkStatCollectionTable 1 }

		
		ZhoneBulkStatCollectionEntry ::=
			SEQUENCE { 
				zhoneBulkStatCollectionId
					Integer32,
				zhoneBulkStatEnabled
					TruthValue,
				zhoneBulkStatOID
					OCTET STRING,
				zhoneBulkStatInstance
					ZhoneAdminString,
				zhoneBulkStatIncludeChildren
					TruthValue,
				zhoneBulkStatsCollectionInterval
					Integer32,
				zhoneBulkStatCollectionRowStatus
					ZhoneRowStatus
			 }

		-- 1.3.6.1.4.1.5504.3.1.15.2.1.1
		zhoneBulkStatCollectionId OBJECT-TYPE
			SYNTAX Integer32 (1..32767)
			MAX-ACCESS not-accessible
			STATUS current
			DESCRIPTION
				"Unique identifier of the bulk statistic row."
			::= { zhoneBulkStatCollectionEntry 1 }

		
		-- 1.3.6.1.4.1.5504.3.1.15.2.1.2
		zhoneBulkStatEnabled OBJECT-TYPE
			SYNTAX TruthValue
			MAX-ACCESS read-create
			STATUS current
			DESCRIPTION
				"Indicate whether collection in enabled for this statistic."
			DEFVAL { true }
			::= { zhoneBulkStatCollectionEntry 2 }

		
		-- 1.3.6.1.4.1.5504.3.1.15.2.1.3
		zhoneBulkStatOID OBJECT-TYPE
			SYNTAX OCTET STRING
			MAX-ACCESS read-create
			STATUS current
			DESCRIPTION
				"The OID of the statistic to be collected in bulk."
			::= { zhoneBulkStatCollectionEntry 3 }

		
		-- 1.3.6.1.4.1.5504.3.1.15.2.1.4
		zhoneBulkStatInstance OBJECT-TYPE
			SYNTAX ZhoneAdminString
			MAX-ACCESS read-write
			STATUS current
			DESCRIPTION
				"The Instance value for the zhoneBulkStatOID."
			::= { zhoneBulkStatCollectionEntry 4 }

		
		-- 1.3.6.1.4.1.5504.3.1.15.2.1.5
		zhoneBulkStatIncludeChildren OBJECT-TYPE
			SYNTAX TruthValue
			MAX-ACCESS read-create
			STATUS current
			DESCRIPTION
				"Indicates whether the statistic collection should include children.
				
				Using the zhoneAtmStatsExtTable (presently with 8 statistics in the table)
				as example, one could enable all stats for all 8 stats with one row entry
				by setting the includeChildren flag.  The zhoneBulkStatOID leaf would 
				contain the OID of zhoneAtmStatsExtEntry, the zhoneBulkStatInstance leaf
				would identify the specific VCL, and this leaf would be set to TRUE."
			DEFVAL { false }
			::= { zhoneBulkStatCollectionEntry 5 }

		
		-- 1.3.6.1.4.1.5504.3.1.15.2.1.6
		zhoneBulkStatsCollectionInterval OBJECT-TYPE
			SYNTAX Integer32
			MAX-ACCESS read-create
			STATUS current
			DESCRIPTION
				"The collection interval for this statistic. 
				Initially, all statistics will be collected on 15 minute intervals,
				and sets to this object are not supported."
			DEFVAL { 15 }
			::= { zhoneBulkStatCollectionEntry 6 }

		
		-- 1.3.6.1.4.1.5504.3.1.15.2.1.7
		zhoneBulkStatCollectionRowStatus OBJECT-TYPE
			SYNTAX ZhoneRowStatus
			MAX-ACCESS read-create
			STATUS current
			DESCRIPTION
				"The row status is used to create or delete an entry in this table."
			::= { zhoneBulkStatCollectionEntry 7 }

		
		-- 1.3.6.1.4.1.5504.3.1.16
		zhoneVideoSystemConfiguration OBJECT-IDENTITY
			STATUS current
			DESCRIPTION 
				"Configuration information for the MALC video 
				Head-End Server configuration.  Managing the
				Head-End configuration requires provisioning
				the MALC with IP information as to the 
				various server addresses."
			::= { zhoneSystem 16 }

		
		-- 1.3.6.1.4.1.5504.3.1.16.1
		zhoneVideoSystemConfigurationIndexNext OBJECT-TYPE
			SYNTAX Integer32 (1..65535)
			MAX-ACCESS read-only
			STATUS current
			DESCRIPTION
				"This object contains an appropriate value to be used 
				for zhoneVideoSystemConfigurationIndex when creating 
				entries in the zhoneVideoSystemConfigurationTable.  The
				value 0 indicates that no unassigned entries are
				available. To obtain the zhoneVideoSystemConfigurationIndex 
				value for a new entry, the manager issues a management
				protocol retrieval operation to obtain the current value
				of this object.  After each retrieval, the agent should
				modify the value to the next unassigned index.
				
				After a manager retrieves a value the agent will
				determine through its local policy when this index
				value will be made available for reuse."
			::= { zhoneVideoSystemConfiguration 1 }

		
		-- 1.3.6.1.4.1.5504.3.1.16.2
		zhoneVideoSystemConfigurationTable OBJECT-TYPE
			SYNTAX SEQUENCE OF ZhoneVideoSystemConfigurationEntry
			MAX-ACCESS not-accessible
			STATUS current
			DESCRIPTION
				"This table is used to identify and manage the Head-End Video Servers.
				Each row in the table represents a Head-End Server."
			::= { zhoneVideoSystemConfiguration 2 }

		
		-- 1.3.6.1.4.1.5504.3.1.16.2.1
		zhoneVideoSystemConfigurationEntry OBJECT-TYPE
			SYNTAX ZhoneVideoSystemConfigurationEntry
			MAX-ACCESS not-accessible
			STATUS current
			DESCRIPTION
				"Defines an entry in the Video System Configuration table."
			INDEX { zhoneVideoSystemConfigurationIndex }
			::= { zhoneVideoSystemConfigurationTable 1 }

		
		ZhoneVideoSystemConfigurationEntry ::=
			SEQUENCE { 
				zhoneVideoSystemConfigurationIndex
					Integer32,
				zhoneVideoSystemConfigurationNtpServerAddress
					IpAddress,
				zhoneVideoSystemConfigurationEpgServerAddress
					IpAddress,
				zhoneVideoSystemConfigurationSettopBoxHeadEndServerAddress
					IpAddress,
				zhoneVideoSystemConfigurationDefaultChannelAddress
					IpAddress,
				zhoneVideoSystemConfigurationNoChannelAvailableAddress
					IpAddress,
				zhoneVideoSystemConfigurationRowStatus
					ZhoneRowStatus,
				zhoneVideoSystemConfigurationEpgType
					INTEGER,
				zhoneVideoSystemConfigurationEpgPort
					Unsigned32,
				zhoneVideoSystemConfigurationEpgFtpAddress
					IpAddress
			 }

		-- 1.3.6.1.4.1.5504.3.1.16.2.1.1
		zhoneVideoSystemConfigurationIndex OBJECT-TYPE
			SYNTAX Integer32 (1..65535)
			MAX-ACCESS not-accessible
			STATUS current
			DESCRIPTION
				"A unique value to identify this video system profile entry."
			::= { zhoneVideoSystemConfigurationEntry 1 }

		
		-- 1.3.6.1.4.1.5504.3.1.16.2.1.2
		zhoneVideoSystemConfigurationNtpServerAddress OBJECT-TYPE
			SYNTAX IpAddress
			MAX-ACCESS read-create
			STATUS current
			DESCRIPTION
				"This oid contains the IP address of the NTP Server
				for a particular Head-End."
			::= { zhoneVideoSystemConfigurationEntry 2 }

		
		-- 1.3.6.1.4.1.5504.3.1.16.2.1.3
		zhoneVideoSystemConfigurationEpgServerAddress OBJECT-TYPE
			SYNTAX IpAddress
			MAX-ACCESS read-create
			STATUS current
			DESCRIPTION
				"This oid contains the IP adress of the EPG 
				(Electronic Programming Guide) for a particular 
				Head-End."
			::= { zhoneVideoSystemConfigurationEntry 3 }

		
		-- 1.3.6.1.4.1.5504.3.1.16.2.1.4
		zhoneVideoSystemConfigurationSettopBoxHeadEndServerAddress OBJECT-TYPE
			SYNTAX IpAddress
			MAX-ACCESS read-create
			STATUS current
			DESCRIPTION
				"This oid contains the IP address of the set-top
				box head-end server."
			::= { zhoneVideoSystemConfigurationEntry 4 }

		
		-- 1.3.6.1.4.1.5504.3.1.16.2.1.5
		zhoneVideoSystemConfigurationDefaultChannelAddress OBJECT-TYPE
			SYNTAX IpAddress
			MAX-ACCESS read-create
			STATUS current
			DESCRIPTION
				"his oid contains the multicast IP address of the channel
				chosen to be the default channel for a particular head-
				end provider."
			::= { zhoneVideoSystemConfigurationEntry 5 }

		
		-- 1.3.6.1.4.1.5504.3.1.16.2.1.6
		zhoneVideoSystemConfigurationNoChannelAvailableAddress OBJECT-TYPE
			SYNTAX IpAddress
			MAX-ACCESS read-create
			STATUS current
			DESCRIPTION
				"This oid contains the multicast address of the channel 
				appropriate to display when a user selects a channel 
				that is not available or not in his channel profile."
			::= { zhoneVideoSystemConfigurationEntry 6 }

		
		-- 1.3.6.1.4.1.5504.3.1.16.2.1.7
		zhoneVideoSystemConfigurationRowStatus OBJECT-TYPE
			SYNTAX ZhoneRowStatus
			MAX-ACCESS read-create
			STATUS current
			DESCRIPTION
				"zhoneVideoSystemConfigurationRowStatus 
				is used to create/delete an entry in the 
				zhoneVideoSystemConfigurationTable."
			::= { zhoneVideoSystemConfigurationEntry 7 }

		
		-- 1.3.6.1.4.1.5504.3.1.16.2.1.8
		zhoneVideoSystemConfigurationEpgType OBJECT-TYPE
			SYNTAX INTEGER
				{
				minerva(1),
				myrio(2)
				}
			MAX-ACCESS read-write
			STATUS current
			DESCRIPTION
				"Indicates the type of EPG that we are talking to. Currently only
				Minerva, and Myrio are envisioned."
			::= { zhoneVideoSystemConfigurationEntry 8 }

		
		-- 1.3.6.1.4.1.5504.3.1.16.2.1.9
		zhoneVideoSystemConfigurationEpgPort OBJECT-TYPE
			SYNTAX Unsigned32
			MAX-ACCESS read-write
			STATUS current
			DESCRIPTION
				"This oid contains the port number to use when talking with the EPG."
			::= { zhoneVideoSystemConfigurationEntry 9 }

		
		-- 1.3.6.1.4.1.5504.3.1.16.2.1.10
		zhoneVideoSystemConfigurationEpgFtpAddress OBJECT-TYPE
			SYNTAX IpAddress
			MAX-ACCESS read-write
			STATUS current
			DESCRIPTION
				"This oid is the IP address to use when FTP data to/from the EPP server."
			::= { zhoneVideoSystemConfigurationEntry 10 }

		
		-- 1.3.6.1.4.1.5504.3.1.17
		zhoneCallDetailRecConfig OBJECT-IDENTITY
			STATUS current
			DESCRIPTION 
				"System wide configuration of the Call Detail Recording."
			::= { zhoneSystem 17 }

		
		-- 1.3.6.1.4.1.5504.3.1.17.1
		zhoneCallDetailRecEnabled OBJECT-TYPE
			SYNTAX TruthValue
			MAX-ACCESS read-write
			STATUS current
			DESCRIPTION
				"Indicates whether CDR is enabled for this device. If false, the 
				CDR is disabled. If true, the CDR is enabled, each call is 
				recorded and a report is sent periodically to the most 
				preferable and active ftp server."
			DEFVAL { false }
			::= { zhoneCallDetailRecConfig 1 }

		
		-- 1.3.6.1.4.1.5504.3.1.17.2
		zhoneCallDetailRecFlushLog OBJECT-TYPE
			SYNTAX TruthValue
			MAX-ACCESS read-write
			STATUS current
			DESCRIPTION
				"If true, indicates the device to upload all pending call records
				and empty the CDR log. After the uploading is completed the flag 
				is automatically set to false. In case of failure, the flag is 
				also set to false but the OperStatus indicates an error."
			DEFVAL { false }
			::= { zhoneCallDetailRecConfig 2 }

		
		-- 1.3.6.1.4.1.5504.3.1.17.3
		zhoneCallDetailRecCurrFtpServer OBJECT-TYPE
			SYNTAX INTEGER
				{
				primary(1),
				secondary(2),
				none(3)
				}
			MAX-ACCESS read-only
			STATUS current
			DESCRIPTION
				"Currently active FTP server. In case all FTP servers are not 
				available the none(3) value is assigned. "
			DEFVAL { none }
			::= { zhoneCallDetailRecConfig 3 }

		
		-- 1.3.6.1.4.1.5504.3.1.17.4
		zhoneCallDetailRecPrimFtpIpAddr OBJECT-TYPE
			SYNTAX IpAddress
			MAX-ACCESS read-write
			STATUS current
			DESCRIPTION
				"IP address of the primary FTP server. If configured and available,
				it becomes the most preferable FTP server."
			::= { zhoneCallDetailRecConfig 4 }

		
		-- 1.3.6.1.4.1.5504.3.1.17.5
		zhoneCallDetailRecSecFtpIpAddr OBJECT-TYPE
			SYNTAX IpAddress
			MAX-ACCESS read-write
			STATUS current
			DESCRIPTION
				"IP address of the secondary FTP server. This server is automatically
				selected when the primary FTP server is not configured or unavailable.
				The device will probe the primary FTP server and return to it 
				automatically once it becomes available. "
			::= { zhoneCallDetailRecConfig 5 }

		
		-- 1.3.6.1.4.1.5504.3.1.17.6
		zhoneCallDetailRecFtpLogin OBJECT-TYPE
			SYNTAX ZhoneAdminString
			MAX-ACCESS read-write
			STATUS current
			DESCRIPTION
				"The FTP login name to be used by the device for initiating the 
				transfer."
			::= { zhoneCallDetailRecConfig 6 }

		
		-- 1.3.6.1.4.1.5504.3.1.17.7
		zhoneCallDetailRecFtpPassword OBJECT-TYPE
			SYNTAX ZhoneAdminString
			MAX-ACCESS read-write
			STATUS current
			DESCRIPTION
				"The FTP password to be used by the device during login to the 
				FTP server."
			::= { zhoneCallDetailRecConfig 7 }

		
		-- 1.3.6.1.4.1.5504.3.1.17.8
		zhoneCallDetailRecFtpDirPath OBJECT-TYPE
			SYNTAX ZhoneFileName
			MAX-ACCESS read-write
			STATUS current
			DESCRIPTION
				"The directory path on the FTP server where a file with CDR records 
				is to be stored. The trailing '/' is not required.
				Within this directory, each device will have its subdirectory. 
				The device subdirectory name is constructed from the device IP 
				address as follows: '172-16-80-224'. The device subdirectory 
				is created remotely from the device by using the FTP protocol. 
				All call records from a device are stored in text files. All file
				names for a single device are unique and constructed as follows:
				YYYY-MM-DD-HH-MM-SN, where:
				YYYY - year
				MM   - month
				DD   - day
				HH   - hour
				MM   - minute
				SN   - sequence number in case two subsequent raports are 
				       generated within the same minute."
			::= { zhoneCallDetailRecConfig 8 }

		
		-- 1.3.6.1.4.1.5504.3.1.17.9
		zhoneCallDetailRecRepPeriod OBJECT-TYPE
			SYNTAX Integer32 (1..60)
			MAX-ACCESS read-write
			STATUS current
			DESCRIPTION
				"This specifies the device reporting period in minutes. During this
				period a device is collecting CDR records and when this period 
				elapses it triggers automatic uploading to the active FTP server. 
				After successful transfer the CDR log is pruned.
				When the CDR log reaches its 'high water mark' before the end of 
				the current reporting period, the transfer takes place immediately, 
				then a new reporting period is commenced."
			DEFVAL { 30 }
			::= { zhoneCallDetailRecConfig 9 }

		
		-- 1.3.6.1.4.1.5504.3.1.17.10
		zhoneCallDetailRecOperStatus OBJECT-TYPE
			SYNTAX INTEGER
				{
				active(1),
				ftpFailure(2),
				overrun(3),
				noConfig(4)
				}
			MAX-ACCESS read-only
			STATUS current
			DESCRIPTION
				"CDR Operational Status:
				active     - CDR is enabled and working OK.
				ftpFailure - CDR cannot upload log due to lack of available FTP server.
				overrun    - In result of FTP failure, CDR discards the oldest records.
				noConfig   - CDR is disabled due to lack of correct configuration."
			::= { zhoneCallDetailRecConfig 10 }

		
		-- 1.3.6.1.4.1.5504.3.1.19
		zhoneSoftwareUpgrade OBJECT-IDENTITY
			STATUS current
			DESCRIPTION 
				"Used to upgrade device software during hitless upgrade."
			::= { zhoneSystem 19 }

		
		-- 1.3.6.1.4.1.5504.3.1.19.1
		zhoneSoftwareUpgradeAction OBJECT-TYPE
			SYNTAX INTEGER
				{
				sw-upgrade(1),
				sw-upgrade-auto-swact(2),
				swact(3),
				swact-abort(4)
				}
			MAX-ACCESS read-write
			STATUS current
			DESCRIPTION
				"Describes which software upgrade action to perform."
			::= { zhoneSoftwareUpgrade 1 }

		
		-- 1.3.6.1.4.1.5504.3.1.19.2
		zhoneSoftwareUpgradeStatus OBJECT-TYPE
			SYNTAX INTEGER
				{
				not-started(1),
				standby-upgrade-started(2),
				standby-upgrade-completed(3),
				standby-upgrade-aborted(4),
				swact-started(5),
				swact-complete(6),
				swact-aborted(7)
				}
			MAX-ACCESS read-only
			STATUS current
			DESCRIPTION
				"Describes status of software upgrade."
			DEFVAL { not-started }
			::= { zhoneSoftwareUpgrade 2 }

		
		-- 1.3.6.1.4.1.5504.3.1.19.3
		zhoneSoftwareUpgradeTimeStarted OBJECT-TYPE
			SYNTAX DateAndTime
			MAX-ACCESS read-only
			STATUS current
			DESCRIPTION
				"Time software upgrade started."
			::= { zhoneSoftwareUpgrade 3 }

		
		-- 1.3.6.1.4.1.5504.3.1.19.4
		zhoneSoftwareUpgradeTimeCompleted OBJECT-TYPE
			SYNTAX DateAndTime
			MAX-ACCESS read-only
			STATUS current
			DESCRIPTION
				"Time software upgrade completed."
			::= { zhoneSoftwareUpgrade 4 }

		
		-- 1.3.6.1.4.1.5504.3.1.20
		zhoneFileSystem OBJECT-IDENTITY
			STATUS current
			DESCRIPTION 
				"Represents SNMP view of Zhone File System available from
				Zhone Command Line Interface."
			::= { zhoneSystem 20 }

		
		-- 1.3.6.1.4.1.5504.3.1.20.1
		zhoneFileAction OBJECT-TYPE
			SYNTAX INTEGER
				{
				cd(1),
				dir(2),
				copy(3),
				rm(4),
				mkdir(5),
				rmdir(6),
				mv(7)
				}
			MAX-ACCESS read-write
			STATUS current
			DESCRIPTION
				"File Action:
				
				cd(1)    - change directory command used in conjunction with
				           zhoneDirectory location which specifies destination
				           directory.
				dir(2)   - listing of files within the directory specified
				           by zhoneDirectoryPath.  The generated file
				           listing is written to zhoneFileTable.
				copy(3)  - make a copy zhoneFileName1 and writes it to
				           zhoneFileName2.  User should prepend pathname to 
				           both filenames if not in default directory.
				rm(4)    - removes file specified by zhoneFileName1.
				mkdir(5) - creates a subdirectory specified by
				           zhoneFileName1.
				rmdir(6) - removes directory specified by zhoneFileName1.
				           If directory not empty, returns error.
				mv(7)    - moves zhoneFileName1 to zhoneFileName2."
			::= { zhoneFileSystem 1 }

		
		-- 1.3.6.1.4.1.5504.3.1.20.2
		zhoneFileName1 OBJECT-TYPE
			SYNTAX ZhoneFileName
			MAX-ACCESS read-write
			STATUS current
			DESCRIPTION
				"Used when zhoneFileAction set to 'copy'.  This will be the
				source filename of the file to be copied.  Prepend a new path
				if you want to specify a file in a directory different from
				your current directory."
			::= { zhoneFileSystem 2 }

		
		-- 1.3.6.1.4.1.5504.3.1.20.3
		zhoneFileName2 OBJECT-TYPE
			SYNTAX ZhoneFileName
			MAX-ACCESS read-write
			STATUS current
			DESCRIPTION
				"Used when zhoneFileAction set to 'copy'.  This will be the
				resulting filename of the copied file.  Prepend a new path
				if you want file to be written to a different directory,
				otherwise it will be written to same directory."
			::= { zhoneFileSystem 3 }

		
		-- 1.3.6.1.4.1.5504.3.1.20.4
		zhoneDirectoryPath OBJECT-TYPE
			SYNTAX ZhoneFileName
			MAX-ACCESS read-write
			STATUS current
			DESCRIPTION
				"This is a read-write object.  If read, it returns your current
				directory location.  If written, it can be used by the 'cd'
				change directory command in order to specify the new 
				directory, or by the 'dir' command to specify which directory
				from which to list files.
				
				NOTE: If it is written and a 'cd' or 'dir' command not
				performed, the next time it is read, it will return your
				current directory."
			::= { zhoneFileSystem 4 }

		
		-- 1.3.6.1.4.1.5504.3.1.20.5
		zhoneDirectoryBytesAvailable OBJECT-TYPE
			SYNTAX Unsigned32
			MAX-ACCESS read-only
			STATUS current
			DESCRIPTION
				"Total number of bytes available on the disk."
			::= { zhoneFileSystem 5 }

		
		-- 1.3.6.1.4.1.5504.3.1.20.6
		zhoneBytesReservedForProvisioning OBJECT-TYPE
			SYNTAX Unsigned32
			MAX-ACCESS read-only
			STATUS current
			DESCRIPTION
				"When in the 'datastor' directory, this object returns
				the number of bytes reserved for Zhone Provisioning.
				These are the number of bytes reserved for the
				database expansion."
			::= { zhoneFileSystem 6 }

		
		-- 1.3.6.1.4.1.5504.3.1.20.7
		zhoneFileTable OBJECT-TYPE
			SYNTAX SEQUENCE OF ZhoneFileEntry
			MAX-ACCESS not-accessible
			STATUS current
			DESCRIPTION
				"Zhone File Listing Table.
				
				Used to view file information for files resident
				on Zhone Flash Memory Devices."
			::= { zhoneFileSystem 7 }

		
		-- 1.3.6.1.4.1.5504.3.1.20.7.1
		zhoneFileEntry OBJECT-TYPE
			SYNTAX ZhoneFileEntry
			MAX-ACCESS not-accessible
			STATUS current
			DESCRIPTION
				"Zhone File Listing Entry.
				
				Used to view file information for files resident
				on Zhone Flash Memory Devices."
			INDEX { zhoneFileIndex }
			::= { zhoneFileTable 1 }

		
		ZhoneFileEntry ::=
			SEQUENCE { 
				zhoneFileIndex
					Integer32,
				zhoneFileDirectoryPath
					ZhoneFileName,
				zhoneFileName
					ZhoneFileName,
				zhoneFilePrivilege
					OCTET STRING,
				zhoneFileSize
					Unsigned32,
				zhoneFileLastModified
					DateAndTime
			 }

		-- 1.3.6.1.4.1.5504.3.1.20.7.1.1
		zhoneFileIndex OBJECT-TYPE
			SYNTAX Integer32 (1..32767)
			MAX-ACCESS not-accessible
			STATUS current
			DESCRIPTION
				"Index values of rows in this table.  Positive ascending
				numbers starting at 1."
			::= { zhoneFileEntry 1 }

		
		-- 1.3.6.1.4.1.5504.3.1.20.7.1.2
		zhoneFileDirectoryPath OBJECT-TYPE
			SYNTAX ZhoneFileName
			MAX-ACCESS read-only
			STATUS current
			DESCRIPTION
				"Directory path of file."
			::= { zhoneFileEntry 2 }

		
		-- 1.3.6.1.4.1.5504.3.1.20.7.1.3
		zhoneFileName OBJECT-TYPE
			SYNTAX ZhoneFileName
			MAX-ACCESS read-only
			STATUS current
			DESCRIPTION
				"Filename."
			::= { zhoneFileEntry 3 }

		
		-- 1.3.6.1.4.1.5504.3.1.20.7.1.4
		zhoneFilePrivilege OBJECT-TYPE
			SYNTAX OCTET STRING (SIZE (10))
			MAX-ACCESS read-only
			STATUS current
			DESCRIPTION
				"File privileges."
			::= { zhoneFileEntry 4 }

		
		-- 1.3.6.1.4.1.5504.3.1.20.7.1.5
		zhoneFileSize OBJECT-TYPE
			SYNTAX Unsigned32
			MAX-ACCESS read-only
			STATUS current
			DESCRIPTION
				"File size in bytes."
			::= { zhoneFileEntry 5 }

		
		-- 1.3.6.1.4.1.5504.3.1.20.7.1.6
		zhoneFileLastModified OBJECT-TYPE
			SYNTAX DateAndTime
			MAX-ACCESS read-only
			STATUS current
			DESCRIPTION
				"Date and time file last modified."
			::= { zhoneFileEntry 6 }

		
		-- 1.3.6.1.4.1.5504.3.1.21
		cpeMgr OBJECT-IDENTITY
			STATUS current
			DESCRIPTION 
				"Access, control and runtime details for managing CPEs connected
				to Zhone CO devices.  Some of these objects will reside on
				CO devices, while others will reside on CPEs supporting CPE
				Manager controls. "
			::= { zhoneSystem 21 }

		
		-- 1.3.6.1.4.1.5504.3.1.22
		zhoneEnhancedStatus OBJECT-IDENTITY
			STATUS current
			DESCRIPTION 
				"Object Identity for Zhone Enhanced Status."
			::= { zhoneSystem 22 }

		
		-- 1.3.6.1.4.1.5504.3.1.22.1
		zhoneEnhancedStatusTable OBJECT-TYPE
			SYNTAX SEQUENCE OF ZhoneEnhancedStatusEntry
			MAX-ACCESS not-accessible
			STATUS current
			DESCRIPTION
				"Table of Zhone Enhanced Status codes which are used to extend the
				current IETF definitions found in snmpdef.h.  These status
				codes and corresponding text can be used by both
				SNMP and CLI.
				
				(see below for current error codes):
				
				/* Values for error_status      */
				#define NO_ERROR                 0
				#define TOO_BIG                  1
				#define NO_SUCH_NAME             2
				#define BAD_VALUE                3
				#define READ_ONLY                4
				#define GEN_ERR                  5
				#define NO_ACCESS                6
				#define WRONG_TYPE               7
				#define WRONG_LENGTH             8
				#define WRONG_ENCODING           9
				#define WRONG_VALUE             10
				#define NO_CREATION             11
				#define INCONSISTENT_VALUE      12
				#define RESOURCE_UNAVAILABLE    13
				#define COMMIT_FAILED           14
				#define UNDO_FAILED             15
				#define AUTHORIZATION_ERROR     16
				#define NOT_WRITABLE            17
				#define INCONSISTENT_NAME       18
				#define LAST_ERROR              19
				"
			::= { zhoneEnhancedStatus 1 }

		
		-- 1.3.6.1.4.1.5504.3.1.22.1.1
		zhoneEnhancedStatusEntry OBJECT-TYPE
			SYNTAX ZhoneEnhancedStatusEntry
			MAX-ACCESS not-accessible
			STATUS current
			DESCRIPTION
				"Row in the table."
			INDEX { zhoneEnhancedStatusIndex }
			::= { zhoneEnhancedStatusTable 1 }

		
		ZhoneEnhancedStatusEntry ::=
			SEQUENCE { 
				zhoneEnhancedStatusIndex
					Integer32,
				zhoneEnhancedStatusCode
					Integer32,
				zhoneEnhancedStatusText
					OCTET STRING
			 }

		-- 1.3.6.1.4.1.5504.3.1.22.1.1.1
		zhoneEnhancedStatusIndex OBJECT-TYPE
			SYNTAX Integer32 (1..2147483647)
			MAX-ACCESS not-accessible
			STATUS current
			DESCRIPTION
				"Entry index value."
			::= { zhoneEnhancedStatusEntry 1 }

		
		-- 1.3.6.1.4.1.5504.3.1.22.1.1.2
		zhoneEnhancedStatusCode OBJECT-TYPE
			SYNTAX Integer32 (20..2147483647)
			MAX-ACCESS read-only
			STATUS current
			DESCRIPTION
				"Status code returned in SNMP packet as a result of issuing getproc_error,
				nextproc_error, testproc_error or setproc_error.  Also used for reporting
				CLI errors."
			::= { zhoneEnhancedStatusEntry 2 }

		
		-- 1.3.6.1.4.1.5504.3.1.22.1.1.3
		zhoneEnhancedStatusText OBJECT-TYPE
			SYNTAX OCTET STRING (SIZE (0..256))
			MAX-ACCESS read-only
			STATUS current
			DESCRIPTION
				"Given the zhoneEnhancedStatusCode, this is the corresponding
				text to be displayed to user in either SNMP or CLI."
			::= { zhoneEnhancedStatusEntry 3 }

		
		-- 1.3.6.1.4.1.5504.3.8.1
		zhoneTrapCpePoll OBJECT-IDENTITY
			STATUS current
			DESCRIPTION 
				"This is the Trap information related to the Zhone CPE
				polling task which exists on the BAN.  This task polls
				all connected Zhone CPE devices by sending SNMP Set messages
				(zhoneZmsExists=TRUE and zhoneZmsConnectionStatus=ACTIVE)
				to each device.  If a certain number of polls fails for a
				device, a Trap is sent to the ZMS indicating the Zhone CPE
				device whose connection has been lost."
			::= { zhoneTrapModules 1 }

		
		-- 1.3.6.1.4.1.5504.3.8.1.0
		zhoneTrapCpePollV2Traps OBJECT-IDENTITY
			STATUS current
			DESCRIPTION 
				"This object identity adds a zero(0) for the next to last
				sub-identifier which should be used for new SNMPv2 Traps."
			::= { zhoneTrapCpePoll 0 }

		
		-- 1.3.6.1.4.1.5504.3.8.1.0.1
		zhoneTrapCpeConnectionDown NOTIFICATION-TYPE
			OBJECTS { zhoneShelfNumber, zhoneSlotNumber, pportNumber, subPortNumber, ipIfVpi, 
				ipIfVci, ipIfLgId, ipIfAddr }
			STATUS current
			DESCRIPTION 
				"A Zhone CPE connection in down.  The Trap objects
				specify the location of the Zhone CPE device."
			::= { zhoneTrapCpePollV2Traps 1 }

		
		-- 1.3.6.1.4.1.5504.3.8.1.0.2
		zhoneTrapCpeConnectionUp NOTIFICATION-TYPE
			OBJECTS { zhoneShelfNumber, zhoneSlotNumber, pportNumber, subPortNumber, ipIfVpi, 
				ipIfVci, ipIfLgId, ipIfAddr }
			STATUS current
			DESCRIPTION 
				"A Zhone CPE connection that has previously been down is
				now up.  The Trap objects specify the location of the
				Zhone CPE device."
			::= { zhoneTrapCpePollV2Traps 2 }

		
		-- 1.3.6.1.4.1.5504.3.8.2
		zhoneTrapConfigSync OBJECT-IDENTITY
			STATUS current
			DESCRIPTION 
				"The trap sent when an object in the
				device datastore is changed"
			::= { zhoneTrapModules 2 }

		
		-- 1.3.6.1.4.1.5504.3.8.2.0
		zhoneTrapConfigSyncV2Traps OBJECT-IDENTITY
			STATUS current
			DESCRIPTION 
				"This object identity adds a zero(0) for the next to last
				sub-identifier which should be used for new SNMPv2 Traps."
			::= { zhoneTrapConfigSync 0 }

		
		-- 1.3.6.1.4.1.5504.3.8.2.0.1
		zhoneTrapConfigSyncChange NOTIFICATION-TYPE
			OBJECTS { zhoneConfigSyncAction, zhoneConfigSyncPriority }
			STATUS current
			DESCRIPTION 
				"An object in the device datastore has changed"
			::= { zhoneTrapConfigSyncV2Traps 1 }

		
		-- 1.3.6.1.4.1.5504.3.8.2.0.2
		zhoneTrapConfigSyncReset NOTIFICATION-TYPE
			OBJECTS { zhoneTrapConfigSyncResetInterval, zhoneTrapConfigSyncResetCount, zhoneTrapConfigSyncResetLastFtpTime, zhoneTrapConfigSyncResetCurrentTime }
			STATUS current
			DESCRIPTION 
				"ConfigSync has timed-out on the device and has
				subsequently been reset to a nominal state by
				the device.   Resetting configsync on the device 
				consists of closing the FTP data and control sockets,
				setting the configsyncstatus to syncerror, cleaning up
				any pending configsync records, resetting the
				ConfigSync state machine to the initial state, and 
				throwing a ConfigSyncReset Trap (this trap)."
			::= { zhoneTrapConfigSyncV2Traps 2 }

		
		-- 1.3.6.1.4.1.5504.3.8.4
		zhoneTrapSnmp OBJECT-IDENTITY
			STATUS current
			DESCRIPTION 
				"These are traps generated by SNMP, itself, when an
				error condition is detected."
			::= { zhoneTrapModules 4 }

		
		-- 1.3.6.1.4.1.5504.3.8.4.0
		zhoneTrapSnmpV2Traps OBJECT-IDENTITY
			STATUS current
			DESCRIPTION 
				"This object identity adds a zero(0) for the next to last
				sub-identifier which should be used for new SNMPv2 Traps."
			::= { zhoneTrapSnmp 0 }

		
		-- 1.3.6.1.4.1.5504.3.8.4.0.1
		zhoneTrapSnmpSATimeout NOTIFICATION-TYPE
			STATUS current
			DESCRIPTION 
				"Trap occurs when an error condition is detected in
				sub agent, causing the Zhone SNMP Master agent to timeout.
				Shelf and slot in the trap will refer to the subagent card which 
				caused the timeout."
			::= { zhoneTrapSnmpV2Traps 1 }

		
		-- 1.3.6.1.4.1.5504.3.8.5
		zhoneTrapCardRedundancy OBJECT-IDENTITY
			STATUS current
			DESCRIPTION 
				"Card Redundancy Traps"
			::= { zhoneTrapModules 5 }

		
		-- 1.3.6.1.4.1.5504.3.8.5.0
		zhoneCardRedundancyV2Traps OBJECT-IDENTITY
			STATUS current
			DESCRIPTION 
				"This object identity adds a zero(0) for the next to last
				sub-identifier which should be used for new SNMPv2 Traps."
			::= { zhoneTrapCardRedundancy 0 }

		
		-- 1.3.6.1.4.1.5504.3.8.5.0.1
		zhoneCardRedundancyStatusChange NOTIFICATION-TYPE
			OBJECTS { zhoneShelfNumber, zhoneSlotNumber, zhoneSysCardRedundancyGroupId }
			STATUS current
			DESCRIPTION 
				"Trap indicates that the specified card has become active."
			::= { zhoneCardRedundancyV2Traps 1 }

		
		-- 1.3.6.1.4.1.5504.3.8.5.0.2
		zhoneCardRedundancyUnsafe NOTIFICATION-TYPE
			OBJECTS { zhoneSysCardRedundancyOperStatus }
			STATUS current
			DESCRIPTION 
				"Trap if system is provisioned for redundant uplinks but is not redundancy ready."
			::= { zhoneCardRedundancyV2Traps 2 }

		
		-- 1.3.6.1.4.1.5504.3.8.6
		zhoneTrapBulkStatistics OBJECT-IDENTITY
			STATUS current
			DESCRIPTION 
				"Bulk Statistics Traps."
			::= { zhoneTrapModules 6 }

		
		-- 1.3.6.1.4.1.5504.3.8.6.0
		zhoneBulkStatisticsV2Traps OBJECT-IDENTITY
			STATUS current
			DESCRIPTION 
				"This object identity adds a zero(0) for the next to last
				sub-identifier which should be used for new SNMPv2 Traps."
			::= { zhoneTrapBulkStatistics 0 }

		
		-- 1.3.6.1.4.1.5504.3.8.6.0.1
		zhoneBulkStatisticsIntervalFailure NOTIFICATION-TYPE
			OBJECTS { zhoneBulkStatsSystemOperStatus }
			STATUS current
			DESCRIPTION 
				"This notification alerts the manager that the device could not 
				successfully complete the current collection interval.   The 
				zhoneBulkStatsSystemOperStatus is included in the trap to indicate
				the type of failure."
			::= { zhoneBulkStatisticsV2Traps 1 }

		
		-- 1.3.6.1.4.1.5504.3.8.7
		zhoneTrapZms OBJECT-IDENTITY
			STATUS current
			DESCRIPTION 
				"Object identifier under which Zhone ZMS related traps
				are defined."
			::= { zhoneTrapModules 7 }

		
		-- 1.3.6.1.4.1.5504.3.8.7.0
		zhoneTrapZmsV2Traps OBJECT-IDENTITY
			STATUS current
			DESCRIPTION 
				"The SNMPv2 zero(0) prefix for Zhone ZMS traps."
			::= { zhoneTrapZms 0 }

		
		-- 1.3.6.1.4.1.5504.3.8.7.0.1
		zhoneZmsBlockCliChange NOTIFICATION-TYPE
			OBJECTS { zhoneZmsBlockCli }
			STATUS deprecated
			DESCRIPTION 
				"This is trap is generated when the value of zhoneZmsBlockCli
				is changed."
			::= { zhoneTrapZmsV2Traps 1 }

		
		-- 1.3.6.1.4.1.5504.3.8.8
		zhoneTrapGeneric OBJECT-IDENTITY
			STATUS current
			DESCRIPTION 
				"Object identifier under which Zhone Generic traps are defined"
			::= { zhoneTrapModules 8 }

		
		-- 1.3.6.1.4.1.5504.3.8.8.0
		zhoneTrapGenericTraps OBJECT-IDENTITY
			STATUS current
			DESCRIPTION 
				"The SNMPv2 zero(0) prefix for Zhone Generic traps."
			::= { zhoneTrapGeneric 0 }

		
		-- 1.3.6.1.4.1.5504.3.8.8.0.1
		zhoneGenericSetClear NOTIFICATION-TYPE
			OBJECTS { ifIndex, zhoneTrapIfName, zhoneTrapProfileId, zhoneTrapName, zhoneTrapDescZms, 
				zhoneTrapDescCli, zhoneTrapProfilesIndexes }
			STATUS current
			DESCRIPTION 
				"This is a generic trap"
			::= { zhoneTrapGenericTraps 1 }

		
		-- 1.3.6.1.4.1.5504.8
		zhoneCompliances OBJECT IDENTIFIER ::= { zhone 8 }

		
		-- 1.3.6.1.4.1.5504.8.1
		zhoneGroups OBJECT IDENTIFIER ::= { zhoneCompliances 1 }

		
		-- 1.3.6.1.4.1.5504.8.1.1
		zhoneSystemGroup OBJECT-GROUP
			OBJECTS { zhoneZmsExists, zhoneZmsConnectionStatus, zhoneZmsIpAddress, zhoneZmsBlockCli, zhoneTrapsCommunityName, 
				zhoneTrapsSequenceNumber, zhoneTrapsResendSequenceNumber, zhoneTrapsAckedSequenceNumber, zhoneTrapsSeverity, zhoneTrapsAllowedCategories, 
				zhoneTrapsAdminStatus, zhoneTrapsRowStatus, zhoneTrapsGatewayTrapServerAddress, zhoneTrapVersion, zhoneTrapFlags, 
				zhoneTrapShelf, zhoneTrapSlot, zhoneTrapPort, zhoneTrapSubPort, zhoneTrapProviderId, 
				zhoneTrapText, zhoneTrapPortType, zhoneTrapPortTypeExtension, zhoneTrapAlarmAction, zhoneTrapAlarmId, 
				zhoneTrapAlarmSeverity, zhoneTrapConfigSyncResetInterval, zhoneTrapConfigSyncResetCount, zhoneTrapConfigSyncResetLastFtpTime, zhoneTrapConfigSyncResetCurrentTime, 
				zhoneTrapUtcTime, zhoneConfigSyncExists, zhoneConfigSyncOverflow, zhoneConfigSyncPriority, zhoneConfigSyncAction, 
				zhoneConfigSyncFileName, zhoneConfigSyncStatus, zhoneConfigSyncUserName, zhoneConfigSyncUserPassword, zhoneAdminCommunityAccess, 
				zhoneAdminCommunityAccessListIndex, zhoneAdminCommunityRowStatus, zhoneNextAdminAccessIndex, zhoneSwCardSwFileName, zhoneSwLoadRowStatus, 
				zhoneSnmpErrorDisplayString, zhoneSnmpErrorTime, zhoneSysSwLogin, zhoneSysSwPassword, zhoneSysSwPriLoadServer, 
				zhoneSysSwSecLoadServer, zhoneSysSwRemoteFilePath, zhoneSysSwLocalFilePath, zhoneSysSwAdmin, zhoneSysSwStatus, 
				zhoneSysRebootAdmin, zhoneSysRebootCardType, zhoneSysCardSpecificSwFileName, zhoneSysCardSwSpecificVers, zhoneSysCardUpgradeSwFileName, 
				zhoneSysCardSwUpgradeVers, zhoneSysCardSwType, zhoneSysCardSwEnable, zhoneSysCardSwUpgradeEnable, zhoneSysCardRowStatus, 
				zhoneSysCardLineType, zhoneSysCardAtmConfiguration, zhoneSysCardLineVoltage, zhoneSysCardVpiVciRange, zhoneSysCardInitString, 
				zhoneSysCardWettingCurrent, nextCardRedundancyGroupId, zhoneSysCardRedundancyGroupId, zhoneSysCardRedundancyWeight, zhoneBulkStatCollectionRowStatus, 
				zhoneVideoSystemConfigurationRowStatus, zhoneBulkStatInstance, zhoneSysCardRedundancyHoldActive, zhoneAdminAccessRowStatus, zhoneUserIdNext, 
				zhoneUserTotalFailedLogins, zhoneUserName, zhoneUserPassword, zhoneUserPrompt, zhoneUserAccessLevel, 
				zhoneUserAdmin, zhoneUserLogins, zhoneUserFailedLogins, zhoneUserRowStatus, zhoneSystemConfigurationNumShelves, 
				zhoneSystemConfigurationShelvesArray, zhoneSystemConfigurationNumCards, zhoneSystemConfigurationIpAddress, zhoneSystemConfigurationAlternateIpAddress, zhoneSystemConfigurationDateAndTime, 
				zhoneSystemConfigurationCountryRegion, zhoneSystemConfigurationRingSource, zhoneSystemCurrentClockSource, zhoneSystemSecondaryClockSource, zhoneSystemClockEligibility, 
				zhoneSystemClockWeight, zhoneSystemClockAvailabilityStatus, zhoneSystemClockTxClockMode, zhoneSystemConsoleLogging, zhoneSystemRevertiveClockSource, 
				zhoneSystemVoiceBandwidthCheck, zhoneAlarmLevelsEnabled, zhoneSystemUserAuthMethod, zhoneSystemRadiusAuthIndex, zhoneSystemSecureFTP, 
				zhoneSystemWebInterface, zhoneSystemConfigurationOptions, zhoneSystemConfigurationReservedVlanIdStart, zhoneSystemConfigurationReservedVlanIdCount, zhoneSysCardRedundancyOperStatus, 
				zhoneSysCardRedundancyRowStatus, zhoneSntpPrimaryServerIpAddr, zhoneSntpSecondaryServerIpAddr, zhoneSntpLocalTimeZone, zhoneSntpDaylightSavingTime, 
				zhoneAdslPotsMaxActiveBypassRelays, zhoneAdslPotsBypassRelayResetAll , zhoneBulkStatsSystemCollectionEnabled, zhoneBulkStatsSystemFtpAddress, zhoneBulkStatsSystemFtpLogin, 
				zhoneBulkStatsSystemFtpPassword, zhoneBulkStatsSystemFtpDirPath, zhoneBulkStatsSystemOperStatus, nextBulkStatCollectionId, zhoneBulkStatEnabled, 
				zhoneBulkStatOID, zhoneBulkStatIncludeChildren, zhoneBulkStatsCollectionInterval, zhoneVideoSystemConfigurationIndexNext, zhoneVideoSystemConfigurationNtpServerAddress, 
				zhoneVideoSystemConfigurationEpgServerAddress, zhoneVideoSystemConfigurationSettopBoxHeadEndServerAddress, zhoneVideoSystemConfigurationDefaultChannelAddress, zhoneVideoSystemConfigurationNoChannelAvailableAddress, zhoneVideoSystemConfigurationEpgType, 
				zhoneVideoSystemConfigurationEpgPort, zhoneVideoSystemConfigurationEpgFtpAddress, zhoneCallDetailRecEnabled, zhoneCallDetailRecFlushLog, zhoneCallDetailRecCurrFtpServer, 
				zhoneCallDetailRecPrimFtpIpAddr, zhoneCallDetailRecSecFtpIpAddr, zhoneCallDetailRecFtpLogin, zhoneCallDetailRecFtpPassword, zhoneCallDetailRecFtpDirPath, 
				zhoneCallDetailRecRepPeriod, zhoneCallDetailRecOperStatus, zhoneSoftwareUpgradeAction, zhoneSoftwareUpgradeStatus, zhoneSoftwareUpgradeTimeStarted, 
				zhoneSoftwareUpgradeTimeCompleted, zhoneFileAction, zhoneFileName1, zhoneFileName2, zhoneDirectoryPath, 
				zhoneDirectoryBytesAvailable, zhoneBytesReservedForProvisioning, zhoneFileDirectoryPath, zhoneFileName, zhoneFilePrivilege, 
				zhoneFileSize, zhoneFileLastModified, zhoneEnhancedStatusCode, zhoneEnhancedStatusText }
			STATUS current
			DESCRIPTION 
				"Description."
			::= { zhoneGroups 1 }

		
		-- 1.3.6.1.4.1.5504.8.1.2
		zhoneDeprecatedSystemGroup OBJECT-GROUP
			OBJECTS { zhonePrimaryClockSource }
			STATUS deprecated
			DESCRIPTION 
				"Description."
			::= { zhoneGroups 2 }

		
		-- 1.3.6.1.4.1.5504.8.1.3
		zhoneTrapGroup NOTIFICATION-GROUP
			NOTIFICATIONS { zhoneTrapCpeConnectionDown, zhoneTrapCpeConnectionUp, zhoneTrapConfigSyncChange, zhoneTrapConfigSyncReset, zhoneTrapSnmpSATimeout, 
				zhoneCardRedundancyStatusChange, zhoneCardRedundancyUnsafe, zhoneBulkStatisticsIntervalFailure, zhoneGenericSetClear }
			STATUS current
			DESCRIPTION 
				"Description."
			::= { zhoneGroups 3 }

		
		-- 1.3.6.1.4.1.5504.8.1.4
		zhoneDeprecatedTrapGroup NOTIFICATION-GROUP
			NOTIFICATIONS { zhoneZmsBlockCliChange }
			STATUS deprecated
			DESCRIPTION 
				"Description."
			::= { zhoneGroups 4 }

		
	
	END

--
-- genSystem.mib
--
