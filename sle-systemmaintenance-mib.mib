--
-- sle-systemmaintenance-mib.mib
-- MIB generated by MG-SOFT Visual MIB Builder Version 6.0  Build 88
-- Tuesday, October 07, 2014 at 14:48:35
--

	SLE-SYSTEMMAINTENANCE-MIB DEFINITIONS ::= BEGIN
 
		IMPORTS
			sleMgmt			
				FROM DASAN-SMI			
			SlePermissionType, SleControlStatusType, SleControlRequestResultType			
				FROM SLE-TC-MIB			
			OBJECT-GROUP, NOTIFICATION-GROUP			
				FROM SNMPv2-CONF			
			TimeTicks, IpAddress, Integer32, Unsigned32, Gauge32, 
			Counter64, BITS, OBJECT-TYPE, MODULE-IDENTITY, NOTIFICATION-TYPE			
				FROM SNMPv2-SMI			
			MacAddress			
				FROM SNMPv2-TC;
	
	
		-- 1.3.6.1.4.1.6296.101.1
		sleSystemMaintenance MODULE-IDENTITY 
			LAST-UPDATED "200412101054Z"		-- December 10, 2004 at 10:54 GMT
			ORGANIZATION 
				"Organization."
			CONTACT-INFO 
				"Contact-info."
			DESCRIPTION 
				"Description."
			::= { sleMgmt 1 }

		
	
--
-- Type definitions
--
	
		EnableFlag ::= INTEGER
			{
			enable(1),
			disable(2)
			}

		SleDefAutoCliScheduleResult ::= INTEGER
			{
			success(1),
			fail(2)
			}

		SleDefAutoCliScheduleType ::= INTEGER
			{
			periodic(1),
			at(2),
			daily(3),
			immediate(4)
			}

		SleDefAutoCliScheduleTransferType ::= INTEGER
			{
			ftp(1),
			tftp(2),
			memory(3),
			none(4)
			}

	
	
--
-- Node definitions
--
	
		-- 1.3.6.1.4.1.6296.101.1.1
		sleSystemBase OBJECT IDENTIFIER ::= { sleSystemMaintenance 1 }

		
		-- 1.3.6.1.4.1.6296.101.1.1.1
		sleSystemBaseInfo OBJECT IDENTIFIER ::= { sleSystemBase 1 }

		
		-- 1.3.6.1.4.1.6296.101.1.1.1.1
		sleSystemModelName OBJECT-TYPE
			SYNTAX OCTET STRING
			MAX-ACCESS read-only
			STATUS current
			DESCRIPTION
				"Description"
			::= { sleSystemBaseInfo 1 }

		
		-- 1.3.6.1.4.1.6296.101.1.1.1.2
		sleSystemSerialNumber OBJECT-TYPE
			SYNTAX OCTET STRING
			MAX-ACCESS read-only
			STATUS current
			DESCRIPTION
				"Description"
			::= { sleSystemBaseInfo 2 }

		
		-- 1.3.6.1.4.1.6296.101.1.1.1.3
		sleSystemHWVersion OBJECT-TYPE
			SYNTAX OCTET STRING
			MAX-ACCESS read-only
			STATUS current
			DESCRIPTION
				"Description"
			::= { sleSystemBaseInfo 3 }

		
		-- 1.3.6.1.4.1.6296.101.1.1.1.4
		sleSystemBLVersion OBJECT-TYPE
			SYNTAX OCTET STRING
			MAX-ACCESS read-only
			STATUS current
			DESCRIPTION
				"Description"
			::= { sleSystemBaseInfo 4 }

		
		-- 1.3.6.1.4.1.6296.101.1.1.1.5
		sleSystemSWCompatibility OBJECT-TYPE
			SYNTAX OCTET STRING
			MAX-ACCESS read-only
			STATUS current
			DESCRIPTION
				"Description"
			::= { sleSystemBaseInfo 5 }

		
		-- 1.3.6.1.4.1.6296.101.1.1.1.6
		sleSystemOSVersion OBJECT-TYPE
			SYNTAX OCTET STRING
			MAX-ACCESS read-only
			STATUS current
			DESCRIPTION
				"Description"
			::= { sleSystemBaseInfo 6 }

		
		-- 1.3.6.1.4.1.6296.101.1.1.1.7
		sleSystemMacAddress OBJECT-TYPE
			SYNTAX MacAddress
			MAX-ACCESS read-only
			STATUS current
			DESCRIPTION
				"Description"
			::= { sleSystemBaseInfo 7 }

		
		-- 1.3.6.1.4.1.6296.101.1.1.1.8
		sleSystemHostName OBJECT-TYPE
			SYNTAX OCTET STRING
			MAX-ACCESS read-only
			STATUS current
			DESCRIPTION
				"Description"
			::= { sleSystemBaseInfo 8 }

		
		-- 1.3.6.1.4.1.6296.101.1.1.1.9
		sleSystemCPULoadAll OBJECT-TYPE
			SYNTAX OCTET STRING
			MAX-ACCESS read-only
			STATUS current
			DESCRIPTION
				"Description"
			::= { sleSystemBaseInfo 9 }

		
		-- 1.3.6.1.4.1.6296.101.1.1.1.10
		sleSystemCPULoadInterrupt OBJECT-TYPE
			SYNTAX OCTET STRING
			MAX-ACCESS read-only
			STATUS current
			DESCRIPTION
				"Description"
			::= { sleSystemBaseInfo 10 }

		
		-- 1.3.6.1.4.1.6296.101.1.1.1.11
		sleSystemCPUThreshold OBJECT-TYPE
			SYNTAX INTEGER (20..100)
			MAX-ACCESS read-only
			STATUS current
			DESCRIPTION
				"Description"
			::= { sleSystemBaseInfo 11 }

		
		-- 1.3.6.1.4.1.6296.101.1.1.1.12
		sleSystemCPUInterval OBJECT-TYPE
			SYNTAX INTEGER (5 | 60 | 600)
			MAX-ACCESS read-only
			STATUS current
			DESCRIPTION
				"Description"
			::= { sleSystemBaseInfo 12 }

		
		-- 1.3.6.1.4.1.6296.101.1.1.1.13
		sleSystemMemoryTotal OBJECT-TYPE
			SYNTAX Unsigned32
			MAX-ACCESS read-only
			STATUS current
			DESCRIPTION
				"Description"
			::= { sleSystemBaseInfo 13 }

		
		-- 1.3.6.1.4.1.6296.101.1.1.1.14
		sleSystemMemoryFree OBJECT-TYPE
			SYNTAX Unsigned32
			MAX-ACCESS read-only
			STATUS current
			DESCRIPTION
				"Description"
			::= { sleSystemBaseInfo 14 }

		
		-- 1.3.6.1.4.1.6296.101.1.1.1.15
		sleSystemMemoryShared OBJECT-TYPE
			SYNTAX Unsigned32
			MAX-ACCESS read-only
			STATUS current
			DESCRIPTION
				"Description"
			::= { sleSystemBaseInfo 15 }

		
		-- 1.3.6.1.4.1.6296.101.1.1.1.16
		sleSystemMemoryBuffers OBJECT-TYPE
			SYNTAX Unsigned32
			MAX-ACCESS read-only
			STATUS current
			DESCRIPTION
				"Description"
			::= { sleSystemBaseInfo 16 }

		
		-- 1.3.6.1.4.1.6296.101.1.1.1.17
		sleSystemMemoryCached OBJECT-TYPE
			SYNTAX Unsigned32
			MAX-ACCESS read-only
			STATUS current
			DESCRIPTION
				"Description"
			::= { sleSystemBaseInfo 17 }

		
		-- 1.3.6.1.4.1.6296.101.1.1.1.18
		sleSystemMemorySwapTotal OBJECT-TYPE
			SYNTAX Unsigned32
			MAX-ACCESS read-only
			STATUS current
			DESCRIPTION
				"Description"
			::= { sleSystemBaseInfo 18 }

		
		-- 1.3.6.1.4.1.6296.101.1.1.1.19
		sleSystemMemorySwapFree OBJECT-TYPE
			SYNTAX Unsigned32
			MAX-ACCESS read-only
			STATUS current
			DESCRIPTION
				"Description"
			::= { sleSystemBaseInfo 19 }

		
		-- 1.3.6.1.4.1.6296.101.1.1.1.20
		sleSystemDefaultOS OBJECT-TYPE
			SYNTAX INTEGER
				{
				noDualOS(0),
				os1(1),
				os2(2)
				}
			MAX-ACCESS read-only
			STATUS current
			DESCRIPTION
				"Description"
			::= { sleSystemBaseInfo 20 }

		
		-- 1.3.6.1.4.1.6296.101.1.1.1.21
		sleSystemOS1Version OBJECT-TYPE
			SYNTAX OCTET STRING
			MAX-ACCESS read-only
			STATUS current
			DESCRIPTION
				"Description"
			::= { sleSystemBaseInfo 21 }

		
		-- 1.3.6.1.4.1.6296.101.1.1.1.22
		sleSystemOS1Size OBJECT-TYPE
			SYNTAX Unsigned32
			MAX-ACCESS read-only
			STATUS current
			DESCRIPTION
				"Description"
			::= { sleSystemBaseInfo 22 }

		
		-- 1.3.6.1.4.1.6296.101.1.1.1.23
		sleSystemOS1BuildNumber OBJECT-TYPE
			SYNTAX OCTET STRING
			MAX-ACCESS read-only
			STATUS current
			DESCRIPTION
				"Description"
			::= { sleSystemBaseInfo 23 }

		
		-- 1.3.6.1.4.1.6296.101.1.1.1.24
		sleSystemOS2Version OBJECT-TYPE
			SYNTAX OCTET STRING
			MAX-ACCESS read-only
			STATUS current
			DESCRIPTION
				"Description"
			::= { sleSystemBaseInfo 24 }

		
		-- 1.3.6.1.4.1.6296.101.1.1.1.25
		sleSystemOS2Size OBJECT-TYPE
			SYNTAX Unsigned32
			MAX-ACCESS read-only
			STATUS current
			DESCRIPTION
				"Description"
			::= { sleSystemBaseInfo 25 }

		
		-- 1.3.6.1.4.1.6296.101.1.1.1.26
		sleSystemOS2BuildNumber OBJECT-TYPE
			SYNTAX OCTET STRING
			MAX-ACCESS read-only
			STATUS current
			DESCRIPTION
				"Description"
			::= { sleSystemBaseInfo 26 }

		
		-- 1.3.6.1.4.1.6296.101.1.1.1.27
		sleSystemFlashTotalSize OBJECT-TYPE
			SYNTAX Unsigned32
			MAX-ACCESS read-only
			STATUS current
			DESCRIPTION
				"Description"
			::= { sleSystemBaseInfo 27 }

		
		-- 1.3.6.1.4.1.6296.101.1.1.1.28
		sleSystemFlashOSSize OBJECT-TYPE
			SYNTAX Unsigned32
			MAX-ACCESS read-only
			STATUS current
			DESCRIPTION
				"Description"
			::= { sleSystemBaseInfo 28 }

		
		-- 1.3.6.1.4.1.6296.101.1.1.1.29
		sleSystemFlashConfigSize OBJECT-TYPE
			SYNTAX Unsigned32
			MAX-ACCESS read-only
			STATUS current
			DESCRIPTION
				"Description"
			::= { sleSystemBaseInfo 29 }

		
		-- 1.3.6.1.4.1.6296.101.1.1.1.30
		sleSystemFlashOSUsedSize OBJECT-TYPE
			SYNTAX Unsigned32
			MAX-ACCESS read-only
			STATUS current
			DESCRIPTION
				"Description"
			::= { sleSystemBaseInfo 30 }

		
		-- 1.3.6.1.4.1.6296.101.1.1.1.31
		sleSystemFlashConfigUsedSize OBJECT-TYPE
			SYNTAX Unsigned32
			MAX-ACCESS read-only
			STATUS current
			DESCRIPTION
				"Description"
			::= { sleSystemBaseInfo 31 }

		
		-- 1.3.6.1.4.1.6296.101.1.1.1.32
		sleSystemClock OBJECT-TYPE
			SYNTAX OCTET STRING
			MAX-ACCESS read-only
			STATUS current
			DESCRIPTION
				"Description"
			::= { sleSystemBaseInfo 32 }

		
		-- 1.3.6.1.4.1.6296.101.1.1.1.33
		sleSystemTimezone OBJECT-TYPE
			SYNTAX OCTET STRING
			MAX-ACCESS read-only
			STATUS current
			DESCRIPTION
				"Description"
			::= { sleSystemBaseInfo 33 }

		
		-- 1.3.6.1.4.1.6296.101.1.1.1.34
		sleSystemDNSDomainName OBJECT-TYPE
			SYNTAX OCTET STRING
			MAX-ACCESS read-only
			STATUS current
			DESCRIPTION
				"Description"
			::= { sleSystemBaseInfo 34 }

		
		-- 1.3.6.1.4.1.6296.101.1.1.1.35
		sleSystemInitBanner OBJECT-TYPE
			SYNTAX OCTET STRING
			MAX-ACCESS read-only
			STATUS current
			DESCRIPTION
				"Description"
			::= { sleSystemBaseInfo 35 }

		
		-- 1.3.6.1.4.1.6296.101.1.1.1.36
		sleSystemSuccessBanner OBJECT-TYPE
			SYNTAX OCTET STRING
			MAX-ACCESS read-only
			STATUS current
			DESCRIPTION
				"Description"
			::= { sleSystemBaseInfo 36 }

		
		-- 1.3.6.1.4.1.6296.101.1.1.1.37
		sleSystemFailBanner OBJECT-TYPE
			SYNTAX OCTET STRING
			MAX-ACCESS read-only
			STATUS current
			DESCRIPTION
				"Description"
			::= { sleSystemBaseInfo 37 }

		
		-- 1.3.6.1.4.1.6296.101.1.1.1.38
		sleSystemSyslogState OBJECT-TYPE
			SYNTAX INTEGER
				{
				notAvailable(-2),
				stop(0),
				start(1)
				}
			MAX-ACCESS read-only
			STATUS current
			DESCRIPTION
				"Description"
			::= { sleSystemBaseInfo 38 }

		
		-- 1.3.6.1.4.1.6296.101.1.1.1.39
		sleSystemSyslogVolatileNumber OBJECT-TYPE
			SYNTAX Integer32
			MAX-ACCESS read-only
			STATUS current
			DESCRIPTION
				"Description"
			::= { sleSystemBaseInfo 39 }

		
		-- 1.3.6.1.4.1.6296.101.1.1.1.40
		sleSystemSyslogNonVolatileNumber OBJECT-TYPE
			SYNTAX Integer32
			MAX-ACCESS read-only
			STATUS current
			DESCRIPTION
				"Description"
			::= { sleSystemBaseInfo 40 }

		
		-- 1.3.6.1.4.1.6296.101.1.1.1.41
		sleSystemSyslogBindAddress OBJECT-TYPE
			SYNTAX IpAddress
			MAX-ACCESS read-only
			STATUS current
			DESCRIPTION
				"Description"
			::= { sleSystemBaseInfo 41 }

		
		-- 1.3.6.1.4.1.6296.101.1.1.1.42
		sleSystemSyslogLocalCode OBJECT-TYPE
			SYNTAX INTEGER (-1 | 0..7)
			MAX-ACCESS read-only
			STATUS current
			DESCRIPTION
				"Description"
			::= { sleSystemBaseInfo 42 }

		
		-- 1.3.6.1.4.1.6296.101.1.1.1.43
		sleSystemSSHState OBJECT-TYPE
			SYNTAX INTEGER
				{
				disable(0),
				enable(1)
				}
			MAX-ACCESS read-only
			STATUS current
			DESCRIPTION
				"Description"
			::= { sleSystemBaseInfo 43 }

		
		-- 1.3.6.1.4.1.6296.101.1.1.1.44
		sleSystemNTPState OBJECT-TYPE
			SYNTAX INTEGER
				{
				disable(0),
				ntp(1),
				sntp(2)
				}
			MAX-ACCESS read-only
			STATUS current
			DESCRIPTION
				"Description"
			::= { sleSystemBaseInfo 44 }

		
		-- 1.3.6.1.4.1.6296.101.1.1.1.45
		sleSystemBackupInterval OBJECT-TYPE
			SYNTAX Integer32
			MAX-ACCESS read-only
			STATUS current
			DESCRIPTION
				"Description."
			::= { sleSystemBaseInfo 45 }

		
		-- 1.3.6.1.4.1.6296.101.1.1.1.46
		sleSystemDhcpActivity OBJECT-TYPE
			SYNTAX INTEGER
				{
				disable(0),
				enable(1)
				}
			MAX-ACCESS read-only
			STATUS current
			DESCRIPTION
				"The activity of DHCP daemon."
			::= { sleSystemBaseInfo 46 }

		
		-- 1.3.6.1.4.1.6296.101.1.1.1.47
		sleSystemDefaultTTL OBJECT-TYPE
			SYNTAX INTEGER (32..255)
			MAX-ACCESS read-only
			STATUS current
			DESCRIPTION
				"The default ttl."
			::= { sleSystemBaseInfo 47 }

		
		-- 1.3.6.1.4.1.6296.101.1.1.1.48
		sleSystemSyslogVolatileSize OBJECT-TYPE
			SYNTAX Integer32
			MAX-ACCESS read-only
			STATUS current
			DESCRIPTION
				"Description."
			::= { sleSystemBaseInfo 48 }

		
		-- 1.3.6.1.4.1.6296.101.1.1.1.49
		sleSystemSyslogBindInterfaceName OBJECT-TYPE
			SYNTAX OCTET STRING
			MAX-ACCESS read-only
			STATUS current
			DESCRIPTION
				"Description."
			::= { sleSystemBaseInfo 49 }

		
		-- 1.3.6.1.4.1.6296.101.1.1.1.50
		sleSystemSessionTime OBJECT-TYPE
			SYNTAX INTEGER (60..3600)
			MAX-ACCESS read-only
			STATUS current
			DESCRIPTION
				"Description."
			::= { sleSystemBaseInfo 50 }

		
		-- 1.3.6.1.4.1.6296.101.1.1.1.51
		sleSystemExecTimeout OBJECT-TYPE
			SYNTAX INTEGER (0..2147519)
			MAX-ACCESS read-only
			STATUS current
			DESCRIPTION
				"Description."
			::= { sleSystemBaseInfo 51 }

		
		-- 1.3.6.1.4.1.6296.101.1.1.1.52
		sleSystemWatchdogStatus OBJECT-TYPE
			SYNTAX INTEGER
				{
				enable(1),
				disable(2)
				}
			MAX-ACCESS read-only
			STATUS current
			DESCRIPTION
				"The status of system watchdog"
			::= { sleSystemBaseInfo 52 }

		
		-- 1.3.6.1.4.1.6296.101.1.1.1.53
		sleSystemNtpBindInterface OBJECT-TYPE
			SYNTAX OCTET STRING
			MAX-ACCESS read-only
			STATUS current
			DESCRIPTION
				"Description."
			::= { sleSystemBaseInfo 53 }

		
		-- 1.3.6.1.4.1.6296.101.1.1.1.54
		sleSystemFtpBindInterface OBJECT-TYPE
			SYNTAX OCTET STRING
			MAX-ACCESS read-only
			STATUS current
			DESCRIPTION
				"Description."
			::= { sleSystemBaseInfo 54 }

		
		-- 1.3.6.1.4.1.6296.101.1.1.1.55
		sleSystemRedundancyPort OBJECT-TYPE
			SYNTAX INTEGER (1..24)
			MAX-ACCESS read-only
			STATUS current
			DESCRIPTION
				"Description."
			::= { sleSystemBaseInfo 55 }

		
		-- 1.3.6.1.4.1.6296.101.1.1.1.56
		sleSystemSyslogVolatileMaxLine OBJECT-TYPE
			SYNTAX INTEGER (0 | 8..16384)
			MAX-ACCESS read-only
			STATUS current
			DESCRIPTION
				"The max lines of volatile.
				Exclusive to sleSystemSyslogVolatileSize.
				(Supported only model 5924N)
				"
			::= { sleSystemBaseInfo 56 }

		
		-- 1.3.6.1.4.1.6296.101.1.1.1.57
		sleSystemBootInfo OBJECT-TYPE
			SYNTAX OCTET STRING
			MAX-ACCESS read-only
			STATUS current
			DESCRIPTION
				"The information of last boot..
				(Supported only model 5924N)
				"
			::= { sleSystemBaseInfo 57 }

		
		-- 1.3.6.1.4.1.6296.101.1.1.1.58
		sleSystemTempHighThreshold OBJECT-TYPE
			SYNTAX Integer32
			MAX-ACCESS read-only
			STATUS current
			DESCRIPTION
				"Description."
			::= { sleSystemBaseInfo 58 }

		
		-- 1.3.6.1.4.1.6296.101.1.1.1.59
		sleSystemTempLowThreshold OBJECT-TYPE
			SYNTAX Integer32
			MAX-ACCESS read-only
			STATUS current
			DESCRIPTION
				"Description."
			::= { sleSystemBaseInfo 59 }

		
		-- 1.3.6.1.4.1.6296.101.1.1.1.60
		sleSystemMemThreshold OBJECT-TYPE
			SYNTAX INTEGER (20..100)
			MAX-ACCESS read-only
			STATUS current
			DESCRIPTION
				"Description."
			::= { sleSystemBaseInfo 60 }

		
		-- 1.3.6.1.4.1.6296.101.1.1.1.61
		sleSystemLowCPUThreshold OBJECT-TYPE
			SYNTAX INTEGER (20..100)
			MAX-ACCESS read-only
			STATUS current
			DESCRIPTION
				"Description."
			::= { sleSystemBaseInfo 61 }

		
		-- 1.3.6.1.4.1.6296.101.1.1.1.62
		sleSystemLowCPUInterval OBJECT-TYPE
			SYNTAX INTEGER (5 | 60 | 600)
			MAX-ACCESS read-only
			STATUS current
			DESCRIPTION
				"Description."
			::= { sleSystemBaseInfo 62 }

		
		-- 1.3.6.1.4.1.6296.101.1.1.1.63
		sleSystemRunningOS OBJECT-TYPE
			SYNTAX INTEGER
				{
				noDualOS(0),
				os1(1),
				os2(2)
				}
			MAX-ACCESS read-only
			STATUS current
			DESCRIPTION
				"Description."
			::= { sleSystemBaseInfo 63 }

		
		-- 1.3.6.1.4.1.6296.101.1.1.1.64
		sleSystemNtpBindAddress OBJECT-TYPE
			SYNTAX IpAddress
			MAX-ACCESS read-only
			STATUS current
			DESCRIPTION
				"The NTP client binding address."
			DEFVAL { ''h }
			::= { sleSystemBaseInfo 64 }

		
		-- 1.3.6.1.4.1.6296.101.1.1.1.65
		sleSystemEnablePasswdType OBJECT-TYPE
			SYNTAX INTEGER
				{
				plain(1),
				encrypt(2)
				}
			MAX-ACCESS read-write
			STATUS current
			DESCRIPTION
				"The type of enable password of command shell.
				plain : no encryption.
				encrypt : encryption"
			DEFVAL { 1 }
			::= { sleSystemBaseInfo 65 }

		
		-- 1.3.6.1.4.1.6296.101.1.1.1.66
		sleSystemEnablePasswd OBJECT-TYPE
			SYNTAX OCTET STRING (SIZE (0..64))
			MAX-ACCESS read-write
			STATUS current
			DESCRIPTION
				"The enable password of command shell."
			::= { sleSystemBaseInfo 66 }

		
		-- 1.3.6.1.4.1.6296.101.1.1.1.67
		sleSystemServicePasswdEncryption OBJECT-TYPE
			SYNTAX INTEGER
				{
				enable(1),
				disable(2)
				}
			MAX-ACCESS read-write
			STATUS current
			DESCRIPTION
				"The encrypt system passwords"
			DEFVAL { 2 }
			::= { sleSystemBaseInfo 67 }

		
		-- 1.3.6.1.4.1.6296.101.1.1.1.68
		sleSystemUptime64 OBJECT-TYPE
			SYNTAX Counter64
			MAX-ACCESS read-write
			STATUS current
			DESCRIPTION
				"The time counter from system up. It is large version of sysUpTime."
			::= { sleSystemBaseInfo 68 }

		
		-- 1.3.6.1.4.1.6296.101.1.1.1.69
		sleSystemNtpPollnterval OBJECT-TYPE
			SYNTAX Integer32 (6..20)
			MAX-ACCESS read-only
			STATUS current
			DESCRIPTION
				"The NTP request polling-interval"
			::= { sleSystemBaseInfo 69 }

		
--   1.3.6.1.4.1.6296.101.1.1.1.70
-- 1.3.6.1.4.1.6296.101.1.1.1.70
		-- 1.3.6.1.4.1.6296.101.1.1.1.70
		sleSystemCPUDuration OBJECT-TYPE
			SYNTAX INTEGER (5..300)
			MAX-ACCESS read-only
			STATUS current
			DESCRIPTION
				"The threshold sampling duration."
			::= { sleSystemBaseInfo 70 }

		
--   1.3.6.1.4.1.6296.101.1.1.1.71
-- 1.3.6.1.4.1.6296.101.1.1.1.71
		-- 1.3.6.1.4.1.6296.101.1.1.1.71
		sleSystemLowCPUDuration OBJECT-TYPE
			SYNTAX INTEGER (5..300)
			MAX-ACCESS read-only
			STATUS current
			DESCRIPTION
				"The threshold sampling duration."
			::= { sleSystemBaseInfo 71 }

		
		-- 1.3.6.1.4.1.6296.101.1.1.1.72
		sleSystemBarcode OBJECT-TYPE
			SYNTAX OCTET STRING
			MAX-ACCESS read-only
			STATUS current
			DESCRIPTION
				"The System Barcode. (only for specific vender)"
			::= { sleSystemBaseInfo 72 }

		
		-- 1.3.6.1.4.1.6296.101.1.1.1.73
		sleSystemEnhancedFeature OBJECT-TYPE
			SYNTAX INTEGER
				{
				enable(1),
				disable(2)
				}
			MAX-ACCESS read-only
			STATUS current
			DESCRIPTION
				"System enhanced feature enable/disable."
			::= { sleSystemBaseInfo 73 }

		
		-- 1.3.6.1.4.1.6296.101.1.1.1.74
		sleSystemGetBranchModel OBJECT-TYPE
			SYNTAX INTEGER
				{
				other(0),
				nsn(1)
				}
			MAX-ACCESS read-only
			STATUS current
			DESCRIPTION
				"The distinction of branch model."
			::= { sleSystemBaseInfo 74 }

		
		-- 1.3.6.1.4.1.6296.101.1.1.1.75
		sleSystemTargetId OBJECT-TYPE
			SYNTAX OCTET STRING
			MAX-ACCESS read-only
			STATUS current
			DESCRIPTION
				"The system target ID."
			::= { sleSystemBaseInfo 75 }

		
		-- 1.3.6.1.4.1.6296.101.1.1.1.76
		sleSystemNodeName OBJECT-TYPE
			SYNTAX OCTET STRING
			MAX-ACCESS read-only
			STATUS current
			DESCRIPTION
				"The system node name."
			::= { sleSystemBaseInfo 76 }

		
		-- 1.3.6.1.4.1.6296.101.1.1.1.77
		sleSystemNetworkName OBJECT-TYPE
			SYNTAX OCTET STRING
			MAX-ACCESS read-only
			STATUS current
			DESCRIPTION
				"The system network name."
			::= { sleSystemBaseInfo 77 }

		
		-- 1.3.6.1.4.1.6296.101.1.1.1.78
		sleSystemShelfId OBJECT-TYPE
			SYNTAX OCTET STRING
			MAX-ACCESS read-only
			STATUS current
			DESCRIPTION
				"The system shelf ID."
			::= { sleSystemBaseInfo 78 }

		
		-- 1.3.6.1.4.1.6296.101.1.1.1.79
		sleSystemSlotId OBJECT-TYPE
			SYNTAX OCTET STRING
			MAX-ACCESS read-only
			STATUS current
			DESCRIPTION
				"The system slot ID."
			::= { sleSystemBaseInfo 79 }

		
		-- 1.3.6.1.4.1.6296.101.1.1.1.80
		sleSystemWebMgmt OBJECT-TYPE
			SYNTAX INTEGER
				{
				enable(1),
				disable(2)
				}
			MAX-ACCESS read-only
			STATUS current
			DESCRIPTION
				"The web-management service status."
			::= { sleSystemBaseInfo 80 }

		
		-- 1.3.6.1.4.1.6296.101.1.1.1.81
		sleSystemManufacturer OBJECT-TYPE
			SYNTAX OCTET STRING
			MAX-ACCESS read-only
			STATUS current
			DESCRIPTION
				"The manufacturer"
			::= { sleSystemBaseInfo 81 }

		
		-- 1.3.6.1.4.1.6296.101.1.1.1.82
		sleSystemManufactureDate OBJECT-TYPE
			SYNTAX OCTET STRING
			MAX-ACCESS read-only
			STATUS current
			DESCRIPTION
				"The manufacture date"
			::= { sleSystemBaseInfo 82 }

		
		-- 1.3.6.1.4.1.6296.101.1.1.1.83
		sleSystemNosUpgradeStatus OBJECT-TYPE
			SYNTAX INTEGER
				{
				none(0),
				ok(1),
				fail(2),
				inprogress(3),
				unknown(255)
				}
			MAX-ACCESS read-only
			STATUS current
			DESCRIPTION
				"The status of NOS download & upload. 
				This represent the progress of NOS upgrade."
			::= { sleSystemBaseInfo 83 }

		
		-- 1.3.6.1.4.1.6296.101.1.1.1.84
		sleSystemAutoReloadInHour OBJECT-TYPE
			SYNTAX INTEGER (0..23)
			MAX-ACCESS read-only
			STATUS current
			DESCRIPTION
				"Auto-Reload Hour from now (Unit: Hour from  Now)."
			::= { sleSystemBaseInfo 84 }

		
		-- 1.3.6.1.4.1.6296.101.1.1.1.85
		sleSystemAutoReloadInMinutes OBJECT-TYPE
			SYNTAX INTEGER (0..59)
			MAX-ACCESS read-only
			STATUS current
			DESCRIPTION
				"Auto-Reload Time from now (Unit: Min from  Now)."
			::= { sleSystemBaseInfo 85 }

		
		-- 1.3.6.1.4.1.6296.101.1.1.1.86
		sleSystemAutoReloadDailyHour OBJECT-TYPE
			SYNTAX INTEGER (0..23)
			MAX-ACCESS read-only
			STATUS current
			DESCRIPTION
				"Auto-Reload Time from now (Unit: Daily from  Now)."
			::= { sleSystemBaseInfo 86 }

		
		-- 1.3.6.1.4.1.6296.101.1.1.1.87
		sleSystemAutoReloadDailyMinutes OBJECT-TYPE
			SYNTAX INTEGER (0..59)
			MAX-ACCESS read-only
			STATUS current
			DESCRIPTION
				"Auto-Reload minutes from now (Unit: Daily from  Now)."
			::= { sleSystemBaseInfo 87 }

		
		-- 1.3.6.1.4.1.6296.101.1.1.1.88
		sleSystemAutoReloadAtYear OBJECT-TYPE
			SYNTAX INTEGER (0 | 2008..2035)
			MAX-ACCESS read-only
			STATUS current
			DESCRIPTION
				"AAuto-Reload year from now (Unit: year from  Now)"
			::= { sleSystemBaseInfo 88 }

		
		-- 1.3.6.1.4.1.6296.101.1.1.1.89
		sleSystemAutoReloadAtMonth OBJECT-TYPE
			SYNTAX INTEGER (0..12)
			MAX-ACCESS read-only
			STATUS current
			DESCRIPTION
				"Auto-Reload month of every year (Unit: month )"
			::= { sleSystemBaseInfo 89 }

		
		-- 1.3.6.1.4.1.6296.101.1.1.1.90
		sleSystemAutoReloadAtDay OBJECT-TYPE
			SYNTAX INTEGER (0..31)
			MAX-ACCESS read-only
			STATUS current
			DESCRIPTION
				"Auto-Reload day of every month "
			::= { sleSystemBaseInfo 90 }

		
		-- 1.3.6.1.4.1.6296.101.1.1.1.91
		sleSystemAutpReloadAtHour OBJECT-TYPE
			SYNTAX INTEGER (0..23)
			MAX-ACCESS read-only
			STATUS current
			DESCRIPTION
				"Auto-Reload Hour from now (Unit: Hour from  Now)"
			::= { sleSystemBaseInfo 91 }

		
		-- 1.3.6.1.4.1.6296.101.1.1.1.92
		sleSystemAutpReloadAtMinutes OBJECT-TYPE
			SYNTAX INTEGER (0..59)
			MAX-ACCESS read-only
			STATUS current
			DESCRIPTION
				"Auto-Reload minute from now (Unit: minute from  Now)"
			::= { sleSystemBaseInfo 92 }

		
		-- 1.3.6.1.4.1.6296.101.1.1.1.93
		sleSystemAdministeredMac OBJECT-TYPE
			SYNTAX OCTET STRING
			MAX-ACCESS read-only
			STATUS current
			DESCRIPTION
				"The system administered MAC address."
			::= { sleSystemBaseInfo 93 }

		
		-- 1.3.6.1.4.1.6296.101.1.1.1.94
		sleSystemBaseMac OBJECT-TYPE
			SYNTAX OCTET STRING
			MAX-ACCESS read-only
			STATUS current
			DESCRIPTION
				"The system base MAC address."
			::= { sleSystemBaseInfo 94 }

		
		-- 1.3.6.1.4.1.6296.101.1.1.2
		sleSystemBaseControl OBJECT IDENTIFIER ::= { sleSystemBase 2 }

		
		-- 1.3.6.1.4.1.6296.101.1.1.2.1
		sleSystemControlRequest OBJECT-TYPE
			SYNTAX INTEGER
				{
				setSystemBaseSystemInfoProfile(1),
				setSystemBaseCPUThresholdProfile(2),
				sleSystemBaseDefaultOS(3),
				setSystemBaseRTCProfile(4),
				setSystemBaseDNSDomainName(5),
				setSystemBaseBannerProfile(6),
				setSystemBaseSyslogProfile(7),
				setSystemBaseSSHState(8),
				setSystemBaseNTPState(9),
				setSystemBaseOSUpgradeProfile(10),
				setSystemBaseBackup(11),
				setSystemBaseBackupInterval(12),
				setSystemBaseReload(13),
				setSystemDhcpActivity(14),
				setSystemBasePonFwDownloadProfile(15),
				setSystemDefaultTTL(16),
				setSystemBaseSyslogBindIfName(17),
				clearSystemBaseSyslogBindIfName(18),
				setSystemConfigPortMove(19),
				setSystemConfigPortCopy(20),
				setSystemConfigPortClear(21),
				setSystemControlSessionTime(22),
				setSystemControlExecTimeout(23),
				setSystemWatchdogStatus(24),
				clearSystemOs(25),
				setNtpBindInterface(26),
				setFtpBindInterface(27),
				setSystemBaseRedundancyPort(28),
				clearRedundancy(29),
				setSystemBaseTempThreshold(30),
				setSystemBaseMemThreshold(31),
				setSystemBaseReloadBoth(32),
				setSystemBaseBootloaderUpgradeProfile(33),
				setNtpBindAddress(34),
				setEnablePasswd(35),
				setEnableSerivceEncryption(36),
				restoreSystemPasswd(37),
				setNtpPollInterval(38),
				setRestoreFactory(39),
				setWebMgmtStatus(40),
				setSystemBaseAutoReloadInTime(41),
				setSystemBaseAutoReloadDailyTime(42),
				setSystemBaseAutoReloadAtTime(43),
				setSystemAdministeredMac(44)
				}
			MAX-ACCESS read-write
			STATUS current
			DESCRIPTION
				"Description"
			::= { sleSystemBaseControl 1 }

		
		-- 1.3.6.1.4.1.6296.101.1.1.2.2
		sleSystemControlStatus OBJECT-TYPE
			SYNTAX SleControlStatusType
			MAX-ACCESS read-only
			STATUS current
			DESCRIPTION
				"Description"
			::= { sleSystemBaseControl 2 }

		
		-- 1.3.6.1.4.1.6296.101.1.1.2.3
		sleSystemControlTimer OBJECT-TYPE
			SYNTAX Gauge32
			MAX-ACCESS read-write
			STATUS current
			DESCRIPTION
				"Description"
			::= { sleSystemBaseControl 3 }

		
		-- 1.3.6.1.4.1.6296.101.1.1.2.4
		sleSystemControlTimeStamp OBJECT-TYPE
			SYNTAX TimeTicks
			MAX-ACCESS read-only
			STATUS current
			DESCRIPTION
				"Description"
			::= { sleSystemBaseControl 4 }

		
		-- 1.3.6.1.4.1.6296.101.1.1.2.5
		sleSystemControlReqResult OBJECT-TYPE
			SYNTAX SleControlRequestResultType
			MAX-ACCESS read-only
			STATUS current
			DESCRIPTION
				"Description"
			::= { sleSystemBaseControl 5 }

		
		-- 1.3.6.1.4.1.6296.101.1.1.2.6
		sleSystemControlHostName OBJECT-TYPE
			SYNTAX OCTET STRING
			MAX-ACCESS read-write
			STATUS current
			DESCRIPTION
				"Description"
			::= { sleSystemBaseControl 6 }

		
		-- 1.3.6.1.4.1.6296.101.1.1.2.7
		sleSystemControlCPUThreshold OBJECT-TYPE
			SYNTAX INTEGER (20..100)
			MAX-ACCESS read-write
			STATUS current
			DESCRIPTION
				"Description"
			::= { sleSystemBaseControl 7 }

		
		-- 1.3.6.1.4.1.6296.101.1.1.2.8
		sleSystemControlCPUInterval OBJECT-TYPE
			SYNTAX INTEGER (5 | 60 | 600)
			MAX-ACCESS read-write
			STATUS current
			DESCRIPTION
				"Description"
			::= { sleSystemBaseControl 8 }

		
		-- 1.3.6.1.4.1.6296.101.1.1.2.9
		sleSystemControlDefaultOS OBJECT-TYPE
			SYNTAX INTEGER
				{
				os1(1),
				os2(2)
				}
			MAX-ACCESS read-write
			STATUS current
			DESCRIPTION
				"Description"
			::= { sleSystemBaseControl 9 }

		
		-- 1.3.6.1.4.1.6296.101.1.1.2.10
		sleSystemControlClock OBJECT-TYPE
			SYNTAX OCTET STRING
			MAX-ACCESS read-write
			STATUS current
			DESCRIPTION
				"Description"
			::= { sleSystemBaseControl 10 }

		
		-- 1.3.6.1.4.1.6296.101.1.1.2.11
		sleSystemControlTimezone OBJECT-TYPE
			SYNTAX OCTET STRING
			MAX-ACCESS read-write
			STATUS current
			DESCRIPTION
				"Description"
			::= { sleSystemBaseControl 11 }

		
		-- 1.3.6.1.4.1.6296.101.1.1.2.12
		sleSystemControlDNSDomainName OBJECT-TYPE
			SYNTAX OCTET STRING
			MAX-ACCESS read-write
			STATUS current
			DESCRIPTION
				"Description"
			::= { sleSystemBaseControl 12 }

		
		-- 1.3.6.1.4.1.6296.101.1.1.2.13
		sleSystemControlInitBanner OBJECT-TYPE
			SYNTAX OCTET STRING
			MAX-ACCESS read-write
			STATUS current
			DESCRIPTION
				"Description"
			::= { sleSystemBaseControl 13 }

		
		-- 1.3.6.1.4.1.6296.101.1.1.2.14
		sleSystemControlSuccessBanner OBJECT-TYPE
			SYNTAX OCTET STRING
			MAX-ACCESS read-write
			STATUS current
			DESCRIPTION
				"Description"
			::= { sleSystemBaseControl 14 }

		
		-- 1.3.6.1.4.1.6296.101.1.1.2.15
		sleSystemControlFailBanner OBJECT-TYPE
			SYNTAX OCTET STRING
			MAX-ACCESS read-write
			STATUS current
			DESCRIPTION
				"Description"
			::= { sleSystemBaseControl 15 }

		
		-- 1.3.6.1.4.1.6296.101.1.1.2.16
		sleSystemControlSyslogState OBJECT-TYPE
			SYNTAX INTEGER
				{
				notAvailable(-2),
				stop(0),
				start(1)
				}
			MAX-ACCESS read-write
			STATUS current
			DESCRIPTION
				"Description"
			::= { sleSystemBaseControl 16 }

		
		-- 1.3.6.1.4.1.6296.101.1.1.2.17
		sleSystemControlSyslogVolatileNumber OBJECT-TYPE
			SYNTAX INTEGER
				{
				notAvailable(-2),
				clearLocalVolatileHistory(0)
				}
			MAX-ACCESS read-write
			STATUS current
			DESCRIPTION
				"Description"
			::= { sleSystemBaseControl 17 }

		
		-- 1.3.6.1.4.1.6296.101.1.1.2.18
		sleSystemControlSyslogNonVolatileNumber OBJECT-TYPE
			SYNTAX INTEGER
				{
				notAvailable(-2),
				clearLocalNonVolatileHistory(0)
				}
			MAX-ACCESS read-write
			STATUS current
			DESCRIPTION
				"Description"
			::= { sleSystemBaseControl 18 }

		
		-- 1.3.6.1.4.1.6296.101.1.1.2.19
		sleSystemControlSyslogBindAddress OBJECT-TYPE
			SYNTAX IpAddress
			MAX-ACCESS read-write
			STATUS current
			DESCRIPTION
				"Description"
			::= { sleSystemBaseControl 19 }

		
		-- 1.3.6.1.4.1.6296.101.1.1.2.20
		sleSystemControlSyslogLocalCode OBJECT-TYPE
			SYNTAX INTEGER (-1 | 0..7)
			MAX-ACCESS read-write
			STATUS current
			DESCRIPTION
				"Description"
			::= { sleSystemBaseControl 20 }

		
		-- 1.3.6.1.4.1.6296.101.1.1.2.21
		sleSystemControlSSHState OBJECT-TYPE
			SYNTAX INTEGER
				{
				disable(0),
				enable(1)
				}
			MAX-ACCESS read-write
			STATUS current
			DESCRIPTION
				"Description"
			::= { sleSystemBaseControl 21 }

		
		-- 1.3.6.1.4.1.6296.101.1.1.2.22
		sleSystemControlNTPState OBJECT-TYPE
			SYNTAX INTEGER
				{
				disable(0),
				ntp(1),
				sntp(2)
				}
			MAX-ACCESS read-write
			STATUS current
			DESCRIPTION
				"Description"
			::= { sleSystemBaseControl 22 }

		
		-- 1.3.6.1.4.1.6296.101.1.1.2.23
		sleSystemControlOSUpgradeNumber OBJECT-TYPE
			SYNTAX INTEGER
				{
				os1(1),
				os2(2)
				}
			MAX-ACCESS read-write
			STATUS current
			DESCRIPTION
				"Description"
			::= { sleSystemBaseControl 23 }

		
		-- 1.3.6.1.4.1.6296.101.1.1.2.24
		sleSystemControlServerAddress OBJECT-TYPE
			SYNTAX IpAddress
			MAX-ACCESS read-write
			STATUS current
			DESCRIPTION
				"Description"
			::= { sleSystemBaseControl 24 }

		
		-- 1.3.6.1.4.1.6296.101.1.1.2.25
		sleSystemControlUpDownFlag OBJECT-TYPE
			SYNTAX INTEGER
				{
				upload(0),
				download(1)
				}
			MAX-ACCESS read-write
			STATUS current
			DESCRIPTION
				"Description"
			::= { sleSystemBaseControl 25 }

		
		-- 1.3.6.1.4.1.6296.101.1.1.2.26
		sleSystemControlUserID OBJECT-TYPE
			SYNTAX OCTET STRING
			MAX-ACCESS read-write
			STATUS current
			DESCRIPTION
				"Description"
			::= { sleSystemBaseControl 26 }

		
		-- 1.3.6.1.4.1.6296.101.1.1.2.27
		sleSystemControlPassword OBJECT-TYPE
			SYNTAX OCTET STRING
			MAX-ACCESS read-write
			STATUS current
			DESCRIPTION
				"Description"
			::= { sleSystemBaseControl 27 }

		
		-- 1.3.6.1.4.1.6296.101.1.1.2.28
		sleSystemControlFileName OBJECT-TYPE
			SYNTAX OCTET STRING
			MAX-ACCESS read-write
			STATUS current
			DESCRIPTION
				"Description"
			::= { sleSystemBaseControl 28 }

		
		-- 1.3.6.1.4.1.6296.101.1.1.2.29
		sleSystemControlBackupFlag OBJECT-TYPE
			SYNTAX INTEGER
				{
				writeMemory(1),
				restoreFactoryDefault(2)
				}
			MAX-ACCESS read-write
			STATUS current
			DESCRIPTION
				"Description"
			::= { sleSystemBaseControl 29 }

		
		-- 1.3.6.1.4.1.6296.101.1.1.2.30
		sleSystemControlReloadOS OBJECT-TYPE
			SYNTAX INTEGER
				{
				notAvailable(0),
				os1(1),
				os2(2)
				}
			MAX-ACCESS read-write
			STATUS current
			DESCRIPTION
				"Description."
			::= { sleSystemBaseControl 30 }

		
		-- 1.3.6.1.4.1.6296.101.1.1.2.31
		sleSystemControlBackupInterval OBJECT-TYPE
			SYNTAX Integer32
			MAX-ACCESS read-write
			STATUS current
			DESCRIPTION
				"Description."
			::= { sleSystemBaseControl 31 }

		
		-- 1.3.6.1.4.1.6296.101.1.1.2.32
		sleSystemControlDhcpActivity OBJECT-TYPE
			SYNTAX INTEGER
				{
				disable(0),
				enable(1)
				}
			MAX-ACCESS read-write
			STATUS current
			DESCRIPTION
				"The activity of DHCP daemon."
			::= { sleSystemBaseControl 32 }

		
		-- 1.3.6.1.4.1.6296.101.1.1.2.33
		sleSystemControlDefaultTTL OBJECT-TYPE
			SYNTAX INTEGER (32..255)
			MAX-ACCESS read-write
			STATUS current
			DESCRIPTION
				"The default ttl."
			::= { sleSystemBaseControl 33 }

		
		-- 1.3.6.1.4.1.6296.101.1.1.2.34
		sleSystemControlSyslogVolatileSize OBJECT-TYPE
			SYNTAX INTEGER (1..2048)
			MAX-ACCESS read-write
			STATUS current
			DESCRIPTION
				"Description."
			::= { sleSystemBaseControl 34 }

		
		-- 1.3.6.1.4.1.6296.101.1.1.2.35
		sleSystemControlSyslogBindInterfaceName OBJECT-TYPE
			SYNTAX OCTET STRING
			MAX-ACCESS read-write
			STATUS current
			DESCRIPTION
				"Description."
			::= { sleSystemBaseControl 35 }

		
		-- 1.3.6.1.4.1.6296.101.1.1.2.36
		sleSystemControlSrcPort OBJECT-TYPE
			SYNTAX INTEGER (1..255)
			MAX-ACCESS read-write
			STATUS current
			DESCRIPTION
				"The source bridge port
				"
			::= { sleSystemBaseControl 36 }

		
		-- 1.3.6.1.4.1.6296.101.1.1.2.37
		sleSystemControlDstPort OBJECT-TYPE
			SYNTAX INTEGER (1..255)
			MAX-ACCESS read-write
			STATUS current
			DESCRIPTION
				"The destination bridge port"
			::= { sleSystemBaseControl 37 }

		
		-- 1.3.6.1.4.1.6296.101.1.1.2.38
		sleSystemControlSessionTime OBJECT-TYPE
			SYNTAX INTEGER (60..600)
			MAX-ACCESS read-write
			STATUS current
			DESCRIPTION
				"Description."
			::= { sleSystemBaseControl 38 }

		
		-- 1.3.6.1.4.1.6296.101.1.1.2.39
		sleSystemControlExecTimeout OBJECT-TYPE
			SYNTAX INTEGER (0..2147519)
			MAX-ACCESS read-write
			STATUS current
			DESCRIPTION
				"Description."
			::= { sleSystemBaseControl 39 }

		
		-- 1.3.6.1.4.1.6296.101.1.1.2.40
		sleSystemControlWatchdogStatus OBJECT-TYPE
			SYNTAX INTEGER
				{
				enable(1),
				disable(2)
				}
			MAX-ACCESS read-write
			STATUS current
			DESCRIPTION
				"Description."
			::= { sleSystemBaseControl 40 }

		
		-- 1.3.6.1.4.1.6296.101.1.1.2.41
		sleSystemControlClearOs OBJECT-TYPE
			SYNTAX Integer32
			MAX-ACCESS read-write
			STATUS current
			DESCRIPTION
				"Description."
			::= { sleSystemBaseControl 41 }

		
		-- 1.3.6.1.4.1.6296.101.1.1.2.42
		sleSystemControlNtpBindInterface OBJECT-TYPE
			SYNTAX OCTET STRING
			MAX-ACCESS read-write
			STATUS current
			DESCRIPTION
				"Description."
			::= { sleSystemBaseControl 42 }

		
		-- 1.3.6.1.4.1.6296.101.1.1.2.43
		sleSystemControlFtpBindInterface OBJECT-TYPE
			SYNTAX OCTET STRING
			MAX-ACCESS read-write
			STATUS current
			DESCRIPTION
				"Description."
			::= { sleSystemBaseControl 43 }

		
		-- 1.3.6.1.4.1.6296.101.1.1.2.44
		sleSystemControlSyslogVolMaxLine OBJECT-TYPE
			SYNTAX INTEGER (8..16384)
			MAX-ACCESS read-write
			STATUS current
			DESCRIPTION
				"Syslog volatile max line.
				(Supported only model 5924N)"
			::= { sleSystemBaseControl 44 }

		
		-- 1.3.6.1.4.1.6296.101.1.1.2.45
		sleSystemControlTempHighThreshold OBJECT-TYPE
			SYNTAX Integer32
			MAX-ACCESS read-write
			STATUS current
			DESCRIPTION
				"Description."
			::= { sleSystemBaseControl 45 }

		
		-- 1.3.6.1.4.1.6296.101.1.1.2.46
		sleSystemControlTempLowThreshold OBJECT-TYPE
			SYNTAX Integer32
			MAX-ACCESS read-write
			STATUS current
			DESCRIPTION
				"Description."
			::= { sleSystemBaseControl 46 }

		
		-- 1.3.6.1.4.1.6296.101.1.1.2.47
		sleSystemControlMemThreshold OBJECT-TYPE
			SYNTAX INTEGER (20..100)
			MAX-ACCESS read-write
			STATUS current
			DESCRIPTION
				"Description."
			::= { sleSystemBaseControl 47 }

		
		-- 1.3.6.1.4.1.6296.101.1.1.2.48
		sleSystemControlLowCPUThreshold OBJECT-TYPE
			SYNTAX INTEGER (20..100)
			MAX-ACCESS read-write
			STATUS current
			DESCRIPTION
				"Description."
			::= { sleSystemBaseControl 48 }

		
		-- 1.3.6.1.4.1.6296.101.1.1.2.49
		sleSystemControlLowCPUInterval OBJECT-TYPE
			SYNTAX INTEGER (5 | 60 | 600)
			MAX-ACCESS read-write
			STATUS current
			DESCRIPTION
				"Description."
			::= { sleSystemBaseControl 49 }

		
		-- 1.3.6.1.4.1.6296.101.1.1.2.50
		sleSystemControlNtpBindAddress OBJECT-TYPE
			SYNTAX IpAddress
			MAX-ACCESS read-write
			STATUS current
			DESCRIPTION
				"The NTP client binding address."
			DEFVAL { ''h }
			::= { sleSystemBaseControl 50 }

		
		-- 1.3.6.1.4.1.6296.101.1.1.2.51
		sleSystemControlEnablePasswdType OBJECT-TYPE
			SYNTAX INTEGER
				{
				plain(1),
				encrypt(2)
				}
			MAX-ACCESS read-write
			STATUS current
			DESCRIPTION
				"The type of enable password of command shell.
				plain : no encryption.
				encrypt : encryption"
			DEFVAL { 2 }
			::= { sleSystemBaseControl 51 }

		
		-- 1.3.6.1.4.1.6296.101.1.1.2.52
		sleSystemControlEnablePasswd OBJECT-TYPE
			SYNTAX OCTET STRING (SIZE (0..64))
			MAX-ACCESS read-write
			STATUS current
			DESCRIPTION
				"The enable password of command shell."
			::= { sleSystemBaseControl 52 }

		
		-- 1.3.6.1.4.1.6296.101.1.1.2.53
		sleSystemControlServicePasswdEncryption OBJECT-TYPE
			SYNTAX INTEGER
				{
				enable(1),
				disable(2)
				}
			MAX-ACCESS read-write
			STATUS current
			DESCRIPTION
				"The encrypt system passwords"
			DEFVAL { 2 }
			::= { sleSystemBaseControl 53 }

		
		-- 1.3.6.1.4.1.6296.101.1.1.2.54
		sleSystemControlNtpPollInterval OBJECT-TYPE
			SYNTAX Integer32 (6..20)
			MAX-ACCESS read-write
			STATUS current
			DESCRIPTION
				"The NTP request polling-interval"
			::= { sleSystemBaseControl 54 }

		
--  1.3.6.1.4.1.6296.101.1.1.2.55
		-- 1.3.6.1.4.1.6296.101.1.1.2.55
		sleSystemControlCPUDuration OBJECT-TYPE
			SYNTAX INTEGER (5..300)
			MAX-ACCESS read-write
			STATUS current
			DESCRIPTION
				"The threshold sampling duration."
			::= { sleSystemBaseControl 55 }

		
--  1.3.6.1.4.1.6296.101.1.1.2.56
		-- 1.3.6.1.4.1.6296.101.1.1.2.56
		sleSystemControlLowCPUDuration OBJECT-TYPE
			SYNTAX INTEGER (5..300)
			MAX-ACCESS read-write
			STATUS current
			DESCRIPTION
				"The threshold sampling duration."
			::= { sleSystemBaseControl 56 }

		
		-- 1.3.6.1.4.1.6296.101.1.1.2.57
		sleSystemControlWebMgmt OBJECT-TYPE
			SYNTAX INTEGER
				{
				enable(1),
				disable(2)
				}
			MAX-ACCESS read-only
			STATUS current
			DESCRIPTION
				"The web-management service status."
			::= { sleSystemBaseControl 57 }

		
		-- 1.3.6.1.4.1.6296.101.1.1.2.58
		sleSystemControlAutoReloadYear OBJECT-TYPE
			SYNTAX Integer32 (0 | 2008..2035)
			MAX-ACCESS read-write
			STATUS current
			DESCRIPTION
				"System Auto-Reload Year.
				0: clear auto-reload time"
			::= { sleSystemBaseControl 58 }

		
		-- 1.3.6.1.4.1.6296.101.1.1.2.59
		sleSystemControlAutoReloadMonth OBJECT-TYPE
			SYNTAX Integer32 (0..12)
			MAX-ACCESS read-write
			STATUS current
			DESCRIPTION
				"System Auto-Reload Month.
				0: clear auto-reload time"
			::= { sleSystemBaseControl 59 }

		
		-- 1.3.6.1.4.1.6296.101.1.1.2.60
		sleSystemControlAutoReloadDay OBJECT-TYPE
			SYNTAX Integer32 (0..31)
			MAX-ACCESS read-write
			STATUS current
			DESCRIPTION
				"System Auto-Reload Day
				0: clear auto-reload time"
			::= { sleSystemBaseControl 60 }

		
		-- 1.3.6.1.4.1.6296.101.1.1.2.61
		sleSystemControlAutoReloadHour OBJECT-TYPE
			SYNTAX Integer32 (0..23)
			MAX-ACCESS read-write
			STATUS current
			DESCRIPTION
				"System Auto-Reload Hour.
				0: clear auto-reload time"
			::= { sleSystemBaseControl 61 }

		
		-- 1.3.6.1.4.1.6296.101.1.1.2.62
		sleSystemControlAutoReloadMinutes OBJECT-TYPE
			SYNTAX Integer32 (0..59)
			MAX-ACCESS read-write
			STATUS current
			DESCRIPTION
				"System Auto-Reload Minutes
				0: clear auto-reload time"
			::= { sleSystemBaseControl 62 }

		
		-- 1.3.6.1.4.1.6296.101.1.1.2.63
		sleSystemControlAdministeredMac OBJECT-TYPE
			SYNTAX OCTET STRING
			MAX-ACCESS read-write
			STATUS current
			DESCRIPTION
				"The system administered MAC address."
			::= { sleSystemBaseControl 63 }

		
		-- 1.3.6.1.4.1.6296.101.1.1.3
		sleSystemBaseNotification OBJECT IDENTIFIER ::= { sleSystemBase 3 }

		
		-- 1.3.6.1.4.1.6296.101.1.1.3.1
		sleSystemSystemInfoProfileChanged NOTIFICATION-TYPE
			OBJECTS { sleSystemControlRequest, sleSystemControlTimeStamp, sleSystemControlReqResult, sleSystemHostName }
			STATUS current
			DESCRIPTION 
				"Description"
			::= { sleSystemBaseNotification 1 }

		
		-- 1.3.6.1.4.1.6296.101.1.1.3.2
		sleSystemCPUThresholdProfileChanged NOTIFICATION-TYPE
			OBJECTS { sleSystemControlRequest, sleSystemControlTimeStamp, sleSystemControlReqResult, sleSystemCPUThreshold, sleSystemCPUInterval, 
				sleSystemLowCPUThreshold, sleSystemLowCPUInterval }
			STATUS current
			DESCRIPTION 
				"Description"
			::= { sleSystemBaseNotification 2 }

		
		-- 1.3.6.1.4.1.6296.101.1.1.3.3
		sleSystemDefaultOSChanged NOTIFICATION-TYPE
			OBJECTS { sleSystemControlRequest, sleSystemControlTimeStamp, sleSystemControlReqResult, sleSystemDefaultOS }
			STATUS current
			DESCRIPTION 
				"Description"
			::= { sleSystemBaseNotification 3 }

		
		-- 1.3.6.1.4.1.6296.101.1.1.3.4
		sleSystemRTCProfileChanged NOTIFICATION-TYPE
			OBJECTS { sleSystemControlRequest, sleSystemControlTimeStamp, sleSystemControlReqResult, sleSystemClock, sleSystemTimezone
				 }
			STATUS current
			DESCRIPTION 
				"Description"
			::= { sleSystemBaseNotification 4 }

		
		-- 1.3.6.1.4.1.6296.101.1.1.3.5
		sleSystemDNSDomainNameChanged NOTIFICATION-TYPE
			OBJECTS { sleSystemControlRequest, sleSystemControlTimeStamp, sleSystemControlReqResult, sleSystemDNSDomainName }
			STATUS current
			DESCRIPTION 
				"Description"
			::= { sleSystemBaseNotification 5 }

		
		-- 1.3.6.1.4.1.6296.101.1.1.3.6
		sleSystemBannerProfileChanged NOTIFICATION-TYPE
			OBJECTS { sleSystemControlRequest, sleSystemControlTimeStamp, sleSystemControlReqResult, sleSystemInitBanner, sleSystemSuccessBanner, 
				sleSystemFailBanner }
			STATUS current
			DESCRIPTION 
				"Description"
			::= { sleSystemBaseNotification 6 }

		
		-- 1.3.6.1.4.1.6296.101.1.1.3.7
		sleSystemSyslogProfileChanged NOTIFICATION-TYPE
			OBJECTS { sleSystemControlRequest, sleSystemControlTimeStamp, sleSystemSyslogVolatileSize, sleSystemSyslogVolatileMaxLine, sleSystemControlReqResult, 
				sleSystemSyslogState, sleSystemSyslogVolatileNumber, sleSystemSyslogNonVolatileNumber, sleSystemSyslogBindAddress, sleSystemSyslogLocalCode
				 }
			STATUS current
			DESCRIPTION 
				"Description"
			::= { sleSystemBaseNotification 7 }

		
		-- 1.3.6.1.4.1.6296.101.1.1.3.8
		sleSystemSSHStateChanged NOTIFICATION-TYPE
			OBJECTS { sleSystemControlRequest, sleSystemControlTimeStamp, sleSystemControlReqResult, sleSystemSSHState }
			STATUS current
			DESCRIPTION 
				"Description"
			::= { sleSystemBaseNotification 8 }

		
		-- 1.3.6.1.4.1.6296.101.1.1.3.9
		sleSystemNTPStateChanged NOTIFICATION-TYPE
			OBJECTS { sleSystemControlRequest, sleSystemControlTimeStamp, sleSystemControlReqResult, sleSystemNTPState }
			STATUS current
			DESCRIPTION 
				"Description"
			::= { sleSystemBaseNotification 9 }

		
		-- 1.3.6.1.4.1.6296.101.1.1.3.10
		sleSystemOSProfileChanged NOTIFICATION-TYPE
			OBJECTS { sleSystemControlRequest, sleSystemControlTimeStamp, sleSystemControlReqResult, sleSystemControlOSUpgradeNumber }
			STATUS current
			DESCRIPTION 
				"Description"
			::= { sleSystemBaseNotification 10 }

		
		-- 1.3.6.1.4.1.6296.101.1.1.3.11
		sleSystemBackupChanged NOTIFICATION-TYPE
			OBJECTS { sleSystemControlRequest, sleSystemControlTimeStamp, sleSystemControlReqResult, sleSystemControlBackupFlag }
			STATUS current
			DESCRIPTION 
				"Description"
			::= { sleSystemBaseNotification 11 }

		
		-- 1.3.6.1.4.1.6296.101.1.1.3.12
		sleSystemBackupIntervalChanged NOTIFICATION-TYPE
			OBJECTS { sleSystemControlRequest, sleSystemControlReqResult, sleSystemControlTimeStamp, sleSystemBackupInterval }
			STATUS current
			DESCRIPTION 
				"Description."
			::= { sleSystemBaseNotification 12 }

		
		-- 1.3.6.1.4.1.6296.101.1.1.3.13
		sleSystemDhcpActivityChanged NOTIFICATION-TYPE
			OBJECTS { sleSystemControlRequest, sleSystemControlTimeStamp, sleSystemControlReqResult, sleSystemDhcpActivity }
			STATUS current
			DESCRIPTION 
				"Description."
			::= { sleSystemBaseNotification 13 }

		
		-- 1.3.6.1.4.1.6296.101.1.1.3.14
		sleSystemDefaultTTLChanged NOTIFICATION-TYPE
			OBJECTS { sleSystemControlRequest, sleSystemControlTimeStamp, sleSystemControlReqResult, sleSystemDefaultTTL }
			STATUS current
			DESCRIPTION 
				"Description."
			::= { sleSystemBaseNotification 14 }

		
		-- 1.3.6.1.4.1.6296.101.1.1.3.15
		sleSystemSyslogBindInterfaceNameChanged NOTIFICATION-TYPE
			OBJECTS { sleSystemControlRequest, sleSystemControlTimeStamp, sleSystemControlReqResult, sleSystemSyslogState, sleSystemSyslogBindInterfaceName
				 }
			STATUS current
			DESCRIPTION 
				"Description."
			::= { sleSystemBaseNotification 15 }

		
		-- 1.3.6.1.4.1.6296.101.1.1.3.16
		sleSystemSyslogBindInterfaceNameCleared NOTIFICATION-TYPE
			OBJECTS { sleSystemControlRequest, sleSystemControlTimeStamp, sleSystemControlReqResult }
			STATUS current
			DESCRIPTION 
				"Description."
			::= { sleSystemBaseNotification 16 }

		
		-- 1.3.6.1.4.1.6296.101.1.1.3.17
		sleSystemConfigPortMoved NOTIFICATION-TYPE
			OBJECTS { sleSystemControlRequest, sleSystemControlTimeStamp, sleSystemControlReqResult, sleSystemControlSrcPort, sleSystemControlDstPort
				 }
			STATUS current
			DESCRIPTION 
				"Description."
			::= { sleSystemBaseNotification 17 }

		
		-- 1.3.6.1.4.1.6296.101.1.1.3.18
		sleSystemConfigPortCopied NOTIFICATION-TYPE
			OBJECTS { sleSystemControlRequest, sleSystemControlTimeStamp, sleSystemControlReqResult, sleSystemControlSrcPort, sleSystemControlDstPort
				 }
			STATUS current
			DESCRIPTION 
				"Description."
			::= { sleSystemBaseNotification 18 }

		
		-- 1.3.6.1.4.1.6296.101.1.1.3.19
		sleSystemConfigPortCleared NOTIFICATION-TYPE
			OBJECTS { sleSystemControlRequest, sleSystemControlTimeStamp, sleSystemControlReqResult, sleSystemControlSrcPort, sleSystemControlDstPort
				 }
			STATUS current
			DESCRIPTION 
				"Description."
			::= { sleSystemBaseNotification 19 }

		
		-- 1.3.6.1.4.1.6296.101.1.1.3.20
		sleSystemSessionTimeChanged NOTIFICATION-TYPE
			OBJECTS { sleSystemControlRequest, sleSystemControlTimeStamp, sleSystemControlReqResult, sleSystemSessionTime }
			STATUS current
			DESCRIPTION 
				"Description."
			::= { sleSystemBaseNotification 20 }

		
		-- 1.3.6.1.4.1.6296.101.1.1.3.21
		sleSystemExecTimeoutChanged NOTIFICATION-TYPE
			OBJECTS { sleSystemControlRequest, sleSystemControlTimeStamp, sleSystemControlReqResult, sleSystemExecTimeout }
			STATUS current
			DESCRIPTION 
				"Description."
			::= { sleSystemBaseNotification 21 }

		
		-- 1.3.6.1.4.1.6296.101.1.1.3.22
		sleSystemWatchdogStatusChanged NOTIFICATION-TYPE
			OBJECTS { sleSystemControlRequest, sleSystemControlTimeStamp, sleSystemControlReqResult, sleSystemWatchdogStatus }
			STATUS current
			DESCRIPTION 
				"Description."
			::= { sleSystemBaseNotification 22 }

		
		-- 1.3.6.1.4.1.6296.101.1.1.3.23
		sleSystemNosDestroyed NOTIFICATION-TYPE
			OBJECTS { sleSystemControlRequest, sleSystemControlTimeStamp, sleSystemControlReqResult, sleSystemControlClearOs }
			STATUS current
			DESCRIPTION 
				"Description."
			::= { sleSystemBaseNotification 23 }

		
		-- 1.3.6.1.4.1.6296.101.1.1.3.24
		sleSystemNtpBindInterfaceChanged NOTIFICATION-TYPE
			OBJECTS { sleSystemControlRequest, sleSystemControlTimeStamp, sleSystemControlReqResult, sleSystemNtpBindInterface }
			STATUS current
			DESCRIPTION 
				"Description."
			::= { sleSystemBaseNotification 24 }

		
		-- 1.3.6.1.4.1.6296.101.1.1.3.25
		sleSystemFtpBindInterfaceChanged NOTIFICATION-TYPE
			OBJECTS { sleSystemControlRequest, sleSystemControlTimeStamp, sleSystemControlReqResult, sleSystemFtpBindInterface }
			STATUS current
			DESCRIPTION 
				"Description."
			::= { sleSystemBaseNotification 25 }

		
		-- 1.3.6.1.4.1.6296.101.1.1.3.26
		sleSystemRedundancyPortChanged NOTIFICATION-TYPE
			OBJECTS { sleSystemControlRequest, sleSystemControlTimeStamp, sleSystemControlReqResult, sleSystemControlSrcPort }
			STATUS current
			DESCRIPTION 
				"Description."
			::= { sleSystemBaseNotification 26 }

		
		-- 1.3.6.1.4.1.6296.101.1.1.3.27
		sleRedundancyPortCleared NOTIFICATION-TYPE
			OBJECTS { sleSystemControlRequest, sleSystemControlTimeStamp, sleSystemControlReqResult }
			STATUS current
			DESCRIPTION 
				"Description."
			::= { sleSystemBaseNotification 27 }

		
		-- 1.3.6.1.4.1.6296.101.1.1.3.28
		sleSystemTempThresholdChanged NOTIFICATION-TYPE
			OBJECTS { sleSystemControlRequest, sleSystemControlTimeStamp, sleSystemControlReqResult, sleSystemControlTempHighThreshold, sleSystemControlTempLowThreshold
				 }
			STATUS current
			DESCRIPTION 
				"Description."
			::= { sleSystemBaseNotification 28 }

		
		-- 1.3.6.1.4.1.6296.101.1.1.3.29
		sleSystemMemThresholdChanged NOTIFICATION-TYPE
			OBJECTS { sleSystemControlRequest, sleSystemControlTimeStamp, sleSystemControlReqResult, sleSystemControlMemThreshold }
			STATUS current
			DESCRIPTION 
				"Description."
			::= { sleSystemBaseNotification 29 }

		
		-- 1.3.6.1.4.1.6296.101.1.1.3.30
		sleSystemBootloaderProfileChanged NOTIFICATION-TYPE
			OBJECTS { sleSystemControlRequest, sleSystemControlTimeStamp, sleSystemControlReqResult }
			STATUS current
			DESCRIPTION 
				"Description"
			::= { sleSystemBaseNotification 30 }

		
		-- 1.3.6.1.4.1.6296.101.1.1.3.31
		sleSystemNtpBindAddressChanged NOTIFICATION-TYPE
			OBJECTS { sleSystemControlRequest, sleSystemControlTimeStamp, sleSystemControlReqResult, sleSystemControlNtpBindAddress }
			STATUS current
			DESCRIPTION 
				"Description."
			::= { sleSystemBaseNotification 31 }

		
		-- 1.3.6.1.4.1.6296.101.1.1.3.32
		sleSystemEnablePasswdChanged NOTIFICATION-TYPE
			OBJECTS { sleSystemControlRequest, sleSystemControlTimeStamp, sleSystemControlReqResult, sleSystemControlEnablePasswdType, sleSystemControlEnablePasswd
				 }
			STATUS current
			DESCRIPTION 
				"Description."
			::= { sleSystemBaseNotification 32 }

		
		-- 1.3.6.1.4.1.6296.101.1.1.3.33
		sleSystemEnableServicePasswdEncryptionChanged NOTIFICATION-TYPE
			OBJECTS { sleSystemControlRequest, sleSystemControlTimeStamp, sleSystemControlReqResult, sleSystemControlServicePasswdEncryption }
			STATUS current
			DESCRIPTION 
				"Encrypt system passwords"
			::= { sleSystemBaseNotification 33 }

		
		-- 1.3.6.1.4.1.6296.101.1.1.3.34
		sleSystemPasswdRestored NOTIFICATION-TYPE
			OBJECTS { sleSystemControlRequest, sleSystemControlTimeStamp, sleSystemControlReqResult }
			STATUS current
			DESCRIPTION 
				"Description."
			::= { sleSystemBaseNotification 34 }

		
		-- 1.3.6.1.4.1.6296.101.1.1.3.35
		sleSystemNtpPollIntervalChanged NOTIFICATION-TYPE
			OBJECTS { sleSystemControlRequest, sleSystemControlTimeStamp, sleSystemControlReqResult, sleSystemNtpPollnterval }
			STATUS current
			DESCRIPTION 
				"Description."
			::= { sleSystemBaseNotification 35 }

		
		-- 1.3.6.1.4.1.6296.101.1.1.3.36
		sleSystemRestoreFactoryChanged NOTIFICATION-TYPE
			OBJECTS { sleSystemControlRequest, sleSystemControlTimeStamp, sleSystemControlReqResult }
			STATUS current
			DESCRIPTION 
				"The command of restory factory."
			::= { sleSystemBaseNotification 36 }

		
		-- 1.3.6.1.4.1.6296.101.1.1.3.37
		sleSystemWebMgmtChanged NOTIFICATION-TYPE
			OBJECTS { sleSystemControlRequest, sleSystemControlTimeStamp, sleSystemControlReqResult, sleSystemControlWebMgmt }
			STATUS current
			DESCRIPTION 
				"setWebMgmtStatus"
			::= { sleSystemBaseNotification 37 }

		
		-- 1.3.6.1.4.1.6296.101.1.1.3.38
		sleSystemAutoReloadInTimeChanged NOTIFICATION-TYPE
			OBJECTS { sleSystemControlRequest, sleSystemControlReqResult, sleSystemControlTimeStamp, sleSystemAutoReloadInHour, sleSystemAutoReloadInMinutes
				 }
			STATUS current
			DESCRIPTION 
				"set auto reload in time"
			::= { sleSystemBaseNotification 38 }

		
		-- 1.3.6.1.4.1.6296.101.1.1.3.39
		sleSystemAutoReloadDailyTimeChanged NOTIFICATION-TYPE
			OBJECTS { sleSystemControlRequest, sleSystemControlReqResult, sleSystemControlTimeStamp, sleSystemAutoReloadDailyMinutes, sleSystemAutoReloadDailyHour
				 }
			STATUS current
			DESCRIPTION 
				"set auto reload daily time"
			::= { sleSystemBaseNotification 39 }

		
		-- 1.3.6.1.4.1.6296.101.1.1.3.40
		sleSystemAutoReloadAtTimeChanged NOTIFICATION-TYPE
			OBJECTS { sleSystemControlRequest, sleSystemControlReqResult, sleSystemControlTimeStamp, sleSystemAutpReloadAtMinutes, sleSystemAutpReloadAtHour, 
				sleSystemAutoReloadAtDay, sleSystemAutoReloadAtMonth, sleSystemAutoReloadAtYear }
			STATUS current
			DESCRIPTION 
				"set auto reload at time"
			::= { sleSystemBaseNotification 40 }

		
		-- 1.3.6.1.4.1.6296.101.1.1.3.41
		sleSystemAdministeredMacChanged NOTIFICATION-TYPE
			OBJECTS { sleSystemControlRequest, sleSystemControlTimeStamp, sleSystemControlReqResult, sleSystemControlAdministeredMac }
			STATUS current
			DESCRIPTION 
				"setSystemAdministeredMac"
			::= { sleSystemBaseNotification 41 }

		
		-- 1.3.6.1.4.1.6296.101.1.1.4
		sleSystemBaseSlotInfo OBJECT IDENTIFIER ::= { sleSystemBase 4 }

		
		-- 1.3.6.1.4.1.6296.101.1.1.4.1
		sleSystemBaseSlotInfoTable OBJECT-TYPE
			SYNTAX SEQUENCE OF SleSystemBaseSlotInfoEntry
			MAX-ACCESS not-accessible
			STATUS current
			DESCRIPTION
				"Description."
			::= { sleSystemBaseSlotInfo 1 }

		
		-- 1.3.6.1.4.1.6296.101.1.1.4.1.1
		sleSystemBaseSlotInfoEntry OBJECT-TYPE
			SYNTAX SleSystemBaseSlotInfoEntry
			MAX-ACCESS not-accessible
			STATUS current
			DESCRIPTION
				"Description."
			INDEX { sleSystemSlotIndex }
			::= { sleSystemBaseSlotInfoTable 1 }

		
		SleSystemBaseSlotInfoEntry ::=
			SEQUENCE { 
				sleSystemSlotIndex
					Integer32,
				sleSystemSlotUptime
					TimeTicks,
				sleSystemSlotModelName
					OCTET STRING,
				sleSystemSlotSerialNumber
					OCTET STRING,
				sleSystemSlotHWVersion
					OCTET STRING,
				sleSystemSlotBLVersion
					OCTET STRING,
				sleSystemSlotSWCompatibility
					OCTET STRING,
				sleSystemSlotOSVersion
					OCTET STRING,
				sleSystemSlotMacAddress
					OCTET STRING,
				sleSystemSlotCPULoadAll
					OCTET STRING,
				sleSystemSlotCPULoadInterrupt
					OCTET STRING,
				sleSystemSlotMemoryTotal
					Unsigned32,
				sleSystemSlotMemoryFree
					Unsigned32,
				sleSystemSlotMemoryShared
					Unsigned32,
				sleSystemSlotMemoryBuffers
					Unsigned32,
				sleSystemSlotMemoryCached
					Unsigned32,
				sleSystemSlotMemorySwapTotal
					Unsigned32,
				sleSystemSlotMemorySwapFree
					Unsigned32,
				sleSystemSlotBootReason
					INTEGER,
				sleSystemSlotBootTime
					Unsigned32,
				sleSystemSlotVoltage
					Unsigned32
			 }

		-- 1.3.6.1.4.1.6296.101.1.1.4.1.1.1
		sleSystemSlotIndex OBJECT-TYPE
			SYNTAX Integer32 (0..64)
			MAX-ACCESS read-only
			STATUS current
			DESCRIPTION
				"Description."
			::= { sleSystemBaseSlotInfoEntry 1 }

		
		-- 1.3.6.1.4.1.6296.101.1.1.4.1.1.2
		sleSystemSlotUptime OBJECT-TYPE
			SYNTAX TimeTicks
			MAX-ACCESS read-only
			STATUS current
			DESCRIPTION
				"Description."
			::= { sleSystemBaseSlotInfoEntry 2 }

		
		-- 1.3.6.1.4.1.6296.101.1.1.4.1.1.3
		sleSystemSlotModelName OBJECT-TYPE
			SYNTAX OCTET STRING
			MAX-ACCESS read-only
			STATUS current
			DESCRIPTION
				"Description."
			::= { sleSystemBaseSlotInfoEntry 3 }

		
		-- 1.3.6.1.4.1.6296.101.1.1.4.1.1.4
		sleSystemSlotSerialNumber OBJECT-TYPE
			SYNTAX OCTET STRING
			MAX-ACCESS read-only
			STATUS current
			DESCRIPTION
				"Description."
			::= { sleSystemBaseSlotInfoEntry 4 }

		
		-- 1.3.6.1.4.1.6296.101.1.1.4.1.1.5
		sleSystemSlotHWVersion OBJECT-TYPE
			SYNTAX OCTET STRING
			MAX-ACCESS read-only
			STATUS current
			DESCRIPTION
				"Description."
			::= { sleSystemBaseSlotInfoEntry 5 }

		
		-- 1.3.6.1.4.1.6296.101.1.1.4.1.1.6
		sleSystemSlotBLVersion OBJECT-TYPE
			SYNTAX OCTET STRING
			MAX-ACCESS read-only
			STATUS current
			DESCRIPTION
				"Description."
			::= { sleSystemBaseSlotInfoEntry 6 }

		
		-- 1.3.6.1.4.1.6296.101.1.1.4.1.1.7
		sleSystemSlotSWCompatibility OBJECT-TYPE
			SYNTAX OCTET STRING
			MAX-ACCESS read-only
			STATUS current
			DESCRIPTION
				"Description."
			::= { sleSystemBaseSlotInfoEntry 7 }

		
		-- 1.3.6.1.4.1.6296.101.1.1.4.1.1.8
		sleSystemSlotOSVersion OBJECT-TYPE
			SYNTAX OCTET STRING
			MAX-ACCESS read-only
			STATUS current
			DESCRIPTION
				"Description."
			::= { sleSystemBaseSlotInfoEntry 8 }

		
		-- 1.3.6.1.4.1.6296.101.1.1.4.1.1.9
		sleSystemSlotMacAddress OBJECT-TYPE
			SYNTAX OCTET STRING
			MAX-ACCESS read-only
			STATUS current
			DESCRIPTION
				"Description."
			::= { sleSystemBaseSlotInfoEntry 9 }

		
		-- 1.3.6.1.4.1.6296.101.1.1.4.1.1.10
		sleSystemSlotCPULoadAll OBJECT-TYPE
			SYNTAX OCTET STRING
			MAX-ACCESS read-only
			STATUS current
			DESCRIPTION
				"Description."
			::= { sleSystemBaseSlotInfoEntry 10 }

		
		-- 1.3.6.1.4.1.6296.101.1.1.4.1.1.11
		sleSystemSlotCPULoadInterrupt OBJECT-TYPE
			SYNTAX OCTET STRING
			MAX-ACCESS read-only
			STATUS current
			DESCRIPTION
				"Description."
			::= { sleSystemBaseSlotInfoEntry 11 }

		
		-- 1.3.6.1.4.1.6296.101.1.1.4.1.1.12
		sleSystemSlotMemoryTotal OBJECT-TYPE
			SYNTAX Unsigned32
			MAX-ACCESS read-only
			STATUS current
			DESCRIPTION
				"Description."
			::= { sleSystemBaseSlotInfoEntry 12 }

		
		-- 1.3.6.1.4.1.6296.101.1.1.4.1.1.13
		sleSystemSlotMemoryFree OBJECT-TYPE
			SYNTAX Unsigned32
			MAX-ACCESS read-only
			STATUS current
			DESCRIPTION
				"Description."
			::= { sleSystemBaseSlotInfoEntry 13 }

		
		-- 1.3.6.1.4.1.6296.101.1.1.4.1.1.14
		sleSystemSlotMemoryShared OBJECT-TYPE
			SYNTAX Unsigned32
			MAX-ACCESS read-only
			STATUS current
			DESCRIPTION
				"Description."
			::= { sleSystemBaseSlotInfoEntry 14 }

		
		-- 1.3.6.1.4.1.6296.101.1.1.4.1.1.15
		sleSystemSlotMemoryBuffers OBJECT-TYPE
			SYNTAX Unsigned32
			MAX-ACCESS read-only
			STATUS current
			DESCRIPTION
				"Description."
			::= { sleSystemBaseSlotInfoEntry 15 }

		
		-- 1.3.6.1.4.1.6296.101.1.1.4.1.1.16
		sleSystemSlotMemoryCached OBJECT-TYPE
			SYNTAX Unsigned32
			MAX-ACCESS read-only
			STATUS current
			DESCRIPTION
				"Description."
			::= { sleSystemBaseSlotInfoEntry 16 }

		
		-- 1.3.6.1.4.1.6296.101.1.1.4.1.1.17
		sleSystemSlotMemorySwapTotal OBJECT-TYPE
			SYNTAX Unsigned32
			MAX-ACCESS read-only
			STATUS current
			DESCRIPTION
				"Description."
			::= { sleSystemBaseSlotInfoEntry 17 }

		
		-- 1.3.6.1.4.1.6296.101.1.1.4.1.1.18
		sleSystemSlotMemorySwapFree OBJECT-TYPE
			SYNTAX Unsigned32
			MAX-ACCESS read-only
			STATUS current
			DESCRIPTION
				"Description."
			::= { sleSystemBaseSlotInfoEntry 18 }

		
		-- 1.3.6.1.4.1.6296.101.1.1.4.1.1.19
		sleSystemSlotBootReason OBJECT-TYPE
			SYNTAX INTEGER
				{
				error(0),
				powerboot(1),
				panic(2),
				swreboot(3),
				lowmemory(4),
				watchdog(5),
				swWatchdog(9),
				swrebootBySfu(11)
				}
			MAX-ACCESS read-only
			STATUS current
			DESCRIPTION
				"Description."
			::= { sleSystemBaseSlotInfoEntry 19 }

		
		-- 1.3.6.1.4.1.6296.101.1.1.4.1.1.20
		sleSystemSlotBootTime OBJECT-TYPE
			SYNTAX Unsigned32
			UNITS "1 second"
			MAX-ACCESS read-only
			STATUS current
			DESCRIPTION
				"Description."
			::= { sleSystemBaseSlotInfoEntry 20 }

		
		-- 1.3.6.1.4.1.6296.101.1.1.4.1.1.21
		sleSystemSlotVoltage OBJECT-TYPE
			SYNTAX Unsigned32
			UNITS "0.1 v"
			MAX-ACCESS read-only
			STATUS current
			DESCRIPTION
				"Description."
			::= { sleSystemBaseSlotInfoEntry 21 }

		
		-- 1.3.6.1.4.1.6296.101.1.2
		sleDNSServer OBJECT IDENTIFIER ::= { sleSystemMaintenance 2 }

		
		-- 1.3.6.1.4.1.6296.101.1.2.1
		sleDNSServerTable OBJECT-TYPE
			SYNTAX SEQUENCE OF SleDNSServerEntry
			MAX-ACCESS not-accessible
			STATUS current
			DESCRIPTION
				"Description."
			::= { sleDNSServer 1 }

		
		-- 1.3.6.1.4.1.6296.101.1.2.1.1
		sleDNSServerEntry OBJECT-TYPE
			SYNTAX SleDNSServerEntry
			MAX-ACCESS not-accessible
			STATUS current
			DESCRIPTION
				"Description."
			INDEX { sleDNSServerIndex }
			::= { sleDNSServerTable 1 }

		
		SleDNSServerEntry ::=
			SEQUENCE { 
				sleDNSServerIndex
					Integer32,
				sleDNSServerName
					IpAddress
			 }

		-- 1.3.6.1.4.1.6296.101.1.2.1.1.1
		sleDNSServerIndex OBJECT-TYPE
			SYNTAX Integer32 (1..65535)
			MAX-ACCESS read-write
			STATUS current
			DESCRIPTION
				"DNS server index"
			::= { sleDNSServerEntry 1 }

		
		-- 1.3.6.1.4.1.6296.101.1.2.1.1.2
		sleDNSServerName OBJECT-TYPE
			SYNTAX IpAddress
			MAX-ACCESS read-only
			STATUS current
			DESCRIPTION
				"Registered DNS server name"
			::= { sleDNSServerEntry 2 }

		
		-- 1.3.6.1.4.1.6296.101.1.2.2
		sleDNSServerControl OBJECT IDENTIFIER ::= { sleDNSServer 2 }

		
		-- 1.3.6.1.4.1.6296.101.1.2.2.1
		sleDNSServerControlRequest OBJECT-TYPE
			SYNTAX INTEGER
				{
				createDNSServer(1),
				destroyDNSServer(2)
				}
			MAX-ACCESS read-write
			STATUS current
			DESCRIPTION
				"Description"
			::= { sleDNSServerControl 1 }

		
		-- 1.3.6.1.4.1.6296.101.1.2.2.2
		sleDNSServerControlStatus OBJECT-TYPE
			SYNTAX SleControlStatusType
			MAX-ACCESS read-only
			STATUS current
			DESCRIPTION
				"Description"
			::= { sleDNSServerControl 2 }

		
		-- 1.3.6.1.4.1.6296.101.1.2.2.3
		sleDNSServerControlTimer OBJECT-TYPE
			SYNTAX Gauge32
			MAX-ACCESS read-write
			STATUS current
			DESCRIPTION
				"Description"
			::= { sleDNSServerControl 3 }

		
		-- 1.3.6.1.4.1.6296.101.1.2.2.4
		sleDNSServerControlTImeStamp OBJECT-TYPE
			SYNTAX TimeTicks
			MAX-ACCESS read-only
			STATUS current
			DESCRIPTION
				"Description"
			::= { sleDNSServerControl 4 }

		
		-- 1.3.6.1.4.1.6296.101.1.2.2.5
		sleDNSServerControlReqResult OBJECT-TYPE
			SYNTAX SleControlRequestResultType
			MAX-ACCESS read-only
			STATUS current
			DESCRIPTION
				"Description"
			::= { sleDNSServerControl 5 }

		
		-- 1.3.6.1.4.1.6296.101.1.2.2.6
		sleDNSServerControlIndex OBJECT-TYPE
			SYNTAX Integer32
			MAX-ACCESS read-write
			STATUS current
			DESCRIPTION
				"This is corresponded to sleDNSServerIndex."
			::= { sleDNSServerControl 6 }

		
		-- 1.3.6.1.4.1.6296.101.1.2.2.7
		sleDNSServerControlName OBJECT-TYPE
			SYNTAX IpAddress
			MAX-ACCESS read-write
			STATUS current
			DESCRIPTION
				"This is corresponded to sleDNSServerName."
			::= { sleDNSServerControl 7 }

		
		-- 1.3.6.1.4.1.6296.101.1.2.3
		sleDNSServerNotification OBJECT IDENTIFIER ::= { sleDNSServer 3 }

		
		-- 1.3.6.1.4.1.6296.101.1.2.3.1
		sleDNSServerCreated NOTIFICATION-TYPE
			OBJECTS { sleDNSServerControlRequest, sleDNSServerControlReqResult, sleDNSServerControlTImeStamp, sleDNSServerName }
			STATUS current
			DESCRIPTION 
				"Description"
			::= { sleDNSServerNotification 1 }

		
		-- 1.3.6.1.4.1.6296.101.1.2.3.2
		sleDNSServerDestroyed NOTIFICATION-TYPE
			OBJECTS { sleDNSServerControlRequest, sleDNSServerControlReqResult, sleDNSServerControlTImeStamp, sleDNSServerControlIndex }
			STATUS current
			DESCRIPTION 
				"Description"
			::= { sleDNSServerNotification 2 }

		
		-- 1.3.6.1.4.1.6296.101.1.3
		sleLogin OBJECT IDENTIFIER ::= { sleSystemMaintenance 3 }

		
		-- 1.3.6.1.4.1.6296.101.1.3.1
		sleLoginTable OBJECT-TYPE
			SYNTAX SEQUENCE OF SleLoginEntry
			MAX-ACCESS not-accessible
			STATUS current
			DESCRIPTION
				"Description."
			::= { sleLogin 1 }

		
		-- 1.3.6.1.4.1.6296.101.1.3.1.1
		sleLoginEntry OBJECT-TYPE
			SYNTAX SleLoginEntry
			MAX-ACCESS not-accessible
			STATUS current
			DESCRIPTION
				"Description."
			INDEX { sleLoginIndex }
			::= { sleLoginTable 1 }

		
		SleLoginEntry ::=
			SEQUENCE { 
				sleLoginIndex
					Integer32,
				sleLoginUser
					OCTET STRING,
				sleLoginTTY
					OCTET STRING,
				sleLoginRemote
					OCTET STRING,
				sleLoginTime
					OCTET STRING
			 }

		-- 1.3.6.1.4.1.6296.101.1.3.1.1.1
		sleLoginIndex OBJECT-TYPE
			SYNTAX Integer32 (1..65536)
			MAX-ACCESS read-only
			STATUS current
			DESCRIPTION
				"Logined user's index"
			::= { sleLoginEntry 1 }

		
		-- 1.3.6.1.4.1.6296.101.1.3.1.1.2
		sleLoginUser OBJECT-TYPE
			SYNTAX OCTET STRING
			MAX-ACCESS read-only
			STATUS current
			DESCRIPTION
				"Logined user name"
			::= { sleLoginEntry 2 }

		
		-- 1.3.6.1.4.1.6296.101.1.3.1.1.3
		sleLoginTTY OBJECT-TYPE
			SYNTAX OCTET STRING
			MAX-ACCESS read-only
			STATUS current
			DESCRIPTION
				"The login user's terminal"
			::= { sleLoginEntry 3 }

		
		-- 1.3.6.1.4.1.6296.101.1.3.1.1.4
		sleLoginRemote OBJECT-TYPE
			SYNTAX OCTET STRING
			MAX-ACCESS read-only
			STATUS current
			DESCRIPTION
				"Remote host"
			::= { sleLoginEntry 4 }

		
		-- 1.3.6.1.4.1.6296.101.1.3.1.1.5
		sleLoginTime OBJECT-TYPE
			SYNTAX OCTET STRING
			MAX-ACCESS read-only
			STATUS current
			DESCRIPTION
				"Logined time."
			::= { sleLoginEntry 5 }

		
		-- 1.3.6.1.4.1.6296.101.1.4
		sleBackup OBJECT IDENTIFIER ::= { sleSystemMaintenance 4 }

		
		-- 1.3.6.1.4.1.6296.101.1.4.1
		sleBackupTable OBJECT-TYPE
			SYNTAX SEQUENCE OF SleBackupEntry
			MAX-ACCESS not-accessible
			STATUS current
			DESCRIPTION
				"Description."
			::= { sleBackup 1 }

		
		-- 1.3.6.1.4.1.6296.101.1.4.1.1
		sleBackupEntry OBJECT-TYPE
			SYNTAX SleBackupEntry
			MAX-ACCESS not-accessible
			STATUS current
			DESCRIPTION
				"Description."
			INDEX { sleBackupConfigFile }
			::= { sleBackupTable 1 }

		
		SleBackupEntry ::=
			SEQUENCE { 
				sleBackupConfigFile
					OCTET STRING
			 }

		-- 1.3.6.1.4.1.6296.101.1.4.1.1.1
		sleBackupConfigFile OBJECT-TYPE
			SYNTAX OCTET STRING
			MAX-ACCESS read-only
			STATUS current
			DESCRIPTION
				"Copied configuration file name'running-config' is reserved config name."
			::= { sleBackupEntry 1 }

		
		-- 1.3.6.1.4.1.6296.101.1.4.2
		sleBackupControl OBJECT IDENTIFIER ::= { sleBackup 2 }

		
		-- 1.3.6.1.4.1.6296.101.1.4.2.1
		sleBackupControlRequest OBJECT-TYPE
			SYNTAX INTEGER
				{
				createBackup(1),
				destroyBackup(2),
				setBackupToRemote(3),
				setBackupConfigBySftp(4),
				setBackupConfigByScp(5),
				setBackupKeyBySftp(6),
				setBackupKeyByScp(7)
				}
			MAX-ACCESS read-write
			STATUS current
			DESCRIPTION
				"Description"
			::= { sleBackupControl 1 }

		
		-- 1.3.6.1.4.1.6296.101.1.4.2.2
		sleBackupControlStatus OBJECT-TYPE
			SYNTAX SleControlStatusType
			MAX-ACCESS read-only
			STATUS current
			DESCRIPTION
				"Description"
			::= { sleBackupControl 2 }

		
		-- 1.3.6.1.4.1.6296.101.1.4.2.3
		sleBackupControlTimer OBJECT-TYPE
			SYNTAX Gauge32
			MAX-ACCESS read-write
			STATUS current
			DESCRIPTION
				"Description"
			::= { sleBackupControl 3 }

		
		-- 1.3.6.1.4.1.6296.101.1.4.2.4
		sleBackupControlTimeStamp OBJECT-TYPE
			SYNTAX TimeTicks
			MAX-ACCESS read-only
			STATUS current
			DESCRIPTION
				"Description"
			::= { sleBackupControl 4 }

		
		-- 1.3.6.1.4.1.6296.101.1.4.2.5
		sleBackupControlReqResult OBJECT-TYPE
			SYNTAX SleControlRequestResultType
			MAX-ACCESS read-only
			STATUS current
			DESCRIPTION
				"Description"
			::= { sleBackupControl 5 }

		
		-- 1.3.6.1.4.1.6296.101.1.4.2.6
		sleBackupControlCreateMode OBJECT-TYPE
			SYNTAX INTEGER
				{
				backupFromRunning(1),
				backupFromLocal(2),
				backupFromRemote(3)
				}
			MAX-ACCESS read-write
			STATUS current
			DESCRIPTION
				"Description"
			::= { sleBackupControl 6 }

		
		-- 1.3.6.1.4.1.6296.101.1.4.2.7
		sleBackupControlServerIP OBJECT-TYPE
			SYNTAX IpAddress
			MAX-ACCESS read-write
			STATUS current
			DESCRIPTION
				"FTP or TFTP server's address."
			::= { sleBackupControl 7 }

		
		-- 1.3.6.1.4.1.6296.101.1.4.2.8
		sleBackupControlUserID OBJECT-TYPE
			SYNTAX OCTET STRING
			MAX-ACCESS read-write
			STATUS current
			DESCRIPTION
				"User's ID of the FTP server.If this is empty string, means that the FTP server is the TFTP server."
			::= { sleBackupControl 8 }

		
		-- 1.3.6.1.4.1.6296.101.1.4.2.9
		sleBackupControlPassword OBJECT-TYPE
			SYNTAX OCTET STRING
			MAX-ACCESS read-write
			STATUS current
			DESCRIPTION
				"User's password of the FTP server."
			::= { sleBackupControl 9 }

		
		-- 1.3.6.1.4.1.6296.101.1.4.2.10
		sleBackupControlSrcConfigFile OBJECT-TYPE
			SYNTAX OCTET STRING
			MAX-ACCESS read-write
			STATUS current
			DESCRIPTION
				"'running-config' is reserved config name."
			::= { sleBackupControl 10 }

		
		-- 1.3.6.1.4.1.6296.101.1.4.2.11
		sleBackupControlDstConfigFile OBJECT-TYPE
			SYNTAX OCTET STRING
			MAX-ACCESS read-write
			STATUS current
			DESCRIPTION
				"Descroption."
			::= { sleBackupControl 11 }

		
		-- 1.3.6.1.4.1.6296.101.1.4.3
		sleBackupNotification OBJECT IDENTIFIER ::= { sleBackup 3 }

		
		-- 1.3.6.1.4.1.6296.101.1.4.3.1
		sleBackupCreated NOTIFICATION-TYPE
			OBJECTS { sleBackupControlRequest, sleBackupControlReqResult, sleBackupControlTimeStamp, sleBackupControlSrcConfigFile }
			STATUS current
			DESCRIPTION 
				"Description"
			::= { sleBackupNotification 1 }

		
		-- 1.3.6.1.4.1.6296.101.1.4.3.2
		sleBackupDestroyed NOTIFICATION-TYPE
			OBJECTS { sleBackupControlRequest, sleBackupControlReqResult, sleBackupControlTimeStamp, sleBackupControlSrcConfigFile }
			STATUS current
			DESCRIPTION 
				"Description"
			::= { sleBackupNotification 2 }

		
		-- 1.3.6.1.4.1.6296.101.1.4.3.3
		sleBackupChanged NOTIFICATION-TYPE
			OBJECTS { sleBackupControlRequest, sleBackupControlTimeStamp, sleBackupControlReqResult, sleBackupControlSrcConfigFile }
			STATUS current
			DESCRIPTION 
				"Description"
			::= { sleBackupNotification 3 }

		
		-- 1.3.6.1.4.1.6296.101.1.4.3.4
		sleBackupConfigBySftpChanged NOTIFICATION-TYPE
			OBJECTS { sleBackupControlRequest, sleBackupControlTimeStamp, sleBackupControlReqResult, sleBackupControlSrcConfigFile }
			STATUS current
			DESCRIPTION 
				"Description"
			::= { sleBackupNotification 4 }

		
		-- 1.3.6.1.4.1.6296.101.1.4.3.5
		sleBackupConfigByScpChanged NOTIFICATION-TYPE
			OBJECTS { sleBackupControlRequest, sleBackupControlTimeStamp, sleBackupControlReqResult, sleBackupControlSrcConfigFile }
			STATUS current
			DESCRIPTION 
				"Description"
			::= { sleBackupNotification 5 }

		
		-- 1.3.6.1.4.1.6296.101.1.4.3.6
		sleBackupKeyBySftpChanged NOTIFICATION-TYPE
			OBJECTS { sleBackupControlRequest, sleBackupControlTimeStamp, sleBackupControlReqResult, sleBackupControlSrcConfigFile }
			STATUS current
			DESCRIPTION 
				"Description"
			::= { sleBackupNotification 6 }

		
		-- 1.3.6.1.4.1.6296.101.1.4.3.7
		sleBackupKeyByScpChanged NOTIFICATION-TYPE
			OBJECTS { sleBackupControlRequest, sleBackupControlTimeStamp, sleBackupControlReqResult, sleBackupControlSrcConfigFile }
			STATUS current
			DESCRIPTION 
				"Description"
			::= { sleBackupNotification 7 }

		
		-- 1.3.6.1.4.1.6296.101.1.5
		sleProcess OBJECT IDENTIFIER ::= { sleSystemMaintenance 5 }

		
		-- 1.3.6.1.4.1.6296.101.1.5.1
		sleProcessTable OBJECT-TYPE
			SYNTAX SEQUENCE OF SleProcessEntry
			MAX-ACCESS not-accessible
			STATUS current
			DESCRIPTION
				"Description."
			::= { sleProcess 1 }

		
		-- 1.3.6.1.4.1.6296.101.1.5.1.1
		sleProcessEntry OBJECT-TYPE
			SYNTAX SleProcessEntry
			MAX-ACCESS not-accessible
			STATUS current
			DESCRIPTION
				"Description."
			INDEX { sleProcessID }
			::= { sleProcessTable 1 }

		
		SleProcessEntry ::=
			SEQUENCE { 
				sleProcessID
					Integer32,
				sleProcessUser
					OCTET STRING,
				sleProcessCPU
					Integer32,
				sleProcessMemory
					Integer32,
				sleProcessVSZ
					Integer32,
				sleProcessRSS
					Integer32,
				sleProcessTerminal
					OCTET STRING,
				sleProcessStatus
					OCTET STRING,
				sleProcessStartTime
					OCTET STRING,
				sleProcessUsedTime
					OCTET STRING,
				sleProcessCommand
					OCTET STRING
			 }

		-- 1.3.6.1.4.1.6296.101.1.5.1.1.1
		sleProcessID OBJECT-TYPE
			SYNTAX Integer32 (1..65535)
			MAX-ACCESS read-write
			STATUS current
			DESCRIPTION
				"Process ID"
			::= { sleProcessEntry 1 }

		
		-- 1.3.6.1.4.1.6296.101.1.5.1.1.2
		sleProcessUser OBJECT-TYPE
			SYNTAX OCTET STRING
			MAX-ACCESS read-only
			STATUS current
			DESCRIPTION
				"Owner name of the process"
			::= { sleProcessEntry 2 }

		
		-- 1.3.6.1.4.1.6296.101.1.5.1.1.3
		sleProcessCPU OBJECT-TYPE
			SYNTAX Integer32
			MAX-ACCESS read-only
			STATUS current
			DESCRIPTION
				"Percent CPU usage (unit : 0.1%)"
			::= { sleProcessEntry 3 }

		
		-- 1.3.6.1.4.1.6296.101.1.5.1.1.4
		sleProcessMemory OBJECT-TYPE
			SYNTAX Integer32
			MAX-ACCESS read-only
			STATUS current
			DESCRIPTION
				"Percent real memory usage (unit : 0.1%)"
			::= { sleProcessEntry 4 }

		
		-- 1.3.6.1.4.1.6296.101.1.5.1.1.5
		sleProcessVSZ OBJECT-TYPE
			SYNTAX Integer32
			MAX-ACCESS read-only
			STATUS current
			DESCRIPTION
				"Virtual address size for the process"
			::= { sleProcessEntry 5 }

		
		-- 1.3.6.1.4.1.6296.101.1.5.1.1.6
		sleProcessRSS OBJECT-TYPE
			SYNTAX Integer32
			MAX-ACCESS read-only
			STATUS current
			DESCRIPTION
				"Residnet set size of the process"
			::= { sleProcessEntry 6 }

		
		-- 1.3.6.1.4.1.6296.101.1.5.1.1.7
		sleProcessTerminal OBJECT-TYPE
			SYNTAX OCTET STRING
			MAX-ACCESS read-only
			STATUS current
			DESCRIPTION
				"Terminal for the process"
			::= { sleProcessEntry 7 }

		
		-- 1.3.6.1.4.1.6296.101.1.5.1.1.8
		sleProcessStatus OBJECT-TYPE
			SYNTAX OCTET STRING
			MAX-ACCESS read-only
			STATUS current
			DESCRIPTION
				"Symbolic process status"
			::= { sleProcessEntry 8 }

		
		-- 1.3.6.1.4.1.6296.101.1.5.1.1.9
		sleProcessStartTime OBJECT-TYPE
			SYNTAX OCTET STRING
			MAX-ACCESS read-only
			STATUS current
			DESCRIPTION
				"Start time of the process"
			::= { sleProcessEntry 9 }

		
		-- 1.3.6.1.4.1.6296.101.1.5.1.1.10
		sleProcessUsedTime OBJECT-TYPE
			SYNTAX OCTET STRING
			MAX-ACCESS read-only
			STATUS current
			DESCRIPTION
				"Current CPU time used"
			::= { sleProcessEntry 10 }

		
		-- 1.3.6.1.4.1.6296.101.1.5.1.1.11
		sleProcessCommand OBJECT-TYPE
			SYNTAX OCTET STRING
			MAX-ACCESS read-only
			STATUS current
			DESCRIPTION
				"Command for the process"
			::= { sleProcessEntry 11 }

		
		-- 1.3.6.1.4.1.6296.101.1.6
		sleNTP OBJECT IDENTIFIER ::= { sleSystemMaintenance 6 }

		
		-- 1.3.6.1.4.1.6296.101.1.6.1
		sleNTPServerTable OBJECT-TYPE
			SYNTAX SEQUENCE OF SleNTPServerEntry
			MAX-ACCESS not-accessible
			STATUS current
			DESCRIPTION
				"The NTP Server table."
			::= { sleNTP 1 }

		
		-- 1.3.6.1.4.1.6296.101.1.6.1.1
		sleNTPServerEntry OBJECT-TYPE
			SYNTAX SleNTPServerEntry
			MAX-ACCESS not-accessible
			STATUS current
			DESCRIPTION
				"Description."
			INDEX { sleNTPServerName }
			::= { sleNTPServerTable 1 }

		
		SleNTPServerEntry ::=
			SEQUENCE { 
				sleNTPServerName
					OCTET STRING
			 }

		-- 1.3.6.1.4.1.6296.101.1.6.1.1.1
		sleNTPServerName OBJECT-TYPE
			SYNTAX OCTET STRING (SIZE (0..256))
			MAX-ACCESS read-only
			STATUS current
			DESCRIPTION
				"The NTP server name."
			::= { sleNTPServerEntry 1 }

		
		-- 1.3.6.1.4.1.6296.101.1.6.2
		sleNTPServerControl OBJECT IDENTIFIER ::= { sleNTP 2 }

		
		-- 1.3.6.1.4.1.6296.101.1.6.2.1
		sleNTPServerControlRequest OBJECT-TYPE
			SYNTAX INTEGER
				{
				createNTPServer(1),
				destoryNTPServer(2)
				}
			MAX-ACCESS read-write
			STATUS current
			DESCRIPTION
				"Description."
			::= { sleNTPServerControl 1 }

		
		-- 1.3.6.1.4.1.6296.101.1.6.2.2
		sleNTPServerControlStatus OBJECT-TYPE
			SYNTAX SleControlStatusType
			MAX-ACCESS read-only
			STATUS current
			DESCRIPTION
				"Description."
			::= { sleNTPServerControl 2 }

		
		-- 1.3.6.1.4.1.6296.101.1.6.2.3
		sleNTPServerControlTimer OBJECT-TYPE
			SYNTAX Gauge32
			MAX-ACCESS read-write
			STATUS current
			DESCRIPTION
				"Description."
			::= { sleNTPServerControl 3 }

		
		-- 1.3.6.1.4.1.6296.101.1.6.2.4
		sleNTPServerControlTImeStamp OBJECT-TYPE
			SYNTAX TimeTicks
			MAX-ACCESS read-only
			STATUS current
			DESCRIPTION
				"Description."
			::= { sleNTPServerControl 4 }

		
		-- 1.3.6.1.4.1.6296.101.1.6.2.5
		sleNTPServerControlReqResult OBJECT-TYPE
			SYNTAX SleControlRequestResultType
			MAX-ACCESS read-only
			STATUS current
			DESCRIPTION
				"Description."
			::= { sleNTPServerControl 5 }

		
		-- 1.3.6.1.4.1.6296.101.1.6.2.6
		sleNTPServerControlName OBJECT-TYPE
			SYNTAX OCTET STRING (SIZE (0..256))
			MAX-ACCESS read-write
			STATUS current
			DESCRIPTION
				"The NTP server name."
			::= { sleNTPServerControl 6 }

		
		-- 1.3.6.1.4.1.6296.101.1.6.3
		sleNTPServerNotification OBJECT IDENTIFIER ::= { sleNTP 3 }

		
		-- 1.3.6.1.4.1.6296.101.1.6.3.1
		sleNTPServerCreated NOTIFICATION-TYPE
			OBJECTS { sleNTPServerControlRequest, sleNTPServerControlTImeStamp, sleNTPServerControlReqResult, sleNTPServerName }
			STATUS current
			DESCRIPTION 
				"Created NTP Server table entry."
			::= { sleNTPServerNotification 1 }

		
		-- 1.3.6.1.4.1.6296.101.1.6.3.2
		sleNTPServerDestroyed NOTIFICATION-TYPE
			OBJECTS { sleNTPServerControlRequest, sleNTPServerControlReqResult, sleNTPServerControlTImeStamp, sleNTPServerControlName }
			STATUS current
			DESCRIPTION 
				"Destroyed NTP Server table entry."
			::= { sleNTPServerNotification 2 }

		
		-- 1.3.6.1.4.1.6296.101.1.7
		sleSyslogConf OBJECT IDENTIFIER ::= { sleSystemMaintenance 7 }

		
		-- 1.3.6.1.4.1.6296.101.1.7.1
		sleSyslogConfTable OBJECT-TYPE
			SYNTAX SEQUENCE OF SleSyslogConfEntry
			MAX-ACCESS not-accessible
			STATUS current
			DESCRIPTION
				"Description."
			::= { sleSyslogConf 1 }

		
		-- 1.3.6.1.4.1.6296.101.1.7.1.1
		sleSyslogConfEntry OBJECT-TYPE
			SYNTAX SleSyslogConfEntry
			MAX-ACCESS not-accessible
			STATUS current
			DESCRIPTION
				"Description."
			INDEX { sleSyslogConfIndex }
			::= { sleSyslogConfTable 1 }

		
		SleSyslogConfEntry ::=
			SEQUENCE { 
				sleSyslogConfIndex
					Integer32,
				sleSyslogConfMode
					INTEGER,
				sleSyslogConfFacility
					INTEGER,
				sleSyslogConfSeverity
					INTEGER,
				sleSyslogConfTarget
					INTEGER,
				sleSyslogConfStorage
					INTEGER,
				sleSyslogConfTargetAddress
					IpAddress
			 }

		-- 1.3.6.1.4.1.6296.101.1.7.1.1.1
		sleSyslogConfIndex OBJECT-TYPE
			SYNTAX Integer32 (1..255)
			MAX-ACCESS read-only
			STATUS current
			DESCRIPTION
				"Message index"
			::= { sleSyslogConfEntry 1 }

		
		-- 1.3.6.1.4.1.6296.101.1.7.1.1.2
		sleSyslogConfMode OBJECT-TYPE
			SYNTAX INTEGER
				{
				general(0),
				priority(1)
				}
			MAX-ACCESS read-only
			STATUS current
			DESCRIPTION
				"Name of the facility that generated message."
			::= { sleSyslogConfEntry 2 }

		
		-- 1.3.6.1.4.1.6296.101.1.7.1.1.3
		sleSyslogConfFacility OBJECT-TYPE
			SYNTAX INTEGER
				{
				auth(0),
				authpriv(1),
				kern(2),
				local0(3),
				local1(4),
				local2(5),
				local3(6),
				local4(7),
				local5(8),
				local6(9),
				local7(10),
				syslog(11),
				user(12),
				nomap(99)
				}
			MAX-ACCESS read-only
			STATUS current
			DESCRIPTION
				"Name of the facility that generated message.
				16~23: local"
			::= { sleSyslogConfEntry 3 }

		
		-- 1.3.6.1.4.1.6296.101.1.7.1.1.4
		sleSyslogConfSeverity OBJECT-TYPE
			SYNTAX INTEGER
				{
				emergency(0),
				alert(1),
				critical(2),
				error(3),
				warning(4),
				notice(5),
				info(6),
				debug(7),
				other(99)
				}
			MAX-ACCESS read-only
			STATUS current
			DESCRIPTION
				"The severity of the message"
			::= { sleSyslogConfEntry 4 }

		
		-- 1.3.6.1.4.1.6296.101.1.7.1.1.5
		sleSyslogConfTarget OBJECT-TYPE
			SYNTAX INTEGER
				{
				local(1),
				consol(2),
				remote(3)
				}
			MAX-ACCESS read-only
			STATUS current
			DESCRIPTION
				"Target type"
			::= { sleSyslogConfEntry 5 }

		
		-- 1.3.6.1.4.1.6296.101.1.7.1.1.6
		sleSyslogConfStorage OBJECT-TYPE
			SYNTAX INTEGER
				{
				notAvailable(-1),
				volatile(0),
				nonvolatile(1)
				}
			MAX-ACCESS read-only
			STATUS current
			DESCRIPTION
				"Description."
			::= { sleSyslogConfEntry 6 }

		
		-- 1.3.6.1.4.1.6296.101.1.7.1.1.7
		sleSyslogConfTargetAddress OBJECT-TYPE
			SYNTAX IpAddress
			MAX-ACCESS read-only
			STATUS current
			DESCRIPTION
				"Description."
			::= { sleSyslogConfEntry 7 }

		
		-- 1.3.6.1.4.1.6296.101.1.7.2
		sleSyslogConfControl OBJECT IDENTIFIER ::= { sleSyslogConf 2 }

		
		-- 1.3.6.1.4.1.6296.101.1.7.2.1
		sleSyslogConfControlRequest OBJECT-TYPE
			SYNTAX INTEGER
				{
				createSyslogConf(1),
				destroySyslogConf(2)
				}
			MAX-ACCESS read-write
			STATUS current
			DESCRIPTION
				"Description."
			::= { sleSyslogConfControl 1 }

		
		-- 1.3.6.1.4.1.6296.101.1.7.2.2
		sleSyslogConfControlStatus OBJECT-TYPE
			SYNTAX Integer32
			MAX-ACCESS read-only
			STATUS current
			DESCRIPTION
				"Description."
			::= { sleSyslogConfControl 2 }

		
		-- 1.3.6.1.4.1.6296.101.1.7.2.3
		sleSyslogConfControlTimer OBJECT-TYPE
			SYNTAX Gauge32
			MAX-ACCESS read-write
			STATUS current
			DESCRIPTION
				"Description."
			::= { sleSyslogConfControl 3 }

		
		-- 1.3.6.1.4.1.6296.101.1.7.2.4
		sleSyslogConfControlTimeStamp OBJECT-TYPE
			SYNTAX TimeTicks
			MAX-ACCESS read-only
			STATUS current
			DESCRIPTION
				"Description."
			::= { sleSyslogConfControl 4 }

		
		-- 1.3.6.1.4.1.6296.101.1.7.2.5
		sleSyslogConfControlReqResult OBJECT-TYPE
			SYNTAX Integer32
			MAX-ACCESS read-only
			STATUS current
			DESCRIPTION
				"Description."
			::= { sleSyslogConfControl 5 }

		
		-- 1.3.6.1.4.1.6296.101.1.7.2.6
		sleSyslogConfControlIndex OBJECT-TYPE
			SYNTAX Integer32
			MAX-ACCESS read-write
			STATUS current
			DESCRIPTION
				"Description."
			::= { sleSyslogConfControl 6 }

		
		-- 1.3.6.1.4.1.6296.101.1.7.2.7
		sleSyslogConfControlMode OBJECT-TYPE
			SYNTAX INTEGER
				{
				general(0),
				priority(1)
				}
			MAX-ACCESS read-write
			STATUS current
			DESCRIPTION
				"Description."
			::= { sleSyslogConfControl 7 }

		
		-- 1.3.6.1.4.1.6296.101.1.7.2.8
		sleSyslogConfControlSeverity OBJECT-TYPE
			SYNTAX INTEGER
				{
				emergency(0),
				alert(1),
				critical(2),
				error(3),
				warning(4),
				notice(5),
				info(6),
				debug(7),
				other(99)
				}
			MAX-ACCESS read-write
			STATUS current
			DESCRIPTION
				"Description."
			::= { sleSyslogConfControl 8 }

		
		-- 1.3.6.1.4.1.6296.101.1.7.2.9
		sleSyslogConfControlFacility OBJECT-TYPE
			SYNTAX INTEGER
				{
				auth(0),
				authpriv(1),
				kern(2),
				local0(3),
				local1(4),
				local2(5),
				local3(6),
				local4(7),
				local5(8),
				local6(9),
				local7(10),
				syslog(11),
				user(12),
				nomap(99)
				}
			MAX-ACCESS read-write
			STATUS current
			DESCRIPTION
				"Description."
			::= { sleSyslogConfControl 9 }

		
		-- 1.3.6.1.4.1.6296.101.1.7.2.10
		sleSyslogConfControlTarget OBJECT-TYPE
			SYNTAX INTEGER
				{
				local(1),
				consol(2),
				remote(3)
				}
			MAX-ACCESS read-write
			STATUS current
			DESCRIPTION
				"Target type"
			::= { sleSyslogConfControl 10 }

		
		-- 1.3.6.1.4.1.6296.101.1.7.2.11
		sleSyslogConfControlStorage OBJECT-TYPE
			SYNTAX INTEGER
				{
				notAvailable(-1),
				volatile(0),
				nonvolatile(1)
				}
			MAX-ACCESS read-write
			STATUS current
			DESCRIPTION
				"Description"
			::= { sleSyslogConfControl 11 }

		
		-- 1.3.6.1.4.1.6296.101.1.7.2.12
		sleSyslogConfControlTargetAddress OBJECT-TYPE
			SYNTAX IpAddress
			MAX-ACCESS read-write
			STATUS current
			DESCRIPTION
				"Description"
			::= { sleSyslogConfControl 12 }

		
		-- 1.3.6.1.4.1.6296.101.1.7.3
		sleSyslogConfNotification OBJECT IDENTIFIER ::= { sleSyslogConf 3 }

		
		-- 1.3.6.1.4.1.6296.101.1.7.3.1
		sleSyslogConfCreated NOTIFICATION-TYPE
			OBJECTS { sleSyslogConfControlRequest, sleSyslogConfControlReqResult, sleSyslogConfControlTimeStamp, sleSyslogConfMode, sleSyslogConfFacility, 
				sleSyslogConfSeverity, sleSyslogConfTarget, sleSyslogConfStorage, sleSyslogConfTargetAddress }
			STATUS current
			DESCRIPTION 
				"Description."
			::= { sleSyslogConfNotification 1 }

		
		-- 1.3.6.1.4.1.6296.101.1.7.3.2
		sleSyslogConfDestroyed NOTIFICATION-TYPE
			OBJECTS { sleSyslogConfControlRequest, sleSyslogConfControlReqResult, sleSyslogConfControlTimeStamp, sleSyslogConfControlIndex }
			STATUS current
			DESCRIPTION 
				"Description."
			::= { sleSyslogConfNotification 2 }

		
		-- 1.3.6.1.4.1.6296.101.1.8
		sleSyslogHistVol OBJECT IDENTIFIER ::= { sleSystemMaintenance 8 }

		
		-- 1.3.6.1.4.1.6296.101.1.8.1
		sleSyslogHistVolTable OBJECT-TYPE
			SYNTAX SEQUENCE OF SleSyslogHistVolEntry
			MAX-ACCESS not-accessible
			STATUS current
			DESCRIPTION
				"Description."
			::= { sleSyslogHistVol 1 }

		
		-- 1.3.6.1.4.1.6296.101.1.8.1.1
		sleSyslogHistVolEntry OBJECT-TYPE
			SYNTAX SleSyslogHistVolEntry
			MAX-ACCESS not-accessible
			STATUS current
			DESCRIPTION
				"Description."
			INDEX { sleSyslogHistVolIndex }
			::= { sleSyslogHistVolTable 1 }

		
		SleSyslogHistVolEntry ::=
			SEQUENCE { 
				sleSyslogHistVolIndex
					Integer32,
				sleSyslogHistVolMsgText
					OCTET STRING,
				sleSyslogHistVolTime
					TimeTicks
			 }

		-- 1.3.6.1.4.1.6296.101.1.8.1.1.1
		sleSyslogHistVolIndex OBJECT-TYPE
			SYNTAX Integer32 (1..65535)
			MAX-ACCESS read-only
			STATUS current
			DESCRIPTION
				"Description."
			::= { sleSyslogHistVolEntry 1 }

		
		-- 1.3.6.1.4.1.6296.101.1.8.1.1.2
		sleSyslogHistVolMsgText OBJECT-TYPE
			SYNTAX OCTET STRING
			MAX-ACCESS read-only
			STATUS current
			DESCRIPTION
				"Description."
			::= { sleSyslogHistVolEntry 2 }

		
		-- 1.3.6.1.4.1.6296.101.1.8.1.1.3
		sleSyslogHistVolTime OBJECT-TYPE
			SYNTAX TimeTicks
			MAX-ACCESS read-only
			STATUS current
			DESCRIPTION
				"Description."
			::= { sleSyslogHistVolEntry 3 }

		
		-- 1.3.6.1.4.1.6296.101.1.9
		sleSyslogHistNVol OBJECT IDENTIFIER ::= { sleSystemMaintenance 9 }

		
		-- 1.3.6.1.4.1.6296.101.1.9.1
		sleSyslogHistNVolTable OBJECT-TYPE
			SYNTAX SEQUENCE OF SleSyslogHistNVolEntry
			MAX-ACCESS not-accessible
			STATUS current
			DESCRIPTION
				"Description."
			::= { sleSyslogHistNVol 1 }

		
		-- 1.3.6.1.4.1.6296.101.1.9.1.1
		sleSyslogHistNVolEntry OBJECT-TYPE
			SYNTAX SleSyslogHistNVolEntry
			MAX-ACCESS not-accessible
			STATUS current
			DESCRIPTION
				"Description."
			INDEX { sleSyslogHistNVolIndex }
			::= { sleSyslogHistNVolTable 1 }

		
		SleSyslogHistNVolEntry ::=
			SEQUENCE { 
				sleSyslogHistNVolIndex
					Integer32,
				sleSyslogHistNVolMsgText
					OCTET STRING,
				sleSyslogHistNVolTime
					TimeTicks
			 }

		-- 1.3.6.1.4.1.6296.101.1.9.1.1.1
		sleSyslogHistNVolIndex OBJECT-TYPE
			SYNTAX Integer32 (1..65535)
			MAX-ACCESS read-only
			STATUS current
			DESCRIPTION
				"Description."
			::= { sleSyslogHistNVolEntry 1 }

		
		-- 1.3.6.1.4.1.6296.101.1.9.1.1.2
		sleSyslogHistNVolMsgText OBJECT-TYPE
			SYNTAX OCTET STRING
			MAX-ACCESS read-only
			STATUS current
			DESCRIPTION
				"The text of the message."
			::= { sleSyslogHistNVolEntry 2 }

		
		-- 1.3.6.1.4.1.6296.101.1.9.1.1.3
		sleSyslogHistNVolTime OBJECT-TYPE
			SYNTAX TimeTicks
			MAX-ACCESS read-only
			STATUS current
			DESCRIPTION
				"The value of sysUpTime when this message was generated"
			::= { sleSyslogHistNVolEntry 3 }

		
		-- 1.3.6.1.4.1.6296.101.1.10
		sleSSHRemote OBJECT IDENTIFIER ::= { sleSystemMaintenance 10 }

		
		-- 1.3.6.1.4.1.6296.101.1.10.1
		sleSSHRemoteTable OBJECT-TYPE
			SYNTAX SEQUENCE OF SleSSHRemoteEntry
			MAX-ACCESS not-accessible
			STATUS current
			DESCRIPTION
				"The table of remote connection's to this SSH Server."
			::= { sleSSHRemote 1 }

		
		-- 1.3.6.1.4.1.6296.101.1.10.1.1
		sleSSHRemoteEntry OBJECT-TYPE
			SYNTAX SleSSHRemoteEntry
			MAX-ACCESS not-accessible
			STATUS current
			DESCRIPTION
				"Remote SSH connection entries."
			INDEX { sleSSHRemoteIndex }
			::= { sleSSHRemoteTable 1 }

		
		SleSSHRemoteEntry ::=
			SEQUENCE { 
				sleSSHRemoteIndex
					INTEGER,
				sleSSHRemoteUser
					OCTET STRING,
				sleSSHRemoteHost
					IpAddress,
				sleSSHRemoteTime
					OCTET STRING,
				sleSSHRemoteFromHost
					OCTET STRING
			 }

		-- 1.3.6.1.4.1.6296.101.1.10.1.1.1
		sleSSHRemoteIndex OBJECT-TYPE
			SYNTAX INTEGER (1..65535)
			MAX-ACCESS read-only
			STATUS current
			DESCRIPTION
				"Proccess ID of remote SSH Client connected to SSH Server."
			::= { sleSSHRemoteEntry 1 }

		
		-- 1.3.6.1.4.1.6296.101.1.10.1.1.2
		sleSSHRemoteUser OBJECT-TYPE
			SYNTAX OCTET STRING (SIZE (0..256))
			MAX-ACCESS read-only
			STATUS current
			DESCRIPTION
				"Remote user ID connected to SSH Server."
			::= { sleSSHRemoteEntry 2 }

		
		-- 1.3.6.1.4.1.6296.101.1.10.1.1.3
		sleSSHRemoteHost OBJECT-TYPE
			SYNTAX IpAddress
			MAX-ACCESS read-only
			STATUS current
			DESCRIPTION
				"Remote host IP address connected to SSH Server."
			::= { sleSSHRemoteEntry 3 }

		
		-- 1.3.6.1.4.1.6296.101.1.10.1.1.4
		sleSSHRemoteTime OBJECT-TYPE
			SYNTAX OCTET STRING (SIZE (0..32))
			MAX-ACCESS read-only
			STATUS current
			DESCRIPTION
				"Connection time to SSH Server of this remote user."
			::= { sleSSHRemoteEntry 4 }

		
		-- 1.3.6.1.4.1.6296.101.1.10.1.1.5
		sleSSHRemoteFromHost OBJECT-TYPE
			SYNTAX OCTET STRING
			MAX-ACCESS read-only
			STATUS current
			DESCRIPTION
				"Remote host Information connected to SSH Server."
			::= { sleSSHRemoteEntry 5 }

		
		-- 1.3.6.1.4.1.6296.101.1.10.2
		sleSSHRemoteControl OBJECT IDENTIFIER ::= { sleSSHRemote 2 }

		
		-- 1.3.6.1.4.1.6296.101.1.10.2.1
		sleSSHRemoteControlRequest OBJECT-TYPE
			SYNTAX INTEGER { destorySshRemoteConnection(1) }
			MAX-ACCESS read-write
			STATUS current
			DESCRIPTION
				"Control Request."
			::= { sleSSHRemoteControl 1 }

		
		-- 1.3.6.1.4.1.6296.101.1.10.2.2
		sleSSHRemoteControlStatus OBJECT-TYPE
			SYNTAX SleControlStatusType
			MAX-ACCESS read-only
			STATUS current
			DESCRIPTION
				"Control Status."
			::= { sleSSHRemoteControl 2 }

		
		-- 1.3.6.1.4.1.6296.101.1.10.2.3
		sleSSHRemoteControlTimer OBJECT-TYPE
			SYNTAX Gauge32
			MAX-ACCESS read-write
			STATUS current
			DESCRIPTION
				"Description."
			::= { sleSSHRemoteControl 3 }

		
		-- 1.3.6.1.4.1.6296.101.1.10.2.4
		sleSSHRemoteControlTImeStamp OBJECT-TYPE
			SYNTAX TimeTicks
			MAX-ACCESS read-only
			STATUS current
			DESCRIPTION
				"Description."
			::= { sleSSHRemoteControl 4 }

		
		-- 1.3.6.1.4.1.6296.101.1.10.2.5
		sleSSHRemoteControlReqResult OBJECT-TYPE
			SYNTAX SleControlRequestResultType
			MAX-ACCESS read-only
			STATUS current
			DESCRIPTION
				"Description."
			::= { sleSSHRemoteControl 5 }

		
		-- 1.3.6.1.4.1.6296.101.1.10.2.6
		sleSSHRemoteControlIndex OBJECT-TYPE
			SYNTAX INTEGER (1..65535)
			MAX-ACCESS read-write
			STATUS current
			DESCRIPTION
				"Proccess ID of remote SSH Client connected to SSH Server."
			::= { sleSSHRemoteControl 6 }

		
		-- 1.3.6.1.4.1.6296.101.1.10.3
		sleSSHRemoteNotification OBJECT IDENTIFIER ::= { sleSSHRemote 3 }

		
		-- 1.3.6.1.4.1.6296.101.1.10.3.1
		sleSSHRemoteConnectiondestoryed NOTIFICATION-TYPE
			OBJECTS { sleSSHRemoteControlRequest, sleSSHRemoteControlReqResult, sleSSHRemoteControlTImeStamp, sleSSHRemoteControlIndex }
			STATUS current
			DESCRIPTION 
				"Destroyed the remote connection to this SSH Server."
			::= { sleSSHRemoteNotification 1 }

		
		-- 1.3.6.1.4.1.6296.101.1.11
		sleAutoCli OBJECT IDENTIFIER ::= { sleSystemMaintenance 11 }

		
		-- 1.3.6.1.4.1.6296.101.1.11.1
		sleAutoCliInfo OBJECT IDENTIFIER ::= { sleAutoCli 1 }

		
		-- 1.3.6.1.4.1.6296.101.1.11.1.1
		sleAutoCliBase OBJECT IDENTIFIER ::= { sleAutoCliInfo 1 }

		
		-- 1.3.6.1.4.1.6296.101.1.11.1.1.1
		sleAutoCliConfStatus OBJECT-TYPE
			SYNTAX EnableFlag
			MAX-ACCESS read-only
			STATUS current
			DESCRIPTION
				"The administrative state of AutoCli Scheduler"
			::= { sleAutoCliBase 1 }

		
		-- 1.3.6.1.4.1.6296.101.1.11.1.1.2
		sleAutoCliMemoryMaxSize OBJECT-TYPE
			SYNTAX Integer32
			MAX-ACCESS read-only
			STATUS current
			DESCRIPTION
				"The max memory size to save output-file"
			::= { sleAutoCliBase 2 }

		
		-- 1.3.6.1.4.1.6296.101.1.11.1.1.3
		sleAutoCliMemoryUsedsize OBJECT-TYPE
			SYNTAX Integer32
			MAX-ACCESS read-only
			STATUS current
			DESCRIPTION
				"The used memory size to save output-file"
			::= { sleAutoCliBase 3 }

		
		-- 1.3.6.1.4.1.6296.101.1.11.1.1.4
		sleAutoCliMemoryFreesize OBJECT-TYPE
			SYNTAX Integer32
			MAX-ACCESS read-only
			STATUS current
			DESCRIPTION
				"The freed memory size to save output-file"
			::= { sleAutoCliBase 4 }

		
		-- 1.3.6.1.4.1.6296.101.1.11.1.1.5
		sleAutoCliTransferInterval OBJECT-TYPE
			SYNTAX Integer32
			UNITS "minute"
			MAX-ACCESS read-only
			STATUS current
			DESCRIPTION
				"The amount of time between the transference of outputfile"
			::= { sleAutoCliBase 5 }

		
		-- 1.3.6.1.4.1.6296.101.1.11.1.2
		sleAutoCliBaseControl OBJECT IDENTIFIER ::= { sleAutoCliInfo 2 }

		
		-- 1.3.6.1.4.1.6296.101.1.11.1.2.1
		sleAutoCliControlRequest OBJECT-TYPE
			SYNTAX INTEGER
				{
				setAutoCliStatus(1),
				setMemoryMaxsize(2),
				setTransferInterval(3)
				}
			MAX-ACCESS read-write
			STATUS current
			DESCRIPTION
				"Description."
			::= { sleAutoCliBaseControl 1 }

		
		-- 1.3.6.1.4.1.6296.101.1.11.1.2.2
		sleAutoCliControlStatus OBJECT-TYPE
			SYNTAX SleControlStatusType
			MAX-ACCESS read-only
			STATUS current
			DESCRIPTION
				"Description."
			::= { sleAutoCliBaseControl 2 }

		
		-- 1.3.6.1.4.1.6296.101.1.11.1.2.3
		sleAutoCliControlTimer OBJECT-TYPE
			SYNTAX Gauge32
			MAX-ACCESS read-write
			STATUS current
			DESCRIPTION
				"Description."
			::= { sleAutoCliBaseControl 3 }

		
		-- 1.3.6.1.4.1.6296.101.1.11.1.2.4
		sleAutoCliControlTimeStamp OBJECT-TYPE
			SYNTAX TimeTicks
			MAX-ACCESS read-only
			STATUS current
			DESCRIPTION
				"Description."
			::= { sleAutoCliBaseControl 4 }

		
		-- 1.3.6.1.4.1.6296.101.1.11.1.2.5
		sleAutoCliControlReqResult OBJECT-TYPE
			SYNTAX SleControlRequestResultType
			MAX-ACCESS read-only
			STATUS current
			DESCRIPTION
				"Description."
			::= { sleAutoCliBaseControl 5 }

		
		-- 1.3.6.1.4.1.6296.101.1.11.1.2.6
		sleAutoCliControlConfStatus OBJECT-TYPE
			SYNTAX EnableFlag
			MAX-ACCESS read-write
			STATUS current
			DESCRIPTION
				"The IpAddress of FTP/TFTP server to save output-file"
			::= { sleAutoCliBaseControl 6 }

		
		-- 1.3.6.1.4.1.6296.101.1.11.1.2.7
		sleAutoCliControlMemoryMaxsize OBJECT-TYPE
			SYNTAX Integer32
			MAX-ACCESS read-write
			STATUS current
			DESCRIPTION
				"The max memory size to save output-file"
			::= { sleAutoCliBaseControl 7 }

		
		-- 1.3.6.1.4.1.6296.101.1.11.1.2.8
		sleAutoCliControlTransferInterval OBJECT-TYPE
			SYNTAX Integer32
			UNITS "minute"
			MAX-ACCESS read-write
			STATUS current
			DESCRIPTION
				"The amount of time between the transference of outputfile"
			::= { sleAutoCliBaseControl 8 }

		
		-- 1.3.6.1.4.1.6296.101.1.11.1.3
		sleAutoCliBaseNotification OBJECT IDENTIFIER ::= { sleAutoCliInfo 3 }

		
		-- 1.3.6.1.4.1.6296.101.1.11.1.3.1
		sleAutoCliStatusChanged NOTIFICATION-TYPE
			OBJECTS { sleAutoCliControlRequest, sleAutoCliControlTimeStamp, sleAutoCliControlReqResult, sleAutoCliConfStatus }
			STATUS current
			DESCRIPTION 
				"Change auto cli administrative status."
			::= { sleAutoCliBaseNotification 1 }

		
		-- 1.3.6.1.4.1.6296.101.1.11.1.3.2
		sleAutoCliMemoryMaxsizeChanged NOTIFICATION-TYPE
			OBJECTS { sleAutoCliControlRequest, sleAutoCliControlTimeStamp, sleAutoCliControlReqResult, sleAutoCliMemoryMaxSize }
			STATUS current
			DESCRIPTION 
				"Description."
			::= { sleAutoCliBaseNotification 2 }

		
		-- 1.3.6.1.4.1.6296.101.1.11.1.3.3
		sleAutoCliTransferIntervalChanged NOTIFICATION-TYPE
			OBJECTS { sleAutoCliControlRequest, sleAutoCliControlTimeStamp, sleAutoCliControlReqResult, sleAutoCliTransferInterval }
			STATUS current
			DESCRIPTION 
				"Description."
			::= { sleAutoCliBaseNotification 3 }

		
		-- 1.3.6.1.4.1.6296.101.1.11.2
		sleAutoCliScriptFile OBJECT IDENTIFIER ::= { sleAutoCli 2 }

		
		-- 1.3.6.1.4.1.6296.101.1.11.2.1
		sleAutoCliScriptFileTable OBJECT-TYPE
			SYNTAX SEQUENCE OF SleAutoCliScriptFileEntry
			MAX-ACCESS not-accessible
			STATUS current
			DESCRIPTION
				"Description."
			::= { sleAutoCliScriptFile 1 }

		
		-- 1.3.6.1.4.1.6296.101.1.11.2.1.1
		sleAutoCliScriptFileEntry OBJECT-TYPE
			SYNTAX SleAutoCliScriptFileEntry
			MAX-ACCESS not-accessible
			STATUS current
			DESCRIPTION
				"Description."
			INDEX { sleAutoCliScriptId }
			::= { sleAutoCliScriptFileTable 1 }

		
		SleAutoCliScriptFileEntry ::=
			SEQUENCE { 
				sleAutoCliScriptId
					INTEGER,
				sleAutoCliScriptFileName
					OCTET STRING,
				sleAutoCliScriptFileUser
					OCTET STRING,
				sleAutoCliScriptFileSize
					Integer32,
				sleAutoCliScriptFileUpdateTime
					OCTET STRING
			 }

		-- 1.3.6.1.4.1.6296.101.1.11.2.1.1.1
		sleAutoCliScriptId OBJECT-TYPE
			SYNTAX INTEGER (1..2147483647)
			MAX-ACCESS read-only
			STATUS current
			DESCRIPTION
				"The id of script file"
			::= { sleAutoCliScriptFileEntry 1 }

		
		-- 1.3.6.1.4.1.6296.101.1.11.2.1.1.2
		sleAutoCliScriptFileName OBJECT-TYPE
			SYNTAX OCTET STRING
			MAX-ACCESS read-only
			STATUS current
			DESCRIPTION
				"The name of script file"
			::= { sleAutoCliScriptFileEntry 2 }

		
		-- 1.3.6.1.4.1.6296.101.1.11.2.1.1.3
		sleAutoCliScriptFileUser OBJECT-TYPE
			SYNTAX OCTET STRING
			MAX-ACCESS read-only
			STATUS current
			DESCRIPTION
				"The user of script file"
			::= { sleAutoCliScriptFileEntry 3 }

		
		-- 1.3.6.1.4.1.6296.101.1.11.2.1.1.4
		sleAutoCliScriptFileSize OBJECT-TYPE
			SYNTAX Integer32
			MAX-ACCESS read-only
			STATUS current
			DESCRIPTION
				"The File size of script file"
			::= { sleAutoCliScriptFileEntry 4 }

		
		-- 1.3.6.1.4.1.6296.101.1.11.2.1.1.5
		sleAutoCliScriptFileUpdateTime OBJECT-TYPE
			SYNTAX OCTET STRING
			MAX-ACCESS read-only
			STATUS current
			DESCRIPTION
				"The last updated time of script file"
			::= { sleAutoCliScriptFileEntry 5 }

		
		-- 1.3.6.1.4.1.6296.101.1.11.2.2
		sleAutoCliScriptFileControl OBJECT IDENTIFIER ::= { sleAutoCliScriptFile 2 }

		
		-- 1.3.6.1.4.1.6296.101.1.11.2.2.1
		sleAutoCliScriptFileControlRequest OBJECT-TYPE
			SYNTAX INTEGER
				{
				ftpgetAutoCliScript(1),
				tftpgetAutoCliScript(2),
				destroyedAutoCliScript(3)
				}
			MAX-ACCESS read-write
			STATUS current
			DESCRIPTION
				"Description."
			::= { sleAutoCliScriptFileControl 1 }

		
		-- 1.3.6.1.4.1.6296.101.1.11.2.2.2
		sleAutoCliScriptFileControlStatus OBJECT-TYPE
			SYNTAX SleControlStatusType
			MAX-ACCESS read-write
			STATUS current
			DESCRIPTION
				"Description."
			::= { sleAutoCliScriptFileControl 2 }

		
		-- 1.3.6.1.4.1.6296.101.1.11.2.2.3
		sleAutoCliScriptFileControlTimer OBJECT-TYPE
			SYNTAX Gauge32
			MAX-ACCESS read-write
			STATUS current
			DESCRIPTION
				"Description."
			::= { sleAutoCliScriptFileControl 3 }

		
		-- 1.3.6.1.4.1.6296.101.1.11.2.2.4
		sleAutoCliScriptFileControlTimeStamp OBJECT-TYPE
			SYNTAX TimeTicks
			MAX-ACCESS read-write
			STATUS current
			DESCRIPTION
				"Description."
			::= { sleAutoCliScriptFileControl 4 }

		
		-- 1.3.6.1.4.1.6296.101.1.11.2.2.5
		sleAutoCliScriptFileControlReqResult OBJECT-TYPE
			SYNTAX SleControlRequestResultType
			MAX-ACCESS read-write
			STATUS current
			DESCRIPTION
				"Description."
			::= { sleAutoCliScriptFileControl 5 }

		
		-- 1.3.6.1.4.1.6296.101.1.11.2.2.6
		sleAutoCliScriptFileControlIpAddress OBJECT-TYPE
			SYNTAX IpAddress
			MAX-ACCESS read-write
			STATUS current
			DESCRIPTION
				"The ip address of FTP server to get a script file."
			::= { sleAutoCliScriptFileControl 6 }

		
		-- 1.3.6.1.4.1.6296.101.1.11.2.2.7
		sleAutoCliScriptFileControlUserName OBJECT-TYPE
			SYNTAX OCTET STRING
			MAX-ACCESS read-write
			STATUS current
			DESCRIPTION
				"The user name of FTP server to get a script file"
			::= { sleAutoCliScriptFileControl 7 }

		
		-- 1.3.6.1.4.1.6296.101.1.11.2.2.8
		sleAutoCliScriptFileControlPassword OBJECT-TYPE
			SYNTAX OCTET STRING
			MAX-ACCESS read-write
			STATUS current
			DESCRIPTION
				"The password of FTP server to get a script file"
			::= { sleAutoCliScriptFileControl 8 }

		
		-- 1.3.6.1.4.1.6296.101.1.11.2.2.9
		sleAutoCliScriptFileControlFilePath OBJECT-TYPE
			SYNTAX OCTET STRING
			MAX-ACCESS read-write
			STATUS current
			DESCRIPTION
				"The file-path of FTP server to get a script file"
			::= { sleAutoCliScriptFileControl 9 }

		
		-- 1.3.6.1.4.1.6296.101.1.11.2.2.10
		sleAutoCliScriptFileControlScriptName OBJECT-TYPE
			SYNTAX OCTET STRING
			MAX-ACCESS read-write
			STATUS current
			DESCRIPTION
				"The script file name"
			::= { sleAutoCliScriptFileControl 10 }

		
		-- 1.3.6.1.4.1.6296.101.1.11.2.3
		sleAutoCliScriptFileNotifications OBJECT IDENTIFIER ::= { sleAutoCliScriptFile 3 }

		
		-- 1.3.6.1.4.1.6296.101.1.11.2.3.1
		sleAutoCliScriptFileFtpCreated NOTIFICATION-TYPE
			OBJECTS { sleAutoCliScriptFileControlRequest, sleAutoCliScriptFileControlTimeStamp, sleAutoCliScriptFileControlReqResult, sleAutoCliScriptFileName }
			STATUS current
			DESCRIPTION 
				"ftpgetAutoCliScript"
			::= { sleAutoCliScriptFileNotifications 1 }

		
		-- 1.3.6.1.4.1.6296.101.1.11.2.3.2
		sleAutoCliScriptFileTftpCreated NOTIFICATION-TYPE
			OBJECTS { sleAutoCliScriptFileControlRequest, sleAutoCliScriptFileControlTimeStamp, sleAutoCliScriptFileControlReqResult, sleAutoCliScriptFileName }
			STATUS current
			DESCRIPTION 
				"tftpgetAutoCliScript"
			::= { sleAutoCliScriptFileNotifications 2 }

		
		-- 1.3.6.1.4.1.6296.101.1.11.2.3.3
		sleAutoCliScriptFileDestroyed NOTIFICATION-TYPE
			OBJECTS { sleAutoCliScriptFileControlRequest, sleAutoCliScriptFileControlTimeStamp, sleAutoCliScriptFileControlReqResult, sleAutoCliScriptFileControlScriptName }
			STATUS current
			DESCRIPTION 
				"destroyedAutoCliScript"
			::= { sleAutoCliScriptFileNotifications 3 }

		
		-- 1.3.6.1.4.1.6296.101.1.11.3
		sleAutoCliSchedule OBJECT IDENTIFIER ::= { sleAutoCli 3 }

		
		-- 1.3.6.1.4.1.6296.101.1.11.3.1
		sleAutoCliScheduleTable OBJECT-TYPE
			SYNTAX SEQUENCE OF SleAutoCliScheduleEntry
			MAX-ACCESS not-accessible
			STATUS current
			DESCRIPTION
				"Description."
			::= { sleAutoCliSchedule 1 }

		
		-- 1.3.6.1.4.1.6296.101.1.11.3.1.1
		sleAutoCliScheduleEntry OBJECT-TYPE
			SYNTAX SleAutoCliScheduleEntry
			MAX-ACCESS not-accessible
			STATUS current
			DESCRIPTION
				"Description."
			INDEX { sleAutoCliScheduleName }
			::= { sleAutoCliScheduleTable 1 }

		
		SleAutoCliScheduleEntry ::=
			SEQUENCE { 
				sleAutoCliScheduleName
					OCTET STRING,
				sleAutoCliScheduleType
					SleDefAutoCliScheduleType,
				sleAutoCliScheduleInterval
					Integer32,
				sleAutoCliScheduleYear
					Integer32,
				sleAutoCliScheduleMonth
					Integer32,
				sleAutoCliScheduleDay
					Integer32,
				sleAutoCliScheduleHour
					Integer32,
				sleAutoCliScheduleMinute
					Integer32,
				sleAutoCliScheduleScriptName
					OCTET STRING,
				sleAutoCliScheduleTransferType
					SleDefAutoCliScheduleTransferType,
				sleAutoCliScheduleLastExecutedTime
					OCTET STRING,
				sleAutoCliScheduleOutputRule
					OCTET STRING,
				sleAutoCliScheduleLastResult
					SleDefAutoCliScheduleResult,
				sleAutoCliScheduleProfileName
					OCTET STRING
			 }

		-- 1.3.6.1.4.1.6296.101.1.11.3.1.1.1
		sleAutoCliScheduleName OBJECT-TYPE
			SYNTAX OCTET STRING
			MAX-ACCESS read-only
			STATUS current
			DESCRIPTION
				"The name of the schedule name "
			::= { sleAutoCliScheduleEntry 1 }

		
		-- 1.3.6.1.4.1.6296.101.1.11.3.1.1.2
		sleAutoCliScheduleType OBJECT-TYPE
			SYNTAX SleDefAutoCliScheduleType
			MAX-ACCESS read-only
			STATUS current
			DESCRIPTION
				"The type of schedule.
				Periodic(1) - scheduled with regular intervals.
				At(2) - scheduled for exactly time.
				Daily(3) - scheduled for every day.
				Immediate(4) - scheduled immediately 
				"
			::= { sleAutoCliScheduleEntry 2 }

		
		-- 1.3.6.1.4.1.6296.101.1.11.3.1.1.3
		sleAutoCliScheduleInterval OBJECT-TYPE
			SYNTAX Integer32
			MAX-ACCESS read-only
			STATUS current
			DESCRIPTION
				"The period of execution time."
			::= { sleAutoCliScheduleEntry 3 }

		
		-- 1.3.6.1.4.1.6296.101.1.11.3.1.1.4
		sleAutoCliScheduleYear OBJECT-TYPE
			SYNTAX Integer32
			MAX-ACCESS read-only
			STATUS current
			DESCRIPTION
				"The value of the year "
			::= { sleAutoCliScheduleEntry 4 }

		
		-- 1.3.6.1.4.1.6296.101.1.11.3.1.1.5
		sleAutoCliScheduleMonth OBJECT-TYPE
			SYNTAX Integer32
			MAX-ACCESS read-only
			STATUS current
			DESCRIPTION
				"The value of the month"
			::= { sleAutoCliScheduleEntry 5 }

		
		-- 1.3.6.1.4.1.6296.101.1.11.3.1.1.6
		sleAutoCliScheduleDay OBJECT-TYPE
			SYNTAX Integer32
			MAX-ACCESS read-only
			STATUS current
			DESCRIPTION
				"Description."
			::= { sleAutoCliScheduleEntry 6 }

		
		-- 1.3.6.1.4.1.6296.101.1.11.3.1.1.7
		sleAutoCliScheduleHour OBJECT-TYPE
			SYNTAX Integer32
			MAX-ACCESS read-only
			STATUS current
			DESCRIPTION
				"The value of the hour"
			::= { sleAutoCliScheduleEntry 7 }

		
		-- 1.3.6.1.4.1.6296.101.1.11.3.1.1.8
		sleAutoCliScheduleMinute OBJECT-TYPE
			SYNTAX Integer32
			MAX-ACCESS read-only
			STATUS current
			DESCRIPTION
				"The value of the minute"
			::= { sleAutoCliScheduleEntry 8 }

		
		-- 1.3.6.1.4.1.6296.101.1.11.3.1.1.9
		sleAutoCliScheduleScriptName OBJECT-TYPE
			SYNTAX OCTET STRING
			MAX-ACCESS read-only
			STATUS current
			DESCRIPTION
				"The name of the script file"
			::= { sleAutoCliScheduleEntry 9 }

		
		-- 1.3.6.1.4.1.6296.101.1.11.3.1.1.10
		sleAutoCliScheduleTransferType OBJECT-TYPE
			SYNTAX SleDefAutoCliScheduleTransferType
			MAX-ACCESS read-only
			STATUS current
			DESCRIPTION
				"The type of the transferation that indicate way to save output file"
			::= { sleAutoCliScheduleEntry 10 }

		
		-- 1.3.6.1.4.1.6296.101.1.11.3.1.1.11
		sleAutoCliScheduleLastExecutedTime OBJECT-TYPE
			SYNTAX OCTET STRING
			MAX-ACCESS read-only
			STATUS current
			DESCRIPTION
				"The time of the last executed time"
			::= { sleAutoCliScheduleEntry 11 }

		
		-- 1.3.6.1.4.1.6296.101.1.11.3.1.1.12
		sleAutoCliScheduleOutputRule OBJECT-TYPE
			SYNTAX OCTET STRING
			MAX-ACCESS read-only
			STATUS current
			DESCRIPTION
				"The Rule of the output file name"
			::= { sleAutoCliScheduleEntry 12 }

		
		-- 1.3.6.1.4.1.6296.101.1.11.3.1.1.13
		sleAutoCliScheduleLastResult OBJECT-TYPE
			SYNTAX SleDefAutoCliScheduleResult
			MAX-ACCESS read-only
			STATUS current
			DESCRIPTION
				"The result of the last executed"
			::= { sleAutoCliScheduleEntry 13 }

		
		-- 1.3.6.1.4.1.6296.101.1.11.3.1.1.14
		sleAutoCliScheduleProfileName OBJECT-TYPE
			SYNTAX OCTET STRING (SIZE (1..32))
			MAX-ACCESS read-write
			STATUS current
			DESCRIPTION
				"Description."
			::= { sleAutoCliScheduleEntry 14 }

		
		-- 1.3.6.1.4.1.6296.101.1.11.3.2
		sleAutoCliScheduleControl OBJECT IDENTIFIER ::= { sleAutoCliSchedule 2 }

		
		-- 1.3.6.1.4.1.6296.101.1.11.3.2.1
		sleAutoCliScheduleControlRequest OBJECT-TYPE
			SYNTAX INTEGER
				{
				createAutoCliSchedule(1),
				destroyAutoCliSchedule(2)
				}
			MAX-ACCESS read-write
			STATUS current
			DESCRIPTION
				"Description."
			::= { sleAutoCliScheduleControl 1 }

		
		-- 1.3.6.1.4.1.6296.101.1.11.3.2.2
		sleAutoCliScheduleControlStatus OBJECT-TYPE
			SYNTAX SleControlStatusType
			MAX-ACCESS read-only
			STATUS current
			DESCRIPTION
				"Description."
			::= { sleAutoCliScheduleControl 2 }

		
		-- 1.3.6.1.4.1.6296.101.1.11.3.2.3
		sleAutoCliScheduleControlTimer OBJECT-TYPE
			SYNTAX Gauge32
			MAX-ACCESS read-write
			STATUS current
			DESCRIPTION
				"Description."
			::= { sleAutoCliScheduleControl 3 }

		
		-- 1.3.6.1.4.1.6296.101.1.11.3.2.4
		sleAutoCliScheduleControlTimeStamp OBJECT-TYPE
			SYNTAX TimeTicks
			MAX-ACCESS read-only
			STATUS current
			DESCRIPTION
				"Description."
			::= { sleAutoCliScheduleControl 4 }

		
		-- 1.3.6.1.4.1.6296.101.1.11.3.2.5
		sleAutoCliScheduleControlReqResult OBJECT-TYPE
			SYNTAX SleControlRequestResultType
			MAX-ACCESS read-only
			STATUS current
			DESCRIPTION
				"Description."
			::= { sleAutoCliScheduleControl 5 }

		
		-- 1.3.6.1.4.1.6296.101.1.11.3.2.6
		sleAutoCliScheduleControlName OBJECT-TYPE
			SYNTAX OCTET STRING
			MAX-ACCESS read-write
			STATUS current
			DESCRIPTION
				"The name of the schedule name"
			::= { sleAutoCliScheduleControl 6 }

		
		-- 1.3.6.1.4.1.6296.101.1.11.3.2.7
		sleAutoCliScheduleControlType OBJECT-TYPE
			SYNTAX SleDefAutoCliScheduleType
			MAX-ACCESS read-write
			STATUS current
			DESCRIPTION
				"The type of schedule.
				Periodic(1) - scheduled with regular intervals.
				At(2) - scheduled for exactly time.
				Daily(3) - scheduled for every day.
				Immediate(4) - scheduled immediately
				"
			::= { sleAutoCliScheduleControl 7 }

		
		-- 1.3.6.1.4.1.6296.101.1.11.3.2.8
		sleAutoCliScheduleControlInterval OBJECT-TYPE
			SYNTAX Integer32
			MAX-ACCESS read-write
			STATUS current
			DESCRIPTION
				"The period of execution time."
			::= { sleAutoCliScheduleControl 8 }

		
		-- 1.3.6.1.4.1.6296.101.1.11.3.2.9
		sleAutoCliScheduleControlYear OBJECT-TYPE
			SYNTAX Integer32
			MAX-ACCESS read-write
			STATUS current
			DESCRIPTION
				"The value of the year "
			::= { sleAutoCliScheduleControl 9 }

		
		-- 1.3.6.1.4.1.6296.101.1.11.3.2.10
		sleAutoCliScheduleControlMonth OBJECT-TYPE
			SYNTAX Integer32
			MAX-ACCESS read-write
			STATUS current
			DESCRIPTION
				"The value of the month"
			::= { sleAutoCliScheduleControl 10 }

		
		-- 1.3.6.1.4.1.6296.101.1.11.3.2.11
		sleAutoCliScheduleControlDay OBJECT-TYPE
			SYNTAX Integer32
			MAX-ACCESS read-write
			STATUS current
			DESCRIPTION
				"Description."
			::= { sleAutoCliScheduleControl 11 }

		
		-- 1.3.6.1.4.1.6296.101.1.11.3.2.12
		sleAutoCliScheduleControlHour OBJECT-TYPE
			SYNTAX Integer32
			MAX-ACCESS read-write
			STATUS current
			DESCRIPTION
				"The value of the hour"
			::= { sleAutoCliScheduleControl 12 }

		
		-- 1.3.6.1.4.1.6296.101.1.11.3.2.13
		sleAutoCliScheduleControlMinute OBJECT-TYPE
			SYNTAX Integer32
			MAX-ACCESS read-write
			STATUS current
			DESCRIPTION
				"The value of the minute"
			::= { sleAutoCliScheduleControl 13 }

		
		-- 1.3.6.1.4.1.6296.101.1.11.3.2.14
		sleAutoCliScheduleControlScriptName OBJECT-TYPE
			SYNTAX OCTET STRING
			MAX-ACCESS read-write
			STATUS current
			DESCRIPTION
				"The name of the script file"
			::= { sleAutoCliScheduleControl 14 }

		
		-- 1.3.6.1.4.1.6296.101.1.11.3.2.15
		sleAutoCliScheduleControlTransferType OBJECT-TYPE
			SYNTAX SleDefAutoCliScheduleTransferType
			MAX-ACCESS read-write
			STATUS current
			DESCRIPTION
				"The type of the transferation that indicate way to save output file"
			::= { sleAutoCliScheduleControl 15 }

		
		-- 1.3.6.1.4.1.6296.101.1.11.3.2.16
		sleAutoCliScheduleControlOutputRule OBJECT-TYPE
			SYNTAX OCTET STRING
			MAX-ACCESS read-write
			STATUS current
			DESCRIPTION
				"The Rule of the output file name"
			::= { sleAutoCliScheduleControl 16 }

		
		-- 1.3.6.1.4.1.6296.101.1.11.3.2.17
		sleAutoCliScheduleControlProfileName OBJECT-TYPE
			SYNTAX OCTET STRING (SIZE (1..32))
			MAX-ACCESS read-write
			STATUS current
			DESCRIPTION
				"Description."
			::= { sleAutoCliScheduleControl 17 }

		
		-- 1.3.6.1.4.1.6296.101.1.11.3.3
		sleAutoCliScheduleNotifications OBJECT IDENTIFIER ::= { sleAutoCliSchedule 3 }

		
		-- 1.3.6.1.4.1.6296.101.1.11.3.3.1
		sleAutoCliScheduleCreated NOTIFICATION-TYPE
			OBJECTS { sleAutoCliScheduleControlRequest, sleAutoCliScheduleControlTimeStamp, sleAutoCliScheduleControlReqResult, sleAutoCliScheduleType, sleAutoCliScheduleInterval, 
				sleAutoCliScheduleYear, sleAutoCliScheduleMonth, sleAutoCliScheduleDay, sleAutoCliScheduleHour, sleAutoCliScheduleMinute, 
				sleAutoCliScheduleScriptName, sleAutoCliScheduleTransferType, sleAutoCliScheduleOutputRule, sleAutoCliScheduleProfileName }
			STATUS current
			DESCRIPTION 
				"Description."
			::= { sleAutoCliScheduleNotifications 1 }

		
		-- 1.3.6.1.4.1.6296.101.1.11.3.3.2
		sleAutoCliScheduleDestroyed NOTIFICATION-TYPE
			OBJECTS { sleAutoCliScheduleControlRequest, sleAutoCliScheduleControlTimer, sleAutoCliScheduleControlReqResult, sleAutoCliScheduleControlName }
			STATUS current
			DESCRIPTION 
				"Description."
			::= { sleAutoCliScheduleNotifications 2 }

		
		-- 1.3.6.1.4.1.6296.101.1.11.4
		sleAutoCliProfile OBJECT IDENTIFIER ::= { sleAutoCli 4 }

		
		-- 1.3.6.1.4.1.6296.101.1.11.4.1
		sleAutoCliProfileTable OBJECT-TYPE
			SYNTAX SEQUENCE OF SleAutoCliProfileEntry
			MAX-ACCESS not-accessible
			STATUS current
			DESCRIPTION
				"Description."
			::= { sleAutoCliProfile 1 }

		
		-- 1.3.6.1.4.1.6296.101.1.11.4.1.1
		sleAutoCliProfileEntry OBJECT-TYPE
			SYNTAX SleAutoCliProfileEntry
			MAX-ACCESS not-accessible
			STATUS current
			DESCRIPTION
				"Description."
			INDEX { sleAutoCliProfileName }
			::= { sleAutoCliProfileTable 1 }

		
		SleAutoCliProfileEntry ::=
			SEQUENCE { 
				sleAutoCliProfileName
					OCTET STRING,
				sleAutoCliProfileType
					INTEGER
			 }

		-- 1.3.6.1.4.1.6296.101.1.11.4.1.1.1
		sleAutoCliProfileName OBJECT-TYPE
			SYNTAX OCTET STRING (SIZE (1..32))
			MAX-ACCESS read-write
			STATUS current
			DESCRIPTION
				"The name of the profile name."
			::= { sleAutoCliProfileEntry 1 }

		
		-- 1.3.6.1.4.1.6296.101.1.11.4.1.1.2
		sleAutoCliProfileType OBJECT-TYPE
			SYNTAX INTEGER
				{
				tftp(1),
				ftp(2)
				}
			MAX-ACCESS read-write
			STATUS current
			DESCRIPTION
				"The name of the profile type."
			::= { sleAutoCliProfileEntry 2 }

		
		-- 1.3.6.1.4.1.6296.101.1.11.4.2
		sleAutoCliProfileControl OBJECT IDENTIFIER ::= { sleAutoCliProfile 2 }

		
		-- 1.3.6.1.4.1.6296.101.1.11.4.2.1
		sleAutoCliProfileControlRequest OBJECT-TYPE
			SYNTAX INTEGER
				{
				createAutoCliProfile(1),
				destroyAutoCliProfile(2)
				}
			MAX-ACCESS read-write
			STATUS current
			DESCRIPTION
				"Description."
			::= { sleAutoCliProfileControl 1 }

		
		-- 1.3.6.1.4.1.6296.101.1.11.4.2.2
		sleAutoCliProfileControlStatus OBJECT-TYPE
			SYNTAX SleControlStatusType
			MAX-ACCESS read-only
			STATUS current
			DESCRIPTION
				"Description."
			::= { sleAutoCliProfileControl 2 }

		
		-- 1.3.6.1.4.1.6296.101.1.11.4.2.3
		sleAutoCliProfileControlTimer OBJECT-TYPE
			SYNTAX Gauge32
			MAX-ACCESS read-write
			STATUS current
			DESCRIPTION
				"Description."
			::= { sleAutoCliProfileControl 3 }

		
		-- 1.3.6.1.4.1.6296.101.1.11.4.2.4
		sleAutoCliProfileControlTimeStamp OBJECT-TYPE
			SYNTAX TimeTicks
			MAX-ACCESS read-only
			STATUS current
			DESCRIPTION
				"Description."
			::= { sleAutoCliProfileControl 4 }

		
		-- 1.3.6.1.4.1.6296.101.1.11.4.2.5
		sleAutoCliProfileControlReqResult OBJECT-TYPE
			SYNTAX SleControlRequestResultType
			MAX-ACCESS read-only
			STATUS current
			DESCRIPTION
				"Description."
			::= { sleAutoCliProfileControl 5 }

		
		-- 1.3.6.1.4.1.6296.101.1.11.4.2.6
		sleAutoCliProfileControlName OBJECT-TYPE
			SYNTAX OCTET STRING (SIZE (1..32))
			MAX-ACCESS read-write
			STATUS current
			DESCRIPTION
				"The name of the profile name"
			::= { sleAutoCliProfileControl 6 }

		
		-- 1.3.6.1.4.1.6296.101.1.11.4.2.7
		sleAutoCliProfileControlType OBJECT-TYPE
			SYNTAX INTEGER
				{
				tftp(1),
				ftp(2)
				}
			MAX-ACCESS read-write
			STATUS current
			DESCRIPTION
				"The name of the profile type"
			::= { sleAutoCliProfileControl 7 }

		
		-- 1.3.6.1.4.1.6296.101.1.11.4.3
		sleAutoCliProfileNotifications OBJECT IDENTIFIER ::= { sleAutoCliProfile 3 }

		
		-- 1.3.6.1.4.1.6296.101.1.11.4.3.1
		sleAutoCliProfileCreated NOTIFICATION-TYPE
			OBJECTS { sleAutoCliProfileControlRequest, sleAutoCliProfileControlTimeStamp, sleAutoCliProfileControlReqResult, sleAutoCliProfileType }
			STATUS current
			DESCRIPTION 
				"Description."
			::= { sleAutoCliProfileNotifications 1 }

		
		-- 1.3.6.1.4.1.6296.101.1.11.4.3.2
		sleAutoCliProfileDestroyed NOTIFICATION-TYPE
			OBJECTS { sleAutoCliProfileControlRequest, sleAutoCliProfileControlTimeStamp, sleAutoCliProfileControlReqResult, sleAutoCliProfileControlName }
			STATUS current
			DESCRIPTION 
				"Description."
			::= { sleAutoCliProfileNotifications 2 }

		
		-- 1.3.6.1.4.1.6296.101.1.11.5
		sleAutoCliProfileServer OBJECT IDENTIFIER ::= { sleAutoCli 5 }

		
		-- 1.3.6.1.4.1.6296.101.1.11.5.1
		sleAutoCliProfileServerTable OBJECT-TYPE
			SYNTAX SEQUENCE OF SleAutoCliProfileServerEntry
			MAX-ACCESS not-accessible
			STATUS current
			DESCRIPTION
				"Description."
			::= { sleAutoCliProfileServer 1 }

		
		-- 1.3.6.1.4.1.6296.101.1.11.5.1.1
		sleAutoCliProfileServerEntry OBJECT-TYPE
			SYNTAX SleAutoCliProfileServerEntry
			MAX-ACCESS not-accessible
			STATUS current
			DESCRIPTION
				"Description."
			INDEX { sleAutoCliProfileName, sleAutoCliProfileServerIpAddress }
			::= { sleAutoCliProfileServerTable 1 }

		
		SleAutoCliProfileServerEntry ::=
			SEQUENCE { 
				sleAutoCliProfileServerType
					INTEGER,
				sleAutoCliProfileServerIpAddress
					IpAddress,
				sleAutoCliProfileServerUser
					OCTET STRING,
				sleAutoCliProfileServerPassword
					OCTET STRING,
				sleAutoCliProfileServerDir
					OCTET STRING
			 }

		-- 1.3.6.1.4.1.6296.101.1.11.5.1.1.1
		sleAutoCliProfileServerType OBJECT-TYPE
			SYNTAX INTEGER
				{
				tftp(1),
				ftp(2)
				}
			MAX-ACCESS read-write
			STATUS current
			DESCRIPTION
				"The name of the profile's remote-server type."
			::= { sleAutoCliProfileServerEntry 1 }

		
		-- 1.3.6.1.4.1.6296.101.1.11.5.1.1.2
		sleAutoCliProfileServerIpAddress OBJECT-TYPE
			SYNTAX IpAddress
			MAX-ACCESS read-write
			STATUS current
			DESCRIPTION
				"The name of the profile's remote-server ip."
			::= { sleAutoCliProfileServerEntry 2 }

		
		-- 1.3.6.1.4.1.6296.101.1.11.5.1.1.3
		sleAutoCliProfileServerUser OBJECT-TYPE
			SYNTAX OCTET STRING (SIZE (0..32))
			MAX-ACCESS read-write
			STATUS current
			DESCRIPTION
				"The name of the profile's remote-server user."
			::= { sleAutoCliProfileServerEntry 3 }

		
		-- 1.3.6.1.4.1.6296.101.1.11.5.1.1.4
		sleAutoCliProfileServerPassword OBJECT-TYPE
			SYNTAX OCTET STRING (SIZE (0..32))
			MAX-ACCESS read-write
			STATUS current
			DESCRIPTION
				"The name of the profile's remote-server password."
			::= { sleAutoCliProfileServerEntry 4 }

		
		-- 1.3.6.1.4.1.6296.101.1.11.5.1.1.5
		sleAutoCliProfileServerDir OBJECT-TYPE
			SYNTAX OCTET STRING (SIZE (0..128))
			MAX-ACCESS read-write
			STATUS current
			DESCRIPTION
				"The name of the profile's remote-server directory."
			::= { sleAutoCliProfileServerEntry 5 }

		
		-- 1.3.6.1.4.1.6296.101.1.11.5.2
		sleAutoCliProfileServerControl OBJECT IDENTIFIER ::= { sleAutoCliProfileServer 2 }

		
		-- 1.3.6.1.4.1.6296.101.1.11.5.2.1
		sleAutoCliProfileServerControlRequest OBJECT-TYPE
			SYNTAX INTEGER
				{
				createAutoCliProfileServer(1),
				destroyAutoCliProfileServer(2),
				destroyAutoCliProfileServerAll(3)
				}
			MAX-ACCESS read-write
			STATUS current
			DESCRIPTION
				"Description."
			::= { sleAutoCliProfileServerControl 1 }

		
		-- 1.3.6.1.4.1.6296.101.1.11.5.2.2
		sleAutoCliProfileServerControlStatus OBJECT-TYPE
			SYNTAX SleControlStatusType
			MAX-ACCESS read-only
			STATUS current
			DESCRIPTION
				"Description."
			::= { sleAutoCliProfileServerControl 2 }

		
		-- 1.3.6.1.4.1.6296.101.1.11.5.2.3
		sleAutoCliProfileServerControlTimer OBJECT-TYPE
			SYNTAX Gauge32
			MAX-ACCESS read-write
			STATUS current
			DESCRIPTION
				"Description."
			::= { sleAutoCliProfileServerControl 3 }

		
		-- 1.3.6.1.4.1.6296.101.1.11.5.2.4
		sleAutoCliProfileServerControlTimeStamp OBJECT-TYPE
			SYNTAX TimeTicks
			MAX-ACCESS read-only
			STATUS current
			DESCRIPTION
				"Description."
			::= { sleAutoCliProfileServerControl 4 }

		
		-- 1.3.6.1.4.1.6296.101.1.11.5.2.5
		sleAutoCliProfileServerControlReqResult OBJECT-TYPE
			SYNTAX SleControlRequestResultType
			MAX-ACCESS read-only
			STATUS current
			DESCRIPTION
				"Description."
			::= { sleAutoCliProfileServerControl 5 }

		
		-- 1.3.6.1.4.1.6296.101.1.11.5.2.6
		sleAutoCliProfileServerControlProfName OBJECT-TYPE
			SYNTAX OCTET STRING (SIZE (1..32))
			MAX-ACCESS read-write
			STATUS current
			DESCRIPTION
				"The name of the profile name"
			::= { sleAutoCliProfileServerControl 6 }

		
		-- 1.3.6.1.4.1.6296.101.1.11.5.2.7
		sleAutoCliProfileServerControlIpAddress OBJECT-TYPE
			SYNTAX IpAddress
			MAX-ACCESS read-write
			STATUS current
			DESCRIPTION
				"Description."
			::= { sleAutoCliProfileServerControl 7 }

		
		-- 1.3.6.1.4.1.6296.101.1.11.5.2.8
		sleAutoCliProfileServerControlUser OBJECT-TYPE
			SYNTAX OCTET STRING (SIZE (0..32))
			MAX-ACCESS read-write
			STATUS current
			DESCRIPTION
				"Description."
			::= { sleAutoCliProfileServerControl 8 }

		
		-- 1.3.6.1.4.1.6296.101.1.11.5.2.9
		sleAutoCliProfileServerControlPassword OBJECT-TYPE
			SYNTAX OCTET STRING (SIZE (0..32))
			MAX-ACCESS read-write
			STATUS current
			DESCRIPTION
				"Description."
			::= { sleAutoCliProfileServerControl 9 }

		
		-- 1.3.6.1.4.1.6296.101.1.11.5.2.10
		sleAutoCliProfileServerControlDir OBJECT-TYPE
			SYNTAX OCTET STRING (SIZE (0..128))
			MAX-ACCESS read-write
			STATUS current
			DESCRIPTION
				"Description."
			::= { sleAutoCliProfileServerControl 10 }

		
		-- 1.3.6.1.4.1.6296.101.1.11.5.3
		sleAutoCliProfileServerNotifications OBJECT IDENTIFIER ::= { sleAutoCliProfileServer 3 }

		
		-- 1.3.6.1.4.1.6296.101.1.11.5.3.1
		sleAutoCliProfileServerCreated NOTIFICATION-TYPE
			OBJECTS { sleAutoCliProfileServerControlRequest, sleAutoCliProfileServerControlTimeStamp, sleAutoCliProfileServerControlReqResult, sleAutoCliProfileServerType, sleAutoCliProfileServerUser, 
				sleAutoCliProfileServerPassword, sleAutoCliProfileServerDir }
			STATUS current
			DESCRIPTION 
				"Description."
			::= { sleAutoCliProfileServerNotifications 1 }

		
		-- 1.3.6.1.4.1.6296.101.1.11.5.3.2
		sleAutoCliProfileServerDestroyed NOTIFICATION-TYPE
			OBJECTS { sleAutoCliProfileServerControlRequest, sleAutoCliProfileServerControlTimeStamp, sleAutoCliProfileServerControlReqResult, sleAutoCliProfileServerControlProfName, sleAutoCliProfileServerControlIpAddress
				 }
			STATUS current
			DESCRIPTION 
				"Description."
			::= { sleAutoCliProfileServerNotifications 2 }

		
		-- 1.3.6.1.4.1.6296.101.1.11.5.3.3
		sleAutoCliProfileServerAllDestroyed NOTIFICATION-TYPE
			OBJECTS { sleAutoCliProfileServerControlRequest, sleAutoCliProfileServerControlTimeStamp, sleAutoCliProfileServerControlReqResult, sleAutoCliProfileServerControlProfName }
			STATUS current
			DESCRIPTION 
				"Description."
			::= { sleAutoCliProfileServerNotifications 3 }

		
		-- 1.3.6.1.4.1.6296.101.1.11.6
		sleAutoCliOutputMemory OBJECT IDENTIFIER ::= { sleAutoCli 6 }

		
		-- 1.3.6.1.4.1.6296.101.1.11.6.1
		sleAutoCliOutputMemoryFileTable OBJECT-TYPE
			SYNTAX SEQUENCE OF SleAutoCliOutputMemoryFileEntry
			MAX-ACCESS not-accessible
			STATUS current
			DESCRIPTION
				"Description."
			::= { sleAutoCliOutputMemory 1 }

		
		-- 1.3.6.1.4.1.6296.101.1.11.6.1.1
		sleAutoCliOutputMemoryFileEntry OBJECT-TYPE
			SYNTAX SleAutoCliOutputMemoryFileEntry
			MAX-ACCESS not-accessible
			STATUS current
			DESCRIPTION
				"Description."
			INDEX { sleAutoCliOutputMemoryFileId }
			::= { sleAutoCliOutputMemoryFileTable 1 }

		
		SleAutoCliOutputMemoryFileEntry ::=
			SEQUENCE { 
				sleAutoCliOutputMemoryFileId
					INTEGER,
				sleAutoCliOutputMemoryFileName
					OCTET STRING,
				sleAutoCliOutputMemoryFileSize
					Integer32,
				sleAutoCliOutputMemoryFileUpdatedTime
					OCTET STRING
			 }

		-- 1.3.6.1.4.1.6296.101.1.11.6.1.1.1
		sleAutoCliOutputMemoryFileId OBJECT-TYPE
			SYNTAX INTEGER (1..2147483647)
			MAX-ACCESS read-only
			STATUS current
			DESCRIPTION
				"The id of the output file."
			::= { sleAutoCliOutputMemoryFileEntry 1 }

		
		-- 1.3.6.1.4.1.6296.101.1.11.6.1.1.2
		sleAutoCliOutputMemoryFileName OBJECT-TYPE
			SYNTAX OCTET STRING
			MAX-ACCESS read-only
			STATUS current
			DESCRIPTION
				"The name of the output file."
			::= { sleAutoCliOutputMemoryFileEntry 2 }

		
		-- 1.3.6.1.4.1.6296.101.1.11.6.1.1.3
		sleAutoCliOutputMemoryFileSize OBJECT-TYPE
			SYNTAX Integer32
			MAX-ACCESS read-only
			STATUS current
			DESCRIPTION
				"The file-size of the output file."
			::= { sleAutoCliOutputMemoryFileEntry 3 }

		
		-- 1.3.6.1.4.1.6296.101.1.11.6.1.1.4
		sleAutoCliOutputMemoryFileUpdatedTime OBJECT-TYPE
			SYNTAX OCTET STRING
			MAX-ACCESS read-only
			STATUS current
			DESCRIPTION
				"The updated time of the output file"
			::= { sleAutoCliOutputMemoryFileEntry 4 }

		
		-- 1.3.6.1.4.1.6296.101.1.11.6.2
		sleAutoCliOutputMemoryFileControl OBJECT IDENTIFIER ::= { sleAutoCliOutputMemory 2 }

		
		-- 1.3.6.1.4.1.6296.101.1.11.6.2.1
		sleAutoCliOutputMemoryFileControlRequest OBJECT-TYPE
			SYNTAX INTEGER
				{
				ftpputOutputFile(1),
				tftpputOutputFile(2),
				destroyOutputFile(3)
				}
			MAX-ACCESS read-write
			STATUS current
			DESCRIPTION
				"Description."
			::= { sleAutoCliOutputMemoryFileControl 1 }

		
		-- 1.3.6.1.4.1.6296.101.1.11.6.2.2
		sleAutoCliOutputMemoryFileControlStatus OBJECT-TYPE
			SYNTAX SleControlStatusType
			MAX-ACCESS read-only
			STATUS current
			DESCRIPTION
				"Description."
			::= { sleAutoCliOutputMemoryFileControl 2 }

		
		-- 1.3.6.1.4.1.6296.101.1.11.6.2.3
		sleAutoCliOutputMemoryFileControlTimer OBJECT-TYPE
			SYNTAX Gauge32
			MAX-ACCESS read-write
			STATUS current
			DESCRIPTION
				"Description."
			::= { sleAutoCliOutputMemoryFileControl 3 }

		
		-- 1.3.6.1.4.1.6296.101.1.11.6.2.4
		sleAutoCliOutputMemoryFileControlTimeStamp OBJECT-TYPE
			SYNTAX TimeTicks
			MAX-ACCESS read-only
			STATUS current
			DESCRIPTION
				"Description."
			::= { sleAutoCliOutputMemoryFileControl 4 }

		
		-- 1.3.6.1.4.1.6296.101.1.11.6.2.5
		sleAutoCliOutputMemoryFileControlReqResult OBJECT-TYPE
			SYNTAX SleControlRequestResultType
			MAX-ACCESS read-only
			STATUS current
			DESCRIPTION
				"Description."
			::= { sleAutoCliOutputMemoryFileControl 5 }

		
		-- 1.3.6.1.4.1.6296.101.1.11.6.2.6
		sleAutoCliOutputMemoryFileControlServer OBJECT-TYPE
			SYNTAX IpAddress
			MAX-ACCESS read-write
			STATUS current
			DESCRIPTION
				"The Ipaddress of the ftp server to put the output file."
			::= { sleAutoCliOutputMemoryFileControl 6 }

		
		-- 1.3.6.1.4.1.6296.101.1.11.6.2.7
		sleAutoCliOutputMemoryFileControlUserName OBJECT-TYPE
			SYNTAX OCTET STRING
			MAX-ACCESS read-write
			STATUS current
			DESCRIPTION
				"The username of the ftp server to put the output file."
			::= { sleAutoCliOutputMemoryFileControl 7 }

		
		-- 1.3.6.1.4.1.6296.101.1.11.6.2.8
		sleAutoCliOutputMemoryFileControlPassword OBJECT-TYPE
			SYNTAX OCTET STRING
			MAX-ACCESS read-write
			STATUS current
			DESCRIPTION
				"The password of the ftp server to put the output file."
			::= { sleAutoCliOutputMemoryFileControl 8 }

		
		-- 1.3.6.1.4.1.6296.101.1.11.6.2.9
		sleAutoCliOutputMemoryFileControlOutputFileName OBJECT-TYPE
			SYNTAX OCTET STRING
			MAX-ACCESS read-write
			STATUS current
			DESCRIPTION
				"The output file name."
			::= { sleAutoCliOutputMemoryFileControl 9 }

		
		-- 1.3.6.1.4.1.6296.101.1.11.6.2.10
		sleAutoCliOutputMemoryFileControlRemotePath OBJECT-TYPE
			SYNTAX OCTET STRING
			MAX-ACCESS read-write
			STATUS current
			DESCRIPTION
				"The remote path of the ftp server to put the output file"
			::= { sleAutoCliOutputMemoryFileControl 10 }

		
		-- 1.3.6.1.4.1.6296.101.1.11.6.3
		sleAutoCliOutputMemoryFileNotification OBJECT IDENTIFIER ::= { sleAutoCliOutputMemory 3 }

		
		-- 1.3.6.1.4.1.6296.101.1.11.6.3.1
		sleAutoCliOutputMemoryFileFtpCreated NOTIFICATION-TYPE
			OBJECTS { sleAutoCliOutputMemoryFileControlRequest, sleAutoCliOutputMemoryFileControlTimeStamp, sleAutoCliOutputMemoryFileControlReqResult, sleAutoCliOutputMemoryFileName }
			STATUS current
			DESCRIPTION 
				"Description."
			::= { sleAutoCliOutputMemoryFileNotification 1 }

		
		-- 1.3.6.1.4.1.6296.101.1.11.6.3.2
		sleAutoCliOutputMemoryFileTftpCreated NOTIFICATION-TYPE
			OBJECTS { sleAutoCliOutputMemoryFileControlRequest, sleAutoCliOutputMemoryFileControlTimeStamp, sleAutoCliOutputMemoryFileControlReqResult, sleAutoCliOutputMemoryFileName }
			STATUS current
			DESCRIPTION 
				"Description."
			::= { sleAutoCliOutputMemoryFileNotification 2 }

		
		-- 1.3.6.1.4.1.6296.101.1.11.6.3.3
		sleAutoCliOutputMemoryFileDestroyed NOTIFICATION-TYPE
			OBJECTS { sleAutoCliOutputMemoryFileControlRequest, sleAutoCliOutputMemoryFileControlTimeStamp, sleAutoCliOutputMemoryFileControlOutputFileName, sleAutoCliOutputMemoryFileControlReqResult }
			STATUS current
			DESCRIPTION 
				"Description."
			::= { sleAutoCliOutputMemoryFileNotification 3 }

		
		-- 1.3.6.1.4.1.6296.101.1.12
		sleAutoReset OBJECT IDENTIFIER ::= { sleSystemMaintenance 12 }

		
		-- 1.3.6.1.4.1.6296.101.1.12.1
		sleAutoResetPing OBJECT IDENTIFIER ::= { sleAutoReset 1 }

		
		-- 1.3.6.1.4.1.6296.101.1.12.1.1
		sleAutoResetPingInfo OBJECT IDENTIFIER ::= { sleAutoResetPing 1 }

		
		-- 1.3.6.1.4.1.6296.101.1.12.1.1.1
		sleAutoResetPingConfStatus OBJECT-TYPE
			SYNTAX EnableFlag
			MAX-ACCESS read-only
			STATUS current
			DESCRIPTION
				"The administrative state of AutoResetPing "
			::= { sleAutoResetPingInfo 1 }

		
		-- 1.3.6.1.4.1.6296.101.1.12.1.1.2
		sleAutoResetPingIpAddress OBJECT-TYPE
			SYNTAX IpAddress
			MAX-ACCESS read-only
			STATUS current
			DESCRIPTION
				"Gateway Ip address"
			::= { sleAutoResetPingInfo 2 }

		
		-- 1.3.6.1.4.1.6296.101.1.12.1.1.3
		sleAutoResetPingTransactionInterval OBJECT-TYPE
			SYNTAX Integer32
			MAX-ACCESS read-only
			STATUS current
			DESCRIPTION
				"The interval between ping transaction (10 - 86400)"
			::= { sleAutoResetPingInfo 3 }

		
		-- 1.3.6.1.4.1.6296.101.1.12.1.1.4
		sleAutoResetPingNumberOfRequest OBJECT-TYPE
			SYNTAX Integer32
			MAX-ACCESS read-only
			STATUS current
			DESCRIPTION
				"The number of ping request in 1 transaction (1-10)"
			::= { sleAutoResetPingInfo 4 }

		
		-- 1.3.6.1.4.1.6296.101.1.12.1.1.5
		sleAutoResetPingRequestInterval OBJECT-TYPE
			SYNTAX Integer32
			MAX-ACCESS read-only
			STATUS current
			DESCRIPTION
				"The interval between ping request (1 - 100)"
			::= { sleAutoResetPingInfo 5 }

		
		-- 1.3.6.1.4.1.6296.101.1.12.1.1.6
		sleAutoResetPingTimeoutOfRequest OBJECT-TYPE
			SYNTAX Integer32
			MAX-ACCESS read-only
			STATUS current
			DESCRIPTION
				"The timeout value for waiting reply message (1 - 10)"
			::= { sleAutoResetPingInfo 6 }

		
		-- 1.3.6.1.4.1.6296.101.1.12.1.1.7
		sleAutoResetPingLossThreshold OBJECT-TYPE
			SYNTAX Integer32
			MAX-ACCESS read-only
			STATUS current
			DESCRIPTION
				"The threshold value of ping-transaction loss count for reset. (1 - 100)
				 If ping-transaction loss count is reached at this value, The system will be reset
				
				"
			::= { sleAutoResetPingInfo 7 }

		
		-- 1.3.6.1.4.1.6296.101.1.12.1.1.8
		sleAutoResetPingEnableTime OBJECT-TYPE
			SYNTAX OCTET STRING
			MAX-ACCESS read-only
			STATUS current
			DESCRIPTION
				"The time of the autoresetping status was enabled"
			::= { sleAutoResetPingInfo 8 }

		
		-- 1.3.6.1.4.1.6296.101.1.12.1.1.9
		sleAutoResetPingRequestCount OBJECT-TYPE
			SYNTAX Integer32
			MAX-ACCESS read-only
			STATUS current
			DESCRIPTION
				"The count of request message in current transaction"
			::= { sleAutoResetPingInfo 9 }

		
		-- 1.3.6.1.4.1.6296.101.1.12.1.1.10
		sleAutoResetPingReplyCount OBJECT-TYPE
			SYNTAX Integer32
			MAX-ACCESS read-only
			STATUS current
			DESCRIPTION
				"The count of reply message in current transaction"
			::= { sleAutoResetPingInfo 10 }

		
		-- 1.3.6.1.4.1.6296.101.1.12.1.1.11
		sleAutoResetPingLossCount OBJECT-TYPE
			SYNTAX Integer32
			MAX-ACCESS read-only
			STATUS current
			DESCRIPTION
				"The count of loss message in current transaction"
			::= { sleAutoResetPingInfo 11 }

		
		-- 1.3.6.1.4.1.6296.101.1.12.1.1.12
		sleAutoResetPingTotalPingTransaction OBJECT-TYPE
			SYNTAX Counter64
			MAX-ACCESS read-only
			STATUS current
			DESCRIPTION
				"The total count of ping transaction"
			::= { sleAutoResetPingInfo 12 }

		
		-- 1.3.6.1.4.1.6296.101.1.12.1.1.13
		sleAutoResetPingTotalLossTransaction OBJECT-TYPE
			SYNTAX Counter64
			MAX-ACCESS read-only
			STATUS current
			DESCRIPTION
				"The total count of loss transaction"
			::= { sleAutoResetPingInfo 13 }

		
		-- 1.3.6.1.4.1.6296.101.1.12.1.1.14
		sleAutoResetPingRebootThreshold OBJECT-TYPE
			SYNTAX INTEGER (1..100)
			MAX-ACCESS read-only
			STATUS current
			DESCRIPTION
				"The threshold of reboot-counter for autoReset. (1 - 100)
				 If system is rebooted more than this value, system is not automatically reset anymore.
				"
			::= { sleAutoResetPingInfo 14 }

		
		-- 1.3.6.1.4.1.6296.101.1.12.1.1.15
		sleAutoResetPingRebootCounter OBJECT-TYPE
			SYNTAX Integer32
			MAX-ACCESS read-only
			STATUS current
			DESCRIPTION
				"The count of system-reboot"
			::= { sleAutoResetPingInfo 15 }

		
		-- 1.3.6.1.4.1.6296.101.1.12.1.1.16
		sleAutoResetPingRebootRecoveryTime OBJECT-TYPE
			SYNTAX Integer32 (10..14400)
			MAX-ACCESS read-only
			STATUS current
			DESCRIPTION
				"The reboot recovery time 10-14400(minute)"
			::= { sleAutoResetPingInfo 16 }

		
		-- 1.3.6.1.4.1.6296.101.1.12.1.2
		sleAutoResetPingControl OBJECT IDENTIFIER ::= { sleAutoResetPing 2 }

		
		-- 1.3.6.1.4.1.6296.101.1.12.1.2.1
		sleAutoResetPingControlRequest OBJECT-TYPE
			SYNTAX INTEGER
				{
				setAutoResetPingStatus(1),
				modifyAutoResetPingInfo(2),
				setAutoResetPingRebootCtrl(3),
				clearAutoResetPingRebootCounter(4)
				}
			MAX-ACCESS read-write
			STATUS current
			DESCRIPTION
				"Description."
			::= { sleAutoResetPingControl 1 }

		
		-- 1.3.6.1.4.1.6296.101.1.12.1.2.2
		sleAutoResetPingControlStatus OBJECT-TYPE
			SYNTAX SleControlStatusType
			MAX-ACCESS read-only
			STATUS current
			DESCRIPTION
				"Description."
			::= { sleAutoResetPingControl 2 }

		
		-- 1.3.6.1.4.1.6296.101.1.12.1.2.3
		sleAutoResetPingControlTimer OBJECT-TYPE
			SYNTAX Gauge32
			MAX-ACCESS read-write
			STATUS current
			DESCRIPTION
				"Description."
			::= { sleAutoResetPingControl 3 }

		
		-- 1.3.6.1.4.1.6296.101.1.12.1.2.4
		sleAutoResetPingControlTimeStamp OBJECT-TYPE
			SYNTAX TimeTicks
			MAX-ACCESS read-only
			STATUS current
			DESCRIPTION
				"Description."
			::= { sleAutoResetPingControl 4 }

		
		-- 1.3.6.1.4.1.6296.101.1.12.1.2.5
		sleAutoResetPingControlReqResult OBJECT-TYPE
			SYNTAX SleControlRequestResultType
			MAX-ACCESS read-only
			STATUS current
			DESCRIPTION
				"Description."
			::= { sleAutoResetPingControl 5 }

		
		-- 1.3.6.1.4.1.6296.101.1.12.1.2.6
		sleAutoResetPingControlConfStatus OBJECT-TYPE
			SYNTAX EnableFlag
			MAX-ACCESS read-write
			STATUS current
			DESCRIPTION
				"The administrative state of AutoResetPing "
			::= { sleAutoResetPingControl 6 }

		
		-- 1.3.6.1.4.1.6296.101.1.12.1.2.7
		sleAutoResetPingControlIpAddress OBJECT-TYPE
			SYNTAX IpAddress
			MAX-ACCESS read-write
			STATUS current
			DESCRIPTION
				"Gateway Ip address"
			::= { sleAutoResetPingControl 7 }

		
		-- 1.3.6.1.4.1.6296.101.1.12.1.2.8
		sleAutoResetPingControlTransactionInterval OBJECT-TYPE
			SYNTAX Integer32
			MAX-ACCESS read-write
			STATUS current
			DESCRIPTION
				"The interval between ping transaction (10 - 86400)"
			::= { sleAutoResetPingControl 8 }

		
		-- 1.3.6.1.4.1.6296.101.1.12.1.2.9
		sleAutoResetPingControlNumberOfRequest OBJECT-TYPE
			SYNTAX Integer32
			MAX-ACCESS read-write
			STATUS current
			DESCRIPTION
				"The number of ping request in 1 transaction (1-10)"
			::= { sleAutoResetPingControl 9 }

		
		-- 1.3.6.1.4.1.6296.101.1.12.1.2.10
		sleAutoResetPingControlRequestInterval OBJECT-TYPE
			SYNTAX Integer32
			MAX-ACCESS read-write
			STATUS current
			DESCRIPTION
				"The interval between ping request (1 - 100)"
			::= { sleAutoResetPingControl 10 }

		
		-- 1.3.6.1.4.1.6296.101.1.12.1.2.11
		sleAutoResetPingControlTimeoutOfRequest OBJECT-TYPE
			SYNTAX Integer32
			MAX-ACCESS read-write
			STATUS current
			DESCRIPTION
				"The timeout value for waiting reply message (1 - 10)"
			::= { sleAutoResetPingControl 11 }

		
		-- 1.3.6.1.4.1.6296.101.1.12.1.2.12
		sleAutoResetPingControlPingLossThreshold OBJECT-TYPE
			SYNTAX Integer32
			MAX-ACCESS read-write
			STATUS current
			DESCRIPTION
				"The threshold value of ping-transaction loss count for reset. (1 - 100)
				 If ping-transaction loss count is reached at this value, The system will be reset
				"
			::= { sleAutoResetPingControl 12 }

		
		-- 1.3.6.1.4.1.6296.101.1.12.1.2.13
		sleAutoResetPingControlRebootThreshold OBJECT-TYPE
			SYNTAX INTEGER (1..100)
			MAX-ACCESS read-write
			STATUS current
			DESCRIPTION
				"The threshold of reboot-counter for autoReset. (1 - 100)
				 If system is rebooted more than this value, system is not automatically reset anymore."
			::= { sleAutoResetPingControl 13 }

		
		-- 1.3.6.1.4.1.6296.101.1.12.1.2.14
		sleAutoResetPingControlRebootRecoveryTime OBJECT-TYPE
			SYNTAX Integer32 (10..14400)
			MAX-ACCESS read-write
			STATUS current
			DESCRIPTION
				"The reboot recovery time 10-14400(minute)"
			::= { sleAutoResetPingControl 14 }

		
		-- 1.3.6.1.4.1.6296.101.1.12.1.3
		sleAutoResetPingNotification OBJECT IDENTIFIER ::= { sleAutoResetPing 3 }

		
		-- 1.3.6.1.4.1.6296.101.1.12.1.3.1
		sleAutoResetPingStatusChanged NOTIFICATION-TYPE
			OBJECTS { sleAutoResetPingControlRequest, sleAutoResetPingControlTimeStamp, sleAutoResetPingControlReqResult, sleAutoResetPingConfStatus }
			STATUS current
			DESCRIPTION 
				"setAutoResetPingStatus"
			::= { sleAutoResetPingNotification 1 }

		
		-- 1.3.6.1.4.1.6296.101.1.12.1.3.2
		sleAutoResetPingInfoModified NOTIFICATION-TYPE
			OBJECTS { sleAutoResetPingControlRequest, sleAutoResetPingControlTimeStamp, sleAutoResetPingControlReqResult, sleAutoResetPingIpAddress, sleAutoResetPingTransactionInterval, 
				sleAutoResetPingNumberOfRequest, sleAutoResetPingRequestInterval, sleAutoResetPingTimeoutOfRequest, sleAutoResetPingLossThreshold }
			STATUS current
			DESCRIPTION 
				"modifyAutoResetPingInfo"
			::= { sleAutoResetPingNotification 2 }

		
		-- 1.3.6.1.4.1.6296.101.1.12.1.3.3
		sleAutoResetPingRebootCtrlModified NOTIFICATION-TYPE
			OBJECTS { sleAutoResetPingControlRequest, sleAutoResetPingControlTimeStamp, sleAutoResetPingControlReqResult, sleAutoResetPingRebootThreshold, sleAutoResetPingRebootRecoveryTime
				 }
			STATUS current
			DESCRIPTION 
				"setAutoResetPingRebootCtrl"
			::= { sleAutoResetPingNotification 3 }

		
		-- 1.3.6.1.4.1.6296.101.1.12.1.3.4
		sleAutoResetPingRebootCountClearSetted NOTIFICATION-TYPE
			OBJECTS { sleAutoResetPingControlRequest, sleAutoResetPingControlTimeStamp, sleAutoResetPingControlReqResult }
			STATUS current
			DESCRIPTION 
				"clearAutoResetPingRebootCounter"
			::= { sleAutoResetPingNotification 4 }

		
		-- 1.3.6.1.4.1.6296.101.1.12.2
		sleAutoResetMemoryleak OBJECT IDENTIFIER ::= { sleAutoReset 2 }

		
		-- 1.3.6.1.4.1.6296.101.1.12.2.1
		sleAutoResetMemoryleakInfo OBJECT IDENTIFIER ::= { sleAutoResetMemoryleak 1 }

		
		-- 1.3.6.1.4.1.6296.101.1.12.2.1.1
		sleAutoResetMemoryleakContStatus OBJECT-TYPE
			SYNTAX EnableFlag
			MAX-ACCESS read-only
			STATUS current
			DESCRIPTION
				"The administrative state of AutoResetMemoryleak."
			::= { sleAutoResetMemoryleakInfo 1 }

		
		-- 1.3.6.1.4.1.6296.101.1.12.2.1.2
		sleAutoResetMemoryleakMemThreshold OBJECT-TYPE
			SYNTAX Integer32
			MAX-ACCESS read-only
			STATUS current
			DESCRIPTION
				"The threshold for the free memory size.(1 - 524288)"
			::= { sleAutoResetMemoryleakInfo 2 }

		
		-- 1.3.6.1.4.1.6296.101.1.12.2.1.3
		sleAutoResetMemoryleakCheckInterval OBJECT-TYPE
			SYNTAX Integer32
			MAX-ACCESS read-only
			STATUS current
			DESCRIPTION
				"The interval between check transaction. (10 - 86400)"
			::= { sleAutoResetMemoryleakInfo 3 }

		
		-- 1.3.6.1.4.1.6296.101.1.12.2.1.4
		sleAutoResetMemoryleakNumberOfVerification OBJECT-TYPE
			SYNTAX Integer32
			MAX-ACCESS read-only
			STATUS current
			DESCRIPTION
				"The number of verification in 1 transaction. (1 - 10)"
			::= { sleAutoResetMemoryleakInfo 4 }

		
		-- 1.3.6.1.4.1.6296.101.1.12.2.1.5
		sleAutoResetMemoryleakVerificationInterval OBJECT-TYPE
			SYNTAX Integer32
			MAX-ACCESS read-only
			STATUS current
			DESCRIPTION
				"The interval of verification. (1 - 10)"
			::= { sleAutoResetMemoryleakInfo 5 }

		
		-- 1.3.6.1.4.1.6296.101.1.12.2.1.6
		sleAutoResetMemoryleakCountThreshold OBJECT-TYPE
			SYNTAX Integer32
			MAX-ACCESS read-only
			STATUS current
			DESCRIPTION
				"The threshold of memory-leak count for reboot-process (1 - 100)"
			::= { sleAutoResetMemoryleakInfo 6 }

		
		-- 1.3.6.1.4.1.6296.101.1.12.2.1.7
		sleAutoResetMemoryleakEnableTime OBJECT-TYPE
			SYNTAX OCTET STRING
			MAX-ACCESS read-only
			STATUS current
			DESCRIPTION
				"The time of the autoresetmemoryleak status was enabled"
			::= { sleAutoResetMemoryleakInfo 7 }

		
		-- 1.3.6.1.4.1.6296.101.1.12.2.1.8
		sleAutoResetMemoryleakLastFreeMemory OBJECT-TYPE
			SYNTAX Integer32
			MAX-ACCESS read-only
			STATUS current
			DESCRIPTION
				"The size of free memory at last verification."
			::= { sleAutoResetMemoryleakInfo 8 }

		
		-- 1.3.6.1.4.1.6296.101.1.12.2.1.9
		sleAutoResetMemoryleakVerificationCount OBJECT-TYPE
			SYNTAX Integer32
			MAX-ACCESS read-only
			STATUS current
			DESCRIPTION
				"The count of verification in current transaction."
			::= { sleAutoResetMemoryleakInfo 9 }

		
		-- 1.3.6.1.4.1.6296.101.1.12.2.1.10
		sleAutoResetMemoryleakDetectionCount OBJECT-TYPE
			SYNTAX Integer32
			MAX-ACCESS read-only
			STATUS current
			DESCRIPTION
				"The count of detection in current transaction."
			::= { sleAutoResetMemoryleakInfo 10 }

		
		-- 1.3.6.1.4.1.6296.101.1.12.2.1.11
		sleAutoResetMemoryleakTotalVerificationCount OBJECT-TYPE
			SYNTAX Counter64
			MAX-ACCESS read-only
			STATUS current
			DESCRIPTION
				"The total verification count."
			::= { sleAutoResetMemoryleakInfo 11 }

		
		-- 1.3.6.1.4.1.6296.101.1.12.2.1.12
		sleAutoResetMemoryleakTotalDetectionCount OBJECT-TYPE
			SYNTAX Counter64
			MAX-ACCESS read-only
			STATUS current
			DESCRIPTION
				"The total detection count."
			::= { sleAutoResetMemoryleakInfo 12 }

		
		-- 1.3.6.1.4.1.6296.101.1.12.2.1.13
		sleAutoResetMemoryleakReboottimeStartHour OBJECT-TYPE
			SYNTAX Integer32 (-1..23)
			MAX-ACCESS read-only
			STATUS current
			DESCRIPTION
				"The start time (hour) to be able to reboot (0 - 23)
				-1: no set"
			::= { sleAutoResetMemoryleakInfo 13 }

		
		-- 1.3.6.1.4.1.6296.101.1.12.2.1.14
		sleAutoResetMemoryleakReboottimeStartMin OBJECT-TYPE
			SYNTAX Integer32 (-1..59)
			MAX-ACCESS read-only
			STATUS current
			DESCRIPTION
				"The start time (minute) to be able to reboot (0 - 59)
				-1: no set"
			::= { sleAutoResetMemoryleakInfo 14 }

		
		-- 1.3.6.1.4.1.6296.101.1.12.2.1.15
		sleAutoResetMemoryleakReboottimeEndHour OBJECT-TYPE
			SYNTAX Integer32 (-1..23)
			MAX-ACCESS read-only
			STATUS current
			DESCRIPTION
				"The end time (hour) to be able to reboot (0 - 23)
				-1: no set"
			::= { sleAutoResetMemoryleakInfo 15 }

		
		-- 1.3.6.1.4.1.6296.101.1.12.2.1.16
		sleAutoResetMemoryleakReboottimeEndMin OBJECT-TYPE
			SYNTAX Integer32 (-1..59)
			MAX-ACCESS read-only
			STATUS current
			DESCRIPTION
				"The end time (minute) to be able to reboot (0 - 59)
				-1: no set"
			::= { sleAutoResetMemoryleakInfo 16 }

		
		-- 1.3.6.1.4.1.6296.101.1.12.2.1.17
		sleAutoResetMemoryleakRebootThreshold OBJECT-TYPE
			SYNTAX INTEGER (1..100)
			MAX-ACCESS read-only
			STATUS current
			DESCRIPTION
				"The threshold of reboot-counter for autoReset. (1 - 100)
				If system is rebooted more than this value, system is not automatically reset anymore.
				"
			::= { sleAutoResetMemoryleakInfo 17 }

		
		-- 1.3.6.1.4.1.6296.101.1.12.2.1.18
		sleAutoResetMemoryleakRebootCount OBJECT-TYPE
			SYNTAX Integer32
			MAX-ACCESS read-only
			STATUS current
			DESCRIPTION
				"The count of system-reboot"
			::= { sleAutoResetMemoryleakInfo 18 }

		
		-- 1.3.6.1.4.1.6296.101.1.12.2.2
		sleAutoResetMemoryleakControl OBJECT IDENTIFIER ::= { sleAutoResetMemoryleak 2 }

		
		-- 1.3.6.1.4.1.6296.101.1.12.2.2.1
		sleAutoResetMemoryleakControlRequest OBJECT-TYPE
			SYNTAX INTEGER
				{
				setAutoResetMemoryleakStatus(1),
				modifyAutoResetMemoryleakInfo(2),
				modifyAutoResetMomoryleakReboottime(3),
				setAutoResetMemoryRebootCtrl(4),
				setAutoResetclearAutoResetRebootCounter(5)
				}
			MAX-ACCESS read-write
			STATUS current
			DESCRIPTION
				"Description."
			::= { sleAutoResetMemoryleakControl 1 }

		
		-- 1.3.6.1.4.1.6296.101.1.12.2.2.2
		sleAutoResetMemoryleakControlStatus OBJECT-TYPE
			SYNTAX SleControlStatusType
			MAX-ACCESS read-only
			STATUS current
			DESCRIPTION
				"Description."
			::= { sleAutoResetMemoryleakControl 2 }

		
		-- 1.3.6.1.4.1.6296.101.1.12.2.2.3
		sleAutoResetMemoryleakControlTimer OBJECT-TYPE
			SYNTAX Gauge32
			MAX-ACCESS read-write
			STATUS current
			DESCRIPTION
				"Description."
			::= { sleAutoResetMemoryleakControl 3 }

		
		-- 1.3.6.1.4.1.6296.101.1.12.2.2.4
		sleAutoResetMemoryleakControlTimeStamp OBJECT-TYPE
			SYNTAX TimeTicks
			MAX-ACCESS read-only
			STATUS current
			DESCRIPTION
				"Description."
			::= { sleAutoResetMemoryleakControl 4 }

		
		-- 1.3.6.1.4.1.6296.101.1.12.2.2.5
		sleAutoResetMemoryleakControlReqResult OBJECT-TYPE
			SYNTAX SleControlRequestResultType
			MAX-ACCESS read-only
			STATUS current
			DESCRIPTION
				"Description."
			::= { sleAutoResetMemoryleakControl 5 }

		
		-- 1.3.6.1.4.1.6296.101.1.12.2.2.6
		sleAutoResetMemoryleakControlConfStatus OBJECT-TYPE
			SYNTAX EnableFlag
			MAX-ACCESS read-write
			STATUS current
			DESCRIPTION
				"The administrative state of AutoResetMemoryleak."
			::= { sleAutoResetMemoryleakControl 6 }

		
		-- 1.3.6.1.4.1.6296.101.1.12.2.2.7
		sleAutoResetMemoryleakControlMemThreshold OBJECT-TYPE
			SYNTAX Integer32
			MAX-ACCESS read-write
			STATUS current
			DESCRIPTION
				"The threshold for the free memory size.(1 - 524288)"
			::= { sleAutoResetMemoryleakControl 7 }

		
		-- 1.3.6.1.4.1.6296.101.1.12.2.2.8
		sleAutoResetMemoryleakControlCheckInterval OBJECT-TYPE
			SYNTAX Integer32
			MAX-ACCESS read-write
			STATUS current
			DESCRIPTION
				"The interval between check transaction. (10 - 86400)"
			::= { sleAutoResetMemoryleakControl 8 }

		
		-- 1.3.6.1.4.1.6296.101.1.12.2.2.9
		sleAutoResetMemoryleakControlNumberOfVerification OBJECT-TYPE
			SYNTAX Integer32
			MAX-ACCESS read-write
			STATUS current
			DESCRIPTION
				"The number of verification in 1 transaction. (1 - 10)"
			::= { sleAutoResetMemoryleakControl 9 }

		
		-- 1.3.6.1.4.1.6296.101.1.12.2.2.10
		sleAutoResetMemoryleakControlVerificationInterval OBJECT-TYPE
			SYNTAX Integer32
			MAX-ACCESS read-write
			STATUS current
			DESCRIPTION
				"The interval of verification. (1 - 10)"
			::= { sleAutoResetMemoryleakControl 10 }

		
		-- 1.3.6.1.4.1.6296.101.1.12.2.2.11
		sleAutoResetMemoryleakControlCountThreshold OBJECT-TYPE
			SYNTAX Integer32
			MAX-ACCESS read-write
			STATUS current
			DESCRIPTION
				"The threshold of memory-leak count for reboot-process (1 - 100)"
			::= { sleAutoResetMemoryleakControl 11 }

		
		-- 1.3.6.1.4.1.6296.101.1.12.2.2.12
		sleAutoResetMemoryleakControlReboottimeStartHour OBJECT-TYPE
			SYNTAX Integer32 (-1..23)
			MAX-ACCESS read-write
			STATUS current
			DESCRIPTION
				"The start time (hour) to be able to reboot (0 - 23)
				-1: clear."
			::= { sleAutoResetMemoryleakControl 12 }

		
		-- 1.3.6.1.4.1.6296.101.1.12.2.2.13
		sleAutoResetMemoryleakControlReboottimeStartMin OBJECT-TYPE
			SYNTAX Integer32 (-1..59)
			MAX-ACCESS read-write
			STATUS current
			DESCRIPTION
				"The start time (minute) to be able to reboot (0 - 59)
				-1: clear"
			::= { sleAutoResetMemoryleakControl 13 }

		
		-- 1.3.6.1.4.1.6296.101.1.12.2.2.14
		sleAutoResetMemoryleakControlReboottimeEndHour OBJECT-TYPE
			SYNTAX Integer32 (-1..23)
			MAX-ACCESS read-write
			STATUS current
			DESCRIPTION
				"The end time (hour) to be able to reboot (0 - 23)
				-1: clear"
			::= { sleAutoResetMemoryleakControl 14 }

		
		-- 1.3.6.1.4.1.6296.101.1.12.2.2.15
		sleAutoResetMemoryleakControlReboottimeEndMin OBJECT-TYPE
			SYNTAX Integer32 (-1..59)
			MAX-ACCESS read-write
			STATUS current
			DESCRIPTION
				"The end time (minute) to be able to reboot (0 - 59)
				-1: clear"
			::= { sleAutoResetMemoryleakControl 15 }

		
		-- 1.3.6.1.4.1.6296.101.1.12.2.2.16
		sleAutoResetMemoryleakControlRebootThreshold OBJECT-TYPE
			SYNTAX INTEGER (1..100)
			MAX-ACCESS read-write
			STATUS current
			DESCRIPTION
				"The threshold of reboot-counter for autoReset.
				If system is rebooted more than this value, system is not automatically reset anymore. (1 - 100)
				"
			::= { sleAutoResetMemoryleakControl 16 }

		
		-- 1.3.6.1.4.1.6296.101.1.12.2.3
		sleAutoResetMemoryleakNotification OBJECT IDENTIFIER ::= { sleAutoResetMemoryleak 3 }

		
		-- 1.3.6.1.4.1.6296.101.1.12.2.3.1
		sleAutoResetMemoryleakStatusChanged NOTIFICATION-TYPE
			OBJECTS { sleAutoResetMemoryleakControlRequest, sleAutoResetMemoryleakControlTimeStamp, sleAutoResetMemoryleakControlReqResult, sleAutoResetMemoryleakContStatus }
			STATUS current
			DESCRIPTION 
				"setAutoResetMemoryleakStatus"
			::= { sleAutoResetMemoryleakNotification 1 }

		
		-- 1.3.6.1.4.1.6296.101.1.12.2.3.2
		sleAutoResetMemoryleakInfoModified NOTIFICATION-TYPE
			OBJECTS { sleAutoResetMemoryleakControlRequest, sleAutoResetMemoryleakControlTimeStamp, sleAutoResetMemoryleakControlReqResult, sleAutoResetMemoryleakMemThreshold, sleAutoResetMemoryleakCheckInterval, 
				sleAutoResetMemoryleakNumberOfVerification, sleAutoResetMemoryleakVerificationInterval, sleAutoResetMemoryleakCountThreshold }
			STATUS current
			DESCRIPTION 
				"modifyAutoResetMemoryleakInfo"
			::= { sleAutoResetMemoryleakNotification 2 }

		
		-- 1.3.6.1.4.1.6296.101.1.12.2.3.3
		sleAutoResetMemoryleakReboottimeModified NOTIFICATION-TYPE
			OBJECTS { sleAutoResetMemoryleakControlRequest, sleAutoResetMemoryleakControlTimeStamp, sleAutoResetMemoryleakControlReqResult, sleAutoResetMemoryleakReboottimeStartHour, sleAutoResetMemoryleakReboottimeStartMin, 
				sleAutoResetMemoryleakReboottimeEndHour, sleAutoResetMemoryleakReboottimeEndMin }
			STATUS current
			DESCRIPTION 
				"modifyAutoResetMomoryleakReboottime"
			::= { sleAutoResetMemoryleakNotification 3 }

		
		-- 1.3.6.1.4.1.6296.101.1.12.2.3.4
		sleAutoResetMemoryleakRebootCtrlModified NOTIFICATION-TYPE
			OBJECTS { sleAutoResetMemoryleakControlRequest, sleAutoResetMemoryleakControlTimeStamp, sleAutoResetMemoryleakControlReqResult, sleAutoResetMemoryleakRebootThreshold }
			STATUS current
			DESCRIPTION 
				"setAutoResetMemoryRebootCtrl"
			::= { sleAutoResetMemoryleakNotification 4 }

		
		-- 1.3.6.1.4.1.6296.101.1.12.2.3.5
		sleAutoResetMemoryleakRebootCountClearSetted NOTIFICATION-TYPE
			OBJECTS { sleAutoResetMemoryleakControlRequest, sleAutoResetMemoryleakControlTimeStamp, sleAutoResetMemoryleakControlReqResult }
			STATUS current
			DESCRIPTION 
				"setAutoResetclearAutoResetRebootCounter"
			::= { sleAutoResetMemoryleakNotification 5 }

		
		-- 1.3.6.1.4.1.6296.101.1.12.3
		sleAutoResetCpu OBJECT IDENTIFIER ::= { sleAutoReset 3 }

		
		-- 1.3.6.1.4.1.6296.101.1.12.3.1
		sleAutoResetCpuInfo OBJECT IDENTIFIER ::= { sleAutoResetCpu 1 }

		
		-- 1.3.6.1.4.1.6296.101.1.12.3.1.1
		sleAutoResetCpuStatus OBJECT-TYPE
			SYNTAX INTEGER
				{
				off(0),
				on(1)
				}
			MAX-ACCESS read-only
			STATUS current
			DESCRIPTION
				"The auto-reset cpu status."
			::= { sleAutoResetCpuInfo 1 }

		
		-- 1.3.6.1.4.1.6296.101.1.12.3.1.2
		sleAutoResetCpuLoad OBJECT-TYPE
			SYNTAX Integer32 (50..100)
			MAX-ACCESS read-only
			STATUS current
			DESCRIPTION
				"CPU load average per 1 min.(50 - 100)"
			::= { sleAutoResetCpuInfo 2 }

		
		-- 1.3.6.1.4.1.6296.101.1.12.3.1.3
		sleAutoResetCpuInterruptLoad OBJECT-TYPE
			SYNTAX Integer32 (1..100)
			MAX-ACCESS read-only
			STATUS current
			DESCRIPTION
				"Interrupt load average per 1 min. (1 - 100)"
			::= { sleAutoResetCpuInfo 3 }

		
		-- 1.3.6.1.4.1.6296.101.1.12.3.1.4
		sleAutoResetCpuTime OBJECT-TYPE
			SYNTAX Integer32
			MAX-ACCESS read-only
			STATUS current
			DESCRIPTION
				"The continuation time."
			::= { sleAutoResetCpuInfo 4 }

		
		-- 1.3.6.1.4.1.6296.101.1.12.3.2
		sleAutoResetCpuControl OBJECT IDENTIFIER ::= { sleAutoResetCpu 2 }

		
		-- 1.3.6.1.4.1.6296.101.1.12.3.2.1
		sleAutoResetCpuControlRequest OBJECT-TYPE
			SYNTAX INTEGER
				{
				setAutoResetCpu(1),
				delAutoResetCpu(2)
				}
			MAX-ACCESS read-write
			STATUS current
			DESCRIPTION
				"The request of a user command"
			::= { sleAutoResetCpuControl 1 }

		
		-- 1.3.6.1.4.1.6296.101.1.12.3.2.2
		sleAutoResetCpuControlStatus OBJECT-TYPE
			SYNTAX SleControlStatusType
			MAX-ACCESS read-only
			STATUS current
			DESCRIPTION
				"The status of user command"
			::= { sleAutoResetCpuControl 2 }

		
		-- 1.3.6.1.4.1.6296.101.1.12.3.2.3
		sleAutoResetCpuControlTimer OBJECT-TYPE
			SYNTAX Gauge32
			MAX-ACCESS read-write
			STATUS current
			DESCRIPTION
				"The maximum time for the manager for a long running user command"
			::= { sleAutoResetCpuControl 3 }

		
		-- 1.3.6.1.4.1.6296.101.1.12.3.2.4
		sleAutoResetCpuControlTimeStamp OBJECT-TYPE
			SYNTAX TimeTicks
			MAX-ACCESS read-only
			STATUS current
			DESCRIPTION
				"The time stamp of the last command(end of command)"
			::= { sleAutoResetCpuControl 4 }

		
		-- 1.3.6.1.4.1.6296.101.1.12.3.2.5
		sleAutoResetCpuControlReqResult OBJECT-TYPE
			SYNTAX SleControlRequestResultType
			MAX-ACCESS read-only
			STATUS current
			DESCRIPTION
				"The result of the last user command"
			::= { sleAutoResetCpuControl 5 }

		
		-- 1.3.6.1.4.1.6296.101.1.12.3.2.6
		sleAutoResetCpuControlLoad OBJECT-TYPE
			SYNTAX Integer32 (50..100)
			MAX-ACCESS read-write
			STATUS current
			DESCRIPTION
				"CPU load average per 1 min.(50 - 100)"
			::= { sleAutoResetCpuControl 6 }

		
		-- 1.3.6.1.4.1.6296.101.1.12.3.2.7
		sleAutoResetCpuControlInterruptLoad OBJECT-TYPE
			SYNTAX Integer32 (1..100)
			MAX-ACCESS read-write
			STATUS current
			DESCRIPTION
				"Interrupt load average per 1 min. (1 - 100)"
			::= { sleAutoResetCpuControl 7 }

		
		-- 1.3.6.1.4.1.6296.101.1.12.3.2.8
		sleAutoResetCpuControlTime OBJECT-TYPE
			SYNTAX Integer32
			MAX-ACCESS read-write
			STATUS current
			DESCRIPTION
				"The continuation time."
			::= { sleAutoResetCpuControl 8 }

		
		-- 1.3.6.1.4.1.6296.101.1.12.3.3
		sleAutoResetCpuNotification OBJECT IDENTIFIER ::= { sleAutoResetCpu 3 }

		
		-- 1.3.6.1.4.1.6296.101.1.12.3.3.1
		sleAutoResetCpuChanged NOTIFICATION-TYPE
			OBJECTS { sleAutoResetCpuControlRequest, sleAutoResetCpuControlTimeStamp, sleAutoResetCpuControlReqResult, sleAutoResetCpuControlLoad, sleAutoResetCpuControlInterruptLoad, 
				sleAutoResetCpuControlTime }
			STATUS current
			DESCRIPTION 
				"setAutoResetCpu"
			::= { sleAutoResetCpuNotification 1 }

		
		-- 1.3.6.1.4.1.6296.101.1.12.3.3.2
		sleAutoResetCpuDeleted NOTIFICATION-TYPE
			OBJECTS { sleAutoResetCpuControlRequest, sleAutoResetCpuControlTimeStamp, sleAutoResetCpuControlReqResult }
			STATUS current
			DESCRIPTION 
				"delAutoResetCpu"
			::= { sleAutoResetCpuNotification 2 }

		
		-- 1.3.6.1.4.1.6296.101.1.12.4
		sleAutoResetInfo OBJECT IDENTIFIER ::= { sleAutoReset 4 }

		
		-- 1.3.6.1.4.1.6296.101.1.12.4.1
		sleAutoResetBootReason OBJECT-TYPE
			SYNTAX OCTET STRING
			MAX-ACCESS read-only
			STATUS current
			DESCRIPTION
				"The Restart reason by auto-reset. (This is used only for trap string)"
			::= { sleAutoResetInfo 1 }

		
		-- 1.3.6.1.4.1.6296.101.1.13
		sleCoreDump OBJECT IDENTIFIER ::= { sleSystemMaintenance 13 }

		
		-- 1.3.6.1.4.1.6296.101.1.13.1
		sleCoreDumpInfoTable OBJECT-TYPE
			SYNTAX SEQUENCE OF SleCoreDumpInfoEntry
			MAX-ACCESS not-accessible
			STATUS current
			DESCRIPTION
				"Description."
			::= { sleCoreDump 1 }

		
		-- 1.3.6.1.4.1.6296.101.1.15.1.1
		sleCoreDumpInfoEntry OBJECT-TYPE
			SYNTAX SleCoreDumpInfoEntry
			MAX-ACCESS not-accessible
			STATUS current
			DESCRIPTION
				"Description."
			INDEX { sleCoreDumpInfoPID }
			::= { sleCoreDumpInfoTable 1 }

		
		SleCoreDumpInfoEntry ::=
			SEQUENCE { 
				sleCoreDumpInfoPID
					INTEGER,
				sleCoreDumpInfoStatus
					INTEGER,
				sleCoreDumpFile
					OCTET STRING
			 }

		-- 1.3.6.1.4.1.6296.101.1.15.1.1.1
		sleCoreDumpInfoPID OBJECT-TYPE
			SYNTAX INTEGER (1..2147483647)
			MAX-ACCESS read-only
			STATUS current
			DESCRIPTION
				"The process ID"
			::= { sleCoreDumpInfoEntry 1 }

		
		-- 1.3.6.1.4.1.6296.101.1.15.1.1.2
		sleCoreDumpInfoStatus OBJECT-TYPE
			SYNTAX INTEGER
				{
				ok(1),
				fail(2)
				}
			MAX-ACCESS read-only
			STATUS current
			DESCRIPTION
				"The status of PID"
			::= { sleCoreDumpInfoEntry 2 }

		
		-- 1.3.6.1.4.1.6296.101.1.15.1.1.3
		sleCoreDumpFile OBJECT-TYPE
			SYNTAX OCTET STRING
			MAX-ACCESS read-only
			STATUS current
			DESCRIPTION
				"Created coredump file name"
			::= { sleCoreDumpInfoEntry 3 }

		
		-- 1.3.6.1.4.1.6296.101.1.13.2
		sleCoreDumpControl OBJECT IDENTIFIER ::= { sleCoreDump 2 }

		
		-- 1.3.6.1.4.1.6296.101.1.13.2.1
		sleCoreDumpControlRequest OBJECT-TYPE
			SYNTAX INTEGER
				{
				createCoredDumpEntry(1),
				destroyCoredDumpEntry(2),
				setCoredDumpEntryToRemote(3)
				}
			MAX-ACCESS read-write
			STATUS current
			DESCRIPTION
				"Description."
			::= { sleCoreDumpControl 1 }

		
		-- 1.3.6.1.4.1.6296.101.1.13.2.2
		sleCoreDumpControlStatus OBJECT-TYPE
			SYNTAX SleControlStatusType
			MAX-ACCESS read-only
			STATUS current
			DESCRIPTION
				"Description."
			::= { sleCoreDumpControl 2 }

		
		-- 1.3.6.1.4.1.6296.101.1.13.2.3
		sleCoreDumpControlTimer OBJECT-TYPE
			SYNTAX Gauge32
			MAX-ACCESS read-write
			STATUS current
			DESCRIPTION
				"Description."
			::= { sleCoreDumpControl 3 }

		
		-- 1.3.6.1.4.1.6296.101.1.13.2.4
		sleCoreDumpControlTimeStamp OBJECT-TYPE
			SYNTAX TimeTicks
			MAX-ACCESS read-only
			STATUS current
			DESCRIPTION
				"Description."
			::= { sleCoreDumpControl 4 }

		
		-- 1.3.6.1.4.1.6296.101.1.13.2.5
		sleCoreDumpControlReqResult OBJECT-TYPE
			SYNTAX SleControlRequestResultType
			MAX-ACCESS read-only
			STATUS current
			DESCRIPTION
				"Description."
			::= { sleCoreDumpControl 5 }

		
		-- 1.3.6.1.4.1.6296.101.1.13.2.6
		sleCoreDumpControlPID OBJECT-TYPE
			SYNTAX INTEGER (1..2147483647)
			MAX-ACCESS read-write
			STATUS current
			DESCRIPTION
				"Description."
			::= { sleCoreDumpControl 6 }

		
		-- 1.3.6.1.4.1.6296.101.1.13.2.7
		sleCoreDumpControlServerIP OBJECT-TYPE
			SYNTAX IpAddress
			MAX-ACCESS read-write
			STATUS current
			DESCRIPTION
				"Description."
			::= { sleCoreDumpControl 7 }

		
		-- 1.3.6.1.4.1.6296.101.1.13.2.8
		sleCoreDumpControlUserID OBJECT-TYPE
			SYNTAX OCTET STRING
			MAX-ACCESS read-write
			STATUS current
			DESCRIPTION
				"Description."
			::= { sleCoreDumpControl 8 }

		
		-- 1.3.6.1.4.1.6296.101.1.13.2.9
		sleCoreDumpControlPassword OBJECT-TYPE
			SYNTAX OCTET STRING
			MAX-ACCESS read-write
			STATUS current
			DESCRIPTION
				"Description."
			::= { sleCoreDumpControl 9 }

		
		-- 1.3.6.1.4.1.6296.101.1.13.2.10
		sleCoreDumpControlCoredumpFile OBJECT-TYPE
			SYNTAX OCTET STRING
			MAX-ACCESS read-write
			STATUS current
			DESCRIPTION
				"Description."
			::= { sleCoreDumpControl 10 }

		
		-- 1.3.6.1.4.1.6296.101.1.13.3
		sleCoreDumpNotification OBJECT IDENTIFIER ::= { sleCoreDump 3 }

		
		-- 1.3.6.1.4.1.6296.101.1.13.3.1
		sleCoreDumpEntryCreated NOTIFICATION-TYPE
			OBJECTS { sleCoreDumpControlRequest, sleCoreDumpControlTimeStamp, sleCoreDumpControlReqResult, sleCoreDumpInfoPID, sleCoreDumpInfoStatus
				 }
			STATUS current
			DESCRIPTION 
				"Description."
			::= { sleCoreDumpNotification 1 }

		
		-- 1.3.6.1.4.1.6296.101.1.13.3.2
		sleCoreDumpEntryDestroyed NOTIFICATION-TYPE
			OBJECTS { sleCoreDumpControlRequest, sleCoreDumpControlTimeStamp, sleCoreDumpControlReqResult, sleCoreDumpInfoPID }
			STATUS current
			DESCRIPTION 
				"Description."
			::= { sleCoreDumpNotification 2 }

		
		-- 1.3.6.1.4.1.6296.101.1.13.3.3
		sleCoreDumpEntryChanged NOTIFICATION-TYPE
			OBJECTS { sleCoreDumpControlRequest, sleCoreDumpControlTimeStamp, sleCoreDumpControlReqResult, sleCoreDumpFile }
			STATUS current
			DESCRIPTION 
				"Description."
			::= { sleCoreDumpNotification 3 }

		
		-- 1.3.6.1.4.1.6296.101.1.14
		sleService OBJECT IDENTIFIER ::= { sleSystemMaintenance 14 }

		
		-- 1.3.6.1.4.1.6296.101.1.14.1
		sleServiceTable OBJECT-TYPE
			SYNTAX SEQUENCE OF SleServiceEntry
			MAX-ACCESS not-accessible
			STATUS current
			DESCRIPTION
				"Description."
			::= { sleService 1 }

		
		-- 1.3.6.1.4.1.6296.101.1.16.1.1
		sleServiceEntry OBJECT-TYPE
			SYNTAX SleServiceEntry
			MAX-ACCESS not-accessible
			STATUS current
			DESCRIPTION
				"Description."
			INDEX { sleServiceIndex, sleServiceProtocol }
			::= { sleServiceTable 1 }

		
		SleServiceEntry ::=
			SEQUENCE { 
				sleServiceIndex
					INTEGER,
				sleServiceProtocol
					INTEGER,
				sleServiceName
					OCTET STRING,
				sleServicePort
					INTEGER,
				sleServiceAdminStatus
					INTEGER
			 }

		-- 1.3.6.1.4.1.6296.101.1.16.1.1.1
		sleServiceIndex OBJECT-TYPE
			SYNTAX INTEGER
				{
				ftpdata(20),
				ftp(21),
				ssh(22),
				telnet(23),
				tftp(69),
				snmp(161)
				}
			MAX-ACCESS read-only
			STATUS current
			DESCRIPTION
				"Service Index"
			::= { sleServiceEntry 1 }

		
		-- 1.3.6.1.4.1.6296.101.1.16.1.1.2
		sleServiceProtocol OBJECT-TYPE
			SYNTAX INTEGER
				{
				tcp(1),
				udp(2)
				}
			MAX-ACCESS read-only
			STATUS current
			DESCRIPTION
				"Service Protocol"
			::= { sleServiceEntry 2 }

		
		-- 1.3.6.1.4.1.6296.101.1.16.1.1.3
		sleServiceName OBJECT-TYPE
			SYNTAX OCTET STRING
			MAX-ACCESS read-only
			STATUS current
			DESCRIPTION
				"Service name"
			::= { sleServiceEntry 3 }

		
		-- 1.3.6.1.4.1.6296.101.1.16.1.1.4
		sleServicePort OBJECT-TYPE
			SYNTAX INTEGER (1..65535)
			MAX-ACCESS read-only
			STATUS current
			DESCRIPTION
				"Service Port"
			::= { sleServiceEntry 4 }

		
		-- 1.3.6.1.4.1.6296.101.1.16.1.1.5
		sleServiceAdminStatus OBJECT-TYPE
			SYNTAX INTEGER
				{
				enable(1),
				disable(2)
				}
			MAX-ACCESS read-only
			STATUS current
			DESCRIPTION
				"The current status of service.
				"
			::= { sleServiceEntry 5 }

		
		-- 1.3.6.1.4.1.6296.101.1.14.2
		sleServiceControl OBJECT IDENTIFIER ::= { sleService 2 }

		
		-- 1.3.6.1.4.1.6296.101.1.14.2.1
		sleServiceControlRequest OBJECT-TYPE
			SYNTAX INTEGER
				{
				setServicePort(1),
				setServiceStatus(2)
				}
			MAX-ACCESS read-write
			STATUS current
			DESCRIPTION
				"Description."
			::= { sleServiceControl 1 }

		
		-- 1.3.6.1.4.1.6296.101.1.14.2.2
		sleServiceControlStatus OBJECT-TYPE
			SYNTAX SleControlStatusType
			MAX-ACCESS read-only
			STATUS current
			DESCRIPTION
				"Description."
			::= { sleServiceControl 2 }

		
		-- 1.3.6.1.4.1.6296.101.1.14.2.3
		sleServiceControlTimer OBJECT-TYPE
			SYNTAX Gauge32
			MAX-ACCESS read-write
			STATUS current
			DESCRIPTION
				"Description."
			::= { sleServiceControl 3 }

		
		-- 1.3.6.1.4.1.6296.101.1.14.2.4
		sleServiceControlTimeStamp OBJECT-TYPE
			SYNTAX TimeTicks
			MAX-ACCESS read-only
			STATUS current
			DESCRIPTION
				"Description."
			::= { sleServiceControl 4 }

		
		-- 1.3.6.1.4.1.6296.101.1.14.2.5
		sleServiceControlReqResult OBJECT-TYPE
			SYNTAX SleControlRequestResultType
			MAX-ACCESS read-only
			STATUS current
			DESCRIPTION
				"Result of the last command."
			::= { sleServiceControl 5 }

		
		-- 1.3.6.1.4.1.6296.101.1.14.2.6
		sleServiceControlIndex OBJECT-TYPE
			SYNTAX INTEGER
				{
				ftpdata(20),
				ftp(21),
				ssh(22),
				telnet(23),
				tftp(69),
				snmp(161)
				}
			MAX-ACCESS read-write
			STATUS current
			DESCRIPTION
				"Service Index"
			::= { sleServiceControl 6 }

		
		-- 1.3.6.1.4.1.6296.101.1.14.2.7
		sleServiceControlProtocol OBJECT-TYPE
			SYNTAX INTEGER
				{
				tcp(1),
				udp(2)
				}
			MAX-ACCESS read-write
			STATUS current
			DESCRIPTION
				"Service Protocol"
			::= { sleServiceControl 7 }

		
		-- 1.3.6.1.4.1.6296.101.1.14.2.8
		sleServiceControlPort OBJECT-TYPE
			SYNTAX INTEGER (1..65535)
			MAX-ACCESS read-write
			STATUS current
			DESCRIPTION
				"Service Port"
			::= { sleServiceControl 8 }

		
		-- 1.3.6.1.4.1.6296.101.1.14.2.9
		sleServiceControlAdminStatus OBJECT-TYPE
			SYNTAX INTEGER
				{
				enable(1),
				disable(2)
				}
			MAX-ACCESS read-write
			STATUS current
			DESCRIPTION
				"The current status of service.
				"
			::= { sleServiceControl 9 }

		
		-- 1.3.6.1.4.1.6296.101.1.14.3
		sleServiceNotification OBJECT IDENTIFIER ::= { sleService 3 }

		
		-- 1.3.6.1.4.1.6296.101.1.14.3.1
		sleServicePortChanged NOTIFICATION-TYPE
			OBJECTS { sleServiceControlRequest, sleServiceControlTimeStamp, sleServiceControlReqResult, sleServicePort }
			STATUS current
			DESCRIPTION 
				"setServicePort"
			::= { sleServiceNotification 1 }

		
		-- 1.3.6.1.4.1.6296.101.1.14.3.2
		sleServiceAdminStatusChanged NOTIFICATION-TYPE
			OBJECTS { sleServiceControlRequest, sleServiceControlTimeStamp, sleServiceControlReqResult, sleServiceControlIndex, sleServiceControlAdminStatus
				 }
			STATUS current
			DESCRIPTION 
				"Description."
			::= { sleServiceNotification 2 }

		
		-- 1.3.6.1.4.1.6296.101.1.15
		sleSystemUser OBJECT IDENTIFIER ::= { sleSystemMaintenance 15 }

		
		-- 1.3.6.1.4.1.6296.101.1.15.1
		sleSystemUserTable OBJECT-TYPE
			SYNTAX SEQUENCE OF SleSystemUserEntry
			MAX-ACCESS not-accessible
			STATUS current
			DESCRIPTION
				"Description."
			::= { sleSystemUser 1 }

		
		-- 1.3.6.1.4.1.6296.101.1.17.1.1
		sleSystemUserEntry OBJECT-TYPE
			SYNTAX SleSystemUserEntry
			MAX-ACCESS not-accessible
			STATUS current
			DESCRIPTION
				"Description."
			INDEX { sleSystemUserName }
			::= { sleSystemUserTable 1 }

		
		SleSystemUserEntry ::=
			SEQUENCE { 
				sleSystemUserName
					OCTET STRING,
				sleSystemUserLevel
					INTEGER,
				sleSystemUserPassword
					OCTET STRING,
				sleSystemUserDesc
					OCTET STRING,
				sleSystemUserLoginFailureCount
					Integer32,
				sleSystemUserLoginLastFailureTime
					OCTET STRING
			 }

		-- 1.3.6.1.4.1.6296.101.1.17.1.1.1
		sleSystemUserName OBJECT-TYPE
			SYNTAX OCTET STRING (SIZE (1..255))
			MAX-ACCESS read-only
			STATUS current
			DESCRIPTION
				"User Name. where 'admin' is reserved name."
			::= { sleSystemUserEntry 1 }

		
		-- 1.3.6.1.4.1.6296.101.1.17.1.1.2
		sleSystemUserLevel OBJECT-TYPE
			SYNTAX INTEGER (0..15)
			MAX-ACCESS read-only
			STATUS current
			DESCRIPTION
				"User's level"
			::= { sleSystemUserEntry 2 }

		
		-- 1.3.6.1.4.1.6296.101.1.17.1.1.3
		sleSystemUserPassword OBJECT-TYPE
			SYNTAX OCTET STRING (SIZE (0..255))
			MAX-ACCESS read-only
			STATUS current
			DESCRIPTION
				"User's password (always encrypted)"
			::= { sleSystemUserEntry 3 }

		
		-- 1.3.6.1.4.1.6296.101.1.17.1.1.4
		sleSystemUserDesc OBJECT-TYPE
			SYNTAX OCTET STRING (SIZE (0..255))
			MAX-ACCESS read-only
			STATUS current
			DESCRIPTION
				"User Description"
			::= { sleSystemUserEntry 4 }

		
		-- 1.3.6.1.4.1.6296.101.1.17.1.1.5
		sleSystemUserLoginFailureCount OBJECT-TYPE
			SYNTAX Integer32 (0..10)
			MAX-ACCESS read-only
			STATUS current
			DESCRIPTION
				"The login failure count.
				"
			::= { sleSystemUserEntry 5 }

		
		-- 1.3.6.1.4.1.6296.101.1.17.1.1.6
		sleSystemUserLoginLastFailureTime OBJECT-TYPE
			SYNTAX OCTET STRING
			MAX-ACCESS read-only
			STATUS current
			DESCRIPTION
				"The last login failure time."
			::= { sleSystemUserEntry 6 }

		
		-- 1.3.6.1.4.1.6296.101.1.15.2
		sleSystemUserControl OBJECT IDENTIFIER ::= { sleSystemUser 2 }

		
		-- 1.3.6.1.4.1.6296.101.1.15.2.1
		sleSystemUserControlRequest OBJECT-TYPE
			SYNTAX INTEGER
				{
				addUser(1),
				renameUser(2),
				setPassword(3),
				deleteUser(4),
				setLevel(5),
				clearLoginAttemptsLog(6)
				}
			MAX-ACCESS read-write
			STATUS current
			DESCRIPTION
				"Description."
			::= { sleSystemUserControl 1 }

		
		-- 1.3.6.1.4.1.6296.101.1.15.2.2
		sleSystemUserControlStatus OBJECT-TYPE
			SYNTAX SleControlStatusType
			MAX-ACCESS read-only
			STATUS current
			DESCRIPTION
				"Description."
			::= { sleSystemUserControl 2 }

		
		-- 1.3.6.1.4.1.6296.101.1.15.2.3
		sleSystemUserControlTimer OBJECT-TYPE
			SYNTAX Gauge32
			MAX-ACCESS read-write
			STATUS current
			DESCRIPTION
				"Description."
			::= { sleSystemUserControl 3 }

		
		-- 1.3.6.1.4.1.6296.101.1.15.2.4
		sleSystemUserControlTimeStamp OBJECT-TYPE
			SYNTAX TimeTicks
			MAX-ACCESS read-only
			STATUS current
			DESCRIPTION
				"Description."
			::= { sleSystemUserControl 4 }

		
		-- 1.3.6.1.4.1.6296.101.1.15.2.5
		sleSystemUserControlReqResult OBJECT-TYPE
			SYNTAX SleControlRequestResultType
			MAX-ACCESS read-only
			STATUS current
			DESCRIPTION
				"Result of the last command."
			::= { sleSystemUserControl 5 }

		
		-- 1.3.6.1.4.1.6296.101.1.15.2.6
		sleSystemUserControlName OBJECT-TYPE
			SYNTAX OCTET STRING (SIZE (1..255))
			MAX-ACCESS read-write
			STATUS current
			DESCRIPTION
				"User Name. where 'admin' is reserved name."
			::= { sleSystemUserControl 6 }

		
		-- 1.3.6.1.4.1.6296.101.1.15.2.7
		sleSystemUserControlRename OBJECT-TYPE
			SYNTAX OCTET STRING (SIZE (1..255))
			MAX-ACCESS read-write
			STATUS current
			DESCRIPTION
				"New User Name. where 'admin' is reserved name. (when rename user.)"
			::= { sleSystemUserControl 7 }

		
		-- 1.3.6.1.4.1.6296.101.1.15.2.8
		sleSystemUserControlLevel OBJECT-TYPE
			SYNTAX INTEGER (0..15)
			MAX-ACCESS read-write
			STATUS current
			DESCRIPTION
				"User's level"
			::= { sleSystemUserControl 8 }

		
		-- 1.3.6.1.4.1.6296.101.1.15.2.9
		sleSystemUserControlPwType OBJECT-TYPE
			SYNTAX INTEGER
				{
				plain(1),
				encrypt(2)
				}
			MAX-ACCESS read-write
			STATUS current
			DESCRIPTION
				"Description."
			::= { sleSystemUserControl 9 }

		
		-- 1.3.6.1.4.1.6296.101.1.15.2.10
		sleSystemUserControlPassword OBJECT-TYPE
			SYNTAX OCTET STRING (SIZE (0..255))
			MAX-ACCESS read-write
			STATUS current
			DESCRIPTION
				"User's password"
			::= { sleSystemUserControl 10 }

		
		-- 1.3.6.1.4.1.6296.101.1.15.2.11
		sleSystemUserControlDesc OBJECT-TYPE
			SYNTAX OCTET STRING (SIZE (0..255))
			MAX-ACCESS read-write
			STATUS current
			DESCRIPTION
				"User Description"
			::= { sleSystemUserControl 11 }

		
		-- 1.3.6.1.4.1.6296.101.1.15.3
		sleSystemUserNotification OBJECT IDENTIFIER ::= { sleSystemUser 3 }

		
		-- 1.3.6.1.4.1.6296.101.1.15.3.1
		sleSystemUserCreated NOTIFICATION-TYPE
			OBJECTS { sleSystemUserControlRequest, sleSystemUserControlTimeStamp, sleSystemUserControlReqResult, sleSystemUserLevel, sleSystemUserPassword, 
				sleSystemUserDesc }
			STATUS current
			DESCRIPTION 
				"addUser"
			::= { sleSystemUserNotification 1 }

		
		-- 1.3.6.1.4.1.6296.101.1.15.3.2
		sleSystemUserNameChanged NOTIFICATION-TYPE
			OBJECTS { sleSystemUserControlRequest, sleSystemUserControlTimeStamp, sleSystemUserControlReqResult, sleSystemUserControlName, sleSystemUserControlRename
				 }
			STATUS current
			DESCRIPTION 
				"renameUser"
			::= { sleSystemUserNotification 2 }

		
		-- 1.3.6.1.4.1.6296.101.1.15.3.3
		sleSystemUserPasswordChanged NOTIFICATION-TYPE
			OBJECTS { sleSystemUserControlRequest, sleSystemUserControlTimeStamp, sleSystemUserControlReqResult, sleSystemUserPassword }
			STATUS current
			DESCRIPTION 
				"setPassword"
			::= { sleSystemUserNotification 3 }

		
		-- 1.3.6.1.4.1.6296.101.1.15.3.4
		sleSystemUserDestroyed NOTIFICATION-TYPE
			OBJECTS { sleSystemUserControlRequest, sleSystemUserControlTimeStamp, sleSystemUserControlReqResult, sleSystemUserControlName }
			STATUS current
			DESCRIPTION 
				"deleteUser"
			::= { sleSystemUserNotification 4 }

		
		-- 1.3.6.1.4.1.6296.101.1.15.3.5
		sleSystemUserLevelChanged NOTIFICATION-TYPE
			OBJECTS { sleSystemUserControlTimeStamp, sleSystemUserControlReqResult, sleSystemUserControlRequest }
			STATUS current
			DESCRIPTION 
				"Description."
			::= { sleSystemUserNotification 5 }

		
		-- 1.3.6.1.4.1.6296.101.1.15.3.6
		sleSystemUserLoginAttemptsFailureLogCleared NOTIFICATION-TYPE
			OBJECTS { sleSystemUserControlRequest, sleSystemUserControlTimeStamp, sleSystemUserControlReqResult, sleSystemUserControlName }
			STATUS current
			DESCRIPTION 
				"clearLoginAttemptsLog"
			::= { sleSystemUserNotification 6 }

		
		-- 1.3.6.1.4.1.6296.101.1.16
		sleParameter OBJECT IDENTIFIER ::= { sleSystemMaintenance 16 }

		
		-- 1.3.6.1.4.1.6296.101.1.16.1
		sleParameterTable OBJECT-TYPE
			SYNTAX SEQUENCE OF SleParameterEntry
			MAX-ACCESS not-accessible
			STATUS current
			DESCRIPTION
				"Description."
			::= { sleParameter 1 }

		
		-- 1.3.6.1.4.1.6296.101.1.16.1.1
		sleParameterEntry OBJECT-TYPE
			SYNTAX SleParameterEntry
			MAX-ACCESS not-accessible
			STATUS current
			DESCRIPTION
				"Description."
			INDEX { sleParameterName }
			::= { sleParameterTable 1 }

		
		SleParameterEntry ::=
			SEQUENCE { 
				sleParameterName
					OCTET STRING,
				sleParameterValue
					OCTET STRING,
				sleParameterMode
					INTEGER
			 }

		-- 1.3.6.1.4.1.6296.101.1.16.1.1.1
		sleParameterName OBJECT-TYPE
			SYNTAX OCTET STRING (SIZE (1..32))
			MAX-ACCESS read-only
			STATUS current
			DESCRIPTION
				"Description."
			::= { sleParameterEntry 1 }

		
		-- 1.3.6.1.4.1.6296.101.1.16.1.1.2
		sleParameterValue OBJECT-TYPE
			SYNTAX OCTET STRING (SIZE (1..64))
			MAX-ACCESS read-only
			STATUS current
			DESCRIPTION
				"Description."
			::= { sleParameterEntry 2 }

		
		-- 1.3.6.1.4.1.6296.101.1.16.1.1.3
		sleParameterMode OBJECT-TYPE
			SYNTAX INTEGER
				{
				dynamic(1),
				static(2)
				}
			MAX-ACCESS read-only
			STATUS current
			DESCRIPTION
				"Description."
			::= { sleParameterEntry 3 }

		
		-- 1.3.6.1.4.1.6296.101.1.16.2
		sleParameterControl OBJECT IDENTIFIER ::= { sleParameter 2 }

		
		-- 1.3.6.1.4.1.6296.101.1.16.2.1
		sleParameterControlRequest OBJECT-TYPE
			SYNTAX INTEGER
				{
				createParameter(1),
				destroyParameter(2),
				modifyParameterMode(3),
				modifyParameterValue(4)
				}
			MAX-ACCESS read-write
			STATUS current
			DESCRIPTION
				"Description."
			::= { sleParameterControl 1 }

		
		-- 1.3.6.1.4.1.6296.101.1.16.2.2
		sleParameterControlStatus OBJECT-TYPE
			SYNTAX SleControlStatusType
			MAX-ACCESS read-only
			STATUS current
			DESCRIPTION
				"Description."
			::= { sleParameterControl 2 }

		
		-- 1.3.6.1.4.1.6296.101.1.16.2.3
		sleParameterControlTimer OBJECT-TYPE
			SYNTAX Gauge32
			MAX-ACCESS read-write
			STATUS current
			DESCRIPTION
				"Description."
			::= { sleParameterControl 3 }

		
		-- 1.3.6.1.4.1.6296.101.1.16.2.4
		sleParameterControlTimeStamp OBJECT-TYPE
			SYNTAX TimeTicks
			MAX-ACCESS read-only
			STATUS current
			DESCRIPTION
				"Description."
			::= { sleParameterControl 4 }

		
		-- 1.3.6.1.4.1.6296.101.1.16.2.5
		sleParameterControlReqResult OBJECT-TYPE
			SYNTAX SleControlRequestResultType
			MAX-ACCESS read-only
			STATUS current
			DESCRIPTION
				"Description."
			::= { sleParameterControl 5 }

		
		-- 1.3.6.1.4.1.6296.101.1.16.2.6
		sleParameterControlName OBJECT-TYPE
			SYNTAX OCTET STRING (SIZE (1..32))
			MAX-ACCESS read-write
			STATUS current
			DESCRIPTION
				"Description."
			::= { sleParameterControl 6 }

		
		-- 1.3.6.1.4.1.6296.101.1.16.2.7
		sleParameterControlValue OBJECT-TYPE
			SYNTAX OCTET STRING (SIZE (1..64))
			MAX-ACCESS read-write
			STATUS current
			DESCRIPTION
				"Description."
			::= { sleParameterControl 7 }

		
		-- 1.3.6.1.4.1.6296.101.1.16.2.8
		sleParameterControlMode OBJECT-TYPE
			SYNTAX INTEGER
				{
				dynamic(1),
				static(2)
				}
			MAX-ACCESS read-write
			STATUS current
			DESCRIPTION
				"Description."
			::= { sleParameterControl 8 }

		
		-- 1.3.6.1.4.1.6296.101.1.16.3
		sleParameterNotification OBJECT IDENTIFIER ::= { sleParameter 3 }

		
		-- 1.3.6.1.4.1.6296.101.1.16.3.1
		sleParameterCreated NOTIFICATION-TYPE
			OBJECTS { sleParameterControlRequest, sleParameterControlTimeStamp, sleParameterControlReqResult, sleParameterValue, sleParameterMode
				 }
			STATUS current
			DESCRIPTION 
				"Description."
			::= { sleParameterNotification 1 }

		
		-- 1.3.6.1.4.1.6296.101.1.16.3.2
		sleParameterDestroyed NOTIFICATION-TYPE
			OBJECTS { sleParameterControlRequest, sleParameterControlTimeStamp, sleParameterControlReqResult, sleParameterControlName }
			STATUS current
			DESCRIPTION 
				"Description."
			::= { sleParameterNotification 2 }

		
		-- 1.3.6.1.4.1.6296.101.1.16.3.3
		sleParameterModeChanged NOTIFICATION-TYPE
			OBJECTS { sleParameterControlRequest, sleParameterControlTimeStamp, sleParameterControlReqResult, sleParameterMode }
			STATUS current
			DESCRIPTION 
				"Description."
			::= { sleParameterNotification 3 }

		
		-- 1.3.6.1.4.1.6296.101.1.16.3.4
		sleParameterValueChanged NOTIFICATION-TYPE
			OBJECTS { sleParameterControlRequest, sleParameterControlTimeStamp, sleParameterControlReqResult, sleParameterValue }
			STATUS current
			DESCRIPTION 
				"Description."
			::= { sleParameterNotification 4 }

		
		-- 1.3.6.1.4.1.6296.101.1.17
		sleSwWatchdogBase OBJECT IDENTIFIER ::= { sleSystemMaintenance 17 }

		
		-- 1.3.6.1.4.1.6296.101.1.17.1
		sleSwWatchdogTable OBJECT-TYPE
			SYNTAX SEQUENCE OF SleSwWatchdogEntry
			MAX-ACCESS not-accessible
			STATUS current
			DESCRIPTION
				"Description."
			::= { sleSwWatchdogBase 1 }

		
		-- 1.3.6.1.4.1.6296.101.1.17.1.1
		sleSwWatchdogEntry OBJECT-TYPE
			SYNTAX SleSwWatchdogEntry
			MAX-ACCESS not-accessible
			STATUS current
			DESCRIPTION
				"Description."
			INDEX { sleSwWatchdogType }
			::= { sleSwWatchdogTable 1 }

		
		SleSwWatchdogEntry ::=
			SEQUENCE { 
				sleSwWatchdogType
					INTEGER,
				sleSwWatchdogInterval
					INTEGER,
				sleSwWatchdogThreshold
					INTEGER,
				sleSwWatchdogAction
					INTEGER,
				sleSwWatchdogErrcnt
					Integer32
			 }

		-- 1.3.6.1.4.1.6296.101.1.17.1.1.1
		sleSwWatchdogType OBJECT-TYPE
			SYNTAX INTEGER
				{
				daemonMonitoring(1),
				inetMonitoring(2),
				ponMonitoring(3)
				}
			MAX-ACCESS read-only
			STATUS current
			DESCRIPTION
				"Description."
			::= { sleSwWatchdogEntry 1 }

		
		-- 1.3.6.1.4.1.6296.101.1.17.1.1.2
		sleSwWatchdogInterval OBJECT-TYPE
			SYNTAX INTEGER (10..86400)
			UNITS "sec"
			MAX-ACCESS read-only
			STATUS current
			DESCRIPTION
				"Description."
			::= { sleSwWatchdogEntry 2 }

		
		-- 1.3.6.1.4.1.6296.101.1.17.1.1.3
		sleSwWatchdogThreshold OBJECT-TYPE
			SYNTAX INTEGER (1..10)
			MAX-ACCESS read-only
			STATUS current
			DESCRIPTION
				"Description."
			::= { sleSwWatchdogEntry 3 }

		
		-- 1.3.6.1.4.1.6296.101.1.17.1.1.4
		sleSwWatchdogAction OBJECT-TYPE
			SYNTAX INTEGER
				{
				none(1),
				daemonRestart(2),
				systemReset(3),
				systemResetWithSaveCfg(4),
				onuPortReset(5)
				}
			MAX-ACCESS read-only
			STATUS current
			DESCRIPTION
				"Description."
			::= { sleSwWatchdogEntry 4 }

		
		-- 1.3.6.1.4.1.6296.101.1.17.1.1.5
		sleSwWatchdogErrcnt OBJECT-TYPE
			SYNTAX Integer32
			MAX-ACCESS read-only
			STATUS current
			DESCRIPTION
				"Description."
			::= { sleSwWatchdogEntry 5 }

		
		-- 1.3.6.1.4.1.6296.101.1.17.2
		sleSwWatchdogControl OBJECT IDENTIFIER ::= { sleSwWatchdogBase 2 }

		
		-- 1.3.6.1.4.1.6296.101.1.17.2.1
		sleSwWatchdogControlRequest OBJECT-TYPE
			SYNTAX INTEGER
				{
				createSwwatchdog(1),
				deleteSwwatchdog(2)
				}
			MAX-ACCESS read-write
			STATUS current
			DESCRIPTION
				"Description."
			::= { sleSwWatchdogControl 1 }

		
		-- 1.3.6.1.4.1.6296.101.1.17.2.2
		sleSwWatchdogControlStatus OBJECT-TYPE
			SYNTAX SleControlStatusType
			MAX-ACCESS read-only
			STATUS current
			DESCRIPTION
				"Description."
			::= { sleSwWatchdogControl 2 }

		
		-- 1.3.6.1.4.1.6296.101.1.17.2.3
		sleSwWatchdogControlTimer OBJECT-TYPE
			SYNTAX Gauge32
			MAX-ACCESS read-write
			STATUS current
			DESCRIPTION
				"Description."
			::= { sleSwWatchdogControl 3 }

		
		-- 1.3.6.1.4.1.6296.101.1.17.2.4
		sleSwWatchdogControlTimeStamp OBJECT-TYPE
			SYNTAX TimeTicks
			MAX-ACCESS read-only
			STATUS current
			DESCRIPTION
				"Description."
			::= { sleSwWatchdogControl 4 }

		
		-- 1.3.6.1.4.1.6296.101.1.17.2.5
		sleSwWatchdogControlReqResult OBJECT-TYPE
			SYNTAX SleControlRequestResultType
			MAX-ACCESS read-only
			STATUS current
			DESCRIPTION
				"Description."
			::= { sleSwWatchdogControl 5 }

		
		-- 1.3.6.1.4.1.6296.101.1.17.2.6
		sleSwWatchdogControlType OBJECT-TYPE
			SYNTAX INTEGER
				{
				daemonMonitoring(1),
				inetMonitoring(2),
				ponMonitoring(3)
				}
			MAX-ACCESS read-write
			STATUS current
			DESCRIPTION
				"Description."
			::= { sleSwWatchdogControl 6 }

		
		-- 1.3.6.1.4.1.6296.101.1.17.2.7
		sleSwWatchdogControlInterval OBJECT-TYPE
			SYNTAX INTEGER (10..86400)
			MAX-ACCESS read-write
			STATUS current
			DESCRIPTION
				"Description."
			::= { sleSwWatchdogControl 7 }

		
		-- 1.3.6.1.4.1.6296.101.1.17.2.8
		sleSwWatchdogControlThreshold OBJECT-TYPE
			SYNTAX INTEGER (1..10)
			MAX-ACCESS read-write
			STATUS current
			DESCRIPTION
				"Description."
			::= { sleSwWatchdogControl 8 }

		
		-- 1.3.6.1.4.1.6296.101.1.17.2.9
		sleSwWatchdogControlAction OBJECT-TYPE
			SYNTAX INTEGER
				{
				none(1),
				daemonRestart(2),
				systemReset(3),
				systemResetWithSaveCfg(4),
				onuPortReset(5)
				}
			MAX-ACCESS read-write
			STATUS current
			DESCRIPTION
				"Description."
			::= { sleSwWatchdogControl 9 }

		
		-- 1.3.6.1.4.1.6296.101.1.17.3
		sleSwWatchdogNotification OBJECT IDENTIFIER ::= { sleSwWatchdogBase 3 }

		
		-- 1.3.6.1.4.1.6296.101.1.17.3.1
		sleSwWatchdogCreated NOTIFICATION-TYPE
			OBJECTS { sleSwWatchdogInterval, sleSwWatchdogThreshold, sleSwWatchdogAction }
			STATUS current
			DESCRIPTION 
				"Description."
			::= { sleSwWatchdogNotification 1 }

		
		-- 1.3.6.1.4.1.6296.101.1.17.3.2
		sleSwWatchdogDeleted NOTIFICATION-TYPE
			OBJECTS { sleSwWatchdogControlType }
			STATUS current
			DESCRIPTION 
				"Description."
			::= { sleSwWatchdogNotification 2 }

		
		-- 1.3.6.1.4.1.6296.101.1.18
		sleAutoUpgrade OBJECT IDENTIFIER ::= { sleSystemMaintenance 18 }

		
		-- 1.3.6.1.4.1.6296.101.1.18.1
		sleAutoUpgradeProfile OBJECT IDENTIFIER ::= { sleAutoUpgrade 1 }

		
		-- 1.3.6.1.4.1.6296.101.1.18.1.1
		sleAutoUpgradeProfileTable OBJECT-TYPE
			SYNTAX SEQUENCE OF SleAutoUpgradeProfileEntry
			MAX-ACCESS not-accessible
			STATUS current
			DESCRIPTION
				"Description."
			::= { sleAutoUpgradeProfile 1 }

		
		-- 1.3.6.1.4.1.6296.101.1.18.1.1.1
		sleAutoUpgradeProfileEntry OBJECT-TYPE
			SYNTAX SleAutoUpgradeProfileEntry
			MAX-ACCESS not-accessible
			STATUS current
			DESCRIPTION
				"Description."
			INDEX { sleAutoUpgradeProfileIndex }
			::= { sleAutoUpgradeProfileTable 1 }

		
		SleAutoUpgradeProfileEntry ::=
			SEQUENCE { 
				sleAutoUpgradeProfileIndex
					Integer32,
				sleAutoUpgradeProfileName
					OCTET STRING,
				sleAutoUpgradeProfileOldVer
					OCTET STRING,
				sleAutoUpgradeProfileNewVer
					OCTET STRING,
				sleAutoUpgradeProfileSize
					Integer32,
				sleAutoUpgradeProfilePeriodType
					INTEGER,
				sleAutoUpgradeProfileDate
					OCTET STRING,
				sleAutoUpgradeProfilePeriodDate
					OCTET STRING,
				sleAutoUpgradeProfileTimeout
					Integer32,
				sleAutoUpgradeProfileRetry
					Integer32,
				sleAutoUpgradeProfileRegSec
					Integer32,
				sleAutoUpgradeProfileReloadTime
					OCTET STRING,
				sleAutoUpgradeProfileModel
					OCTET STRING
			 }

		-- 1.3.6.1.4.1.6296.101.1.18.1.1.1.1
		sleAutoUpgradeProfileIndex OBJECT-TYPE
			SYNTAX Integer32 (1..65535)
			MAX-ACCESS read-only
			STATUS current
			DESCRIPTION
				"The auto upgrade profile index"
			::= { sleAutoUpgradeProfileEntry 1 }

		
		-- 1.3.6.1.4.1.6296.101.1.18.1.1.1.2
		sleAutoUpgradeProfileName OBJECT-TYPE
			SYNTAX OCTET STRING
			MAX-ACCESS read-only
			STATUS current
			DESCRIPTION
				"Description."
			::= { sleAutoUpgradeProfileEntry 2 }

		
		-- 1.3.6.1.4.1.6296.101.1.18.1.1.1.3
		sleAutoUpgradeProfileOldVer OBJECT-TYPE
			SYNTAX OCTET STRING
			MAX-ACCESS read-only
			STATUS current
			DESCRIPTION
				"Description."
			::= { sleAutoUpgradeProfileEntry 3 }

		
		-- 1.3.6.1.4.1.6296.101.1.18.1.1.1.4
		sleAutoUpgradeProfileNewVer OBJECT-TYPE
			SYNTAX OCTET STRING
			MAX-ACCESS read-only
			STATUS current
			DESCRIPTION
				"Description."
			::= { sleAutoUpgradeProfileEntry 4 }

		
		-- 1.3.6.1.4.1.6296.101.1.18.1.1.1.5
		sleAutoUpgradeProfileSize OBJECT-TYPE
			SYNTAX Integer32
			MAX-ACCESS read-only
			STATUS current
			DESCRIPTION
				"Description."
			::= { sleAutoUpgradeProfileEntry 5 }

		
		-- 1.3.6.1.4.1.6296.101.1.18.1.1.1.6
		sleAutoUpgradeProfilePeriodType OBJECT-TYPE
			SYNTAX INTEGER
				{
				auto(1),
				daily(2),
				weekly(3),
				monthly(4),
				interval(5),
				once(6)
				}
			MAX-ACCESS read-only
			STATUS current
			DESCRIPTION
				"Description."
			::= { sleAutoUpgradeProfileEntry 6 }

		
		-- 1.3.6.1.4.1.6296.101.1.18.1.1.1.7
		sleAutoUpgradeProfileDate OBJECT-TYPE
			SYNTAX OCTET STRING
			MAX-ACCESS read-only
			STATUS current
			DESCRIPTION
				"Description."
			::= { sleAutoUpgradeProfileEntry 7 }

		
		-- 1.3.6.1.4.1.6296.101.1.18.1.1.1.8
		sleAutoUpgradeProfilePeriodDate OBJECT-TYPE
			SYNTAX OCTET STRING
			MAX-ACCESS read-only
			STATUS current
			DESCRIPTION
				"Description."
			::= { sleAutoUpgradeProfileEntry 8 }

		
		-- 1.3.6.1.4.1.6296.101.1.18.1.1.1.9
		sleAutoUpgradeProfileTimeout OBJECT-TYPE
			SYNTAX Integer32
			MAX-ACCESS read-only
			STATUS current
			DESCRIPTION
				"Description."
			::= { sleAutoUpgradeProfileEntry 9 }

		
		-- 1.3.6.1.4.1.6296.101.1.18.1.1.1.10
		sleAutoUpgradeProfileRetry OBJECT-TYPE
			SYNTAX Integer32 (-1 | 1..2147483647)
			MAX-ACCESS read-only
			STATUS current
			DESCRIPTION
				"Description."
			::= { sleAutoUpgradeProfileEntry 10 }

		
		-- 1.3.6.1.4.1.6296.101.1.18.1.1.1.11
		sleAutoUpgradeProfileRegSec OBJECT-TYPE
			SYNTAX Integer32
			MAX-ACCESS read-only
			STATUS current
			DESCRIPTION
				"Description."
			::= { sleAutoUpgradeProfileEntry 11 }

		
		-- 1.3.6.1.4.1.6296.101.1.18.1.1.1.12
		sleAutoUpgradeProfileReloadTime OBJECT-TYPE
			SYNTAX OCTET STRING
			MAX-ACCESS read-only
			STATUS current
			DESCRIPTION
				"Description."
			::= { sleAutoUpgradeProfileEntry 12 }

		
		-- 1.3.6.1.4.1.6296.101.1.18.1.1.1.13
		sleAutoUpgradeProfileModel OBJECT-TYPE
			SYNTAX OCTET STRING
			MAX-ACCESS read-only
			STATUS current
			DESCRIPTION
				"The Model Name
				"
			::= { sleAutoUpgradeProfileEntry 13 }

		
		-- 1.3.6.1.4.1.6296.101.1.18.1.2
		sleAutoUpgradeProfileControl OBJECT IDENTIFIER ::= { sleAutoUpgradeProfile 2 }

		
		-- 1.3.6.1.4.1.6296.101.1.18.1.2.1
		sleAutoUpgradeProfileControlRequest OBJECT-TYPE
			SYNTAX INTEGER
				{
				createAutoUpgrdProfile(1),
				destroyAutoUpgrdProfile(2),
				modifyAutoUpgrdProfile(3)
				}
			MAX-ACCESS read-write
			STATUS current
			DESCRIPTION
				"Description."
			::= { sleAutoUpgradeProfileControl 1 }

		
		-- 1.3.6.1.4.1.6296.101.1.18.1.2.2
		sleAutoUpgradeProfileControlStatus OBJECT-TYPE
			SYNTAX SleControlStatusType
			MAX-ACCESS read-only
			STATUS current
			DESCRIPTION
				"Description."
			::= { sleAutoUpgradeProfileControl 2 }

		
		-- 1.3.6.1.4.1.6296.101.1.18.1.2.3
		sleAutoUpgradeProfileControlTimer OBJECT-TYPE
			SYNTAX Gauge32
			MAX-ACCESS read-write
			STATUS current
			DESCRIPTION
				"Description."
			::= { sleAutoUpgradeProfileControl 3 }

		
		-- 1.3.6.1.4.1.6296.101.1.18.1.2.4
		sleAutoUpgradeProfileControlTimeStamp OBJECT-TYPE
			SYNTAX TimeTicks
			MAX-ACCESS read-only
			STATUS current
			DESCRIPTION
				"Description."
			::= { sleAutoUpgradeProfileControl 4 }

		
		-- 1.3.6.1.4.1.6296.101.1.18.1.2.5
		sleAutoUpgradeProfileControlReqResult OBJECT-TYPE
			SYNTAX SleControlRequestResultType
			MAX-ACCESS read-only
			STATUS current
			DESCRIPTION
				"Description."
			::= { sleAutoUpgradeProfileControl 5 }

		
		-- 1.3.6.1.4.1.6296.101.1.18.1.2.6
		sleAutoUpgradeProfileControlName OBJECT-TYPE
			SYNTAX OCTET STRING
			MAX-ACCESS read-write
			STATUS current
			DESCRIPTION
				"Description."
			::= { sleAutoUpgradeProfileControl 6 }

		
		-- 1.3.6.1.4.1.6296.101.1.18.1.2.7
		sleAutoUpgradeProfileControlOldVer OBJECT-TYPE
			SYNTAX OCTET STRING
			MAX-ACCESS read-write
			STATUS current
			DESCRIPTION
				"Description."
			::= { sleAutoUpgradeProfileControl 7 }

		
		-- 1.3.6.1.4.1.6296.101.1.18.1.2.8
		sleAutoUpgradeProfileControlNewVer OBJECT-TYPE
			SYNTAX OCTET STRING
			MAX-ACCESS read-write
			STATUS current
			DESCRIPTION
				"Description."
			::= { sleAutoUpgradeProfileControl 8 }

		
		-- 1.3.6.1.4.1.6296.101.1.18.1.2.9
		sleAutoUpgradeProfileControlSize OBJECT-TYPE
			SYNTAX Integer32
			MAX-ACCESS read-write
			STATUS current
			DESCRIPTION
				"Description."
			::= { sleAutoUpgradeProfileControl 9 }

		
		-- 1.3.6.1.4.1.6296.101.1.18.1.2.10
		sleAutoUpgradeProfileControlPeriodType OBJECT-TYPE
			SYNTAX INTEGER
				{
				auto(1),
				daily(2),
				weekly(3),
				monthly(4),
				interval(5),
				once(6)
				}
			MAX-ACCESS read-write
			STATUS current
			DESCRIPTION
				"Description."
			::= { sleAutoUpgradeProfileControl 10 }

		
		-- 1.3.6.1.4.1.6296.101.1.18.1.2.11
		sleAutoUpgradeProfileControlDate OBJECT-TYPE
			SYNTAX OCTET STRING
			MAX-ACCESS read-write
			STATUS current
			DESCRIPTION
				"Description."
			::= { sleAutoUpgradeProfileControl 11 }

		
		-- 1.3.6.1.4.1.6296.101.1.18.1.2.12
		sleAutoUpgradeProfileControlPeriodDate OBJECT-TYPE
			SYNTAX OCTET STRING
			MAX-ACCESS read-write
			STATUS current
			DESCRIPTION
				"Description."
			::= { sleAutoUpgradeProfileControl 12 }

		
		-- 1.3.6.1.4.1.6296.101.1.18.1.2.13
		sleAutoUpgradeProfileControlTimeout OBJECT-TYPE
			SYNTAX Integer32
			MAX-ACCESS read-write
			STATUS current
			DESCRIPTION
				"Description."
			::= { sleAutoUpgradeProfileControl 13 }

		
		-- 1.3.6.1.4.1.6296.101.1.18.1.2.14
		sleAutoUpgradeProfileControlRetry OBJECT-TYPE
			SYNTAX Integer32 (-1 | 1..2147483647)
			MAX-ACCESS read-write
			STATUS current
			DESCRIPTION
				"Description."
			::= { sleAutoUpgradeProfileControl 14 }

		
		-- 1.3.6.1.4.1.6296.101.1.18.1.2.15
		sleAutoUpgradeProfileControlRegSec OBJECT-TYPE
			SYNTAX Integer32
			MAX-ACCESS read-write
			STATUS current
			DESCRIPTION
				"Description."
			::= { sleAutoUpgradeProfileControl 15 }

		
		-- 1.3.6.1.4.1.6296.101.1.18.1.2.16
		sleAutoUpgradeProfileControlReloadTime OBJECT-TYPE
			SYNTAX OCTET STRING
			MAX-ACCESS read-write
			STATUS current
			DESCRIPTION
				"Description."
			::= { sleAutoUpgradeProfileControl 16 }

		
		-- 1.3.6.1.4.1.6296.101.1.18.1.2.17
		sleAutoUpgradeProfileControlModel OBJECT-TYPE
			SYNTAX OCTET STRING
			MAX-ACCESS read-write
			STATUS current
			DESCRIPTION
				"The Model Name"
			::= { sleAutoUpgradeProfileControl 17 }

		
		-- 1.3.6.1.4.1.6296.101.1.18.1.3
		sleAutoUpgradeProfileNotification OBJECT IDENTIFIER ::= { sleAutoUpgradeProfile 3 }

		
		-- 1.3.6.1.4.1.6296.101.1.18.1.3.1
		sleAutoUpgradeProfileCreated NOTIFICATION-TYPE
			OBJECTS { sleAutoUpgradeProfileControlRequest, sleAutoUpgradeProfileControlTimeStamp, sleAutoUpgradeProfileControlReqResult, sleAutoUpgradeProfileControlName, sleAutoUpgradeProfileControlOldVer, 
				sleAutoUpgradeProfileControlNewVer, sleAutoUpgradeProfileControlSize, sleAutoUpgradeProfileControlDate, sleAutoUpgradeProfileControlPeriodType, sleAutoUpgradeProfileControlPeriodDate, 
				sleAutoUpgradeProfileControlTimeout, sleAutoUpgradeProfileControlRetry, sleAutoUpgradeProfileControlRegSec, sleAutoUpgradeProfileControlReloadTime, sleAutoUpgradeProfileControlModel
				 }
			STATUS current
			DESCRIPTION 
				"Description."
			::= { sleAutoUpgradeProfileNotification 1 }

		
		-- 1.3.6.1.4.1.6296.101.1.18.1.3.2
		sleAutoUpgradeProfileDeleted NOTIFICATION-TYPE
			OBJECTS { sleAutoUpgradeProfileControlRequest, sleAutoUpgradeProfileControlTimeStamp, sleAutoUpgradeProfileControlReqResult, sleAutoUpgradeProfileControlName }
			STATUS current
			DESCRIPTION 
				"Description."
			::= { sleAutoUpgradeProfileNotification 2 }

		
		-- 1.3.6.1.4.1.6296.101.1.18.1.3.3
		sleAutoUpgradeProfileChanged NOTIFICATION-TYPE
			OBJECTS { sleAutoUpgradeProfileControlRequest, sleAutoUpgradeProfileControlTimeStamp, sleAutoUpgradeProfileControlReqResult, sleAutoUpgradeProfileControlName, sleAutoUpgradeProfileControlOldVer, 
				sleAutoUpgradeProfileControlNewVer, sleAutoUpgradeProfileControlSize, sleAutoUpgradeProfileControlDate, sleAutoUpgradeProfileControlPeriodType, sleAutoUpgradeProfileControlPeriodDate, 
				sleAutoUpgradeProfileControlTimeout, sleAutoUpgradeProfileControlRetry, sleAutoUpgradeProfileControlRegSec, sleAutoUpgradeProfileControlReloadTime, sleAutoUpgradeProfileControlModel
				 }
			STATUS current
			DESCRIPTION 
				"Description."
			::= { sleAutoUpgradeProfileNotification 3 }

		
		-- 1.3.6.1.4.1.6296.101.1.18.2
		sleAutoUpgradeMgmt OBJECT IDENTIFIER ::= { sleAutoUpgrade 2 }

		
		-- 1.3.6.1.4.1.6296.101.1.18.2.1
		sleAutoUpgradeOltTable OBJECT-TYPE
			SYNTAX SEQUENCE OF SleAutoUpgradeOltEntry
			MAX-ACCESS not-accessible
			STATUS current
			DESCRIPTION
				"Description."
			::= { sleAutoUpgradeMgmt 1 }

		
		-- 1.3.6.1.4.1.6296.101.1.18.2.1.1
		sleAutoUpgradeOltEntry OBJECT-TYPE
			SYNTAX SleAutoUpgradeOltEntry
			MAX-ACCESS not-accessible
			STATUS current
			DESCRIPTION
				"Description."
			INDEX { sleAutoUpgradeOltSlotIndex, sleAutoUpgradeOltFwType, sleAutoUpgradeOltProfileName, sleAutoUpgradeOltSlotType }
			::= { sleAutoUpgradeOltTable 1 }

		
		SleAutoUpgradeOltEntry ::=
			SEQUENCE { 
				sleAutoUpgradeOltSlotIndex
					INTEGER,
				sleAutoUpgradeOltFwType
					INTEGER,
				sleAutoUpgradeOltProfileName
					OCTET STRING,
				sleAutoUpgradeOltSlotType
					INTEGER
			 }

		-- 1.3.6.1.4.1.6296.101.1.18.2.1.1.1
		sleAutoUpgradeOltSlotIndex OBJECT-TYPE
			SYNTAX INTEGER (0..64)
			MAX-ACCESS read-only
			STATUS current
			DESCRIPTION
				"Description."
			::= { sleAutoUpgradeOltEntry 1 }

		
		-- 1.3.6.1.4.1.6296.101.1.18.2.1.1.2
		sleAutoUpgradeOltFwType OBJECT-TYPE
			SYNTAX INTEGER
				{
				os(1),
				bootloader(2)
				}
			MAX-ACCESS read-only
			STATUS current
			DESCRIPTION
				"Description."
			::= { sleAutoUpgradeOltEntry 2 }

		
		-- 1.3.6.1.4.1.6296.101.1.18.2.1.1.3
		sleAutoUpgradeOltProfileName OBJECT-TYPE
			SYNTAX OCTET STRING
			MAX-ACCESS read-only
			STATUS current
			DESCRIPTION
				"Description."
			::= { sleAutoUpgradeOltEntry 3 }

		
		-- 1.3.6.1.4.1.6296.101.1.18.2.1.1.4
		sleAutoUpgradeOltSlotType OBJECT-TYPE
			SYNTAX INTEGER
				{
				sfu(1),
				siuge12(2),
				siuepon12(3),
				siugpon4(4),
				niuge12(5)
				}
			MAX-ACCESS read-only
			STATUS current
			DESCRIPTION
				"Description."
			::= { sleAutoUpgradeOltEntry 4 }

		
		-- 1.3.6.1.4.1.6296.101.1.18.2.2
		sleAutoUpgradeOntTable OBJECT-TYPE
			SYNTAX SEQUENCE OF SleAutoUpgradeOntEntry
			MAX-ACCESS not-accessible
			STATUS current
			DESCRIPTION
				"Description."
			::= { sleAutoUpgradeMgmt 2 }

		
		-- 1.3.6.1.4.1.6296.101.1.18.2.2.1
		sleAutoUpgradeOntEntry OBJECT-TYPE
			SYNTAX SleAutoUpgradeOntEntry
			MAX-ACCESS not-accessible
			STATUS current
			DESCRIPTION
				"Description."
			INDEX { sleAutoUpgradeOntOltIndex, sleAutoUpgradeOntIndex, sleAutoUpgradeOntFwType, sleAutoUpgradeOntProfileName }
			::= { sleAutoUpgradeOntTable 1 }

		
		SleAutoUpgradeOntEntry ::=
			SEQUENCE { 
				sleAutoUpgradeOntOltIndex
					INTEGER,
				sleAutoUpgradeOntIndex
					INTEGER,
				sleAutoUpgradeOntFwType
					INTEGER,
				sleAutoUpgradeOntProfileName
					OCTET STRING
			 }

		-- 1.3.6.1.4.1.6296.101.1.18.2.2.1.1
		sleAutoUpgradeOntOltIndex OBJECT-TYPE
			SYNTAX INTEGER (0..64)
			MAX-ACCESS read-only
			STATUS current
			DESCRIPTION
				"Description."
			::= { sleAutoUpgradeOntEntry 1 }

		
		-- 1.3.6.1.4.1.6296.101.1.18.2.2.1.2
		sleAutoUpgradeOntIndex OBJECT-TYPE
			SYNTAX INTEGER (0..64)
			MAX-ACCESS read-only
			STATUS current
			DESCRIPTION
				"Description."
			::= { sleAutoUpgradeOntEntry 2 }

		
		-- 1.3.6.1.4.1.6296.101.1.18.2.2.1.3
		sleAutoUpgradeOntFwType OBJECT-TYPE
			SYNTAX INTEGER
				{
				os(1),
				bootloader(2)
				}
			MAX-ACCESS read-only
			STATUS current
			DESCRIPTION
				"Description."
			::= { sleAutoUpgradeOntEntry 3 }

		
		-- 1.3.6.1.4.1.6296.101.1.18.2.2.1.4
		sleAutoUpgradeOntProfileName OBJECT-TYPE
			SYNTAX OCTET STRING
			MAX-ACCESS read-only
			STATUS current
			DESCRIPTION
				"Description."
			::= { sleAutoUpgradeOntEntry 4 }

		
		-- 1.3.6.1.4.1.6296.101.1.18.2.3
		sleAutoUpgradeMgmtControl OBJECT IDENTIFIER ::= { sleAutoUpgradeMgmt 3 }

		
		-- 1.3.6.1.4.1.6296.101.1.18.2.3.1
		sleAutoUpgradeMgmtControlRequest OBJECT-TYPE
			SYNTAX INTEGER
				{
				setAutoUpgrdOltProfile(1),
				unsetAutoUpgrdOltProfile(2),
				setAutoUpgrdOntProfile(3),
				unsetAutoUpgrdOntProfile(4)
				}
			MAX-ACCESS read-write
			STATUS current
			DESCRIPTION
				"Description."
			::= { sleAutoUpgradeMgmtControl 1 }

		
		-- 1.3.6.1.4.1.6296.101.1.18.2.3.2
		sleAutoUpgradeMgmtControlStatus OBJECT-TYPE
			SYNTAX SleControlStatusType
			MAX-ACCESS read-only
			STATUS current
			DESCRIPTION
				"Description."
			::= { sleAutoUpgradeMgmtControl 2 }

		
		-- 1.3.6.1.4.1.6296.101.1.18.2.3.3
		sleAutoUpgradeMgmtControlTimer OBJECT-TYPE
			SYNTAX Gauge32
			MAX-ACCESS read-write
			STATUS current
			DESCRIPTION
				"Description."
			::= { sleAutoUpgradeMgmtControl 3 }

		
		-- 1.3.6.1.4.1.6296.101.1.18.2.3.4
		sleAutoUpgradeMgmtControlTimeStamp OBJECT-TYPE
			SYNTAX TimeTicks
			MAX-ACCESS read-only
			STATUS current
			DESCRIPTION
				"Description."
			::= { sleAutoUpgradeMgmtControl 4 }

		
		-- 1.3.6.1.4.1.6296.101.1.18.2.3.5
		sleAutoUpgradeMgmtControlReqResult OBJECT-TYPE
			SYNTAX SleControlRequestResultType
			MAX-ACCESS read-only
			STATUS current
			DESCRIPTION
				"Description."
			::= { sleAutoUpgradeMgmtControl 5 }

		
		-- 1.3.6.1.4.1.6296.101.1.18.2.3.6
		sleAutoUpgradeMgmtControlOltIndex OBJECT-TYPE
			SYNTAX OCTET STRING
			MAX-ACCESS read-write
			STATUS current
			DESCRIPTION
				"Description."
			::= { sleAutoUpgradeMgmtControl 6 }

		
		-- 1.3.6.1.4.1.6296.101.1.18.2.3.7
		sleAutoUpgradeMgmtControlOntIndex OBJECT-TYPE
			SYNTAX OCTET STRING
			MAX-ACCESS read-write
			STATUS current
			DESCRIPTION
				"Description."
			::= { sleAutoUpgradeMgmtControl 7 }

		
		-- 1.3.6.1.4.1.6296.101.1.18.2.3.8
		sleAutoUpgradeMgmtControlFwType OBJECT-TYPE
			SYNTAX INTEGER
				{
				os(1),
				bootloader(2)
				}
			MAX-ACCESS read-write
			STATUS current
			DESCRIPTION
				"Description."
			::= { sleAutoUpgradeMgmtControl 8 }

		
		-- 1.3.6.1.4.1.6296.101.1.18.2.3.9
		sleAutoUpgradeMgmtControlProfileName OBJECT-TYPE
			SYNTAX OCTET STRING
			MAX-ACCESS read-write
			STATUS current
			DESCRIPTION
				"Description."
			::= { sleAutoUpgradeMgmtControl 9 }

		
		-- 1.3.6.1.4.1.6296.101.1.18.2.3.10
		sleAutoUpgradeMgmtControlSlotType OBJECT-TYPE
			SYNTAX INTEGER
				{
				sfu(1),
				siuge12(2),
				siuepon12(3),
				siugpon4(4),
				niuge12(5)
				}
			MAX-ACCESS read-write
			STATUS current
			DESCRIPTION
				"Description."
			::= { sleAutoUpgradeMgmtControl 10 }

		
		-- 1.3.6.1.4.1.6296.101.1.18.2.4
		sleAutoUpgradeMgmtNotification OBJECT IDENTIFIER ::= { sleAutoUpgradeMgmt 4 }

		
		-- 1.3.6.1.4.1.6296.101.1.18.2.4.1
		sleAutoUpgradeSetOltProfile NOTIFICATION-TYPE
			OBJECTS { sleAutoUpgradeMgmtControlRequest, sleAutoUpgradeMgmtControlTimeStamp, sleAutoUpgradeMgmtControlReqResult, sleAutoUpgradeMgmtControlOltIndex, sleAutoUpgradeMgmtControlFwType, 
				sleAutoUpgradeMgmtControlProfileName, sleAutoUpgradeMgmtControlSlotType }
			STATUS current
			DESCRIPTION 
				"Description."
			::= { sleAutoUpgradeMgmtNotification 1 }

		
		-- 1.3.6.1.4.1.6296.101.1.18.2.4.2
		sleAutoUpgradeUnSetOltProfile NOTIFICATION-TYPE
			OBJECTS { sleAutoUpgradeMgmtControlRequest, sleAutoUpgradeMgmtControlTimeStamp, sleAutoUpgradeMgmtControlReqResult, sleAutoUpgradeMgmtControlOltIndex, sleAutoUpgradeMgmtControlFwType, 
				sleAutoUpgradeMgmtControlProfileName, sleAutoUpgradeMgmtControlSlotType }
			STATUS current
			DESCRIPTION 
				"Description."
			::= { sleAutoUpgradeMgmtNotification 2 }

		
		-- 1.3.6.1.4.1.6296.101.1.18.2.4.3
		sleAutoUpgradeSetOntProfile NOTIFICATION-TYPE
			OBJECTS { sleAutoUpgradeMgmtControlRequest, sleAutoUpgradeMgmtControlTimeStamp, sleAutoUpgradeMgmtControlReqResult, sleAutoUpgradeMgmtControlOntIndex, sleAutoUpgradeMgmtControlFwType, 
				sleAutoUpgradeMgmtControlProfileName }
			STATUS current
			DESCRIPTION 
				"Description."
			::= { sleAutoUpgradeMgmtNotification 3 }

		
		-- 1.3.6.1.4.1.6296.101.1.18.2.4.4
		sleAutoUpgradeUnSetOntProfile NOTIFICATION-TYPE
			OBJECTS { sleAutoUpgradeMgmtControlRequest, sleAutoUpgradeMgmtControlTimeStamp, sleAutoUpgradeMgmtControlReqResult, sleAutoUpgradeMgmtControlOntIndex, sleAutoUpgradeMgmtControlFwType, 
				sleAutoUpgradeMgmtControlProfileName }
			STATUS current
			DESCRIPTION 
				"Description."
			::= { sleAutoUpgradeMgmtNotification 4 }

		
		-- 1.3.6.1.4.1.6296.101.1.18.3
		sleAutoUpgradeLog OBJECT IDENTIFIER ::= { sleAutoUpgrade 3 }

		
		-- 1.3.6.1.4.1.6296.101.1.18.3.1
		sleAutoUpgradeLogInfo OBJECT IDENTIFIER ::= { sleAutoUpgradeLog 1 }

		
		-- 1.3.6.1.4.1.6296.101.1.18.3.2
		sleAutoUpgradeLogControl OBJECT IDENTIFIER ::= { sleAutoUpgradeLog 2 }

		
		-- 1.3.6.1.4.1.6296.101.1.18.3.2.1
		sleAutoUpgradeLogControlRequest OBJECT-TYPE
			SYNTAX INTEGER
				{
				delAutoUpgradeOltLog(1),
				delAutoUpgradeOltLogAll(2),
				delAutoUpgradeOntLog(3),
				delAutoUpgradeOntLogAll(4),
				exportAutoUpgradeOltLog(5),
				exportAutoUpgradeOntLog(6)
				}
			MAX-ACCESS read-write
			STATUS current
			DESCRIPTION
				"Description."
			::= { sleAutoUpgradeLogControl 1 }

		
		-- 1.3.6.1.4.1.6296.101.1.18.3.2.2
		sleAutoUpgradeLogControlStatus OBJECT-TYPE
			SYNTAX SleControlStatusType
			MAX-ACCESS read-only
			STATUS current
			DESCRIPTION
				"Description."
			::= { sleAutoUpgradeLogControl 2 }

		
		-- 1.3.6.1.4.1.6296.101.1.18.3.2.3
		sleAutoUpgradeLogControlTimer OBJECT-TYPE
			SYNTAX Gauge32
			MAX-ACCESS read-write
			STATUS current
			DESCRIPTION
				"Description."
			::= { sleAutoUpgradeLogControl 3 }

		
		-- 1.3.6.1.4.1.6296.101.1.18.3.2.4
		sleAutoUpgradeLogControlTimeStamp OBJECT-TYPE
			SYNTAX TimeTicks
			MAX-ACCESS read-only
			STATUS current
			DESCRIPTION
				"Description."
			::= { sleAutoUpgradeLogControl 4 }

		
		-- 1.3.6.1.4.1.6296.101.1.18.3.2.5
		sleAutoUpgradeLogControlReqResult OBJECT-TYPE
			SYNTAX SleControlRequestResultType
			MAX-ACCESS read-only
			STATUS current
			DESCRIPTION
				"Description."
			::= { sleAutoUpgradeLogControl 5 }

		
		-- 1.3.6.1.4.1.6296.101.1.18.3.2.6
		sleAutoUpgradeLogControlSlotIndex OBJECT-TYPE
			SYNTAX OCTET STRING
			MAX-ACCESS read-write
			STATUS current
			DESCRIPTION
				"Description."
			::= { sleAutoUpgradeLogControl 6 }

		
		-- 1.3.6.1.4.1.6296.101.1.18.3.2.7
		sleAutoUpgradeLogControlOntIndex OBJECT-TYPE
			SYNTAX OCTET STRING
			MAX-ACCESS read-write
			STATUS current
			DESCRIPTION
				"Description."
			::= { sleAutoUpgradeLogControl 7 }

		
		-- 1.3.6.1.4.1.6296.101.1.18.3.2.8
		sleAutoUpgradeLogControlExportMethod OBJECT-TYPE
			SYNTAX INTEGER
				{
				ftp(1),
				tftp(2)
				}
			MAX-ACCESS read-write
			STATUS current
			DESCRIPTION
				"Description."
			::= { sleAutoUpgradeLogControl 8 }

		
		-- 1.3.6.1.4.1.6296.101.1.18.3.2.9
		sleAutoUpgradeLogControlServer OBJECT-TYPE
			SYNTAX IpAddress
			MAX-ACCESS read-write
			STATUS current
			DESCRIPTION
				"Description."
			::= { sleAutoUpgradeLogControl 9 }

		
		-- 1.3.6.1.4.1.6296.101.1.18.3.2.10
		sleAutoUpgradeLogControlUser OBJECT-TYPE
			SYNTAX OCTET STRING
			MAX-ACCESS read-write
			STATUS current
			DESCRIPTION
				"Description."
			::= { sleAutoUpgradeLogControl 10 }

		
		-- 1.3.6.1.4.1.6296.101.1.18.3.2.11
		sleAutoUpgradeLogControlPasswd OBJECT-TYPE
			SYNTAX OCTET STRING
			MAX-ACCESS read-write
			STATUS current
			DESCRIPTION
				"Description."
			::= { sleAutoUpgradeLogControl 11 }

		
		-- 1.3.6.1.4.1.6296.101.1.18.3.3
		sleAutoUpgradeLogNotification OBJECT IDENTIFIER ::= { sleAutoUpgradeLog 3 }

		
		-- 1.3.6.1.4.1.6296.101.1.18.3.3.1
		sleAutoUpgradeDeleteOltLog NOTIFICATION-TYPE
			OBJECTS { sleAutoUpgradeLogControlRequest, sleAutoUpgradeLogControlTimeStamp, sleAutoUpgradeLogControlReqResult, sleAutoUpgradeLogControlSlotIndex }
			STATUS current
			DESCRIPTION 
				"Description."
			::= { sleAutoUpgradeLogNotification 1 }

		
		-- 1.3.6.1.4.1.6296.101.1.18.3.3.2
		sleAutoUpgradeDeleteAllOltLog NOTIFICATION-TYPE
			OBJECTS { sleAutoUpgradeLogControlRequest, sleAutoUpgradeLogControlTimeStamp, sleAutoUpgradeLogControlReqResult }
			STATUS current
			DESCRIPTION 
				"Description."
			::= { sleAutoUpgradeLogNotification 2 }

		
		-- 1.3.6.1.4.1.6296.101.1.18.3.3.3
		sleAutoUpgradeDeleteOntLog NOTIFICATION-TYPE
			OBJECTS { sleAutoUpgradeLogControlRequest, sleAutoUpgradeLogControlTimeStamp, sleAutoUpgradeLogControlReqResult, sleAutoUpgradeLogControlOntIndex }
			STATUS current
			DESCRIPTION 
				"Description."
			::= { sleAutoUpgradeLogNotification 3 }

		
		-- 1.3.6.1.4.1.6296.101.1.18.3.3.4
		sleAutoUpgradeDeleteAllOntLog NOTIFICATION-TYPE
			OBJECTS { sleAutoUpgradeLogControlRequest, sleAutoUpgradeLogControlTimeStamp, sleAutoUpgradeLogControlReqResult }
			STATUS current
			DESCRIPTION 
				"Description."
			::= { sleAutoUpgradeLogNotification 4 }

		
		-- 1.3.6.1.4.1.6296.101.1.18.3.3.5
		sleAutoUpgradeExportOltLog NOTIFICATION-TYPE
			OBJECTS { sleAutoUpgradeLogControlRequest, sleAutoUpgradeLogControlTimeStamp, sleAutoUpgradeLogControlReqResult, sleAutoUpgradeLogControlSlotIndex, sleAutoUpgradeLogControlExportMethod, 
				sleAutoUpgradeLogControlServer, sleAutoUpgradeLogControlUser }
			STATUS current
			DESCRIPTION 
				"Description."
			::= { sleAutoUpgradeLogNotification 5 }

		
		-- 1.3.6.1.4.1.6296.101.1.18.3.3.6
		sleAutoUpgradeExportOntLog NOTIFICATION-TYPE
			OBJECTS { sleAutoUpgradeLogControlRequest, sleAutoUpgradeLogControlTimeStamp, sleAutoUpgradeLogControlReqResult, sleAutoUpgradeLogControlOntIndex, sleAutoUpgradeLogControlExportMethod, 
				sleAutoUpgradeLogControlServer, sleAutoUpgradeLogControlUser }
			STATUS current
			DESCRIPTION 
				"Description."
			::= { sleAutoUpgradeLogNotification 6 }

		
		-- 1.3.6.1.4.1.6296.101.1.19
		sleWatchdog OBJECT IDENTIFIER ::= { sleSystemMaintenance 19 }

		
		-- 1.3.6.1.4.1.6296.101.1.19.1
		sleWatchdogInfo OBJECT IDENTIFIER ::= { sleWatchdog 1 }

		
		-- 1.3.6.1.4.1.6296.101.1.19.1.1
		sleWatchdogAdminStatus OBJECT-TYPE
			SYNTAX INTEGER
				{
				enable(1),
				disable(2)
				}
			MAX-ACCESS read-only
			STATUS current
			DESCRIPTION
				"The status of system watchdog
				"
			::= { sleWatchdogInfo 1 }

		
		-- 1.3.6.1.4.1.6296.101.1.19.1.2
		sleWatchdogTimeout OBJECT-TYPE
			SYNTAX Integer32
			MAX-ACCESS read-only
			STATUS current
			DESCRIPTION
				"The timeout of system watchdog (unit: sec)"
			::= { sleWatchdogInfo 2 }

		
		-- 1.3.6.1.4.1.6296.101.1.19.1.3
		sleWatchdogMode OBJECT-TYPE
			SYNTAX INTEGER
				{
				top(1),
				timer(2),
				thread(3)
				}
			MAX-ACCESS read-only
			STATUS current
			DESCRIPTION
				"The trriger mode of system watchdog"
			::= { sleWatchdogInfo 3 }

		
		-- 1.3.6.1.4.1.6296.101.1.19.2
		sleWatchdogControl OBJECT IDENTIFIER ::= { sleWatchdog 2 }

		
		-- 1.3.6.1.4.1.6296.101.1.19.2.1
		sleWatchdogControlRequest OBJECT-TYPE
			SYNTAX INTEGER
				{
				setWatchdogStatus(1),
				setWatchdogTimeout(2),
				setWatchdogMode(3)
				}
			MAX-ACCESS read-write
			STATUS current
			DESCRIPTION
				"Description."
			::= { sleWatchdogControl 1 }

		
		-- 1.3.6.1.4.1.6296.101.1.19.2.2
		sleWatchdogControlStatus OBJECT-TYPE
			SYNTAX SleControlStatusType
			MAX-ACCESS read-only
			STATUS current
			DESCRIPTION
				"Description."
			::= { sleWatchdogControl 2 }

		
		-- 1.3.6.1.4.1.6296.101.1.19.2.3
		sleWatchdogControlTimer OBJECT-TYPE
			SYNTAX Gauge32
			MAX-ACCESS read-write
			STATUS current
			DESCRIPTION
				"Description."
			::= { sleWatchdogControl 3 }

		
		-- 1.3.6.1.4.1.6296.101.1.19.2.4
		sleWatchdogControlTimeStamp OBJECT-TYPE
			SYNTAX TimeTicks
			MAX-ACCESS read-only
			STATUS current
			DESCRIPTION
				"Description."
			::= { sleWatchdogControl 4 }

		
		-- 1.3.6.1.4.1.6296.101.1.19.2.5
		sleWatchdogControlReqResult OBJECT-TYPE
			SYNTAX SleControlRequestResultType
			MAX-ACCESS read-only
			STATUS current
			DESCRIPTION
				"Description."
			::= { sleWatchdogControl 5 }

		
		-- 1.3.6.1.4.1.6296.101.1.19.2.6
		sleWatchdogControlAdminStatus OBJECT-TYPE
			SYNTAX INTEGER
				{
				enable(1),
				disable(2)
				}
			MAX-ACCESS read-write
			STATUS current
			DESCRIPTION
				"The status of system watchdog
				"
			::= { sleWatchdogControl 6 }

		
		-- 1.3.6.1.4.1.6296.101.1.19.2.7
		sleWatchdogControlTimeout OBJECT-TYPE
			SYNTAX Integer32
			MAX-ACCESS read-write
			STATUS current
			DESCRIPTION
				"The timeout of system watchdog (unit: sec)"
			::= { sleWatchdogControl 7 }

		
		-- 1.3.6.1.4.1.6296.101.1.19.2.8
		sleWatchdogControlMode OBJECT-TYPE
			SYNTAX INTEGER
				{
				top(1),
				timer(2),
				thread(3)
				}
			MAX-ACCESS read-write
			STATUS current
			DESCRIPTION
				"The trriger mode of system watchdog"
			::= { sleWatchdogControl 8 }

		
		-- 1.3.6.1.4.1.6296.101.1.19.3
		sleWatchdogNotification OBJECT IDENTIFIER ::= { sleWatchdog 3 }

		
		-- 1.3.6.1.4.1.6296.101.1.19.3.1
		sleWatchdogAdminStatusChanged NOTIFICATION-TYPE
			OBJECTS { sleWatchdogControlRequest, sleWatchdogControlTimeStamp, sleWatchdogControlReqResult, sleWatchdogControlAdminStatus }
			STATUS current
			DESCRIPTION 
				"Description."
			::= { sleWatchdogNotification 1 }

		
		-- 1.3.6.1.4.1.6296.101.1.19.3.2
		sleWatchdogTimeoutChanged NOTIFICATION-TYPE
			OBJECTS { sleWatchdogControlRequest, sleWatchdogControlTimeStamp, sleWatchdogControlReqResult, sleWatchdogControlTimeout }
			STATUS current
			DESCRIPTION 
				"Description."
			::= { sleWatchdogNotification 2 }

		
		-- 1.3.6.1.4.1.6296.101.1.19.3.3
		sleWatchdogModeChanged NOTIFICATION-TYPE
			OBJECTS { sleWatchdogControlRequest, sleWatchdogControlTimeStamp, sleWatchdogControlReqResult, sleWatchdogControlMode }
			STATUS current
			DESCRIPTION 
				"Description."
			::= { sleWatchdogNotification 3 }

		
		-- 1.3.6.1.4.1.6296.101.1.100
		sleFtpclient OBJECT IDENTIFIER ::= { sleSystemMaintenance 100 }

		
		-- 1.3.6.1.4.1.6296.101.1.100.1
		sleFtpclientTable OBJECT-TYPE
			SYNTAX SEQUENCE OF SleFtpclientEntry
			MAX-ACCESS not-accessible
			STATUS current
			DESCRIPTION
				"Description."
			::= { sleFtpclient 1 }

		
		-- 1.3.6.1.4.1.6296.101.1.100.1.1
		sleFtpclientEntry OBJECT-TYPE
			SYNTAX SleFtpclientEntry
			MAX-ACCESS not-accessible
			STATUS current
			DESCRIPTION
				"Description."
			INDEX { sleFtpclientIndex }
			::= { sleFtpclientTable 1 }

		
		SleFtpclientEntry ::=
			SEQUENCE { 
				sleFtpclientIndex
					Integer32,
				sleFtpclientFileName
					OCTET STRING,
				sleFtpclientFileSize
					Integer32
			 }

		-- 1.3.6.1.4.1.6296.101.1.100.1.1.1
		sleFtpclientIndex OBJECT-TYPE
			SYNTAX Integer32 (1..65535)
			MAX-ACCESS read-only
			STATUS current
			DESCRIPTION
				"index."
			::= { sleFtpclientEntry 1 }

		
		-- 1.3.6.1.4.1.6296.101.1.100.1.1.2
		sleFtpclientFileName OBJECT-TYPE
			SYNTAX OCTET STRING
			MAX-ACCESS read-only
			STATUS current
			DESCRIPTION
				"The File name."
			::= { sleFtpclientEntry 2 }

		
		-- 1.3.6.1.4.1.6296.101.1.100.1.1.3
		sleFtpclientFileSize OBJECT-TYPE
			SYNTAX Integer32
			MAX-ACCESS read-only
			STATUS current
			DESCRIPTION
				"The File size."
			::= { sleFtpclientEntry 3 }

		
		-- 1.3.6.1.4.1.6296.101.1.100.2
		sleFtpclientControl OBJECT IDENTIFIER ::= { sleFtpclient 2 }

		
		-- 1.3.6.1.4.1.6296.101.1.100.2.1
		sleFtpclientControlRequest OBJECT-TYPE
			SYNTAX INTEGER { updateDirectoryInfo(1) }
			MAX-ACCESS read-write
			STATUS current
			DESCRIPTION
				"Description."
			::= { sleFtpclientControl 1 }

		
		-- 1.3.6.1.4.1.6296.101.1.100.2.2
		sleFtpclientControlStatus OBJECT-TYPE
			SYNTAX SleControlStatusType
			MAX-ACCESS read-only
			STATUS current
			DESCRIPTION
				"Description."
			::= { sleFtpclientControl 2 }

		
		-- 1.3.6.1.4.1.6296.101.1.100.2.3
		sleFtpclientControlTimer OBJECT-TYPE
			SYNTAX Gauge32
			MAX-ACCESS read-write
			STATUS current
			DESCRIPTION
				"Description."
			::= { sleFtpclientControl 3 }

		
		-- 1.3.6.1.4.1.6296.101.1.100.2.4
		sleFtpclientControlTimeStamp OBJECT-TYPE
			SYNTAX TimeTicks
			MAX-ACCESS read-only
			STATUS current
			DESCRIPTION
				"Description."
			::= { sleFtpclientControl 4 }

		
		-- 1.3.6.1.4.1.6296.101.1.100.2.5
		sleFtpclientControlReqResult OBJECT-TYPE
			SYNTAX SleControlRequestResultType
			MAX-ACCESS read-only
			STATUS current
			DESCRIPTION
				"Description."
			::= { sleFtpclientControl 5 }

		
		-- 1.3.6.1.4.1.6296.101.1.100.2.6
		sleFtpclientControlServerIp OBJECT-TYPE
			SYNTAX IpAddress
			MAX-ACCESS read-write
			STATUS current
			DESCRIPTION
				"The server IP address."
			::= { sleFtpclientControl 6 }

		
		-- 1.3.6.1.4.1.6296.101.1.100.2.7
		sleFtpclientControlUserId OBJECT-TYPE
			SYNTAX OCTET STRING
			MAX-ACCESS read-write
			STATUS current
			DESCRIPTION
				"The user ID."
			::= { sleFtpclientControl 7 }

		
		-- 1.3.6.1.4.1.6296.101.1.100.2.8
		sleFtpclientControlPassword OBJECT-TYPE
			SYNTAX OCTET STRING
			MAX-ACCESS read-write
			STATUS current
			DESCRIPTION
				"The password"
			::= { sleFtpclientControl 8 }

		
		-- 1.3.6.1.4.1.6296.101.1.100.2.9
		sleFtpclientControlDirectoryPath OBJECT-TYPE
			SYNTAX OCTET STRING
			MAX-ACCESS read-write
			STATUS current
			DESCRIPTION
				"The directory path."
			::= { sleFtpclientControl 9 }

		
		-- 1.3.6.1.4.1.6296.101.1.100.3
		sleFtpclientNotification OBJECT IDENTIFIER ::= { sleFtpclient 3 }

		
		-- 1.3.6.1.4.1.6296.101.1.100.3.1
		sleFtpclientDirectoryInfoUpdated NOTIFICATION-TYPE
			OBJECTS { sleFtpclientControlRequest, sleFtpclientControlTimeStamp, sleFtpclientControlReqResult, sleFtpclientControlServerIp, sleFtpclientControlUserId, 
				sleFtpclientControlPassword, sleFtpclientControlDirectoryPath }
			STATUS current
			DESCRIPTION 
				"UpdateDirectoryInfo"
			::= { sleFtpclientNotification 1 }

		
		-- 1.3.6.1.4.1.6296.101.1.101
		sleSystemMaintenanceGroup OBJECT-GROUP
			OBJECTS { sleSystemModelName, sleSystemSerialNumber, sleSystemHWVersion, sleSystemBLVersion, sleSystemSWCompatibility, 
				sleSystemOSVersion, sleSystemMacAddress, sleSystemHostName, sleSystemCPULoadAll, sleSystemCPULoadInterrupt, 
				sleSystemCPUThreshold, sleSystemCPUInterval, sleSystemMemoryTotal, sleSystemMemoryFree, sleSystemMemoryShared, 
				sleSystemMemoryBuffers, sleSystemMemoryCached, sleSystemMemorySwapTotal, sleSystemMemorySwapFree, sleSystemDefaultOS, 
				sleSystemOS1Version, sleSystemOS1Size, sleSystemOS1BuildNumber, sleSystemOS2Version, sleSystemOS2Size, 
				sleSystemOS2BuildNumber, sleSystemFlashTotalSize, sleSystemFlashOSSize, sleSystemFlashConfigSize, sleSystemFlashOSUsedSize, 
				sleSystemFlashConfigUsedSize, sleSystemClock, sleSystemTimezone, sleSystemDNSDomainName, sleSystemInitBanner, 
				sleSystemSuccessBanner, sleSystemFailBanner, sleSystemSyslogState, sleSystemSyslogVolatileNumber, sleSystemSyslogNonVolatileNumber, 
				sleSystemSyslogBindAddress, sleSystemSyslogLocalCode, sleSystemSSHState, sleSystemNTPState, sleSystemBackupInterval, 
				sleSystemDhcpActivity, sleSystemDefaultTTL, sleSystemSyslogVolatileSize, sleSystemSyslogBindInterfaceName, sleSystemSessionTime, 
				sleSystemExecTimeout, sleSystemWatchdogStatus, sleLoginIndex, sleLoginUser, sleLoginTTY, 
				sleLoginRemote, sleLoginTime, sleBackupConfigFile, sleProcessID, sleProcessUser, 
				sleProcessCPU, sleProcessMemory, sleProcessVSZ, sleProcessRSS, sleProcessTerminal, 
				sleProcessStatus, sleProcessStartTime, sleProcessUsedTime, sleProcessCommand, sleNTPServerName, 
				sleSyslogConfIndex, sleSyslogConfMode, sleSyslogConfFacility, sleSyslogConfSeverity, sleSyslogConfTarget, 
				sleSyslogConfStorage, sleSyslogConfTargetAddress, sleSyslogHistVolIndex, sleSyslogHistVolMsgText, sleSyslogHistVolTime, 
				sleSyslogHistNVolIndex, sleSyslogHistNVolMsgText, sleSyslogHistNVolTime, sleSSHRemoteIndex, sleSSHRemoteUser, 
				sleSSHRemoteHost, sleSSHRemoteTime, sleAutoCliConfStatus, sleAutoCliMemoryMaxSize, sleAutoCliMemoryUsedsize, 
				sleAutoCliMemoryFreesize, sleAutoCliTransferInterval, sleAutoCliScriptId, sleAutoCliScriptFileName, sleAutoCliScriptFileUser, 
				sleAutoCliScriptFileSize, sleAutoCliScriptFileUpdateTime, sleAutoCliScheduleName, sleAutoCliScheduleType, sleAutoCliScheduleInterval, 
				sleAutoCliScheduleYear, sleAutoCliScheduleMonth, sleAutoCliScheduleDay, sleAutoCliScheduleHour, sleAutoCliScheduleMinute, 
				sleAutoCliScheduleScriptName, sleAutoCliScheduleTransferType, sleAutoCliScheduleLastExecutedTime, sleAutoCliScheduleOutputRule, sleAutoCliScheduleLastResult, 
				sleAutoCliOutputMemoryFileId, sleAutoCliOutputMemoryFileName, sleAutoCliOutputMemoryFileSize, sleAutoCliOutputMemoryFileUpdatedTime, sleAutoResetPingConfStatus, 
				sleAutoResetPingIpAddress, sleAutoResetPingTransactionInterval, sleAutoResetPingNumberOfRequest, sleAutoResetPingRequestInterval, sleAutoResetPingTimeoutOfRequest, 
				sleAutoResetPingEnableTime, sleAutoResetPingRequestCount, sleAutoResetPingReplyCount, sleAutoResetPingLossCount, sleAutoResetPingTotalPingTransaction, 
				sleAutoResetPingTotalLossTransaction, sleAutoResetMemoryleakContStatus, sleAutoResetMemoryleakMemThreshold, sleAutoResetMemoryleakCheckInterval, sleAutoResetMemoryleakNumberOfVerification, 
				sleAutoResetMemoryleakVerificationInterval, sleAutoResetMemoryleakRebootCount, sleAutoResetMemoryleakEnableTime, sleAutoResetMemoryleakLastFreeMemory, sleAutoResetMemoryleakVerificationCount, 
				sleAutoResetMemoryleakDetectionCount, sleAutoResetMemoryleakTotalVerificationCount, sleAutoResetMemoryleakTotalDetectionCount, sleAutoResetMemoryleakReboottimeStartHour, sleAutoResetMemoryleakReboottimeStartMin, 
				sleAutoResetMemoryleakReboottimeEndHour, sleAutoResetMemoryleakReboottimeEndMin, sleCoreDumpInfoPID, sleCoreDumpInfoStatus, sleCoreDumpFile, 
				sleServiceIndex, sleServiceProtocol, sleServiceName, sleServicePort, sleSystemNtpBindInterface, 
				sleSystemFtpBindInterface, sleSystemRedundancyPort, sleDNSServerIndex, sleDNSServerName, sleAutoResetMemoryleakRebootThreshold, 
				sleAutoResetMemoryleakCountThreshold, sleAutoResetPingRebootCounter, sleSystemSyslogVolatileMaxLine, sleParameterMode, sleParameterValue, 
				sleParameterName, sleAutoResetPingRebootThreshold, sleAutoResetPingLossThreshold, sleSystemUserName, sleSystemUserLevel, 
				sleSystemUserPassword, sleAutoCliScheduleProfileName, sleAutoCliProfileServerType, sleAutoCliProfileServerIpAddress, sleAutoCliProfileServerUser, 
				sleAutoCliProfileServerPassword, sleAutoCliProfileServerDir, sleSwWatchdogType, sleSwWatchdogInterval, sleSwWatchdogThreshold, 
				sleSwWatchdogAction, sleSwWatchdogErrcnt, sleSystemBootInfo, sleSystemTempHighThreshold, sleSystemTempLowThreshold, 
				sleSystemMemThreshold, sleSystemLowCPUThreshold, sleSystemLowCPUInterval, sleSystemControlRequest, sleSystemControlStatus, 
				sleSystemControlTimer, sleSystemControlTimeStamp, sleSystemControlReqResult, sleSystemControlHostName, sleSystemControlCPUThreshold, 
				sleSystemControlCPUInterval, sleSystemControlDefaultOS, sleSystemControlClock, sleSystemControlTimezone, sleSystemControlDNSDomainName, 
				sleSystemControlInitBanner, sleSystemControlSuccessBanner, sleSystemControlFailBanner, sleSystemControlSyslogState, sleSystemControlSyslogVolatileNumber, 
				sleSystemControlSyslogNonVolatileNumber, sleSystemControlSyslogBindAddress, sleSystemControlSyslogLocalCode, sleSystemControlSSHState, sleSystemControlNTPState, 
				sleSystemControlOSUpgradeNumber, sleSystemControlServerAddress, sleSystemControlUpDownFlag, sleSystemControlUserID, sleSystemControlPassword, 
				sleSystemControlFileName, sleSystemControlBackupFlag, sleSystemControlReloadOS, sleSystemControlBackupInterval, sleSystemControlDhcpActivity, 
				sleSystemControlDefaultTTL, sleSystemControlSyslogVolatileSize, sleSystemControlSyslogBindInterfaceName, sleSystemControlSrcPort, sleSystemControlDstPort, 
				sleSystemControlSessionTime, sleSystemControlExecTimeout, sleSystemControlWatchdogStatus, sleSystemControlClearOs, sleSystemControlNtpBindInterface, 
				sleSystemControlFtpBindInterface, sleSystemControlSyslogVolMaxLine, sleSystemControlTempHighThreshold, sleSystemControlTempLowThreshold, sleSystemControlMemThreshold, 
				sleSystemControlLowCPUThreshold, sleSystemControlLowCPUInterval, sleDNSServerControlRequest, sleDNSServerControlStatus, sleDNSServerControlTimer, 
				sleDNSServerControlTImeStamp, sleDNSServerControlReqResult, sleDNSServerControlIndex, sleDNSServerControlName, sleBackupControlRequest, 
				sleBackupControlStatus, sleBackupControlTimer, sleBackupControlTimeStamp, sleBackupControlReqResult, sleBackupControlCreateMode, 
				sleBackupControlServerIP, sleBackupControlUserID, sleBackupControlPassword, sleBackupControlSrcConfigFile, sleBackupControlDstConfigFile, 
				sleNTPServerControlRequest, sleNTPServerControlStatus, sleNTPServerControlTimer, sleNTPServerControlTImeStamp, sleNTPServerControlReqResult, 
				sleNTPServerControlName, sleSyslogConfControlRequest, sleSyslogConfControlStatus, sleSyslogConfControlTimer, sleSyslogConfControlTimeStamp, 
				sleSyslogConfControlReqResult, sleSyslogConfControlIndex, sleSyslogConfControlMode, sleSyslogConfControlSeverity, sleSyslogConfControlFacility, 
				sleSyslogConfControlTarget, sleSyslogConfControlStorage, sleSyslogConfControlTargetAddress, sleSSHRemoteControlRequest, sleSSHRemoteControlStatus, 
				sleSSHRemoteControlTimer, sleSSHRemoteControlTImeStamp, sleSSHRemoteControlReqResult, sleSSHRemoteControlIndex, sleAutoCliControlRequest, 
				sleAutoCliControlStatus, sleAutoCliControlTimer, sleAutoCliControlTimeStamp, sleAutoCliControlReqResult, sleAutoCliControlConfStatus, 
				sleAutoCliControlMemoryMaxsize, sleAutoCliControlTransferInterval, sleAutoCliScriptFileControlRequest, sleAutoCliScriptFileControlStatus, sleAutoCliScriptFileControlTimer, 
				sleAutoCliScriptFileControlTimeStamp, sleAutoCliScriptFileControlReqResult, sleAutoCliScriptFileControlIpAddress, sleAutoCliScriptFileControlUserName, sleAutoCliScriptFileControlPassword, 
				sleAutoCliScriptFileControlFilePath, sleAutoCliScriptFileControlScriptName, sleAutoCliScheduleControlRequest, sleAutoCliScheduleControlStatus, sleAutoCliScheduleControlTimer, 
				sleAutoCliScheduleControlTimeStamp, sleAutoCliScheduleControlReqResult, sleAutoCliScheduleControlName, sleAutoCliScheduleControlType, sleAutoCliScheduleControlInterval, 
				sleAutoCliScheduleControlYear, sleAutoCliScheduleControlMonth, sleAutoCliScheduleControlDay, sleAutoCliScheduleControlHour, sleAutoCliScheduleControlMinute, 
				sleAutoCliScheduleControlScriptName, sleAutoCliScheduleControlTransferType, sleAutoCliScheduleControlOutputRule, sleAutoCliScheduleControlProfileName, sleAutoCliProfileControlRequest, 
				sleAutoCliProfileControlStatus, sleAutoCliProfileControlTimer, sleAutoCliProfileControlTimeStamp, sleAutoCliProfileControlReqResult, sleAutoCliProfileControlName, 
				sleAutoCliProfileControlType, sleAutoCliProfileServerControlRequest, sleAutoCliProfileServerControlStatus, sleAutoCliProfileServerControlTimer, sleAutoCliProfileServerControlTimeStamp, 
				sleAutoCliProfileServerControlReqResult, sleAutoCliProfileServerControlProfName, sleAutoCliProfileServerControlIpAddress, sleAutoCliProfileServerControlUser, sleAutoCliProfileServerControlPassword, 
				sleAutoCliProfileServerControlDir, sleAutoCliOutputMemoryFileControlRequest, sleAutoCliOutputMemoryFileControlStatus, sleAutoCliOutputMemoryFileControlTimer, sleAutoCliOutputMemoryFileControlTimeStamp, 
				sleAutoCliOutputMemoryFileControlReqResult, sleAutoCliOutputMemoryFileControlServer, sleAutoCliOutputMemoryFileControlUserName, sleAutoCliOutputMemoryFileControlPassword, sleAutoCliOutputMemoryFileControlOutputFileName, 
				sleAutoCliOutputMemoryFileControlRemotePath, sleAutoResetPingControlRequest, sleAutoResetPingControlStatus, sleAutoResetPingControlTimer, sleAutoResetPingControlTimeStamp, 
				sleAutoResetPingControlReqResult, sleAutoResetPingControlConfStatus, sleAutoResetPingControlIpAddress, sleAutoResetPingControlTransactionInterval, sleAutoResetPingControlNumberOfRequest, 
				sleAutoResetPingControlRequestInterval, sleAutoResetPingControlTimeoutOfRequest, sleAutoResetPingControlPingLossThreshold, sleAutoResetPingControlRebootThreshold, sleAutoResetMemoryleakControlRequest, 
				sleAutoResetMemoryleakControlStatus, sleAutoResetMemoryleakControlTimer, sleAutoResetMemoryleakControlTimeStamp, sleAutoResetMemoryleakControlReqResult, sleAutoResetMemoryleakControlConfStatus, 
				sleAutoResetMemoryleakControlMemThreshold, sleAutoResetMemoryleakControlCheckInterval, sleAutoResetMemoryleakControlNumberOfVerification, sleAutoResetMemoryleakControlVerificationInterval, sleAutoResetMemoryleakControlCountThreshold, 
				sleAutoResetMemoryleakControlReboottimeStartHour, sleAutoResetMemoryleakControlReboottimeStartMin, sleAutoResetMemoryleakControlReboottimeEndHour, sleAutoResetMemoryleakControlReboottimeEndMin, sleAutoResetMemoryleakControlRebootThreshold, 
				sleCoreDumpControlRequest, sleCoreDumpControlStatus, sleCoreDumpControlTimer, sleCoreDumpControlTimeStamp, sleCoreDumpControlReqResult, 
				sleCoreDumpControlPID, sleCoreDumpControlServerIP, sleCoreDumpControlUserID, sleCoreDumpControlPassword, sleCoreDumpControlCoredumpFile, 
				sleServiceControlRequest, sleServiceControlStatus, sleServiceControlTimer, sleServiceControlTimeStamp, sleServiceControlReqResult, 
				sleServiceControlIndex, sleServiceControlProtocol, sleServiceControlPort, sleSystemUserControlRequest, sleSystemUserControlStatus, 
				sleSystemUserControlTimer, sleSystemUserControlTimeStamp, sleSystemUserControlReqResult, sleSystemUserControlName, sleSystemUserControlRename, 
				sleSystemUserControlLevel, sleSystemUserControlPwType, sleSystemUserControlPassword, sleSystemUserControlDesc, sleParameterControlRequest, 
				sleParameterControlStatus, sleParameterControlTimer, sleParameterControlTimeStamp, sleParameterControlReqResult, sleParameterControlName, 
				sleParameterControlValue, sleParameterControlMode, sleSwWatchdogControlRequest, sleSwWatchdogControlStatus, sleSwWatchdogControlTimer, 
				sleSwWatchdogControlTimeStamp, sleSwWatchdogControlReqResult, sleSwWatchdogControlType, sleSwWatchdogControlInterval, sleSwWatchdogControlThreshold, 
				sleSwWatchdogControlAction, sleSystemRunningOS, sleSystemSlotIndex, sleSystemSlotUptime, sleSystemSlotModelName, 
				sleSystemSlotSerialNumber, sleSystemSlotHWVersion, sleSystemSlotBLVersion, sleSystemSlotSWCompatibility, sleSystemSlotOSVersion, 
				sleSystemSlotMacAddress, sleSystemSlotCPULoadAll, sleSystemSlotCPULoadInterrupt, sleSystemSlotMemoryTotal, sleSystemSlotMemoryFree, 
				sleSystemSlotMemoryShared, sleSystemSlotMemoryBuffers, sleSystemSlotMemoryCached, sleSystemSlotMemorySwapTotal, sleSystemSlotMemorySwapFree, 
				sleSystemSlotBootReason, sleSystemSlotBootTime, sleSystemSlotVoltage, sleAutoUpgradeProfileName, sleAutoUpgradeProfileOldVer, 
				sleAutoUpgradeProfileNewVer, sleAutoUpgradeProfileSize, sleAutoUpgradeProfileDate, sleAutoUpgradeProfilePeriodType, sleAutoUpgradeProfilePeriodDate, 
				sleAutoUpgradeProfileTimeout, sleAutoUpgradeProfileRetry, sleAutoUpgradeProfileRegSec, sleAutoUpgradeProfileReloadTime, sleAutoUpgradeProfileControlRequest, 
				sleAutoUpgradeProfileControlStatus, sleAutoUpgradeProfileControlTimer, sleAutoUpgradeProfileControlTimeStamp, sleAutoUpgradeProfileControlReqResult, sleAutoUpgradeProfileControlName, 
				sleAutoUpgradeProfileControlOldVer, sleAutoUpgradeProfileControlNewVer, sleAutoUpgradeProfileControlSize, sleAutoUpgradeProfileControlDate, sleAutoUpgradeProfileControlPeriodType, 
				sleAutoUpgradeProfileControlPeriodDate, sleAutoUpgradeProfileControlTimeout, sleAutoUpgradeProfileControlRetry, sleAutoUpgradeProfileControlRegSec, sleAutoUpgradeProfileControlReloadTime, 
				sleAutoUpgradeOltSlotIndex, sleAutoUpgradeOltFwType, sleAutoUpgradeOltSlotType, sleAutoUpgradeOntOltIndex, sleAutoUpgradeOntIndex, 
				sleAutoUpgradeOntFwType, sleAutoUpgradeMgmtControlRequest, sleAutoUpgradeMgmtControlStatus, sleAutoUpgradeMgmtControlTimer, sleAutoUpgradeMgmtControlTimeStamp, 
				sleAutoUpgradeMgmtControlReqResult, sleAutoUpgradeMgmtControlOltIndex, sleAutoUpgradeMgmtControlOntIndex, sleAutoUpgradeMgmtControlFwType, sleAutoUpgradeLogControlRequest, 
				sleAutoUpgradeLogControlStatus, sleAutoUpgradeLogControlTimer, sleAutoUpgradeLogControlTimeStamp, sleAutoUpgradeLogControlReqResult, sleAutoUpgradeLogControlSlotIndex, 
				sleAutoUpgradeLogControlOntIndex, sleAutoUpgradeLogControlExportMethod, sleAutoUpgradeLogControlServer, sleAutoUpgradeLogControlUser, sleAutoUpgradeLogControlPasswd, 
				sleAutoUpgradeMgmtControlSlotType, sleSystemNtpBindAddress, sleSystemEnablePasswdType, sleSystemEnablePasswd, sleSystemServicePasswdEncryption, 
				sleSystemControlNtpBindAddress, sleSystemControlEnablePasswdType, sleSystemControlEnablePasswd, sleSystemControlServicePasswdEncryption, sleServiceAdminStatus, 
				sleServiceControlAdminStatus, sleSystemUptime64, sleSystemNtpPollnterval, sleSystemControlNtpPollInterval, sleSystemCPUDuration, 
				sleSystemLowCPUDuration, sleSystemControlCPUDuration, sleSystemControlLowCPUDuration, sleAutoResetCpuStatus, sleAutoResetCpuLoad, 
				sleAutoResetCpuInterruptLoad, sleAutoResetCpuTime, sleAutoResetCpuControlLoad, sleAutoResetCpuControlInterruptLoad, sleAutoResetCpuControlTime, 
				sleSystemUserDesc, sleAutoCliProfileName, sleAutoCliProfileType, sleAutoUpgradeOltProfileName, sleAutoUpgradeOntProfileName, 
				sleSystemBarcode, sleAutoResetBootReason, sleAutoResetPingRebootRecoveryTime, sleAutoResetPingControlRebootRecoveryTime, sleSystemEnhancedFeature, 
				sleSystemGetBranchModel, sleFtpclientIndex, sleFtpclientFileName, sleFtpclientFileSize, sleFtpclientControlRequest, 
				sleFtpclientControlStatus, sleFtpclientControlTimer, sleFtpclientControlTimeStamp, sleFtpclientControlReqResult, sleFtpclientControlServerIp, 
				sleFtpclientControlUserId, sleFtpclientControlPassword, sleFtpclientControlDirectoryPath, sleSystemTargetId, sleSystemNodeName, 
				sleSystemNetworkName, sleSystemShelfId, sleSystemSlotId, sleSystemWebMgmt, sleSystemControlWebMgmt, 
				sleSystemManufacturer, sleSystemManufactureDate, sleAutoUpgradeProfileModel, sleAutoUpgradeProfileControlModel, sleAutoUpgradeProfileIndex, 
				sleAutoUpgradeMgmtControlProfileName, sleAutoResetCpuControlRequest, sleAutoResetCpuControlStatus, sleAutoResetCpuControlTimer, sleAutoResetCpuControlTimeStamp, 
				sleAutoResetCpuControlReqResult, sleWatchdogAdminStatus, sleWatchdogTimeout, sleWatchdogMode, sleWatchdogControlRequest, 
				sleWatchdogControlStatus, sleWatchdogControlTimer, sleWatchdogControlTimeStamp, sleWatchdogControlReqResult, sleWatchdogControlAdminStatus, 
				sleWatchdogControlTimeout, sleSystemAdministeredMac, sleSystemControlAdministeredMac, sleSystemAutoReloadInHour, sleSystemAutoReloadInMinutes, 
				sleSystemAutoReloadDailyHour, sleSystemAutoReloadDailyMinutes, sleSystemAutoReloadAtYear, sleSystemAutoReloadAtMonth, sleSystemAutoReloadAtDay, 
				sleSystemAutpReloadAtHour, sleSystemAutpReloadAtMinutes, sleSystemControlAutoReloadYear, sleSystemControlAutoReloadMonth, sleSystemControlAutoReloadDay, 
				sleSystemControlAutoReloadHour, sleSystemControlAutoReloadMinutes, sleSystemBaseMac, sleWatchdogControlMode, sleSystemNosUpgradeStatus, 
				sleSSHRemoteFromHost, sleSystemUserLoginFailureCount, sleSystemUserLoginLastFailureTime }
			STATUS current
			DESCRIPTION 
				"Description."
			::= { sleSystemMaintenance 101 }

		
		-- 1.3.6.1.4.1.6296.101.1.102
		sleSystemMaintenanceNotificationGroup NOTIFICATION-GROUP
			NOTIFICATIONS { sleSystemSystemInfoProfileChanged, sleSystemCPUThresholdProfileChanged, sleSystemDefaultOSChanged, sleSystemRTCProfileChanged, sleSystemDNSDomainNameChanged, 
				sleSystemBannerProfileChanged, sleSystemSyslogProfileChanged, sleSystemSSHStateChanged, sleSystemNTPStateChanged, sleSystemOSProfileChanged, 
				sleSystemBackupChanged, sleSystemBackupIntervalChanged, sleSystemDhcpActivityChanged, sleSystemDefaultTTLChanged, sleSystemSyslogBindInterfaceNameChanged, 
				sleSystemSyslogBindInterfaceNameCleared, sleSystemConfigPortMoved, sleSystemConfigPortCopied, sleSystemConfigPortCleared, sleSystemSessionTimeChanged, 
				sleSystemExecTimeoutChanged, sleSystemWatchdogStatusChanged, sleSystemNosDestroyed, sleDNSServerCreated, sleDNSServerDestroyed, 
				sleBackupCreated, sleBackupDestroyed, sleBackupChanged, sleNTPServerCreated, sleNTPServerDestroyed, 
				sleSyslogConfCreated, sleSyslogConfDestroyed, sleSSHRemoteConnectiondestoryed, sleAutoCliStatusChanged, sleAutoCliMemoryMaxsizeChanged, 
				sleAutoCliTransferIntervalChanged, sleAutoCliScriptFileFtpCreated, sleAutoCliScriptFileDestroyed, sleAutoCliScheduleCreated, sleAutoCliScheduleDestroyed, 
				sleAutoCliOutputMemoryFileFtpCreated, sleAutoCliOutputMemoryFileDestroyed, sleAutoResetPingStatusChanged, sleAutoResetPingInfoModified, sleAutoResetMemoryleakStatusChanged, 
				sleAutoResetMemoryleakInfoModified, sleAutoResetMemoryleakReboottimeModified, sleCoreDumpEntryCreated, sleCoreDumpEntryDestroyed, sleCoreDumpEntryChanged, 
				sleServicePortChanged, sleAutoResetMemoryleakRebootCountClearSetted, sleAutoResetMemoryleakRebootCtrlModified, sleAutoResetPingRebootCountClearSetted, sleParameterValueChanged, 
				sleParameterModeChanged, sleParameterDestroyed, sleParameterCreated, sleAutoResetPingRebootCtrlModified, sleSystemNtpBindInterfaceChanged, 
				sleSystemFtpBindInterfaceChanged, sleSystemRedundancyPortChanged, sleRedundancyPortCleared, sleBackupConfigBySftpChanged, sleBackupConfigByScpChanged, 
				sleBackupKeyBySftpChanged, sleBackupKeyByScpChanged, sleSystemUserCreated, sleSystemUserNameChanged, sleSystemUserPasswordChanged, 
				sleAutoCliScriptFileTftpCreated, sleAutoCliProfileCreated, sleAutoCliProfileServerCreated, sleAutoCliProfileServerDestroyed, sleAutoCliProfileServerAllDestroyed, 
				sleAutoCliOutputMemoryFileTftpCreated, sleSwWatchdogCreated, sleSwWatchdogDeleted, sleSystemTempThresholdChanged, sleSystemMemThresholdChanged, 
				sleAutoUpgradeProfileCreated, sleAutoUpgradeProfileDeleted, sleAutoUpgradeProfileChanged, sleAutoUpgradeSetOltProfile, sleAutoUpgradeUnSetOltProfile, 
				sleAutoUpgradeSetOntProfile, sleAutoUpgradeUnSetOntProfile, sleAutoUpgradeDeleteOltLog, sleAutoUpgradeDeleteAllOltLog, sleAutoUpgradeDeleteOntLog, 
				sleAutoUpgradeDeleteAllOntLog, sleAutoUpgradeExportOltLog, sleAutoUpgradeExportOntLog, sleSystemBootloaderProfileChanged, sleSystemNtpBindAddressChanged, 
				sleSystemEnablePasswdChanged, sleSystemEnableServicePasswdEncryptionChanged, sleServiceAdminStatusChanged, sleSystemUserLevelChanged, sleSystemPasswdRestored, 
				sleSystemNtpPollIntervalChanged, sleAutoResetCpuChanged, sleAutoResetCpuDeleted, sleSystemUserDestroyed, sleFtpclientDirectoryInfoUpdated, 
				sleSystemWebMgmtChanged, sleSystemUserLoginAttemptsFailureLogCleared, sleSystemAdministeredMacChanged, sleSystemAutoReloadInTimeChanged, sleSystemAutoReloadDailyTimeChanged, 
				sleSystemAutoReloadAtTimeChanged, sleAutoCliProfileDestroyed, sleSystemRestoreFactoryChanged, sleWatchdogAdminStatusChanged, sleWatchdogTimeoutChanged, 
				sleWatchdogModeChanged }
			STATUS current
			DESCRIPTION 
				"Description."
			::= { sleSystemMaintenance 102 }

		
	
	END

--
-- sle-systemmaintenance-mib.mib
--
