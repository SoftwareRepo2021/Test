--
-- File:                 gnc.mib
-- Version:              1.00.03
-- Date of Last Update:  06/30/2009
--
-- Description: This MIB describes the manageable elements for the GNC
-- management module.  This MIB is based on SNMPv1 MIB-2 specification.
--
-- Copyright (c) 2008-2009 - Sorrento Networks, Inc.
-- All Rights Reserved
--
-- History of Changes:
--    1.00.03:  (06/30/2009)
--              Added facility Opr, OprLowTh, OprHighTh for GMCR10G & GMCRF10G
--              Added facility Opr, OprLowTh, OprHighTh and LoopbackState  
--                  for GMCR10GL & GMCRF10GL
--              Changed gmmr4 Bay InputPower for Working and protection 
--                  port to read-only
--              Added CardMismatch and CardConfigChanged Trap
--
--    1.00.02:  (03/17/2008)
--
--              Update:  This header section
--
--    1.00.01:  (10/04/2007)
--
--              Fix 50GHz support for GMCR10G, GMCR10GL, GMCRF10G, GMCRF10GL.
--              By changing the ItuNum selection
--              From ItuSelection to ItuSelection2 (super set)
--              For the following cards...
--                      gmcr10g
--                      gmcr10gl
--                      gmcrf10g
--                      gmcrf10gl
--
--              Plus other previous check-in(s)
--
--
--    1.00.00:  (12/07/2006)
--

GNC-MIB DEFINITIONS ::= BEGIN

    IMPORTS
            enterprises, Counter,
            Gauge, IpAddress        FROM RFC1155-SMI
            DisplayString           FROM RFC1213-MIB
            OBJECT-TYPE             FROM RFC-1212
            TRAP-TYPE               FROM RFC-1215;

    -- Full OID: iso org(3) dod(6) internet(1) private(4)
    -- enterprises (1)  1.3.6.1.4.1.2522

    osicomTechnologies      OBJECT IDENTIFIER ::= { enterprises 2522 }
    gigaNest                OBJECT IDENTIFIER ::= { osicomTechnologies 1 }
    otm32                   OBJECT IDENTIFIER ::= { gigaNest 102 }
    configuration           OBJECT IDENTIFIER ::= { otm32 1 }
    cardConfiguration       OBJECT IDENTIFIER ::= { otm32 2 }
    security                OBJECT IDENTIFIER ::= { otm32 3 }
    events                  OBJECT IDENTIFIER ::= { otm32 4 }

    -- subgroups in the configuration group
    sys                     OBJECT IDENTIFIER ::= { configuration 1 }
    ntp                     OBJECT IDENTIFIER ::= { configuration 2 }
    spanningTree            OBJECT IDENTIFIER ::= { configuration 3 }
    eqpt                    OBJECT IDENTIFIER ::= { configuration 4 }
    pwr                     OBJECT IDENTIFIER ::= { configuration 5 }
    fan                     OBJECT IDENTIFIER ::= { configuration 6 }
    traphost                OBJECT IDENTIFIER ::= { configuration 7 }
    zms                     OBJECT IDENTIFIER ::= { configuration 8 }
    inventory               OBJECT IDENTIFIER ::= { configuration 9 }
    softwareDownload        OBJECT IDENTIFIER ::= { configuration 10 }

    -- subgroups in the cardConfiguration group
--    epc                     OBJECT IDENTIFIER ::= { cardConfiguration 1 }
--    fnr                     OBJECT IDENTIFIER ::= { cardConfiguration 2 }
--    fnt                     OBJECT IDENTIFIER ::= { cardConfiguration 3 }
    fpmr                    OBJECT IDENTIFIER ::= { cardConfiguration 4 }
    fpmt                    OBJECT IDENTIFIER ::= { cardConfiguration 5 }
--    fps2w                   OBJECT IDENTIFIER ::= { cardConfiguration 6 }
    gm10ge10g               OBJECT IDENTIFIER ::= { cardConfiguration 7 }
--    gm2ge2g5                OBJECT IDENTIFIER ::= { cardConfiguration 8 }
    gm4ge2g5                OBJECT IDENTIFIER ::= { cardConfiguration 9 }
    gmad                    OBJECT IDENTIFIER ::= { cardConfiguration 10 }
    gmad100                 OBJECT IDENTIFIER ::= { cardConfiguration 11 }
    gmbp                    OBJECT IDENTIFIER ::= { cardConfiguration 12 }
--    gmcm                    OBJECT IDENTIFIER ::= { cardConfiguration 13 }
    gmcr10g                 OBJECT IDENTIFIER ::= { cardConfiguration 14 }
    gmcr10gl                OBJECT IDENTIFIER ::= { cardConfiguration 15 }
    gmcr2g5                 OBJECT IDENTIFIER ::= { cardConfiguration 16 }
--    gmcr35                  OBJECT IDENTIFIER ::= { cardConfiguration 17 }
    gmcrf10g                OBJECT IDENTIFIER ::= { cardConfiguration 18 }
    gmcrf10gl               OBJECT IDENTIFIER ::= { cardConfiguration 19 }
    gmdcm                   OBJECT IDENTIFIER ::= { cardConfiguration 20 }
--    gmde                    OBJECT IDENTIFIER ::= { cardConfiguration 21 }
    gmdm10                  OBJECT IDENTIFIER ::= { cardConfiguration 22 }
    gmdpm                   OBJECT IDENTIFIER ::= { cardConfiguration 23 }
--    gme                     OBJECT IDENTIFIER ::= { cardConfiguration 24 }
    gme1c                   OBJECT IDENTIFIER ::= { cardConfiguration 25 }
    gmeb                    OBJECT IDENTIFIER ::= { cardConfiguration 26 }
--    gmei                    OBJECT IDENTIFIER ::= { cardConfiguration 27 }
    gmer                    OBJECT IDENTIFIER ::= { cardConfiguration 28 }
--    gmfc2g5                 OBJECT IDENTIFIER ::= { cardConfiguration 29 }
--    gmfe                    OBJECT IDENTIFIER ::= { cardConfiguration 30 }
    gmfti                   OBJECT IDENTIFIER ::= { cardConfiguration 31 }
--    gmi                     OBJECT IDENTIFIER ::= { cardConfiguration 32 }
--    gmlei                   OBJECT IDENTIFIER ::= { cardConfiguration 33 }
    gmmd                    OBJECT IDENTIFIER ::= { cardConfiguration 34 }
    gmmd100                 OBJECT IDENTIFIER ::= { cardConfiguration 35 }
    gmmr2g5                 OBJECT IDENTIFIER ::= { cardConfiguration 36 }
    gmmr4                   OBJECT IDENTIFIER ::= { cardConfiguration 37 }
--    gmoaT1                  OBJECT IDENTIFIER ::= { cardConfiguration 38 }
--    gmoaT2                  OBJECT IDENTIFIER ::= { cardConfiguration 39 }
--    gmoaT3                  OBJECT IDENTIFIER ::= { cardConfiguration 40 }
    gmoaT4                  OBJECT IDENTIFIER ::= { cardConfiguration 41 }
    gmoaT5                  OBJECT IDENTIFIER ::= { cardConfiguration 42 }
    gmoaT6                  OBJECT IDENTIFIER ::= { cardConfiguration 43 }
    gmox                    OBJECT IDENTIFIER ::= { cardConfiguration 44 }
--    gmox10g                 OBJECT IDENTIFIER ::= { cardConfiguration 45 }
    gmox2g5                 OBJECT IDENTIFIER ::= { cardConfiguration 46 }
    gmrb                    OBJECT IDENTIFIER ::= { cardConfiguration 47 }
--    gmsmx10g                OBJECT IDENTIFIER ::= { cardConfiguration 48 }
    gmsmx2g5                OBJECT IDENTIFIER ::= { cardConfiguration 49 }
    gmtm                    OBJECT IDENTIFIER ::= { cardConfiguration 50 }
--    gmtm2                   OBJECT IDENTIFIER ::= { cardConfiguration 51 }
--    gmtr                    OBJECT IDENTIFIER ::= { cardConfiguration 52 }
--    gmwd                    OBJECT IDENTIFIER ::= { cardConfiguration 53 }
    gnc                     OBJECT IDENTIFIER ::= { cardConfiguration 54 }
    mgr                     OBJECT IDENTIFIER ::= { cardConfiguration 55 }
--    oc192                   OBJECT IDENTIFIER ::= { cardConfiguration 56 }
    gmosc                     OBJECT IDENTIFIER ::= { cardConfiguration 57 }
    gmosc100                  OBJECT IDENTIFIER ::= { cardConfiguration 58 }
    scf                     OBJECT IDENTIFIER ::= { cardConfiguration 59 }
    gmvga                   OBJECT IDENTIFIER ::= { cardConfiguration 60 }
    gmvoa40                 OBJECT IDENTIFIER ::= { cardConfiguration 61 }
    gmroadm                 OBJECT IDENTIFIER ::= { cardConfiguration 62 }
    gmei80                  OBJECT IDENTIFIER ::= { cardConfiguration 63 }

    -- subgroups of the faults group

    -- subgroups of the security group
    users           OBJECT IDENTIFIER ::= { security 1 }

    -- Textual conventions for the Boolean data type
    Boolean ::= INTEGER { true(1), false(2) }

    -- Textual conventions for the CardType data type
    CardType ::= INTEGER 
                       {
                           null(0),
                           gnc(1),
                           mgr(2),
                           gmox(3),
                           gmtr(4),
                           gmoa(5),
                           gmmd(6),
                           gmde(7),
                           gme(8),
                           gmmd100(9),
                           gmeb(10),
                           gmer(11),
                           gmrb(12),
                           gmfti(13),
                           gmad100(14),
                           gmbp(15),
                           gmmr2g5(16),
                           fpmr(17),
                           fpmt(18),
                           osc(19),
                           scf(20),
                           pwr(21),
                           fan(22),
                           oc192(23), 
                           gmcr35(24),
                           gmox10g(25),
                           gmox2g5(26),
                           gmcr2g5(27),
                           gmcr10g(28),
                           gmcrf10g(29),
                           gmsmx2g5(30),
                           gmsmx10g(31),
                           gmei(32),
                           gme1c(33),
                           gmad(34),
                           gmcm(35),  
                           epc(36),
                           fps2w(37),
                           gmi(38),
                           gmlei(39),
                           gmfe(40),
                           gmwd(41),
                           fnr(42),
                           fnt(43),
                           gmtm(44),
                           gmtm2(45),
                           gm2ge2g5(46),
                           gm4ge2g5(47),
                           gmdpm(48),
                           gmdcm(49),
                           gmfc2g5(50),
                           osc100(51),
                           gmcr10gl(52),
                           gmcrf10gl(53),
                           gm10ge10g(54), 
                           gmdm10(55),
                           gmmr4(56),
                           gmvga(57),
                           gmvoa40(58),
                           unknown(59),
                           gmroadm(60),
                           gmei80(61)
                       }

    -- Textual conventions for the ItuSelection data type
    ItuSelection ::= INTEGER 
                       {
                           na(0),
                           itu-20(1),       
                           itu-21(2),
                           itu-22(3),
                           itu-23(4),       
                           itu-24(5),
                           itu-25(6),
                           itu-26(7),       
                           itu-27(8),
                           itu-28(9),
                           itu-29(10),       
                           itu-30(11),
                           itu-31(12),
                           itu-32(13),       
                           itu-33(14),
                           itu-34(15),
                           itu-35(16),       
                           itu-36(17),
                           itu-37(18),
                           itu-38(19),       
                           itu-39(20),
                           itu-40(21),
                           itu-41(22),
                           itu-42(23),       
                           itu-43(24),
                           itu-44(25),
                           itu-45(26),       
                           itu-46(27),
                           itu-47(28),
                           itu-48(29),       
                           itu-49(30),
                           itu-50(31),
                           itu-51(32),
                           itu-52(33),       
                           itu-53(34),
                           itu-54(35),
                           itu-55(36),       
                           itu-56(37),
                           itu-57(38),
                           itu-58(39),       
                           itu-59(40),
                           unknown(56)
                       }

    -- Textual conventions for the ItuSelection2 data type
    ItuSelection2 ::= INTEGER 
                       {
                           itu-20(1),
                           itu-21(2),
                           itu-22(3),
                           itu-23(4),
                           itu-24(5),
                           itu-25(6),
                           itu-26(7),
                           itu-27(8),
                           itu-28(9),
                           itu-29(10),
                           itu-30(11),
                           itu-31(12),
                           itu-32(13),
                           itu-33(14),
                           itu-34(15),
                           itu-35(16),
                           itu-36(17),
                           itu-37(18),
                           itu-38(19),
                           itu-39(20),
                           itu-40(21),
                           itu-41(22),
                           itu-42(23),
                           itu-43(24),
                           itu-44(25),
                           itu-45(26),
                           itu-46(27),
                           itu-47(28),
                           itu-48(29),
                           itu-49(30),
                           itu-50(31),
                           itu-51(32),
                           itu-52(33),
                           itu-53(34),
                           itu-54(35),
                           itu-55(36),
                           itu-56(37),
                           itu-57(38),
                           itu-58(39),
                           itu-59(40),
                           copper(41),
                           cw1270(42),
                           cw1290(43),
                           cw1310(44),
                           cw1470(45),
                           cw1490(46),
                           cw1510(47),
                           cw1530(48),
                           cw1550(49),
                           cw1570(50),
                           cw1590(51),
                           cw1610(52),
                           cw850(53),
                           cwrf(54),
                           notset(55),
                           unknown(56),
                           itu-19p5(57),
                           itu-20p5(58),
                           itu-21p5(59),
                           itu-22p5(60),
                           itu-23p5(61),
                           itu-24p5(62),
                           itu-25p5(63),
                           itu-26p5(64),
                           itu-27p5(65),
                           itu-28p5(66),
                           itu-29p5(67),
                           itu-30p5(68),
                           itu-31p5(69),
                           itu-32p5(70),
                           itu-33p5(71),
                           itu-34p5(72),
                           itu-35p5(73),
                           itu-36p5(74),
                           itu-37p5(75),
                           itu-38p5(76),
                           itu-39p5(77),
                           itu-40p5(78),
                           itu-41p5(79),
                           itu-42p5(80),
                           itu-43p5(81),
                           itu-44p5(82),
                           itu-45p5(83),
                           itu-46p5(84),
                           itu-47p5(85),
                           itu-48p5(86),
                           itu-49p5(87),
                           itu-50p5(88),
                           itu-51p5(89),
                           itu-52p5(90),
                           itu-53p5(91),
                           itu-54p5(92),
                           itu-55p5(93),
                           itu-56p5(94),
                           itu-57p5(95),
                           itu-58p5(96)
                       }

    -- Textual conventions for the LoopbackState data type
    LoopbackState ::= INTEGER { enabled(1), disabled(2) }

    -- Textual conventions for the PmState data type
    PmState ::= INTEGER { allowed(1), inhibited(2), notreported(3), na(4) }

    -- Textual conventions for the PrimaryState data type
    PrimaryState ::= INTEGER 
                     {
                         na(0),
                         is(1),
                         isanr(2),
                         isnr(3),
                         oos(4),
                         oosau(5),
                         oosauma(6),
                         oosma(7),
                         oosmaanr(8),
                         uas(9)
                     }

    -- Textual conventions for the SecondaryState data type
    SecondaryState ::= INTEGER 
                       {
                           act(1),
                           busy(2),
                           dsbld(3),
                           flt(4),
                           frcd(5),
                           idle(6),
                           lpbk(7),
                           mea(8),
                           nil(9),
                           pwr(10),
                           sgeo(11),
                           swtch(12),
                           swto(13),
                           trmt(14),
                           uas(15),
                           ueq(16)
                       }

    -- Textual conventions for the ZmsAdminString data type
    ZmsAdminString ::= DisplayString  (SIZE (0..32))

    -- Textual conventions for the ZmsFileName data type
    ZmsFileName    ::= DisplayString  (SIZE (0..64))

    --
    -- The elements in the sys subgroup of the configuration group
    --

    gncSysSourceId OBJECT-TYPE
        SYNTAX DisplayString  (SIZE (0..20))
        ACCESS read-write
        STATUS mandatory
        DESCRIPTION
            "System source ID.  Thisis equivalent to the system name."
        ::= { sys 1 }

    gncSysDate     OBJECT-TYPE
        SYNTAX DisplayString  (SIZE (0..10))
        ACCESS read-write
        STATUS mandatory
        DESCRIPTION
            "System date."
        ::= { sys 2 }

    gncSysTime     OBJECT-TYPE
        SYNTAX DisplayString  (SIZE (0..8))
        ACCESS read-write
        STATUS mandatory
        DESCRIPTION
            "System time"
        ::= { sys 3 }

    gncSysNeType   OBJECT-TYPE
        SYNTAX INTEGER  { otm32(1), otm32-p(2), icore(3), icore-P(4) }
        ACCESS read-write
        STATUS mandatory
        DESCRIPTION
            "Network element type."
        ::= { sys 4 }

    gncSysGncPlus  OBJECT-TYPE
        SYNTAX INTEGER  { yes(1), no(2) }
        ACCESS read-write
        STATUS mandatory
        DESCRIPTION
            "Indicates whether the system is configured as a GNC Plus"
        ::= { sys 5 }

    gncSysDbVer    OBJECT-TYPE
        SYNTAX DisplayString
        ACCESS read-only
        STATUS mandatory
        DESCRIPTION
            "Database version."
        ::= { sys 6 }

    gncSysIpAddress    OBJECT-TYPE
        SYNTAX IpAddress
        ACCESS read-write
        STATUS mandatory
        DESCRIPTION
            "System IP address."
        ::= { sys 7 }

    gncSysNetMask      OBJECT-TYPE
        SYNTAX IpAddress
        ACCESS read-write
        STATUS mandatory
        DESCRIPTION
            "System network submask."
        ::= { sys 8 }

    gncSysGateWay      OBJECT-TYPE
        SYNTAX IpAddress
        ACCESS read-write
        STATUS mandatory
        DESCRIPTION
            "System default gateway."
        ::= { sys 9 }

    gncSysExternalMACAddress   OBJECT-TYPE
        SYNTAX DisplayString
        ACCESS read-only
        STATUS mandatory
        DESCRIPTION
            "MAC address of external ethernet port."
        ::= { sys 10 }

    gncSysInternalMACAddress   OBJECT-TYPE
        SYNTAX DisplayString
        ACCESS read-only
        STATUS mandatory
        DESCRIPTION
            "MAC address of internal ring ethernet port. "
        ::= { sys 11 }

    gncSysVLan     OBJECT-TYPE
        SYNTAX INTEGER
        ACCESS read-write
        STATUS mandatory
        DESCRIPTION
            "VLAN number for internal management IP addresses."
        ::= { sys 12 }

    gncSysAddCard  OBJECT-TYPE
        SYNTAX DisplayString
        ACCESS read-write
        STATUS mandatory
        DESCRIPTION
            "System command to add card to the chassis.  The format for 
             adding each card type is listed below.  Note: the format
             may vary from module to module.
             
             Module type    Format
             FPMR           <bay>-<shelf>-<slot>-FPMR,<ITU number>
             FPMT           <bay>-<shelf>-<slot>-FPMT
             GM10GE10G      <bay>-<shelf>-<slot>-GM10GE10G,<subtype - LR,LRT>,<ITU number>
             GM4GE2G5       <bay>-<shelf>-<slot>-GM4GE2G5,<subtype - A,M,R>,<ITU number>
             GMCR10G        <bay>-<shelf>-<slot>-GMCR10G,<subtype - EW,LW,LWT>,<ITU number>
             GMCR10GL       <bay>-<shelf>-<slot>-GMCR10GL,<subtype - ER,FC,FCT,LR,LRT>,<ITU number>
             GMCR2G5        <bay>-<shelf>-<slot>-GMCR2G5,<subtype - A,M,R>,<ITU number>
             GMCRF10G       <bay>-<shelf>-<slot>-GMCRF10G,<subtype - EW,LW,LWT>,<ITU number>
             GMCRF10GL      <bay>-<shelf>-<slot>-GMCRF10GL,<subtype - ER,FC,FCT,LR,LRT>,<ITU number>
             GMAD           <bay>-<shelf>-<slot>-GMAD,<ITU number>
             GMAD100        <bay>-<shelf>-<slot>-GMAD100,<ICore Id>
             GMBP           <bay>-<shelf>-<slot>-GMBP,<group Id>
             GMDCM          <bay>-<shelf>-<slot>-GMDCM
             GMDM10         <bay>-<shelf>-<slot>-GMDM10,<subtype - LR,LRT>,<ITU number>
             GMDPM          <bay>-<shelf>-<slot>-GMDPM
             GME1C          <bay>-<shelf>-<slot>-GME1C
             GMEB           <bay>-<shelf>-<slot>-GMEB,<subtype - C>
             GMEI80         <bay>-<shelf>-<slot>-GMEI80
             GMER           <bay>-<shelf>-<slot>-GMER,<subtype - C>
             GMFTI          <bay>-<shelf>-<slot>-GMFTI,<subtype - C,CL>
             GMMD           <bay>-<shelf>-<slot>-GMMD,<subtype - G1,G2,G3,G4,G5,G6,G7,G8,GME2>
             GMMD100        <bay>-<shelf>-<slot>-GMMD100,<group Id>
             GMMR2G5        <bay>-<shelf>-<slot>-GMMR2G5,<subtype - A,M,R>,<ITU number>
             GMMR4          <bay>-<shelf>-<slot>-GMMR4
             GMOAT4         <bay>-<shelf>-<slot>-GMOA,<subtype - T4C>
             GMOAT5         <bay>-<shelf>-<slot>-GMOA,<subtype - T5,T5C>
             GMOAT6         <bay>-<shelf>-<slot>-GMOA,<subtype - T6,T6C>
             GMOX           <bay>-<shelf>-<slot>-GMOX,<subtype>,<ITU number>
             GMOX2G5        <bay>-<shelf>-<slot>-GMOX2G5,<subtype - A,M,R>,<ITU number>
             GMRB           <bay>-<shelf>-<slot>-GMRB,<subtype - C>
             GMROADM        <bay>-<shelf>-<slot>-GMROADM,<subtype - 40C,40C50>
             GMSMX2G5       <bay>-<shelf>-<slot>-GMSMX2G5,<subtype - A,M,R>,<ITU number>
             GMTM           <bay>-<shelf>-<slot>-GMTM
             GMVGA          <bay>-<shelf>-<slot>-GMVGA,<subtype - T17,T20_4,T20_9>
             GMVOA40        <bay>-<shelf>-<slot>-GMVOA40
             OSC            <bay>-<shelf>-<slot>-OSC,<direction>
             OSC100         <bay>-<shelf>-<slot>-OSC100,<direction>
             SCF            <bay>-<shelf>-<slot>-SCF

             GMTM is not support in Bay 1, Shelf 8 (the GNC shelf).
             "
        ::= { sys 13 }
    gncSysRecoverCardAlarm  OBJECT-TYPE
        SYNTAX DisplayString
        ACCESS read-write
        STATUS mandatory
        DESCRIPTION
            "System command to recover card alarms. The format is 
             <bay>-<shelf>-<slot>-<cardType>
             "
        ::= { sys 14 }
    --
    -- The elements in the ntp subgroup of the configuration group
    --

    ntpServer   OBJECT-TYPE
        SYNTAX IpAddress
        ACCESS read-write
        STATUS mandatory
        DESCRIPTION
            "NTP server."
        ::= { ntp 1 }

    ntpStatus   OBJECT-TYPE
        SYNTAX INTEGER  { off(1), on(2) }
        ACCESS read-write
        STATUS mandatory
        DESCRIPTION
            "NTP status."
        ::= { ntp 2 }

    ntpInterval OBJECT-TYPE
        SYNTAX INTEGER
        ACCESS read-write
        STATUS mandatory
        DESCRIPTION
            "NTP update interval."
        ::= { ntp 3 }

    ntpForceSet OBJECT-TYPE
        SYNTAX INTEGER  { yes(1), no(2) }
        ACCESS read-write
        STATUS mandatory
        DESCRIPTION
            "Force set NTP."
        ::= { ntp 4 }

    --
    -- The elements in the spanningTree subgroup of the configuration group
    --

    spanPriority    OBJECT-TYPE
        SYNTAX INTEGER (1..32)
        ACCESS read-write
        STATUS mandatory
        DESCRIPTION
            "Nodes spanning tree priority.  Highest = 1 and lowest = 32."
        ::= { spanningTree 1 }

    spanHelloTime   OBJECT-TYPE
        SYNTAX INTEGER (1..10)
        ACCESS read-write
        STATUS mandatory
        DESCRIPTION
            "Spanning tree hello time.  This is the time (in seconds)
             between sending BPDUs."
        ::= { spanningTree 2 }

    spanIsRoot  OBJECT-TYPE
        SYNTAX INTEGER { yes(1), no(2) }
        ACCESS read-only
        STATUS mandatory
        DESCRIPTION
            "Indicates whether node is a spanning tree root node."
        ::= { spanningTree 3 }

    --
    -- The elements in the eqpt subgroup of the configuration group
    --

    eqptTable   OBJECT-TYPE
            SYNTAX  SEQUENCE OF EqptEntry
            ACCESS  not-accessible
            STATUS  mandatory
            DESCRIPTION
                    "Summary table of modules known by the GNC."
            ::= { eqpt 1 }

    eqptEntry   OBJECT-TYPE
            SYNTAX  EqptEntry
            ACCESS  not-accessible
            STATUS  mandatory
            DESCRIPTION
                    "Equipment entry format"
            INDEX   { eqptBay, eqptShelf, eqptSlot }
            ::= { eqptTable 1 }

    EqptEntry   ::=
            SEQUENCE 
            {
                eqptBay                     INTEGER,
                eqptShelf                   INTEGER,
                eqptSlot                    INTEGER,
                eqptCardType                INTEGER,
                eqptItuNum                  ItuSelection,
                eqptSubType                 DisplayString,
                eqptSlipSpeed               INTEGER,
                eqptPrimaryState            INTEGER,
                eqptSecondaryState          INTEGER
            }

    eqptBay    OBJECT-TYPE
        SYNTAX INTEGER
        ACCESS read-only
        STATUS mandatory
        DESCRIPTION
            "Bay portion of module address."
        ::= { eqptEntry 1 }

    eqptShelf  OBJECT-TYPE
        SYNTAX INTEGER
        ACCESS read-only
        STATUS mandatory
        DESCRIPTION
            "Shelf portion of module address."
        ::= { eqptEntry 2 }

    eqptSlot   OBJECT-TYPE
        SYNTAX INTEGER
        ACCESS read-write
        STATUS mandatory
        DESCRIPTION
            "Slot portion of module address.  Set to 0 to delete card"
        ::= { eqptEntry 3 }

    eqptCardType OBJECT-TYPE
        SYNTAX CardType
        ACCESS read-only
        STATUS mandatory
        DESCRIPTION
            "Module card type."
        ::= { eqptEntry 4 }

    eqptItuNum OBJECT-TYPE
        SYNTAX ItuSelection 
        ACCESS read-only
        STATUS mandatory
        DESCRIPTION
            "Module supported ITU channel.  na(0) is return for modules that do 
             not support ITU channels."
        ::= { eqptEntry 5 }

    eqptSubType OBJECT-TYPE
        SYNTAX DisplayString
        ACCESS read-only
        STATUS mandatory
        DESCRIPTION
            "Module sub type."
        ::= { eqptEntry 6 }

    eqptSlipSpeed OBJECT-TYPE
        SYNTAX INTEGER { baud-38000(1), baud-9600(2), na(3) }
        ACCESS read-only
        STATUS mandatory
        DESCRIPTION
            "SLIP speed used to talk to module across backplane."
        ::= { eqptEntry 7 }

    eqptPrimaryState OBJECT-TYPE
        SYNTAX PrimaryState 
        ACCESS read-only
        STATUS mandatory
        DESCRIPTION
            "Primary state of module."
        ::= { eqptEntry 8 }

    eqptSecondaryState OBJECT-TYPE
        SYNTAX SecondaryState
        ACCESS read-only
        STATUS mandatory
        DESCRIPTION
            "Secondary state of module."
        ::= { eqptEntry 9 }

    --
    -- The elements in the pwr subgroup of the configuration group
    --

    pwrTable   OBJECT-TYPE
            SYNTAX  SEQUENCE OF PwrEntry
            ACCESS  not-accessible
            STATUS  mandatory
            DESCRIPTION
                    "Summary table of known power supplies."
            ::= { pwr 1 }

    pwrEntry   OBJECT-TYPE
            SYNTAX  PwrEntry
            ACCESS  not-accessible
            STATUS  mandatory
            DESCRIPTION
                    "Power entry format"
            INDEX   { pwrBay, pwrShelf, pwrId }
            ::= { pwrTable 1 }

    PwrEntry   ::=
            SEQUENCE 
            {
                pwrBay                      INTEGER,
                pwrShelf                    INTEGER,
                pwrCardType                 INTEGER,
                pwrId                       INTEGER,
                pwrPrimaryState             INTEGER,
                pwrSecondaryState           INTEGER
            }

    pwrBay    OBJECT-TYPE
        SYNTAX INTEGER
        ACCESS read-only
        STATUS mandatory
        DESCRIPTION
            "Bay portion of power supplies address."
        ::= { pwrEntry 1 }

    pwrShelf  OBJECT-TYPE
        SYNTAX INTEGER
        ACCESS read-only
        STATUS mandatory
        DESCRIPTION
            "Shelf portion of power supplies address."
        ::= { pwrEntry 2 }

    pwrCardType OBJECT-TYPE
        SYNTAX CardType
        ACCESS read-only
        STATUS mandatory
        DESCRIPTION
            "Power supply type string."
        ::= { pwrEntry 3 }

    pwrId   OBJECT-TYPE
        SYNTAX INTEGER  { a(1), b(2) }
        ACCESS read-only
        STATUS mandatory
        DESCRIPTION
            "Power supply Id."
        ::= { pwrEntry 4 }

    pwrPrimaryState OBJECT-TYPE
        SYNTAX PrimaryState 
        ACCESS read-only
        STATUS mandatory
        DESCRIPTION
            "Primary state of power supply."
        ::= { pwrEntry 5 }

    pwrSecondaryState OBJECT-TYPE
        SYNTAX SecondaryState
        ACCESS read-only
        STATUS mandatory
        DESCRIPTION
            "Secondary state of power supply."
        ::= { pwrEntry 6 }

    --
    -- The elements in the fan subgroup of the configuration group
    --

    fanTable   OBJECT-TYPE
            SYNTAX  SEQUENCE OF FanEntry
            ACCESS  not-accessible
            STATUS  mandatory
            DESCRIPTION
                    "Summary table of known fans."
            ::= { fan 1 }

    fanEntry   OBJECT-TYPE
            SYNTAX  FanEntry
            ACCESS  not-accessible
            STATUS  mandatory
            DESCRIPTION
                    "Fan entry format"
            INDEX   { fanBay, fanShelf, fanId }
            ::= { fanTable 1 }

    FanEntry   ::=
            SEQUENCE 
            {
                fanBay                      INTEGER,
                fanShelf                    INTEGER,
                fanCardType                 INTEGER,
                fanId                       INTEGER,
                fanPrimaryState             INTEGER,
                fanSecondaryState           INTEGER
            }

    fanBay    OBJECT-TYPE
        SYNTAX INTEGER
        ACCESS read-only
        STATUS mandatory
        DESCRIPTION
            "Bay portion of fan address."
        ::= { fanEntry 1 }

    fanShelf  OBJECT-TYPE
        SYNTAX INTEGER
        ACCESS read-only
        STATUS mandatory
        DESCRIPTION
            "Shelf portion of fan address."
        ::= { fanEntry 2 }

    fanCardType OBJECT-TYPE
        SYNTAX CardType
        ACCESS read-only
        STATUS mandatory
        DESCRIPTION
            "Fan type string."
        ::= { fanEntry 3 }

    fanId   OBJECT-TYPE
        SYNTAX INTEGER { a(1), b(2), c(3) }
        ACCESS read-only
        STATUS mandatory
        DESCRIPTION
            "Fan Id."
        ::= { fanEntry 4 }

    fanPrimaryState OBJECT-TYPE
        SYNTAX PrimaryState 
        ACCESS read-only
        STATUS mandatory
        DESCRIPTION
            "Primary state of fan."
        ::= { fanEntry 5 }

    fanSecondaryState OBJECT-TYPE
        SYNTAX SecondaryState
        ACCESS read-only
        STATUS mandatory
        DESCRIPTION
            "Secondary state of fan."
        ::= { fanEntry 6 }

    --
    -- The elements in the trapHost subgroup of the configuration group
    --

    trapHostTable   OBJECT-TYPE
            SYNTAX  SEQUENCE OF TrapHostEntry
            ACCESS  not-accessible
            STATUS  mandatory
            DESCRIPTION
                    "Trap host table."
            ::= { traphost 1 }

    trapHostEntry   OBJECT-TYPE
            SYNTAX  TrapHostEntry
            ACCESS  not-accessible
            STATUS  mandatory
            DESCRIPTION
                    "Trap host entry format."
            INDEX   { gncHostIndex }
            ::= { trapHostTable 1 }

    TrapHostEntry   ::=
            SEQUENCE 
            {
                    gncHostIndex               INTEGER,
                    gncHostAddress             IpAddress,
                    gncHostPort                INTEGER,
                    gncHostTrapCommunity       DisplayString
            }

    gncHostIndex    OBJECT-TYPE
        SYNTAX INTEGER
        ACCESS read-only
        STATUS mandatory
        DESCRIPTION
            "Index of trap host entry."
        ::= { trapHostEntry 1 }

    gncHostAddress    OBJECT-TYPE
        SYNTAX IpAddress
        ACCESS read-write
        STATUS mandatory
        DESCRIPTION
            "Trap host IP address."
        ::= { trapHostEntry 2 }

    gncHostPort    OBJECT-TYPE
        SYNTAX INTEGER (0..65534)
        ACCESS read-write
        STATUS mandatory
        DESCRIPTION
            "Trap host trap port."
        ::= { trapHostEntry 3 }

    gncHostTrapCommunity    OBJECT-TYPE
        SYNTAX DisplayString (SIZE (0..32))
        ACCESS read-write
        STATUS mandatory
        DESCRIPTION
            "Trap host trap community string."
        ::= { trapHostEntry 4 }


    --
    -- The elements in the zms subgroup of the configuration group
    --

    gncZmsConfigSyncExists OBJECT-TYPE
        SYNTAX Boolean
        ACCESS read-only
        STATUS current
        DESCRIPTION
            "Indicates whether or not there exists records to be
            sent to the ZMS config synch manager for changes
            that have been made by CLI/HTTP to the data base."
        ::= { zms 1 }

    
    gncZmsConfigSyncOverflow OBJECT-TYPE
        SYNTAX Boolean
        ACCESS read-only
        STATUS current
        DESCRIPTION
            "Indicates whether or not the device had to discard
            update data base records due to resource constraints.
            If TRUE, traps will be sent to the ZMS Config Synch
            Manager indicating a download of the entire data
            base is required."
        ::= { zms 2 }

    
    gncZmsConfigSyncPriority OBJECT-TYPE
        SYNTAX INTEGER
            {
            none(1),
            low(2),
            medium(3),
            high(4)
            }
        ACCESS read-only
        STATUS current
        DESCRIPTION
            "Indicates the highest priority configuration synchronization trap 
            outstanding. This flag is set to none at boot time and whenever a file
            of synchronization changes has been sent to ZMS. If a parameter change
            has been made to either the same or lower prioirty, the device does
            not have to send a change notification to ZMS. Higher priority
            fields must immediately cause traps to be sent to ZMS."
        ::= { zms 3 }

    
    gncZmsConfigSyncAction OBJECT-TYPE
        SYNTAX INTEGER
            {
            noAction(1),
            createList(2),
            createFullList(3),
            createFullListWithAlarms(4),
            createAlarmsList(5)
            }
        ACCESS read-write
        STATUS current
        DESCRIPTION
            "Used by ZMS when it wants to create a list
            of config synch records. It must first write the
            filename expected and then set the action. The
            create list action allows the device to determine
            whether the complete database (synchoverflow 
            occured) needs to be sent or only those records
            that have been modified. create full list 
            specifies that ZMS would like to receive the
            complete database."
        ::= { zms 4 }

    
    gncZmsConfigSyncFileName OBJECT-TYPE
        SYNTAX ZmsFileName
        ACCESS read-write
        STATUS current
        DESCRIPTION
            "File Name to be used when creating the config
            synch records."
        ::= { zms 5 }

    
    gncZmsConfigSyncStatus OBJECT-TYPE
        SYNTAX INTEGER
            {
            syncComplete(1),
            syncPending(2),
            syncError(3),
            syncInitializing(4)
            }
        ACCESS read-only
        STATUS current
        DESCRIPTION
            "Used by Config Sync Acgent when processing a request
            to create a list of config synch records."
        ::= { zms 6 }

    
    gncZmsConfigSyncUserName OBJECT-TYPE
        SYNTAX ZmsAdminString
        ACCESS read-write
        STATUS current
        DESCRIPTION
            "User Name to be used when sending the config
            synch records.
            
            When read, the last user name is returned. "
        ::= { zms 7 }

    
    gncZmsConfigSyncUserPassword OBJECT-TYPE
        SYNTAX ZmsAdminString
        ACCESS read-write
        STATUS current
        DESCRIPTION
            "Password to be used when sending the config
            synch records. For use in FTP authentication.
            
            When read, always returns the NULL string"
        ::= { zms 8 }

    gncZmsConfigSyncIpAddress OBJECT-TYPE
        SYNTAX IpAddress
        ACCESS read-write
        STATUS current
        DESCRIPTION
            "This is the ZMS IP address for which configuration synchronization 
            messages and any other special handling is performed."
        ::= { zms 9 }

    --
    -- The elements in the moduleInventory subgroup of the configuration group
    --

    invModuleTable   OBJECT-TYPE
            SYNTAX  SEQUENCE OF InvModuleEntry
            ACCESS  not-accessible
            STATUS  mandatory
            DESCRIPTION
                    "Inventory module table"
            ::= { inventory 1 }

    invModuleEntry   OBJECT-TYPE
            SYNTAX  InvModuleEntry
            ACCESS  not-accessible
            STATUS  mandatory
            DESCRIPTION
                    "Inventory entry format."
            INDEX   { eqptBay, eqptShelf, eqptSlot }
            ::= { invModuleTable 1 }

    InvModuleEntry   ::=
            SEQUENCE 
            {
                invModuleSwVersion              DisplayString,
                invModuleHwVersion              DisplayString,
                invModuleCpldVersion            DisplayString,
                invModuleFgpaVersion            DisplayString,
                invModuleMfgDate                DisplayString,
                invModuleSerialNum              DisplayString,
                invModulePartNum                DisplayString,
                invModuleClei                   DisplayString
            }

    invModuleSwVersion   OBJECT-TYPE
        SYNTAX DisplayString
        ACCESS read-only
        STATUS mandatory
        DESCRIPTION
            "Software version of module."
        ::= { invModuleEntry 1 }

    invModuleHwVersion   OBJECT-TYPE
        SYNTAX DisplayString
        ACCESS read-only
        STATUS mandatory
        DESCRIPTION
            "Hardware version of module."
        ::= { invModuleEntry 2 }

    invModuleCpldVersion   OBJECT-TYPE
        SYNTAX DisplayString
        ACCESS read-only
        STATUS mandatory
        DESCRIPTION
            "CPLD version of module."
        ::= { invModuleEntry 3 }

    invModuleFgpaVersion   OBJECT-TYPE
        SYNTAX DisplayString
        ACCESS read-only
        STATUS mandatory
        DESCRIPTION
            "FGPA version of module."
        ::= { invModuleEntry 4 }

    invModuleMfgDate     OBJECT-TYPE
        SYNTAX DisplayString
        ACCESS read-only
        STATUS mandatory
        DESCRIPTION
            "Manufacturing date of module."
        ::= { invModuleEntry 5 }

    invModuleSerialNum   OBJECT-TYPE
        SYNTAX DisplayString
        ACCESS read-only
        STATUS mandatory
        DESCRIPTION
            "Serial number of module."
        ::= { invModuleEntry 6 }

    invModulePartNum     OBJECT-TYPE
        SYNTAX DisplayString
        ACCESS read-only
        STATUS mandatory
        DESCRIPTION
            "Part number of module."
        ::= { invModuleEntry 7 }

    invModuleClei        OBJECT-TYPE
        SYNTAX DisplayString
        ACCESS read-only
        STATUS mandatory
        DESCRIPTION
            "CLEI of module."
        ::= { invModuleEntry 8 }

    --
    -- The elements in the opticalInventory subgroup of the configuration group
    --

    invOpticalTable   OBJECT-TYPE
            SYNTAX  SEQUENCE OF InvOpticalEntry
            ACCESS  not-accessible
            STATUS  mandatory
            DESCRIPTION
                    "Optical inventory module table"
            ::= { inventory 2 }

    invOpticalEntry   OBJECT-TYPE
            SYNTAX  InvOpticalEntry
            ACCESS  not-accessible
            STATUS  mandatory
            DESCRIPTION
                    "Optical inventory entry format."
            INDEX   { eqptBay, eqptShelf, eqptSlot }
            ::= { invOpticalTable 1 }

    InvOpticalEntry   ::=
            SEQUENCE 
            {
                invOpticalSerialNum              DisplayString,
                invOpticalPartNum                DisplayString,
                invOpticalMfgDate                DisplayString,
                invOpticalClei                   DisplayString,
                invOpticalConnectorType          INTEGER,
                invOpticalFiberType              INTEGER,
                invOpticalMediaType              INTEGER,
                invOpticalStatus                 INTEGER
            }

    invOpticalSerialNum   OBJECT-TYPE
        SYNTAX DisplayString
        ACCESS read-only
        STATUS mandatory
        DESCRIPTION
            "Serial number of the optical device."
        ::= { invOpticalEntry 1 }

    invOpticalPartNum     OBJECT-TYPE
        SYNTAX DisplayString
        ACCESS read-only
        STATUS mandatory
        DESCRIPTION
            "Part number of the optical device."
        ::= { invOpticalEntry 2 }

    invOpticalMfgDate     OBJECT-TYPE
        SYNTAX DisplayString
        ACCESS read-only
        STATUS mandatory
        DESCRIPTION
            "Manufacturing date of the optical device."
        ::= { invOpticalEntry 3 }

    invOpticalClei        OBJECT-TYPE
        SYNTAX DisplayString
        ACCESS read-only
        STATUS mandatory
        DESCRIPTION
            "CLEI of the optical device."
        ::= { invOpticalEntry 4 }

    invOpticalConnectorType OBJECT-TYPE
        SYNTAX INTEGER
        ACCESS read-only
        STATUS mandatory
        DESCRIPTION
            "Connector type of the optical device."
        ::= { invOpticalEntry 5 }

    invOpticalFiberType     OBJECT-TYPE
        SYNTAX INTEGER
        ACCESS read-only
        STATUS mandatory
        DESCRIPTION
            "Fiber tpye of the optical device."
        ::= { invOpticalEntry 6 }

    invOpticalMediaType     OBJECT-TYPE
        SYNTAX INTEGER
        ACCESS read-only
        STATUS mandatory
        DESCRIPTION
            "Media type of the optical device"
        ::= { invOpticalEntry 7 }

    invOpticalStatus        OBJECT-TYPE
        SYNTAX INTEGER
        ACCESS read-only
        STATUS mandatory
        DESCRIPTION
            "Status of the optical device."
        ::= { invOpticalEntry 8 }

    --
    -- The elements in the softwareDownload subgroup of the configuration group
    --

    swDlEqptBay   OBJECT-TYPE
        SYNTAX INTEGER
        ACCESS read-write
        STATUS mandatory
        DESCRIPTION
            "Bay of module to receive software."
        ::= { softwareDownload 1 }

    swDlEqptShelf   OBJECT-TYPE
        SYNTAX INTEGER
        ACCESS read-write
        STATUS mandatory
        DESCRIPTION
            "shelf of module to receive software."
        ::= { softwareDownload 2 }

    swDlEqptSlot   OBJECT-TYPE
        SYNTAX INTEGER
        ACCESS read-write
        STATUS mandatory
        DESCRIPTION
            "Slot of module to receive software.  Downloads
             to GNC modules will always be stored as the
             standby image."
        ::= { softwareDownload 3 }

    swDlFtpIpAddress   OBJECT-TYPE
        SYNTAX IpAddress
        ACCESS read-write
        STATUS mandatory
        DESCRIPTION
            "IP address of FTP server."
        ::= { softwareDownload 4 }

    swDlFtpPort     OBJECT-TYPE
        SYNTAX INTEGER
        ACCESS read-write
        STATUS mandatory
        DESCRIPTION
            "Port used for FTP requests on server."
        ::= { softwareDownload 5 }

    swDlFtpLoginId  OBJECT-TYPE
        SYNTAX DisplayString
        ACCESS read-write
        STATUS mandatory
        DESCRIPTION
            "Account login on FTP server."
        ::= { softwareDownload 6 }

    swDlFtpPassword OBJECT-TYPE
        SYNTAX DisplayString
        ACCESS read-write
        STATUS mandatory
        DESCRIPTION
            "Account password on FTP server."
        ::= { softwareDownload 7 }

    swDlFtpFilename OBJECT-TYPE
        SYNTAX DisplayString
        ACCESS read-write
        STATUS mandatory
        DESCRIPTION
            "Path and name of file to be downloaded."
        ::= { softwareDownload 8 }

    swDlStatus     OBJECT-TYPE
        SYNTAX INTEGER
        {
            startDownload(1),
            softwareDownloadInProgress(2),
            softwareDownloadComplete(3),
            softwareDownloadFailed(4),
            moduleDownloadStarted(5),
            moduleDownloadInProgress(6),
            moduleDownloadComplete(7),
            moduleDownloadFailed(8)
        }
        ACCESS read-write
        STATUS mandatory
        DESCRIPTION
            "Software download status.  The FTP transfer is
             initiated when swDlStatus is set to startDownload(1).
             All other swDl fields should be set before transfer
             is initiated. An error will be returned is swDlStatus
             is set to anything other than startDownload(1).  An
             error will also be returned if a download is already 
             in progress when swDlStatus is set."
        ::= { softwareDownload 9 }

    --
    -- The elements in the fpmr subgroup of the cardConfiguration group
    --

    fpmrTable   OBJECT-TYPE
            SYNTAX  SEQUENCE OF FpmrEntry
            ACCESS  not-accessible
            STATUS  mandatory
            DESCRIPTION
                    "FPMR module table"
            ::= { fpmr 1 }

    fpmrEntry   OBJECT-TYPE
            SYNTAX  FpmrEntry
            ACCESS  not-accessible
            STATUS  mandatory
            DESCRIPTION
                    "FPMR entry format."
            INDEX   { eqptBay, eqptShelf, eqptSlot }
            ::= { fpmrTable 1 }

    FpmrEntry   ::=
            SEQUENCE 
            {
                fpmrItuNum                 ItuSelection,
                fpmrPrimaryState           INTEGER,
                fpmrSecondaryState         INTEGER,
                fpmrAdminState             INTEGER
            }

    fpmrItuNum OBJECT-TYPE
        SYNTAX ItuSelection
        ACCESS read-only
        STATUS mandatory
        DESCRIPTION
            "Module supported ITU channel."
        ::= { fpmrEntry 1 }

    fpmrPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { fpmrEntry 2 }

    fpmrSecondaryState OBJECT-TYPE
        SYNTAX SecondaryState
        ACCESS read-only
        STATUS mandatory
        DESCRIPTION
            "Secondary state of module."
        ::= { fpmrEntry 3 }

    fpmrAdminState OBJECT-TYPE
        SYNTAX INTEGER { other(1), reset(2) }
        ACCESS read-write
        STATUS mandatory
        DESCRIPTION
            "Administration state of module.  This field is used
             to reset the module.  Reading this field always 
             returns other(1)."
        ::= { fpmrEntry 4 }

    --
    -- The elements in the fpmrProtnSw subgroup of the configuration group
    --

    fpmrProtnSwTable   OBJECT-TYPE
            SYNTAX  SEQUENCE OF FpmrProtnSwEntry
            ACCESS  not-accessible
            STATUS  mandatory
            DESCRIPTION
                    "FPMR facility table."
            ::= { fpmr 2 }

    fpmrProtnSwEntry   OBJECT-TYPE
            SYNTAX  FpmrProtnSwEntry
            ACCESS  not-accessible
            STATUS  mandatory
            DESCRIPTION
                    "FPMR protection switch entry format"
            INDEX   { eqptBay, eqptShelf, eqptSlot }
            ::= { fpmrProtnSwTable 1 }

    FpmrProtnSwEntry   ::=
            SEQUENCE 
            {
                fpmrProtnSwProtnSwCmd           INTEGER,
                fpmrProtnSwOperationMode        INTEGER,
                fpmrProtnSwOperatingTrunk       INTEGER,
                fpmrProtnSwTrunk1Status         INTEGER,
                fpmrProtnSwTrunk2Status         INTEGER
            }

    fpmrProtnSwProtnSwCmd OBJECT-TYPE
        SYNTAX INTEGER
        {
            clearTrunk1(1),
            clearTrunk2(2),
            lockOutTrunk1(3),
            lockOutTrunk2(4),
            forcedSwitchTrunk1(5),
            forcedSwitchTrunk2(6),
            autoSwitchTrunk1(7),
            autoSwitchTrunk2(8),
            manualSwitchTrunk1(9),
            manualSwitchTrunk2(10)
        }
        ACCESS read-only
        STATUS mandatory
        DESCRIPTION
            ""
        ::= { fpmrProtnSwEntry 1 }

    fpmrProtnSwOperationMode OBJECT-TYPE
        SYNTAX INTEGER
        {
            auto(1),
            frcd(2),
            lockout(3),
            man(4),
            normal(5)
        }
        ACCESS read-only
        STATUS mandatory
        DESCRIPTION
            "FPMR operation mode description:-  
             autoNoRequest(1): Automatic Switch No Request
             lockoutPrequest(2): Lock out of Protection Request
             forceSwitchWtoP(3): Force Switch from working to protection request
             forceSwitchPtoW(4): Force Switch from protection to working request
             manualSwitchWtoP(5): Manual Switch from working to protection request"
        ::= { fpmrProtnSwEntry 2 }

    fpmrProtnSwOperatingTrunk OBJECT-TYPE
        SYNTAX INTEGER { oprTrunk1(1), oprTrunk2(2), unknown(3) }
        ACCESS read-write
        STATUS mandatory
        DESCRIPTION
            "Indicates which trunk is the current working trunk."
        ::= { fpmrProtnSwEntry 3 }

    fpmrProtnSwTrunk1Status OBJECT-TYPE
        SYNTAX INTEGER
        {
            degraded(1),
            failed(2),
            functional(3)
        }
        ACCESS read-write
        STATUS mandatory
        DESCRIPTION
            "State of fiber Working Line for a FPMR module."
        ::= { fpmrProtnSwEntry 4 }

    fpmrProtnSwTrunk2Status OBJECT-TYPE
        SYNTAX INTEGER
        {
            degraded(1),
            failed(2),
            functional(3)
        }
        ACCESS read-only
        STATUS mandatory
        DESCRIPTION
            "State of fiber Protection Line for a FPMR module."
        ::= { fpmrProtnSwEntry 5 }

    --
    -- The elements in the fpmt subgroup of the cardConfiguration group
    --

    fpmtTable   OBJECT-TYPE
            SYNTAX  SEQUENCE OF FpmtEntry
            ACCESS  not-accessible
            STATUS  mandatory
            DESCRIPTION
                    "FPMT module table"
            ::= { fpmt 1 }

    fpmtEntry   OBJECT-TYPE
            SYNTAX  FpmtEntry
            ACCESS  not-accessible
            STATUS  mandatory
            DESCRIPTION
                    "FPMT entry format."
            INDEX   { eqptBay, eqptShelf, eqptSlot }
            ::= { fpmtTable 1 }

    FpmtEntry   ::=
            SEQUENCE 
            {
                fpmtPrimaryState            INTEGER,
                fpmtSecondaryState          INTEGER
            }

    fpmtPrimaryState OBJECT-TYPE
        SYNTAX PrimaryState 
        ACCESS read-write
        STATUS mandatory
        DESCRIPTION
            "Primary state of module."
        ::= { fpmtEntry 1 }

    fpmtSecondaryState OBJECT-TYPE
        SYNTAX SecondaryState
        ACCESS read-only
        STATUS mandatory
        DESCRIPTION
            "Secondary state of module."
        ::= { fpmtEntry 2 }

    --
    -- The elements in the gm10ge10g subgroup of the cardConfiguration group
    --

    gm10ge10gTable   OBJECT-TYPE
            SYNTAX  SEQUENCE OF Gm10ge10gEntry
            ACCESS  not-accessible
            STATUS  mandatory
            DESCRIPTION
                    "GM10GE10G module table"
            ::= { gm10ge10g 1 }

    gm10ge10gEntry   OBJECT-TYPE
            SYNTAX  Gm10ge10gEntry
            ACCESS  not-accessible
            STATUS  mandatory
            DESCRIPTION
                    "GM10GE10G entry format."
            INDEX   { eqptBay, eqptShelf, eqptSlot }
            ::= { gm10ge10gTable 1 }

    Gm10ge10gEntry   ::=
            SEQUENCE 
            {
                gm10ge10gSubType                 DisplayString,
                gm10ge10gItuNum                  ItuSelection2,
                gm10ge10gLbc0                    DisplayString,
                gm10ge10gOpt0                    DisplayString,
                gm10ge10gFarEndAlsd              INTEGER,
                gm10ge10gFarEndAlsdType          INTEGER,
                gm10ge10gPrimaryState            INTEGER,
                gm10ge10gSecondaryState          INTEGER,
                gm10ge10gAdminState              INTEGER,
                gm10ge10gPmStatus                INTEGER
            }

    gm10ge10gSubType OBJECT-TYPE
        SYNTAX DisplayString
        ACCESS read-only
        STATUS mandatory
        DESCRIPTION
            "Module sub type."
        ::= { gm10ge10gEntry 1 }

    gm10ge10gItuNum OBJECT-TYPE
        SYNTAX ItuSelection2
        ACCESS read-write
        STATUS mandatory
        DESCRIPTION
            "Module supported ITU channel."
        ::= { gm10ge10gEntry 2 }

    gm10ge10gLbc0 OBJECT-TYPE
        SYNTAX DisplayString
        ACCESS read-only
        STATUS mandatory
        DESCRIPTION
            "Nominal value of the Laser Bias Current (LBC) in mA."
        ::= { gm10ge10gEntry 3 }

    gm10ge10gOpt0 OBJECT-TYPE
        SYNTAX DisplayString
        ACCESS read-only
        STATUS mandatory
        DESCRIPTION
            "Nominal value of average optical output power of the
             transmitter, or the Optical Power Transmitted (OPT)
             in dBm."
        ::= { gm10ge10gEntry 4 }

    gm10ge10gFarEndAlsd OBJECT-TYPE
        SYNTAX INTEGER { off(1), on(2) }
        ACCESS read-write
        STATUS mandatory
        DESCRIPTION
            "Controls whether Far End ALSD feature is enabled."
        ::= { gm10ge10gEntry 5 }

    gm10ge10gFarEndAlsdType OBJECT-TYPE
        SYNTAX INTEGER
        {
            dedicatedch10(1),
            inband(2)
        }
        ACCESS read-only
        STATUS mandatory
        DESCRIPTION
            "Behavior of the circuit pack to support Far End
             Automatic Laser Shut Down (ALSD) Feature."
        ::= { gm10ge10gEntry 6 }

    gm10ge10gPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gm10ge10gEntry 7 }

    gm10ge10gSecondaryState OBJECT-TYPE
        SYNTAX SecondaryState
        ACCESS read-only
        STATUS mandatory
        DESCRIPTION
            "Secondary state of module."
        ::= { gm10ge10gEntry 8 }

    gm10ge10gAdminState OBJECT-TYPE
        SYNTAX INTEGER { other(1), reset(2) }
        ACCESS read-write
        STATUS mandatory
        DESCRIPTION
            "Administration state of module.  This field is used
             to reset the module.  Reading this field always 
             returns other(1)."
        ::= { gm10ge10gEntry 9 }

    gm10ge10gPmStatus OBJECT-TYPE
        SYNTAX PmState
        ACCESS read-write
        STATUS mandatory
        DESCRIPTION
            "Perfornance monitoring status of module."
        ::= { gm10ge10gEntry 10 }

    --
    -- The elements in the gm10ge10gFacilities subgroup of the configuration group
    --

    gm10ge10gFacTable   OBJECT-TYPE
            SYNTAX  SEQUENCE OF Gm10ge10gFacEntry
            ACCESS  not-accessible
            STATUS  mandatory
            DESCRIPTION
                    "GM10GE10G facility table."
            ::= { gm10ge10g 2 }

    gm10ge10gFacEntry   OBJECT-TYPE
            SYNTAX  Gm10ge10gFacEntry
            ACCESS  not-accessible
            STATUS  mandatory
            DESCRIPTION
                    "GM10GE10G facility entry format"
            INDEX   { eqptBay, eqptShelf, eqptSlot, gm10ge10gFacPort }
            ::= { gm10ge10gFacTable 1 }

    Gm10ge10gFacEntry   ::=
            SEQUENCE 
            {
                gm10ge10gFacPort                    INTEGER,
                gm10ge10gFacAutoNegotiate           INTEGER,
                gm10ge10gFacFlowControl             INTEGER,
                gm10ge10gFacLaserControl            INTEGER,
                gm10ge10gFacFrameErrRateThreshold   INTEGER,
                gm10ge10gFacMaxFrameSize            INTEGER,
                gm10ge10gFacMediaType               INTEGER,
                gm10ge10gFacLinkStatus              INTEGER,
                gm10ge10gFacLinkStatusReason        DisplayString,
                gm10ge10gFacFarEndLinkStatus        INTEGER,
                gm10ge10gFacFarEndLinkStatusReason  DisplayString,
                gm10ge10gFacOpr0                    DisplayString,
                gm10ge10gFacPrimaryState            INTEGER,
                gm10ge10gFacSecondaryState          INTEGER,
                gm10ge10gFacLoopbackState           INTEGER
            }

    gm10ge10gFacPort OBJECT-TYPE
        SYNTAX INTEGER { ch1(1), ch2(2), ch3(3), ch4(4), ch5(5), ch6(6), ch7(7), ch8(8), ch9(9), ch10(10), line(11) }
        ACCESS read-only
        STATUS mandatory
        DESCRIPTION
            "Port portion of GM10GE10G facility address."
        ::= { gm10ge10gFacEntry 1 }

    gm10ge10gFacAutoNegotiate OBJECT-TYPE
        SYNTAX INTEGER { off(1), on(2) }
        ACCESS read-write
        STATUS mandatory
        DESCRIPTION
            "Enable/disable auto negotiation.  Client port only."
        ::= { gm10ge10gFacEntry 2 }

    gm10ge10gFacFlowControl OBJECT-TYPE
        SYNTAX INTEGER { enabled(1), disabled(2) }
        ACCESS read-write
        STATUS mandatory
        DESCRIPTION
            "Enable/disable flow control."
        ::= { gm10ge10gFacEntry 3 }

    gm10ge10gFacLaserControl OBJECT-TYPE
        SYNTAX INTEGER
        {
            apsd(1),
            farEndAlsd(2),
            forcedOFF(3),
            forcedON(4)
        }
        ACCESS read-write
        STATUS mandatory
        DESCRIPTION
            "APSD(1)      : Tx Laser state controlled by APSD rules
                            based on state of local receiver.
             farEndALSD(2): Tx Laser state controlled by APSD rules
                            based on state of local receiver and
                            corresponding Far End receiver also.
             forcedOFF(3) : Tx Laser always OFF.
             forcedON(4)  : Tx Laser always ON. "
        ::= { gm10ge10gFacEntry 4 }

    gm10ge10gFacFrameErrRateThreshold OBJECT-TYPE
        SYNTAX INTEGER
        {
            exp-7(7),
            exp-8(8),
            exp-9(9),
            exp-10(10),
            exp-11(11),
            exp-12(12)
        }
        ACCESS read-write
        STATUS mandatory
        DESCRIPTION
            "Frame Error Rate threshold."
        ::= { gm10ge10gFacEntry 5 }

    gm10ge10gFacMaxFrameSize OBJECT-TYPE
        SYNTAX INTEGER
        ACCESS read-write
        STATUS mandatory
        DESCRIPTION
            "The size of the largest datagram which can be
             sent/received on the interface, specified in
             octets.  For interfaces that are used for
             transmitting network datagrams, this is the size
             of the largest network datagram that can be sent
             on the interface."
        ::= { gm10ge10gFacEntry 6 }

    gm10ge10gFacMediaType OBJECT-TYPE
        SYNTAX INTEGER { lx(1), sx(2), unknown(3) }
        ACCESS read-only
        STATUS mandatory
        DESCRIPTION
            "The type of media."
        ::= { gm10ge10gFacEntry 7 }

    gm10ge10gFacLinkStatus OBJECT-TYPE
        SYNTAX   INTEGER
        {
            up(1),
            down(2)
        }
        ACCESS read-only
        STATUS mandatory
        DESCRIPTION
            "Status of the transceiver.
             faultyOrAbsent: Either Transceiver is not 
                             present or it is faulty.
             disabled: The Transceiver is disabled. 
             linkDown: Link is down.
             linkUp: Link is up."
        ::= { gm10ge10gFacEntry 8 }

    gm10ge10gFacLinkStatusReason OBJECT-TYPE
        SYNTAX DisplayString
        ACCESS read-only
        STATUS mandatory
        DESCRIPTION
            "Cause of Local Link being Down."
        ::= { gm10ge10gFacEntry 9 }

    gm10ge10gFacFarEndLinkStatus OBJECT-TYPE
        SYNTAX  INTEGER
        {
            linkUP(1),
            linkDown(2),
            na(3)
        }
        ACCESS read-only
        STATUS mandatory
        DESCRIPTION
            "Far End Link status.
             linkUp   : Far End Link is up.
             linkDown : Far End Link is down.
             na       : Far End Link information is not-applicable."
        ::= { gm10ge10gFacEntry 10 }

    gm10ge10gFacFarEndLinkStatusReason OBJECT-TYPE
        SYNTAX DisplayString
        ACCESS read-only
        STATUS mandatory
        DESCRIPTION
            "Cause of Far End Link being Down."
        ::= { gm10ge10gFacEntry 11 }

    gm10ge10gFacOpr0 OBJECT-TYPE
        SYNTAX DisplayString
        ACCESS read-write
        STATUS mandatory
        DESCRIPTION
            "Nominal value of average optical output power
             of the received signal, or the Optical Power Received
             (OPR) in dBm."
        ::= { gm10ge10gFacEntry 12 }

    gm10ge10gFacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gm10ge10gFacEntry 13 }

    gm10ge10gFacSecondaryState OBJECT-TYPE
        SYNTAX SecondaryState
        ACCESS read-only
        STATUS mandatory
        DESCRIPTION
            "Secondary state of port."
        ::= { gm10ge10gFacEntry 14 }

    gm10ge10gFacLoopbackState OBJECT-TYPE
        SYNTAX LoopbackState
        ACCESS read-write
        STATUS mandatory
        DESCRIPTION
            "Loopback state of port. Ports must be set OOS before they
             can be placed into loopback."
        ::= { gm10ge10gFacEntry 15 }

    --
    -- The elements in the gm10ge10gEqptPmCurrTable subgroup of the cardConfiguration group
    --

    gm10ge10gEqptPmCurrTable   OBJECT-TYPE
            SYNTAX  SEQUENCE OF Gm10ge10gEqptPmCurrEntry
            ACCESS  not-accessible
            STATUS  mandatory
            DESCRIPTION
                    "GM10GE10G current equipment PM table"
            ::= { gm10ge10g 3 }

    gm10ge10gEqptPmCurrEntry   OBJECT-TYPE
            SYNTAX  Gm10ge10gEqptPmCurrEntry
            ACCESS  not-accessible
            STATUS  mandatory
            DESCRIPTION
                    "GM10GE10G current equipment PM entry format."
            INDEX   { eqptBay, eqptShelf, eqptSlot, gm10ge10gEqptPmCurrType }
            ::= { gm10ge10gEqptPmCurrTable 1 }

    Gm10ge10gEqptPmCurrEntry   ::=
            SEQUENCE 
            {
                gm10ge10gEqptPmCurrType         INTEGER,
                gm10ge10gEqptPmCurrValue        DisplayString,
                gm10ge10gEqptPmCurrValidity     INTEGER,
                gm10ge10gEqptPmCurrLocation     INTEGER,
                gm10ge10gEqptPmCurrDirection    INTEGER,
                gm10ge10gEqptPmCurrDate         DisplayString,
                gm10ge10gEqptPmCurrTime         DisplayString
            }

    gm10ge10gEqptPmCurrType OBJECT-TYPE
        SYNTAX INTEGER { lbc(2), ltemp(4), opt(5) }
        ACCESS read-only
        STATUS mandatory
        DESCRIPTION
            "Current equipment PM type."
        ::= { gm10ge10gEqptPmCurrEntry 1 }

    gm10ge10gEqptPmCurrValue OBJECT-TYPE
        SYNTAX DisplayString
        ACCESS read-only
        STATUS mandatory
        DESCRIPTION
            "Current equipment PM value."
        ::= { gm10ge10gEqptPmCurrEntry 2 }

    gm10ge10gEqptPmCurrValidity OBJECT-TYPE
        SYNTAX INTEGER { false(1), true(2) }
        ACCESS read-only
        STATUS mandatory
        DESCRIPTION
            "Current equipment PM validity."
        ::= { gm10ge10gEqptPmCurrEntry 3 }

    gm10ge10gEqptPmCurrLocation OBJECT-TYPE
        SYNTAX INTEGER { farEnd(1), nearEnd(2) }
        ACCESS read-only
        STATUS mandatory
        DESCRIPTION
            "Current equipment PM location."
        ::= { gm10ge10gEqptPmCurrEntry 4 }

    gm10ge10gEqptPmCurrDirection OBJECT-TYPE
        SYNTAX INTEGER { na(1), rcv(2), trmt(3) }
        ACCESS read-only
        STATUS mandatory
        DESCRIPTION
            "Current equipment PM direction."
        ::= { gm10ge10gEqptPmCurrEntry 5 }

    gm10ge10gEqptPmCurrDate OBJECT-TYPE
        SYNTAX DisplayString
        ACCESS read-only
        STATUS mandatory
        DESCRIPTION
            "Current equipment PM date."
        ::= { gm10ge10gEqptPmCurrEntry 6 }

    gm10ge10gEqptPmCurrTime OBJECT-TYPE
        SYNTAX DisplayString
        ACCESS read-only
        STATUS mandatory
        DESCRIPTION
            "Current equipment PM time."
        ::= { gm10ge10gEqptPmCurrEntry 7 }

    --
    -- The elements in the gm10ge10gEqptPmHistTable subgroup of the cardConfiguration group
    --

    gm10ge10gEqptPmHistTable   OBJECT-TYPE
            SYNTAX  SEQUENCE OF Gm10ge10gEqptPmHistEntry
            ACCESS  not-accessible
            STATUS  mandatory
            DESCRIPTION
                    "GM10GE10G historical equipment PM table"
            ::= { gm10ge10g 4 }

    gm10ge10gEqptPmHistEntry   OBJECT-TYPE
            SYNTAX  Gm10ge10gEqptPmHistEntry
            ACCESS  not-accessible
            STATUS  mandatory
            DESCRIPTION
                    "GM10GE10G historical equipment PM entry format."
            INDEX   { eqptBay, eqptShelf, eqptSlot, gm10ge10gEqptPmHistInterval, gm10ge10gEqptPmHistType }
            ::= { gm10ge10gEqptPmHistTable 1 }

    Gm10ge10gEqptPmHistEntry   ::=
            SEQUENCE 
            {
                gm10ge10gEqptPmHistInterval     INTEGER,
                gm10ge10gEqptPmHistType         INTEGER,
                gm10ge10gEqptPmHistValue        DisplayString,
                gm10ge10gEqptPmHistValidity     INTEGER,
                gm10ge10gEqptPmHistLocation     INTEGER,
                gm10ge10gEqptPmHistDirection    INTEGER,
                gm10ge10gEqptPmHistDate         DisplayString,
                gm10ge10gEqptPmHistTime         DisplayString
            }

    gm10ge10gEqptPmHistInterval OBJECT-TYPE
        SYNTAX INTEGER (1..32)
        ACCESS read-only
        STATUS mandatory
        DESCRIPTION
            "Historical equipment PM interval."
        ::= { gm10ge10gEqptPmHistEntry 1 }

    gm10ge10gEqptPmHistType OBJECT-TYPE
        SYNTAX INTEGER { lbc(2), ltemp(4), opt(5) }
        ACCESS read-only
        STATUS mandatory
        DESCRIPTION
            "Historical equipment PM type."
        ::= { gm10ge10gEqptPmHistEntry 2 }

    gm10ge10gEqptPmHistValue OBJECT-TYPE
        SYNTAX DisplayString
        ACCESS read-only
        STATUS mandatory
        DESCRIPTION
            "Historical equipment PM value."
        ::= { gm10ge10gEqptPmHistEntry 3 }

    gm10ge10gEqptPmHistValidity OBJECT-TYPE
        SYNTAX INTEGER { false(1), true(2) }
        ACCESS read-only
        STATUS mandatory
        DESCRIPTION
            "Historical equipment PM validity."
        ::= { gm10ge10gEqptPmHistEntry 4 }

    gm10ge10gEqptPmHistLocation OBJECT-TYPE
        SYNTAX INTEGER { farEnd(1), nearEnd(2) }
        ACCESS read-only
        STATUS mandatory
        DESCRIPTION
            "Historical equipment PM location."
        ::= { gm10ge10gEqptPmHistEntry 5 }

    gm10ge10gEqptPmHistDirection OBJECT-TYPE
        SYNTAX INTEGER { na(1), rcv(2), trmt(3) }
        ACCESS read-only
        STATUS mandatory
        DESCRIPTION
            "Historical equipment PM direction."
        ::= { gm10ge10gEqptPmHistEntry 6 }

    gm10ge10gEqptPmHistDate OBJECT-TYPE
        SYNTAX DisplayString
        ACCESS read-only
        STATUS mandatory
        DESCRIPTION
            "Historical equipment PM date."
        ::= { gm10ge10gEqptPmHistEntry 7 }

    gm10ge10gEqptPmHistTime OBJECT-TYPE
        SYNTAX DisplayString
        ACCESS read-only
        STATUS mandatory
        DESCRIPTION
            "Historical equipment PM time."
        ::= { gm10ge10gEqptPmHistEntry 8 }

    --
    -- The elements in the gm10ge10gFacPmCurrTable subgroup of the cardConfiguration group
    --

    gm10ge10gFacPmCurrTable   OBJECT-TYPE
            SYNTAX  SEQUENCE OF Gm10ge10gFacPmCurrEntry
            ACCESS  not-accessible
            STATUS  mandatory
            DESCRIPTION
                    "GM10GE10G current facility PM table"
            ::= { gm10ge10g 5 }

    gm10ge10gFacPmCurrEntry   OBJECT-TYPE
            SYNTAX  Gm10ge10gFacPmCurrEntry
            ACCESS  not-accessible
            STATUS  mandatory
            DESCRIPTION
                    "GM10GE10G current facility PM entry format."
            INDEX   { eqptBay, eqptShelf, eqptSlot, gm10ge10gFacPort, gm10ge10gFacPmCurrType }
            ::= { gm10ge10gFacPmCurrTable 1 }

    Gm10ge10gFacPmCurrEntry   ::=
            SEQUENCE 
            {
                gm10ge10gFacPmCurrType         INTEGER,
                gm10ge10gFacPmCurrValue        DisplayString,
                gm10ge10gFacPmCurrOcFacility   INTEGER,
                gm10ge10gFacPmCurrValidity     INTEGER,
                gm10ge10gFacPmCurrLocation     INTEGER,
                gm10ge10gFacPmCurrDirection    INTEGER,
                gm10ge10gFacPmCurrDate         DisplayString,
                gm10ge10gFacPmCurrTime         DisplayString
            }

    gm10ge10gFacPmCurrType OBJECT-TYPE
        SYNTAX INTEGER { opr(8) }
        ACCESS read-only
        STATUS mandatory
        DESCRIPTION
            "Current facility PM type."
        ::= { gm10ge10gFacPmCurrEntry 1 }

    gm10ge10gFacPmCurrValue OBJECT-TYPE
        SYNTAX DisplayString
        ACCESS read-only
        STATUS mandatory
        DESCRIPTION
            "Current facility PM value."
        ::= { gm10ge10gFacPmCurrEntry 2 }

    gm10ge10gFacPmCurrOcFacility OBJECT-TYPE
        SYNTAX INTEGER { oc12(1), oc192(2), oc24(3), oc48(4), oc3(5) }
        ACCESS read-only
        STATUS mandatory
        DESCRIPTION
            "Current facility PM OC facility."
        ::= { gm10ge10gFacPmCurrEntry 3 }

    gm10ge10gFacPmCurrValidity OBJECT-TYPE
        SYNTAX INTEGER { false(1), true(2) }
        ACCESS read-only
        STATUS mandatory
        DESCRIPTION
            "Current facility PM validity."
        ::= { gm10ge10gFacPmCurrEntry 4 }

    gm10ge10gFacPmCurrLocation OBJECT-TYPE
        SYNTAX INTEGER { farEnd(1), nearEnd(2) }
        ACCESS read-only
        STATUS mandatory
        DESCRIPTION
            "Current facility PM location."
        ::= { gm10ge10gFacPmCurrEntry 5 }

    gm10ge10gFacPmCurrDirection OBJECT-TYPE
        SYNTAX INTEGER { na(1), rcv(2), trmt(3) }
        ACCESS read-only
        STATUS mandatory
        DESCRIPTION
            "Current facility PM direction."
        ::= { gm10ge10gFacPmCurrEntry 6 }

    gm10ge10gFacPmCurrDate OBJECT-TYPE
        SYNTAX DisplayString
        ACCESS read-only
        STATUS mandatory
        DESCRIPTION
            "Current facility PM date."
        ::= { gm10ge10gFacPmCurrEntry 7 }

    gm10ge10gFacPmCurrTime OBJECT-TYPE
        SYNTAX DisplayString
        ACCESS read-only
        STATUS mandatory
        DESCRIPTION
            "Current facility PM time."
        ::= { gm10ge10gFacPmCurrEntry 8 }

    --
    -- The elements in the gm10ge10gFacPmHistTable subgroup of the cardConfiguration group
    --

    gm10ge10gFacPmHistTable   OBJECT-TYPE
            SYNTAX  SEQUENCE OF Gm10ge10gFacPmHistEntry
            ACCESS  not-accessible
            STATUS  mandatory
            DESCRIPTION
                    "GM10GE10G historical facility PM table"
            ::= { gm10ge10g 6 }

    gm10ge10gFacPmHistEntry   OBJECT-TYPE
            SYNTAX  Gm10ge10gFacPmHistEntry
            ACCESS  not-accessible
            STATUS  mandatory
            DESCRIPTION
                    "GM10GE10G historical facility PM entry format."
            INDEX   { eqptBay, eqptShelf, eqptSlot, gm10ge10gFacPort, gm10ge10gFacPmHistInterval, gm10ge10gFacPmHistType }
            ::= { gm10ge10gFacPmHistTable 1 }

    Gm10ge10gFacPmHistEntry   ::=
            SEQUENCE 
            {
                gm10ge10gFacPmHistInterval     INTEGER,
                gm10ge10gFacPmHistType         INTEGER,
                gm10ge10gFacPmHistValue        DisplayString,
                gm10ge10gFacPmHistOcFacility   INTEGER,
                gm10ge10gFacPmHistValidity     INTEGER,
                gm10ge10gFacPmHistLocation     INTEGER,
                gm10ge10gFacPmHistDirection    INTEGER,
                gm10ge10gFacPmHistDate         DisplayString,
                gm10ge10gFacPmHistTime         DisplayString
            }

    gm10ge10gFacPmHistInterval OBJECT-TYPE
        SYNTAX INTEGER (1..32)
        ACCESS read-only
        STATUS mandatory
        DESCRIPTION
            "Historical facility PM interval."
        ::= { gm10ge10gFacPmHistEntry 1 }

    gm10ge10gFacPmHistType OBJECT-TYPE
        SYNTAX INTEGER { opr(8) }
        ACCESS read-only
        STATUS mandatory
        DESCRIPTION
            "Historical facility PM type."
        ::= { gm10ge10gFacPmHistEntry 2 }

    gm10ge10gFacPmHistValue OBJECT-TYPE
        SYNTAX DisplayString
        ACCESS read-only
        STATUS mandatory
        DESCRIPTION
            "Historical facility PM value."
        ::= { gm10ge10gFacPmHistEntry 3 }

    gm10ge10gFacPmHistOcFacility OBJECT-TYPE
        SYNTAX INTEGER { oc12(1), oc192(2), oc24(3), oc48(4), oc3(5) }
        ACCESS read-only
        STATUS mandatory
        DESCRIPTION
            "Historical facility PM OC facility."
        ::= { gm10ge10gFacPmHistEntry 4 }

    gm10ge10gFacPmHistValidity OBJECT-TYPE
        SYNTAX INTEGER { false(1), true(2) }
        ACCESS read-only
        STATUS mandatory
        DESCRIPTION
            "Historical facility PM validity."
        ::= { gm10ge10gFacPmHistEntry 5 }

    gm10ge10gFacPmHistLocation OBJECT-TYPE
        SYNTAX INTEGER { farEnd(1), nearEnd(2) }
        ACCESS read-only
        STATUS mandatory
        DESCRIPTION
            "Historical facility PM location."
        ::= { gm10ge10gFacPmHistEntry 6 }

    gm10ge10gFacPmHistDirection OBJECT-TYPE
        SYNTAX INTEGER { na(1), rcv(2), trmt(3) }
        ACCESS read-only
        STATUS mandatory
        DESCRIPTION
            "Historical facility PM direction."
        ::= { gm10ge10gFacPmHistEntry 7 }

    gm10ge10gFacPmHistDate OBJECT-TYPE
        SYNTAX DisplayString
        ACCESS read-only
        STATUS mandatory
        DESCRIPTION
            "Historical facility PM date."
        ::= { gm10ge10gFacPmHistEntry 8 }

    gm10ge10gFacPmHistTime OBJECT-TYPE
        SYNTAX DisplayString
        ACCESS read-only
        STATUS mandatory
        DESCRIPTION
            "Historical facility PM time."
        ::= { gm10ge10gFacPmHistEntry 9 }

    --
    -- The elements in the gm4ge2g5 subgroup of the cardConfiguration group
    --

    gm4ge2g5Table   OBJECT-TYPE
            SYNTAX  SEQUENCE OF Gm4ge2g5Entry
            ACCESS  not-accessible
            STATUS  mandatory
            DESCRIPTION
                    "GM4GE2G5 module table"
            ::= { gm4ge2g5 1 }

    gm4ge2g5Entry   OBJECT-TYPE
            SYNTAX  Gm4ge2g5Entry
            ACCESS  not-accessible
            STATUS  mandatory
            DESCRIPTION
                    "GM4GE2G5 entry format."
            INDEX   { eqptBay, eqptShelf, eqptSlot }
            ::= { gm4ge2g5Table 1 }

    Gm4ge2g5Entry   ::=
            SEQUENCE 
            {
                gm4ge2g5SubType                 DisplayString,
                gm4ge2g5ItuNum                  ItuSelection,
                gm4ge2g5Apsd                    INTEGER,
                gm4ge2g5ApsdMode                INTEGER,
                gm4ge2g5ClockSource             INTEGER,
                gm4ge2g5ClockSelection          INTEGER,
                gm4ge2g5ActiveTimingSource      INTEGER,
                gm4ge2g5Protocol                INTEGER,
                gm4ge2g5PrimaryState            INTEGER,
                gm4ge2g5SecondaryState          INTEGER,
                gm4ge2g5AdminState              INTEGER,
                gm4ge2g5PmStatus                INTEGER
            }

    gm4ge2g5SubType OBJECT-TYPE
        SYNTAX DisplayString
        ACCESS read-only
        STATUS mandatory
        DESCRIPTION
            "Module sub type."
        ::= { gm4ge2g5Entry 1 }

    gm4ge2g5ItuNum OBJECT-TYPE
        SYNTAX ItuSelection
        ACCESS read-only
        STATUS mandatory
        DESCRIPTION
            "Module supported ITU channel."
        ::= { gm4ge2g5Entry 2 }

    gm4ge2g5Apsd      OBJECT-TYPE
        SYNTAX INTEGER { off(1), on(2) }
        ACCESS read-write
        STATUS mandatory
        DESCRIPTION
            "Module Automatic Power Shut Down setting.  The modules's
             primary state must be set OOS to modified this field."
        ::= { gm4ge2g5Entry 3 }

    gm4ge2g5ApsdMode      OBJECT-TYPE
        SYNTAX INTEGER { los(1), losSf(2), losSfSd(3) }
        ACCESS read-write
        STATUS mandatory
        DESCRIPTION
            "Module Automatic Power Shut Down Mode."
        ::= { gm4ge2g5Entry 4 }

    gm4ge2g5ClockSource      OBJECT-TYPE
        SYNTAX INTEGER
        {
            extThruLineInt(1),
            thruExtLineInt(2),
            ext(3),
            thru(4),
            loop(5),
            int(6),
            extLineInt(7),
            lineExtInt(8),
            line(13)
        }
        ACCESS read-write
        STATUS mandatory
        DESCRIPTION
            "Module clock timing source setting."
        ::= { gm4ge2g5Entry 5 }

    gm4ge2g5ClockSelection      OBJECT-TYPE
        SYNTAX INTEGER { auto(1), forced(2) }
        ACCESS read-write
        STATUS mandatory
        DESCRIPTION
            "Module clock timing selection setting.."
        ::= { gm4ge2g5Entry 6 }

    gm4ge2g5ActiveTimingSource    OBJECT-TYPE
        SYNTAX INTEGER
        {
            ext(1),
            int(2),
            line(3),
            loop(4),
            primary(5),
            protect1(6),
            protect2(7),
            thru(8),
            unknown(9)
        }
        ACCESS read-only
        STATUS mandatory
        DESCRIPTION
            "Active timing source for the module."
        ::= { gm4ge2g5Entry 7 }

    gm4ge2g5Protocol  OBJECT-TYPE
        SYNTAX INTEGER { sdh(1), sonet(2) }
        ACCESS read-write
        STATUS mandatory
        DESCRIPTION
            "Module PM reporting protocol."
        ::= { gm4ge2g5Entry 8 }

    gm4ge2g5PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gm4ge2g5Entry 9 }

    gm4ge2g5SecondaryState OBJECT-TYPE
        SYNTAX SecondaryState
        ACCESS read-only
        STATUS mandatory
        DESCRIPTION
            "Secondary state of module."
        ::= { gm4ge2g5Entry 10 }

    gm4ge2g5AdminState OBJECT-TYPE
        SYNTAX INTEGER { other(1), reset(2) }
        ACCESS read-write
        STATUS mandatory
        DESCRIPTION
            "Administration state of module.  This field is used
             to reset the module.  Reading this field always 
             returns other(1)."
        ::= { gm4ge2g5Entry 11 }

    gm4ge2g5PmStatus OBJECT-TYPE
        SYNTAX PmState
        ACCESS read-write
        STATUS mandatory
        DESCRIPTION
            "Perfornance monitoring status of module."
        ::= { gm4ge2g5Entry 12 }

    --
    -- The elements in the gm4ge2g5Facilities subgroup of the configuration group
    --

    gm4ge2g5FacTable   OBJECT-TYPE
            SYNTAX  SEQUENCE OF Gm4ge2g5FacEntry
            ACCESS  not-accessible
            STATUS  mandatory
            DESCRIPTION
                    "GM4GE2G5 facility table."
            ::= { gm4ge2g5 2 }

    gm4ge2g5FacEntry   OBJECT-TYPE
            SYNTAX  Gm4ge2g5FacEntry
            ACCESS  not-accessible
            STATUS  mandatory
            DESCRIPTION
                    "GM4GE2G5 facility entry format"
            INDEX   { eqptBay, eqptShelf, eqptSlot, gm4ge2g5FacPort }
            ::= { gm4ge2g5FacTable 1 }

    Gm4ge2g5FacEntry   ::=
            SEQUENCE 
            {
                gm4ge2g5FacPort                 INTEGER,
                gm4ge2g5FacAutoNegotiate        INTEGER,
                gm4ge2g5FacMaxFrameSize         INTEGER,
                gm4ge2g5FacMACAddress           DisplayString,
                gm4ge2g5FacMediaType            INTEGER,
                gm4ge2g5FacMaxBandwidth         INTEGER,
                gm4ge2g5FacFullDuplex           INTEGER,
                gm4ge2g5FacLinkStatus           INTEGER,
                gm4ge2g5FacFarEndAlsd           INTEGER,
                gm4ge2g5FacFarEndLinkStatus     INTEGER,
                gm4ge2g5FacOpr0                 DisplayString,
                gm4ge2g5FacPrimaryState         INTEGER,
                gm4ge2g5FacSecondaryState       INTEGER,
                gm4ge2g5FacLoopbackState        INTEGER
            }

    gm4ge2g5FacPort OBJECT-TYPE
        SYNTAX INTEGER { ch1(1), ch2(2), ch3(3), ch4(4), line(5) }
        ACCESS read-only
        STATUS mandatory
        DESCRIPTION
            "Port portion of GM4GE2G5 facility address."
        ::= { gm4ge2g5FacEntry 1 }

    gm4ge2g5FacAutoNegotiate OBJECT-TYPE
        SYNTAX INTEGER { off(1), on(2) }
        ACCESS read-write
        STATUS mandatory
        DESCRIPTION
            "Enable/disable auto negotiation."
        ::= { gm4ge2g5FacEntry 2 }

    gm4ge2g5FacMaxFrameSize OBJECT-TYPE
        SYNTAX INTEGER
        ACCESS read-write
        STATUS mandatory
        DESCRIPTION
            "The size of the largest datagram which can be
             sent/received on the interface, specified in
             octets.  For interfaces that are used for
             transmitting network datagrams, this is the size
             of the largest network datagram that can be sent
             on the interface."
        ::= { gm4ge2g5FacEntry 3 }

    gm4ge2g5FacMACAddress OBJECT-TYPE
        SYNTAX DisplayString
        ACCESS read-only
        STATUS mandatory
        DESCRIPTION
            "MAC Address of the port."
        ::= { gm4ge2g5FacEntry 4 }

    gm4ge2g5FacMediaType OBJECT-TYPE
        SYNTAX INTEGER { lx(1), sx(2), unknown(3) }
        ACCESS read-only
        STATUS mandatory
        DESCRIPTION
            "The type of media."
        ::= { gm4ge2g5FacEntry 5 }

    gm4ge2g5FacMaxBandwidth OBJECT-TYPE
        SYNTAX INTEGER
        {
            m0(1),
            m1050(2),
            m150(3),
            m300(4),
            m450(5),
            m600(6),
            m750(7),
            m900(8)
        }
        ACCESS read-write
        STATUS mandatory
        DESCRIPTION
            "The current configured speed of the interface."
        ::= { gm4ge2g5FacEntry 6 }

    gm4ge2g5FacFullDuplex OBJECT-TYPE
        SYNTAX INTEGER { off(1), on(2) }
        ACCESS read-only
        STATUS mandatory
        DESCRIPTION
            "Indicated where interface is in full duplex mode."
        ::= { gm4ge2g5FacEntry 7 }

    gm4ge2g5FacLinkStatus OBJECT-TYPE
        SYNTAX INTEGER { off(1), on(2) }
        ACCESS read-only
        STATUS mandatory
        DESCRIPTION
            "Indicates if the link is up."
        ::= { gm4ge2g5FacEntry 8 }

    gm4ge2g5FacFarEndAlsd OBJECT-TYPE
        SYNTAX INTEGER { off(1), on(2) }
        ACCESS read-write
        STATUS mandatory
        DESCRIPTION
            "Enable/disable Far End Auto Link Shut Down. 
             If enabled in case of loss of link at the corresponding 
             far end port, the local MAC port would be shut down."
        ::= { gm4ge2g5FacEntry 9 }

    gm4ge2g5FacFarEndLinkStatus OBJECT-TYPE
        SYNTAX INTEGER { off(1), on(2) }
        ACCESS read-only
        STATUS mandatory
        DESCRIPTION
            "Indicates if the far end link is up."
        ::= { gm4ge2g5FacEntry 10 }

    gm4ge2g5FacOpr0 OBJECT-TYPE
        SYNTAX DisplayString
        ACCESS read-write
        STATUS mandatory
        DESCRIPTION
            "Nominal value of average optical output power
             of the received signal, or the Optical Power Received
             (OPR) in dBm. The valid range differs based on the
             current port.  The valid range for the line port is
             -28.0 to -8.0.  OPR0 is invalid for all other ports."
        ::= { gm4ge2g5FacEntry 11 }

    gm4ge2g5FacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gm4ge2g5FacEntry 12 }

    gm4ge2g5FacSecondaryState OBJECT-TYPE
        SYNTAX SecondaryState
        ACCESS read-only
        STATUS mandatory
        DESCRIPTION
            "Secondary state of port."
        ::= { gm4ge2g5FacEntry 13 }

    gm4ge2g5FacLoopbackState OBJECT-TYPE
        SYNTAX LoopbackState
        ACCESS read-write
        STATUS mandatory
        DESCRIPTION
            "Loopback state of port. Ports must be set OOS before they
             can be placed into loopback."
        ::= { gm4ge2g5FacEntry 14 }

    --
    -- The elements in the gm4ge2g5EqptPmCurrTable subgroup of the cardConfiguration group
    --

    gm4ge2g5EqptPmCurrTable   OBJECT-TYPE
            SYNTAX  SEQUENCE OF Gm4ge2g5EqptPmCurrEntry
            ACCESS  not-accessible
            STATUS  mandatory
            DESCRIPTION
                    "GM4GE2G5 current equipment PM table"
            ::= { gm4ge2g5 3 }

    gm4ge2g5EqptPmCurrEntry   OBJECT-TYPE
            SYNTAX  Gm4ge2g5EqptPmCurrEntry
            ACCESS  not-accessible
            STATUS  mandatory
            DESCRIPTION
                    "GM4GE2G5 current equipment PM entry format."
            INDEX   { eqptBay, eqptShelf, eqptSlot, gm4ge2g5EqptPmCurrType }
            ::= { gm4ge2g5EqptPmCurrTable 1 }

    Gm4ge2g5EqptPmCurrEntry   ::=
            SEQUENCE 
            {
                gm4ge2g5EqptPmCurrType         INTEGER,
                gm4ge2g5EqptPmCurrValue        DisplayString,
                gm4ge2g5EqptPmCurrValidity     INTEGER,
                gm4ge2g5EqptPmCurrLocation     INTEGER,
                gm4ge2g5EqptPmCurrDirection    INTEGER,
                gm4ge2g5EqptPmCurrDate         DisplayString,
                gm4ge2g5EqptPmCurrTime         DisplayString
            }

    gm4ge2g5EqptPmCurrType OBJECT-TYPE
        SYNTAX INTEGER { lbc(2), ltemp(4), opt(5) }
        ACCESS read-only
        STATUS mandatory
        DESCRIPTION
            "Current equipment PM type."
        ::= { gm4ge2g5EqptPmCurrEntry 1 }

    gm4ge2g5EqptPmCurrValue OBJECT-TYPE
        SYNTAX DisplayString
        ACCESS read-only
        STATUS mandatory
        DESCRIPTION
            "Current equipment PM value."
        ::= { gm4ge2g5EqptPmCurrEntry 2 }

    gm4ge2g5EqptPmCurrValidity OBJECT-TYPE
        SYNTAX INTEGER { false(1), true(2) }
        ACCESS read-only
        STATUS mandatory
        DESCRIPTION
            "Current equipment PM validity."
        ::= { gm4ge2g5EqptPmCurrEntry 3 }

    gm4ge2g5EqptPmCurrLocation OBJECT-TYPE
        SYNTAX INTEGER { farEnd(1), nearEnd(2) }
        ACCESS read-only
        STATUS mandatory
        DESCRIPTION
            "Current equipment PM location."
        ::= { gm4ge2g5EqptPmCurrEntry 4 }

    gm4ge2g5EqptPmCurrDirection OBJECT-TYPE
        SYNTAX INTEGER { na(1), rcv(2), trmt(3) }
        ACCESS read-only
        STATUS mandatory
        DESCRIPTION
            "Current equipment PM direction."
        ::= { gm4ge2g5EqptPmCurrEntry 5 }

    gm4ge2g5EqptPmCurrDate OBJECT-TYPE
        SYNTAX DisplayString
        ACCESS read-only
        STATUS mandatory
        DESCRIPTION
            "Current equipment PM date."
        ::= { gm4ge2g5EqptPmCurrEntry 6 }

    gm4ge2g5EqptPmCurrTime OBJECT-TYPE
        SYNTAX DisplayString
        ACCESS read-only
        STATUS mandatory
        DESCRIPTION
            "Current equipment PM time."
        ::= { gm4ge2g5EqptPmCurrEntry 7 }

    --
    -- The elements in the gm4ge2g5EqptPmHistTable subgroup of the cardConfiguration group
    --

    gm4ge2g5EqptPmHistTable   OBJECT-TYPE
            SYNTAX  SEQUENCE OF Gm4ge2g5EqptPmHistEntry
            ACCESS  not-accessible
            STATUS  mandatory
            DESCRIPTION
                    "GM4GE2G5 historical equipment PM table"
            ::= { gm4ge2g5 4 }

    gm4ge2g5EqptPmHistEntry   OBJECT-TYPE
            SYNTAX  Gm4ge2g5EqptPmHistEntry
            ACCESS  not-accessible
            STATUS  mandatory
            DESCRIPTION
                    "GM4GE2G5 historical equipment PM entry format."
            INDEX   { eqptBay, eqptShelf, eqptSlot, gm4ge2g5EqptPmHistInterval, gm4ge2g5EqptPmHistType }
            ::= { gm4ge2g5EqptPmHistTable 1 }

    Gm4ge2g5EqptPmHistEntry   ::=
            SEQUENCE 
            {
                gm4ge2g5EqptPmHistInterval     INTEGER,
                gm4ge2g5EqptPmHistType         INTEGER,
                gm4ge2g5EqptPmHistValue        DisplayString,
                gm4ge2g5EqptPmHistValidity     INTEGER,
                gm4ge2g5EqptPmHistLocation     INTEGER,
                gm4ge2g5EqptPmHistDirection    INTEGER,
                gm4ge2g5EqptPmHistDate         DisplayString,
                gm4ge2g5EqptPmHistTime         DisplayString
            }

    gm4ge2g5EqptPmHistInterval OBJECT-TYPE
        SYNTAX INTEGER (1..32)
        ACCESS read-only
        STATUS mandatory
        DESCRIPTION
            "Historical equipment PM interval."
        ::= { gm4ge2g5EqptPmHistEntry 1 }

    gm4ge2g5EqptPmHistType OBJECT-TYPE
        SYNTAX INTEGER { lbc(2), ltemp(4), opt(5) }
        ACCESS read-only
        STATUS mandatory
        DESCRIPTION
            "Historical equipment PM type."
        ::= { gm4ge2g5EqptPmHistEntry 2 }

    gm4ge2g5EqptPmHistValue OBJECT-TYPE
        SYNTAX DisplayString
        ACCESS read-only
        STATUS mandatory
        DESCRIPTION
            "Historical equipment PM value."
        ::= { gm4ge2g5EqptPmHistEntry 3 }

    gm4ge2g5EqptPmHistValidity OBJECT-TYPE
        SYNTAX INTEGER { false(1), true(2) }
        ACCESS read-only
        STATUS mandatory
        DESCRIPTION
            "Historical equipment PM validity."
        ::= { gm4ge2g5EqptPmHistEntry 4 }

    gm4ge2g5EqptPmHistLocation OBJECT-TYPE
        SYNTAX INTEGER { farEnd(1), nearEnd(2) }
        ACCESS read-only
        STATUS mandatory
        DESCRIPTION
            "Historical equipment PM location."
        ::= { gm4ge2g5EqptPmHistEntry 5 }

    gm4ge2g5EqptPmHistDirection OBJECT-TYPE
        SYNTAX INTEGER { na(1), rcv(2), trmt(3) }
        ACCESS read-only
        STATUS mandatory
        DESCRIPTION
            "Historical equipment PM direction."
        ::= { gm4ge2g5EqptPmHistEntry 6 }

    gm4ge2g5EqptPmHistDate OBJECT-TYPE
        SYNTAX DisplayString
        ACCESS read-only
        STATUS mandatory
        DESCRIPTION
            "Historical equipment PM date."
        ::= { gm4ge2g5EqptPmHistEntry 7 }

    gm4ge2g5EqptPmHistTime OBJECT-TYPE
        SYNTAX DisplayString
        ACCESS read-only
        STATUS mandatory
        DESCRIPTION
            "Historical equipment PM time."
        ::= { gm4ge2g5EqptPmHistEntry 8 }

    --
    -- The elements in the gm4ge2g5FacPmCurrTable subgroup of the cardConfiguration group
    --

    gm4ge2g5FacPmCurrTable   OBJECT-TYPE
            SYNTAX  SEQUENCE OF Gm4ge2g5FacPmCurrEntry
            ACCESS  not-accessible
            STATUS  mandatory
            DESCRIPTION
                    "GM4GE2G5 current facility PM table"
            ::= { gm4ge2g5 5 }

    gm4ge2g5FacPmCurrEntry   OBJECT-TYPE
            SYNTAX  Gm4ge2g5FacPmCurrEntry
            ACCESS  not-accessible
            STATUS  mandatory
            DESCRIPTION
                    "GM4GE2G5 current facility PM entry format."
            INDEX   { eqptBay, eqptShelf, eqptSlot, gm4ge2g5FacPort, gm4ge2g5FacPmCurrType }
            ::= { gm4ge2g5FacPmCurrTable 1 }

    Gm4ge2g5FacPmCurrEntry   ::=
            SEQUENCE 
            {
                gm4ge2g5FacPmCurrType         INTEGER,
                gm4ge2g5FacPmCurrValue        DisplayString,
                gm4ge2g5FacPmCurrOcFacility   INTEGER,
                gm4ge2g5FacPmCurrValidity     INTEGER,
                gm4ge2g5FacPmCurrLocation     INTEGER,
                gm4ge2g5FacPmCurrDirection    INTEGER,
                gm4ge2g5FacPmCurrDate         DisplayString,
                gm4ge2g5FacPmCurrTime         DisplayString
            }

    gm4ge2g5FacPmCurrType OBJECT-TYPE
        SYNTAX INTEGER { cvs(4), ess(5), opr(8), sefss(11), sess(12) }
        ACCESS read-only
        STATUS mandatory
        DESCRIPTION
            "Current facility PM type."
        ::= { gm4ge2g5FacPmCurrEntry 1 }

    gm4ge2g5FacPmCurrValue OBJECT-TYPE
        SYNTAX DisplayString
        ACCESS read-only
        STATUS mandatory
        DESCRIPTION
            "Current facility PM value."
        ::= { gm4ge2g5FacPmCurrEntry 2 }

    gm4ge2g5FacPmCurrOcFacility OBJECT-TYPE
        SYNTAX INTEGER { oc12(1), oc192(2), oc24(3), oc48(4), oc3(5) }
        ACCESS read-only
        STATUS mandatory
        DESCRIPTION
            "Current facility PM OC facility."
        ::= { gm4ge2g5FacPmCurrEntry 3 }

    gm4ge2g5FacPmCurrValidity OBJECT-TYPE
        SYNTAX INTEGER { false(1), true(2) }
        ACCESS read-only
        STATUS mandatory
        DESCRIPTION
            "Current facility PM validity."
        ::= { gm4ge2g5FacPmCurrEntry 4 }

    gm4ge2g5FacPmCurrLocation OBJECT-TYPE
        SYNTAX INTEGER { farEnd(1), nearEnd(2) }
        ACCESS read-only
        STATUS mandatory
        DESCRIPTION
            "Current facility PM location."
        ::= { gm4ge2g5FacPmCurrEntry 5 }

    gm4ge2g5FacPmCurrDirection OBJECT-TYPE
        SYNTAX INTEGER { na(1), rcv(2), trmt(3) }
        ACCESS read-only
        STATUS mandatory
        DESCRIPTION
            "Current facility PM direction."
        ::= { gm4ge2g5FacPmCurrEntry 6 }

    gm4ge2g5FacPmCurrDate OBJECT-TYPE
        SYNTAX DisplayString
        ACCESS read-only
        STATUS mandatory
        DESCRIPTION
            "Current facility PM date."
        ::= { gm4ge2g5FacPmCurrEntry 7 }

    gm4ge2g5FacPmCurrTime OBJECT-TYPE
        SYNTAX DisplayString
        ACCESS read-only
        STATUS mandatory
        DESCRIPTION
            "Current facility PM time."
        ::= { gm4ge2g5FacPmCurrEntry 8 }

    --
    -- The elements in the gm4ge2g5FacPmHistTable subgroup of the cardConfiguration group
    --

    gm4ge2g5FacPmHistTable   OBJECT-TYPE
            SYNTAX  SEQUENCE OF Gm4ge2g5FacPmHistEntry
            ACCESS  not-accessible
            STATUS  mandatory
            DESCRIPTION
                    "GM4GE2G5 historical facility PM table"
            ::= { gm4ge2g5 6 }

    gm4ge2g5FacPmHistEntry   OBJECT-TYPE
            SYNTAX  Gm4ge2g5FacPmHistEntry
            ACCESS  not-accessible
            STATUS  mandatory
            DESCRIPTION
                    "GM4GE2G5 historical facility PM entry format."
            INDEX   { eqptBay, eqptShelf, eqptSlot, gm4ge2g5FacPort, gm4ge2g5FacPmHistInterval, gm4ge2g5FacPmHistType }
            ::= { gm4ge2g5FacPmHistTable 1 }

    Gm4ge2g5FacPmHistEntry   ::=
            SEQUENCE 
            {
                gm4ge2g5FacPmHistInterval     INTEGER,
                gm4ge2g5FacPmHistType         INTEGER,
                gm4ge2g5FacPmHistValue        DisplayString,
                gm4ge2g5FacPmHistOcFacility   INTEGER,
                gm4ge2g5FacPmHistValidity     INTEGER,
                gm4ge2g5FacPmHistLocation     INTEGER,
                gm4ge2g5FacPmHistDirection    INTEGER,
                gm4ge2g5FacPmHistDate         DisplayString,
                gm4ge2g5FacPmHistTime         DisplayString
            }

    gm4ge2g5FacPmHistInterval OBJECT-TYPE
        SYNTAX INTEGER (1..32)
        ACCESS read-only
        STATUS mandatory
        DESCRIPTION
            "Historical facility PM interval."
        ::= { gm4ge2g5FacPmHistEntry 1 }

    gm4ge2g5FacPmHistType OBJECT-TYPE
        SYNTAX INTEGER { cvs(4), ess(5), opr(8), sefss(11), sess(12) }
        ACCESS read-only
        STATUS mandatory
        DESCRIPTION
            "Historical facility PM type."
        ::= { gm4ge2g5FacPmHistEntry 2 }

    gm4ge2g5FacPmHistValue OBJECT-TYPE
        SYNTAX DisplayString
        ACCESS read-only
        STATUS mandatory
        DESCRIPTION
            "Historical facility PM value."
        ::= { gm4ge2g5FacPmHistEntry 3 }

    gm4ge2g5FacPmHistOcFacility OBJECT-TYPE
        SYNTAX INTEGER { oc12(1), oc192(2), oc24(3), oc48(4), oc3(5) }
        ACCESS read-only
        STATUS mandatory
        DESCRIPTION
            "Historical facility PM OC facility."
        ::= { gm4ge2g5FacPmHistEntry 4 }

    gm4ge2g5FacPmHistValidity OBJECT-TYPE
        SYNTAX INTEGER { false(1), true(2) }
        ACCESS read-only
        STATUS mandatory
        DESCRIPTION
            "Historical facility PM validity."
        ::= { gm4ge2g5FacPmHistEntry 5 }

    gm4ge2g5FacPmHistLocation OBJECT-TYPE
        SYNTAX INTEGER { farEnd(1), nearEnd(2) }
        ACCESS read-only
        STATUS mandatory
        DESCRIPTION
            "Historical facility PM location."
        ::= { gm4ge2g5FacPmHistEntry 6 }

    gm4ge2g5FacPmHistDirection OBJECT-TYPE
        SYNTAX INTEGER { na(1), rcv(2), trmt(3) }
        ACCESS read-only
        STATUS mandatory
        DESCRIPTION
            "Historical facility PM direction."
        ::= { gm4ge2g5FacPmHistEntry 7 }

    gm4ge2g5FacPmHistDate OBJECT-TYPE
        SYNTAX DisplayString
        ACCESS read-only
        STATUS mandatory
        DESCRIPTION
            "Historical facility PM date."
        ::= { gm4ge2g5FacPmHistEntry 8 }

    gm4ge2g5FacPmHistTime OBJECT-TYPE
        SYNTAX DisplayString
        ACCESS read-only
        STATUS mandatory
        DESCRIPTION
            "Historical facility PM time."
        ::= { gm4ge2g5FacPmHistEntry 9 }

    --
    -- The elements in the gmad subgroup of the cardConfiguration group
    --

    gmadTable   OBJECT-TYPE
            SYNTAX  SEQUENCE OF GmadEntry
            ACCESS  not-accessible
            STATUS  mandatory
            DESCRIPTION
                    "GMAD module table"
            ::= { gmad 1 }

    gmadEntry   OBJECT-TYPE
            SYNTAX  GmadEntry
            ACCESS  not-accessible
            STATUS  mandatory
            DESCRIPTION
                    "GMAD entry format."
            INDEX   { eqptBay, eqptShelf, eqptSlot }
            ::= { gmadTable 1 }

    GmadEntry   ::=
            SEQUENCE 
            {
                gmadItuNum                 ItuSelection,
                gmadPrimaryState           INTEGER,
                gmadSecondaryState         INTEGER
            }

    gmadItuNum OBJECT-TYPE
        SYNTAX ItuSelection
        ACCESS read-only
        STATUS mandatory
        DESCRIPTION
            "Module supported ITU channel."
        ::= { gmadEntry 1 }

    gmadPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmadEntry 2 }

    gmadSecondaryState OBJECT-TYPE
        SYNTAX SecondaryState
        ACCESS read-only
        STATUS mandatory
        DESCRIPTION
            "Secondary state of module."
        ::= { gmadEntry 3 }

    --
    -- The elements in the gmad100 subgroup of the cardConfiguration group
    --

    gmad100Table   OBJECT-TYPE
            SYNTAX  SEQUENCE OF Gmad100Entry
            ACCESS  not-accessible
            STATUS  mandatory
            DESCRIPTION
                    "GMAD100 module table"
            ::= { gmad100 1 }

    gmad100Entry   OBJECT-TYPE
            SYNTAX  Gmad100Entry
            ACCESS  not-accessible
            STATUS  mandatory
            DESCRIPTION
                    "GMAD100 entry format."
            INDEX   { eqptBay, eqptShelf, eqptSlot }
            ::= { gmad100Table 1 }

    Gmad100Entry   ::=
            SEQUENCE 
            {
                gmad100ICoreId              DisplayString,
                gmad100PrimaryState         INTEGER,
                gmad100SecondaryState       INTEGER,
                gmad100AdminState           INTEGER
            }

    gmad100ICoreId OBJECT-TYPE
        SYNTAX DisplayString
        ACCESS read-only
        STATUS mandatory
        DESCRIPTION
            "Module ICore Id."
        ::= { gmad100Entry 1 }

    gmad100PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmad100Entry 2 }

    gmad100SecondaryState OBJECT-TYPE
        SYNTAX SecondaryState
        ACCESS read-only
        STATUS mandatory
        DESCRIPTION
            "Secondary state of module."
        ::= { gmad100Entry 3 }

    gmad100AdminState OBJECT-TYPE
        SYNTAX INTEGER { other(1), reset(2) }
        ACCESS read-write
        STATUS mandatory
        DESCRIPTION
            "Administration state of module.  This field is used
             to reset the module.  Reading this field always 
             returns other(1)."
        ::= { gmad100Entry 4 }

    --
    -- The elements in the gmad100Facilities subgroup of the configuration group
    --

    gmad100FacTable   OBJECT-TYPE
            SYNTAX  SEQUENCE OF Gmad100FacEntry
            ACCESS  not-accessible
            STATUS  mandatory
            DESCRIPTION
                    "GMAD100 facility table."
            ::= { gmad100 2 }

    gmad100FacEntry   OBJECT-TYPE
            SYNTAX  Gmad100FacEntry
            ACCESS  not-accessible
            STATUS  mandatory
            DESCRIPTION
                    "GMAD100 facility entry format"
            INDEX   { eqptBay, eqptShelf, eqptSlot, gmad100FacPort }
            ::= { gmad100FacTable 1 }

    Gmad100FacEntry   ::=
            SEQUENCE 
            {
                gmad100FacPort              INTEGER,
                gmad100FacDescription       DisplayString,
                gmad100FacInsertionLoss     DisplayString
            }

    gmad100FacPort OBJECT-TYPE
        SYNTAX INTEGER (1..4)
        ACCESS read-only
        STATUS mandatory
        DESCRIPTION
            "Facility index."
        ::= { gmad100FacEntry 1 }

    gmad100FacDescription OBJECT-TYPE
        SYNTAX DisplayString
        ACCESS read-only
        STATUS mandatory
        DESCRIPTION
            "Facility description."
        ::= { gmad100FacEntry 2 }

    gmad100FacInsertionLoss OBJECT-TYPE
        SYNTAX DisplayString
        ACCESS read-only
        STATUS mandatory
        DESCRIPTION
            "Value of the path Insertion Loss."
        ::= { gmad100FacEntry 3 }

    --
    -- The elements in the gmbp subgroup of the cardConfiguration group
    --

    gmbpTable   OBJECT-TYPE
            SYNTAX  SEQUENCE OF GmbpEntry
            ACCESS  not-accessible
            STATUS  mandatory
            DESCRIPTION
                    "GMBP module table"
            ::= { gmbp 1 }

    gmbpEntry   OBJECT-TYPE
            SYNTAX  GmbpEntry
            ACCESS  not-accessible
            STATUS  mandatory
            DESCRIPTION
                    "GMBP entry format."
            INDEX   { eqptBay, eqptShelf, eqptSlot }
            ::= { gmbpTable 1 }

    GmbpEntry   ::=
            SEQUENCE 
            {
                gmbpGroupId                INTEGER,
                gmbpPrimaryState           INTEGER,
                gmbpSecondaryState         INTEGER,
                gmbpAdminState             INTEGER
            }

    gmbpGroupId OBJECT-TYPE
        SYNTAX INTEGER { a(1),  b(3),  c(4),  d(5),  e(6),  f(8),  g(9),  h(10),
                         i(11), j(13), k(14), l(15), m(16), n(18), o(19), p(20) }
        ACCESS read-only
        STATUS mandatory
        DESCRIPTION
            "Module group Id."
        ::= { gmbpEntry 1 }

    gmbpPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmbpEntry 2 }

    gmbpSecondaryState OBJECT-TYPE
        SYNTAX SecondaryState
        ACCESS read-only
        STATUS mandatory
        DESCRIPTION
            "Secondary state of module."
        ::= { gmbpEntry 3 }

    gmbpAdminState OBJECT-TYPE
        SYNTAX INTEGER { other(1), reset(2) }
        ACCESS read-write
        STATUS mandatory
        DESCRIPTION
            "Administration state of module.  This field is used
             to reset the module.  Reading this field always 
             returns other(1)."
        ::= { gmbpEntry 4 }

    --
    -- The elements in the gmbpFacilities subgroup of the configuration group
    --

    gmbpFacTable   OBJECT-TYPE
            SYNTAX  SEQUENCE OF GmbpFacEntry
            ACCESS  not-accessible
            STATUS  mandatory
            DESCRIPTION
                    "GMBP facility table."
            ::= { gmbp 2 }

    gmbpFacEntry   OBJECT-TYPE
            SYNTAX  GmbpFacEntry
            ACCESS  not-accessible
            STATUS  mandatory
            DESCRIPTION
                    "GMBP facility entry format"
            INDEX   { eqptBay, eqptShelf, eqptSlot, gmbpFacPort }
            ::= { gmbpFacTable 1 }

    GmbpFacEntry   ::=
            SEQUENCE 
            {
                gmbpFacPort             INTEGER,
                gmbpFacDescription      DisplayString,
                gmbpFacInsertionLoss    DisplayString
            }

    gmbpFacPort OBJECT-TYPE
        SYNTAX INTEGER (1..8)
        ACCESS read-only
        STATUS mandatory
        DESCRIPTION
            "Facility index."
        ::= { gmbpFacEntry 1 }

    gmbpFacDescription OBJECT-TYPE
        SYNTAX DisplayString
        ACCESS read-only
        STATUS mandatory
        DESCRIPTION
            "Facility description."
        ::= { gmbpFacEntry 2 }

    gmbpFacInsertionLoss OBJECT-TYPE
        SYNTAX DisplayString
        ACCESS read-only
        STATUS mandatory
        DESCRIPTION
            "Value of the path Insertion Loss."
        ::= { gmbpFacEntry 3 }

    --
    -- The elements in the gmcr10g subgroup of the cardConfiguration group
    --

    gmcr10gTable   OBJECT-TYPE
            SYNTAX  SEQUENCE OF Gmcr10gEntry
            ACCESS  not-accessible
            STATUS  mandatory
            DESCRIPTION
                    "GMCR10G module table"
            ::= { gmcr10g 1 }

    gmcr10gEntry   OBJECT-TYPE
            SYNTAX  Gmcr10gEntry
            ACCESS  not-accessible
            STATUS  mandatory
            DESCRIPTION
                    "GMCR10G entry format."
            INDEX   { eqptBay, eqptShelf, eqptSlot }
            ::= { gmcr10gTable 1 }

    Gmcr10gEntry   ::=
            SEQUENCE 
            {
                gmcr10gSubType                 DisplayString,
                gmcr10gItuNum                  ItuSelection2,
                gmcr10gApsd                    INTEGER,
                gmcr10gClockSource             INTEGER,
                gmcr10gClockSelection          INTEGER,
                gmcr10gProtocol                INTEGER,
                gmcr10gPrimaryState            INTEGER,
                gmcr10gSecondaryState          INTEGER,
                gmcr10gAdminState              INTEGER,
                gmcr10gPmStatus                INTEGER
            }

    gmcr10gSubType OBJECT-TYPE
        SYNTAX DisplayString
        ACCESS read-only
        STATUS mandatory
        DESCRIPTION
            "Module sub type."
        ::= { gmcr10gEntry 1 }

    gmcr10gItuNum    OBJECT-TYPE
        SYNTAX ItuSelection2
        ACCESS read-write
        STATUS mandatory
        DESCRIPTION
            "Module supported ITU channel.  This field is setable
             for modules with LWT subtype only.  Setting this field 
             for modules with any other subtype will return an error."
        ::= { gmcr10gEntry 2 }

    gmcr10gApsd      OBJECT-TYPE
        SYNTAX INTEGER { off(1), on(2) }
        ACCESS read-write
        STATUS mandatory
        DESCRIPTION
            "Module Automatic Power Shut Down setting.  The modules's
             primary state must be set OOS to modified this field."
        ::= { gmcr10gEntry 3 }

    gmcr10gClockSource      OBJECT-TYPE
        SYNTAX INTEGER
        {
            extThruLineInt(1),
            thruExtLineInt(2),
            ext(3),
            thru(4),
            loop(5),
            int(6),
            extLineInt(7),
            lineExtInt(8),
            line(13)
        }
        ACCESS read-write
        STATUS mandatory
        DESCRIPTION
            "Module clock timing source setting."
        ::= { gmcr10gEntry 4 }

    gmcr10gClockSelection      OBJECT-TYPE
        SYNTAX INTEGER { auto(1), forced(2) }
        ACCESS read-only
        STATUS mandatory
        DESCRIPTION
            "Module clock timing selection setting.."
        ::= { gmcr10gEntry 5 }

    gmcr10gProtocol  OBJECT-TYPE
        SYNTAX INTEGER { sdh(1), sonet(2) }
        ACCESS read-write
        STATUS mandatory
        DESCRIPTION
            "Module PM reporting protocol."
        ::= { gmcr10gEntry 6 }

    gmcr10gPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmcr10gEntry 7 }

    gmcr10gSecondaryState OBJECT-TYPE
        SYNTAX SecondaryState
        ACCESS read-only
        STATUS mandatory
        DESCRIPTION
            "Secondary state of module."
        ::= { gmcr10gEntry 8 }

    gmcr10gAdminState OBJECT-TYPE
        SYNTAX INTEGER { other(1), reset(2) }
        ACCESS read-write
        STATUS mandatory
        DESCRIPTION
            "Administration state of module.  This field is used
             to reset the module.  Reading this field always 
             returns other(1)."
        ::= { gmcr10gEntry 9 }

    gmcr10gPmStatus OBJECT-TYPE
        SYNTAX PmState
        ACCESS read-write
        STATUS mandatory
        DESCRIPTION
            "Performance monitoring status of module."
        ::= { gmcr10gEntry 10 }

    --
    -- The elements in the gmcr10gFacilities subgroup of the configuration group
    --

    gmcr10gFacTable   OBJECT-TYPE
            SYNTAX  SEQUENCE OF Gmcr10gFacEntry
            ACCESS  not-accessible
            STATUS  mandatory
            DESCRIPTION
                    "GMCR10G facility table."
            ::= { gmcr10g 2 }

    gmcr10gFacEntry   OBJECT-TYPE
            SYNTAX  Gmcr10gFacEntry
            ACCESS  not-accessible
            STATUS  mandatory
            DESCRIPTION
                    "GMCR10G facility entry format"
            INDEX   { eqptBay, eqptShelf, eqptSlot, gmcr10gFacPort }
            ::= { gmcr10gFacTable 1 }

    Gmcr10gFacEntry   ::=
            SEQUENCE 
            {
                gmcr10gFacPort             INTEGER,
                gmcr10gFacOpr0             DisplayString,
                gmcr10gFacSdTh             DisplayString,
                gmcr10gFacSfTh             DisplayString,
                gmcr10gFacPrimaryState     INTEGER,
                gmcr10gFacSecondaryState   INTEGER,
                gmcr10gFacLoopbackState    INTEGER,
                gmcr10gFacOpr              DisplayString,
                gmcr10gFacOprLowTh         DisplayString,
                gmcr10gFacOprHighTh        DisplayString
            }

    gmcr10gFacPort OBJECT-TYPE
        SYNTAX INTEGER { cpe(1), line(2) }
        ACCESS read-only
        STATUS mandatory
        DESCRIPTION
            "Port portion of GMCR10G facility address."
        ::= { gmcr10gFacEntry 1 }

    gmcr10gFacOpr0 OBJECT-TYPE
        SYNTAX DisplayString
        ACCESS read-write
        STATUS mandatory
        DESCRIPTION
            "Nominal value of average optical output power
             of the received signal, or the Optical Power Received
             (OPR) in dBm. The valid range differs based on the
             port. Valid range for the CPE port is -18.0 to 1.0.
             The valid range for the Line port is -26 to -6."
        ::= { gmcr10gFacEntry 2 }

    gmcr10gFacSdTh      OBJECT-TYPE
        SYNTAX DisplayString
        ACCESS read-write
        STATUS mandatory
        DESCRIPTION
            "B2 error rate threshold for SD. Entry format is 10e-<exp>.
             Where exp is a value between 5 and 12.  I.e., 10e-11"
        ::= { gmcr10gFacEntry 3 }

    gmcr10gFacSfTh    OBJECT-TYPE
        SYNTAX DisplayString
        ACCESS read-write
        STATUS mandatory
        DESCRIPTION
            "B2 error rate threshold for SF. Entry format is 10e-<exp>.
             Where exp is a value between 3 and 9.  I.e., 10e-8"
        ::= { gmcr10gFacEntry 4 }

    gmcr10gFacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmcr10gFacEntry 5 }

    gmcr10gFacSecondaryState OBJECT-TYPE
        SYNTAX SecondaryState
        ACCESS read-only
        STATUS mandatory
        DESCRIPTION
            "Secondary state of port."
        ::= { gmcr10gFacEntry 6 }

    gmcr10gFacLoopbackState OBJECT-TYPE
        SYNTAX LoopbackState
        ACCESS read-write
        STATUS mandatory
        DESCRIPTION
            "Loopback state of port. Ports must be set OOS before
             they can be placed into loopback."
        ::= { gmcr10gFacEntry 7 }

    gmcr10gFacOpr OBJECT-TYPE
        SYNTAX DisplayString
        ACCESS read-only
        STATUS mandatory
        DESCRIPTION
            "Nominal value of average optical output power
             of the received signal, or the Optical Power Received
             (OPR) in dBm. gmcr10gFacOpr is valid for port line(1or2)
             only."  
        ::= { gmcr10gFacEntry 8 }

    gmcr10gFacOprLowTh OBJECT-TYPE
        SYNTAX DisplayString
        ACCESS read-write
        STATUS mandatory
        DESCRIPTION
            "Threshold value of OPRlow in dBm.
             The valid range is Min. -20.0 dBm to Max. -0.4 dBm."
        ::= { gmcr10gFacEntry 9 }

    gmcr10gFacOprHighTh OBJECT-TYPE
        SYNTAX DisplayString
        ACCESS read-write
        STATUS mandatory
        DESCRIPTION
            "Threshold value of OPR high in dBm.
             The valid range is Min. 0.4 dBm to Max. 20.0 dBm."
        ::= { gmcr10gFacEntry 10 }

    --
    -- The elements in the gmcr10gEqptPmCurrTable subgroup of the cardConfiguration group
    --

    gmcr10gEqptPmCurrTable   OBJECT-TYPE
            SYNTAX  SEQUENCE OF Gmcr10gEqptPmCurrEntry
            ACCESS  not-accessible
            STATUS  mandatory
            DESCRIPTION
                    "GMCR10G current equipment PM table"
            ::= { gmcr10g 3 }

    gmcr10gEqptPmCurrEntry   OBJECT-TYPE
            SYNTAX  Gmcr10gEqptPmCurrEntry
            ACCESS  not-accessible
            STATUS  mandatory
            DESCRIPTION
                    "GMCR10G current equipment PM entry format."
            INDEX   { eqptBay, eqptShelf, eqptSlot, gmcr10gEqptPmCurrType }
            ::= { gmcr10gEqptPmCurrTable 1 }

    Gmcr10gEqptPmCurrEntry   ::=
            SEQUENCE 
            {
                gmcr10gEqptPmCurrType         INTEGER,
                gmcr10gEqptPmCurrValue        DisplayString,
                gmcr10gEqptPmCurrValidity     INTEGER,
                gmcr10gEqptPmCurrLocation     INTEGER,
                gmcr10gEqptPmCurrDirection    INTEGER,
                gmcr10gEqptPmCurrDate         DisplayString,
                gmcr10gEqptPmCurrTime         DisplayString
            }

    gmcr10gEqptPmCurrType OBJECT-TYPE
        SYNTAX INTEGER { lbc(2), ltemp(4), opt(5) }
        ACCESS read-only
        STATUS mandatory
        DESCRIPTION
            "Current equipment PM type."
        ::= { gmcr10gEqptPmCurrEntry 1 }

    gmcr10gEqptPmCurrValue OBJECT-TYPE
        SYNTAX DisplayString
        ACCESS read-only
        STATUS mandatory
        DESCRIPTION
            "Current equipment PM value."
        ::= { gmcr10gEqptPmCurrEntry 2 }

    gmcr10gEqptPmCurrValidity OBJECT-TYPE
        SYNTAX INTEGER { false(1), true(2) }
        ACCESS read-only
        STATUS mandatory
        DESCRIPTION
            "Current equipment PM validity."
        ::= { gmcr10gEqptPmCurrEntry 3 }

    gmcr10gEqptPmCurrLocation OBJECT-TYPE
        SYNTAX INTEGER { farEnd(1), nearEnd(2) }
        ACCESS read-only
        STATUS mandatory
        DESCRIPTION
            "Current equipment PM location."
        ::= { gmcr10gEqptPmCurrEntry 4 }

    gmcr10gEqptPmCurrDirection OBJECT-TYPE
        SYNTAX INTEGER { na(1), rcv(2), trmt(3) }
        ACCESS read-only
        STATUS mandatory
        DESCRIPTION
            "Current equipment PM direction."
        ::= { gmcr10gEqptPmCurrEntry 5 }

    gmcr10gEqptPmCurrDate OBJECT-TYPE
        SYNTAX DisplayString
        ACCESS read-only
        STATUS mandatory
        DESCRIPTION
            "Current equipment PM date."
        ::= { gmcr10gEqptPmCurrEntry 6 }

    gmcr10gEqptPmCurrTime OBJECT-TYPE
        SYNTAX DisplayString
        ACCESS read-only
        STATUS mandatory
        DESCRIPTION
            "Current equipment PM time."
        ::= { gmcr10gEqptPmCurrEntry 7 }

    --
    -- The elements in the gmcr10gEqptPmHistTable subgroup of the cardConfiguration group
    --

    gmcr10gEqptPmHistTable   OBJECT-TYPE
            SYNTAX  SEQUENCE OF Gmcr10gEqptPmHistEntry
            ACCESS  not-accessible
            STATUS  mandatory
            DESCRIPTION
                    "GMCR10G historical equipment PM table"
            ::= { gmcr10g 4 }

    gmcr10gEqptPmHistEntry   OBJECT-TYPE
            SYNTAX  Gmcr10gEqptPmHistEntry
            ACCESS  not-accessible
            STATUS  mandatory
            DESCRIPTION
                    "GMCR10G historical equipment PM entry format."
            INDEX   { eqptBay, eqptShelf, eqptSlot, gmcr10gEqptPmHistInterval, gmcr10gEqptPmHistType }
            ::= { gmcr10gEqptPmHistTable 1 }

    Gmcr10gEqptPmHistEntry   ::=
            SEQUENCE 
            {
                gmcr10gEqptPmHistInterval     INTEGER,
                gmcr10gEqptPmHistType         INTEGER,
                gmcr10gEqptPmHistValue        DisplayString,
                gmcr10gEqptPmHistValidity     INTEGER,
                gmcr10gEqptPmHistLocation     INTEGER,
                gmcr10gEqptPmHistDirection    INTEGER,
                gmcr10gEqptPmHistDate         DisplayString,
                gmcr10gEqptPmHistTime         DisplayString
            }

    gmcr10gEqptPmHistInterval OBJECT-TYPE
        SYNTAX INTEGER (1..32)
        ACCESS read-only
        STATUS mandatory
        DESCRIPTION
            "Historical equipment PM interval."
        ::= { gmcr10gEqptPmHistEntry 1 }

    gmcr10gEqptPmHistType OBJECT-TYPE
        SYNTAX INTEGER { lbc(2), ltemp(4), opt(5) }
        ACCESS read-only
        STATUS mandatory
        DESCRIPTION
            "Historical equipment PM type."
        ::= { gmcr10gEqptPmHistEntry 2 }

    gmcr10gEqptPmHistValue OBJECT-TYPE
        SYNTAX DisplayString
        ACCESS read-only
        STATUS mandatory
        DESCRIPTION
            "Historical equipment PM value."
        ::= { gmcr10gEqptPmHistEntry 3 }

    gmcr10gEqptPmHistValidity OBJECT-TYPE
        SYNTAX INTEGER { false(1), true(2) }
        ACCESS read-only
        STATUS mandatory
        DESCRIPTION
            "Historical equipment PM validity."
        ::= { gmcr10gEqptPmHistEntry 4 }

    gmcr10gEqptPmHistLocation OBJECT-TYPE
        SYNTAX INTEGER { farEnd(1), nearEnd(2) }
        ACCESS read-only
        STATUS mandatory
        DESCRIPTION
            "Historical equipment PM location."
        ::= { gmcr10gEqptPmHistEntry 5 }

    gmcr10gEqptPmHistDirection OBJECT-TYPE
        SYNTAX INTEGER { na(1), rcv(2), trmt(3) }
        ACCESS read-only
        STATUS mandatory
        DESCRIPTION
            "Historical equipment PM direction."
        ::= { gmcr10gEqptPmHistEntry 6 }

    gmcr10gEqptPmHistDate OBJECT-TYPE
        SYNTAX DisplayString
        ACCESS read-only
        STATUS mandatory
        DESCRIPTION
            "Historical equipment PM date."
        ::= { gmcr10gEqptPmHistEntry 7 }

    gmcr10gEqptPmHistTime OBJECT-TYPE
        SYNTAX DisplayString
        ACCESS read-only
        STATUS mandatory
        DESCRIPTION
            "Historical equipment PM time."
        ::= { gmcr10gEqptPmHistEntry 8 }

    --
    -- The elements in the gmcr10gFacPmCurrTable subgroup of the cardConfiguration group
    --

    gmcr10gFacPmCurrTable   OBJECT-TYPE
            SYNTAX  SEQUENCE OF Gmcr10gFacPmCurrEntry
            ACCESS  not-accessible
            STATUS  mandatory
            DESCRIPTION
                    "GMCR10G current facility PM table"
            ::= { gmcr10g 5 }

    gmcr10gFacPmCurrEntry   OBJECT-TYPE
            SYNTAX  Gmcr10gFacPmCurrEntry
            ACCESS  not-accessible
            STATUS  mandatory
            DESCRIPTION
                    "GMCR10G current facility PM entry format."
            INDEX   { eqptBay, eqptShelf, eqptSlot, gmcr10gFacPort, gmcr10gFacPmCurrType }
            ::= { gmcr10gFacPmCurrTable 1 }

    Gmcr10gFacPmCurrEntry   ::=
            SEQUENCE 
            {
                gmcr10gFacPmCurrType         INTEGER,
                gmcr10gFacPmCurrValue        DisplayString,
                gmcr10gFacPmCurrOcFacility   INTEGER,
                gmcr10gFacPmCurrValidity     INTEGER,
                gmcr10gFacPmCurrLocation     INTEGER,
                gmcr10gFacPmCurrDirection    INTEGER,
                gmcr10gFacPmCurrDate         DisplayString,
                gmcr10gFacPmCurrTime         DisplayString
            }

    gmcr10gFacPmCurrType OBJECT-TYPE
        SYNTAX INTEGER { cvs(4), ess(5), opr(8), sefss(11), sess(12) }
        ACCESS read-only
        STATUS mandatory
        DESCRIPTION
            "Current facility PM type."
        ::= { gmcr10gFacPmCurrEntry 1 }

    gmcr10gFacPmCurrValue OBJECT-TYPE
        SYNTAX DisplayString
        ACCESS read-only
        STATUS mandatory
        DESCRIPTION
            "Current facility PM value."
        ::= { gmcr10gFacPmCurrEntry 2 }

    gmcr10gFacPmCurrOcFacility OBJECT-TYPE
        SYNTAX INTEGER { oc12(1), oc192(2), oc24(3), oc48(4), oc3(5) }
        ACCESS read-only
        STATUS mandatory
        DESCRIPTION
            "Current facility PM OC facility."
        ::= { gmcr10gFacPmCurrEntry 3 }

    gmcr10gFacPmCurrValidity OBJECT-TYPE
        SYNTAX INTEGER { false(1), true(2) }
        ACCESS read-only
        STATUS mandatory
        DESCRIPTION
            "Current facility PM validity."
        ::= { gmcr10gFacPmCurrEntry 4 }

    gmcr10gFacPmCurrLocation OBJECT-TYPE
        SYNTAX INTEGER { farEnd(1), nearEnd(2) }
        ACCESS read-only
        STATUS mandatory
        DESCRIPTION
            "Current facility PM location."
        ::= { gmcr10gFacPmCurrEntry 5 }

    gmcr10gFacPmCurrDirection OBJECT-TYPE
        SYNTAX INTEGER { na(1), rcv(2), trmt(3) }
        ACCESS read-only
        STATUS mandatory
        DESCRIPTION
            "Current facility PM direction."
        ::= { gmcr10gFacPmCurrEntry 6 }

    gmcr10gFacPmCurrDate OBJECT-TYPE
        SYNTAX DisplayString
        ACCESS read-only
        STATUS mandatory
        DESCRIPTION
            "Current facility PM date."
        ::= { gmcr10gFacPmCurrEntry 7 }

    gmcr10gFacPmCurrTime OBJECT-TYPE
        SYNTAX DisplayString
        ACCESS read-only
        STATUS mandatory
        DESCRIPTION
            "Current facility PM time."
        ::= { gmcr10gFacPmCurrEntry 8 }

    --
    -- The elements in the gmcr10gFacPmHistTable subgroup of the cardConfiguration group
    --

    gmcr10gFacPmHistTable   OBJECT-TYPE
            SYNTAX  SEQUENCE OF Gmcr10gFacPmHistEntry
            ACCESS  not-accessible
            STATUS  mandatory
            DESCRIPTION
                    "GMCR10G historical facility PM table"
            ::= { gmcr10g 6 }

    gmcr10gFacPmHistEntry   OBJECT-TYPE
            SYNTAX  Gmcr10gFacPmHistEntry
            ACCESS  not-accessible
            STATUS  mandatory
            DESCRIPTION
                    "GMCR10G historical facility PM entry format."
            INDEX   { eqptBay, eqptShelf, eqptSlot, gmcr10gFacPort, gmcr10gFacPmHistInterval, gmcr10gFacPmHistType }
            ::= { gmcr10gFacPmHistTable 1 }

    Gmcr10gFacPmHistEntry   ::=
            SEQUENCE 
            {
                gmcr10gFacPmHistInterval     INTEGER,
                gmcr10gFacPmHistType         INTEGER,
                gmcr10gFacPmHistValue        DisplayString,
                gmcr10gFacPmHistOcFacility   INTEGER,
                gmcr10gFacPmHistValidity     INTEGER,
                gmcr10gFacPmHistLocation     INTEGER,
                gmcr10gFacPmHistDirection    INTEGER,
                gmcr10gFacPmHistDate         DisplayString,
                gmcr10gFacPmHistTime         DisplayString
            }

    gmcr10gFacPmHistInterval OBJECT-TYPE
        SYNTAX INTEGER (1..32)
        ACCESS read-only
        STATUS mandatory
        DESCRIPTION
            "Historical facility PM interval."
        ::= { gmcr10gFacPmHistEntry 1 }

    gmcr10gFacPmHistType OBJECT-TYPE
        SYNTAX INTEGER { cvs(4), ess(5), opr(8), sefss(11), sess(12) }
        ACCESS read-only
        STATUS mandatory
        DESCRIPTION
            "Historical facility PM type."
        ::= { gmcr10gFacPmHistEntry 2 }

    gmcr10gFacPmHistValue OBJECT-TYPE
        SYNTAX DisplayString
        ACCESS read-only
        STATUS mandatory
        DESCRIPTION
            "Historical facility PM value."
        ::= { gmcr10gFacPmHistEntry 3 }

    gmcr10gFacPmHistOcFacility OBJECT-TYPE
        SYNTAX INTEGER { oc12(1), oc192(2), oc24(3), oc48(4), oc3(5) }
        ACCESS read-only
        STATUS mandatory
        DESCRIPTION
            "Historical facility PM OC facility."
        ::= { gmcr10gFacPmHistEntry 4 }

    gmcr10gFacPmHistValidity OBJECT-TYPE
        SYNTAX INTEGER { false(1), true(2) }
        ACCESS read-only
        STATUS mandatory
        DESCRIPTION
            "Historical facility PM validity."
        ::= { gmcr10gFacPmHistEntry 5 }

    gmcr10gFacPmHistLocation OBJECT-TYPE
        SYNTAX INTEGER { farEnd(1), nearEnd(2) }
        ACCESS read-only
        STATUS mandatory
        DESCRIPTION
            "Historical facility PM location."
        ::= { gmcr10gFacPmHistEntry 6 }

    gmcr10gFacPmHistDirection OBJECT-TYPE
        SYNTAX INTEGER { na(1), rcv(2), trmt(3) }
        ACCESS read-only
        STATUS mandatory
        DESCRIPTION
            "Historical facility PM direction."
        ::= { gmcr10gFacPmHistEntry 7 }

    gmcr10gFacPmHistDate OBJECT-TYPE
        SYNTAX DisplayString
        ACCESS read-only
        STATUS mandatory
        DESCRIPTION
            "Historical facility PM date."
        ::= { gmcr10gFacPmHistEntry 8 }

    gmcr10gFacPmHistTime OBJECT-TYPE
        SYNTAX DisplayString
        ACCESS read-only
        STATUS mandatory
        DESCRIPTION
            "Historical facility PM time."
        ::= { gmcr10gFacPmHistEntry 9 }

    --
    -- The elements in the gmcr10gl subgroup of the cardConfiguration group
    --

    gmcr10glTable   OBJECT-TYPE
            SYNTAX  SEQUENCE OF Gmcr10glEntry
            ACCESS  not-accessible
            STATUS  mandatory
            DESCRIPTION
                    "GMCR10GL module table"
            ::= { gmcr10gl 1 }

    gmcr10glEntry   OBJECT-TYPE
            SYNTAX  Gmcr10glEntry
            ACCESS  not-accessible
            STATUS  mandatory
            DESCRIPTION
                    "GMCR10GL entry format."
            INDEX   { eqptBay, eqptShelf, eqptSlot }
            ::= { gmcr10glTable 1 }

    Gmcr10glEntry   ::=
            SEQUENCE 
            {
                gmcr10glSubType                 DisplayString,
                gmcr10glItuNum                  ItuSelection2,
                gmcr10glApsd                    INTEGER,
                gmcr10glProtocol                INTEGER,
                gmcr10glPrimaryState            INTEGER,
                gmcr10glSecondaryState          INTEGER,
                gmcr10glAdminState              INTEGER,
                gmcr10glPmStatus                INTEGER
            }

    gmcr10glSubType OBJECT-TYPE
        SYNTAX DisplayString
        ACCESS read-only
        STATUS mandatory
        DESCRIPTION
            "Module sub type."
        ::= { gmcr10glEntry 1 }

    gmcr10glItuNum    OBJECT-TYPE
        SYNTAX ItuSelection2
        ACCESS read-write
        STATUS mandatory
        DESCRIPTION
            "Module supported ITU channel.  This field is setable
             for modules with LRT subtype only.  Setting this field 
             for modules with any other subtype will return an error."
        ::= { gmcr10glEntry 2 }

    gmcr10glApsd      OBJECT-TYPE
        SYNTAX INTEGER { off(1), on(2) }
        ACCESS read-write
        STATUS mandatory
        DESCRIPTION
            "Module Automatic Power Shut Down setting.  The modules's
             primary state must be set OOS to modified this field."
        ::= { gmcr10glEntry 3 }

    gmcr10glProtocol  OBJECT-TYPE
        SYNTAX INTEGER { sdh(1), sonet(2) }
        ACCESS read-write
        STATUS mandatory
        DESCRIPTION
            "Module PM reporting protocol."
        ::= { gmcr10glEntry 4 }

    gmcr10glPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmcr10glEntry 5 }

    gmcr10glSecondaryState OBJECT-TYPE
        SYNTAX SecondaryState
        ACCESS read-only
        STATUS mandatory
        DESCRIPTION
            "Secondary state of module."
        ::= { gmcr10glEntry 6 }

    gmcr10glAdminState OBJECT-TYPE
        SYNTAX INTEGER { other(1), reset(2) }
        ACCESS read-write
        STATUS mandatory
        DESCRIPTION
            "Administration state of module.  This field is used
             to reset the module.  Reading this field always 
             returns other(1)."
        ::= { gmcr10glEntry 7 }

    gmcr10glPmStatus OBJECT-TYPE
        SYNTAX PmState
        ACCESS read-write
        STATUS mandatory
        DESCRIPTION
            "Perfornance monitoring status of module."
        ::= { gmcr10glEntry 8 }

    --
    -- The elements in the gmcr10glFacilities subgroup of the configuration group
    --

    gmcr10glFacTable   OBJECT-TYPE
            SYNTAX  SEQUENCE OF Gmcr10glFacEntry
            ACCESS  not-accessible
            STATUS  mandatory
            DESCRIPTION
                    "GMCR10GL facility table."
            ::= { gmcr10gl 2 }

    gmcr10glFacEntry   OBJECT-TYPE
            SYNTAX  Gmcr10glFacEntry
            ACCESS  not-accessible
            STATUS  mandatory
            DESCRIPTION
                    "GMCR10GL facility entry format"
            INDEX   { eqptBay, eqptShelf, eqptSlot, gmcr10glFacPort }
            ::= { gmcr10glFacTable 1 }

    Gmcr10glFacEntry   ::=
            SEQUENCE 
            {
                gmcr10glFacPort             INTEGER,
                gmcr10glFacOpr0             DisplayString,
                gmcr10glFacPrimaryState     INTEGER,
                gmcr10glFacSecondaryState   INTEGER,
                gmcr10glFacOpr              DisplayString,
                gmcr10glFacOprLowTh         DisplayString,
                gmcr10glFacOprHighTh        DisplayString,
                gmcr10glFacLoopbackState    INTEGER
            }

    gmcr10glFacPort OBJECT-TYPE
        SYNTAX INTEGER { cpe(1), line(2) }
        ACCESS read-only
        STATUS mandatory
        DESCRIPTION
            "Port portion of GMCR10GL facility address."
        ::= { gmcr10glFacEntry 1 }

    gmcr10glFacOpr0 OBJECT-TYPE
        SYNTAX DisplayString
        ACCESS read-write
        STATUS mandatory
        DESCRIPTION
            "Nominal value of average optical output power
             of the received signal, or the Optical Power Received
             (OPR) in dBm. gmcr10glFacOpr0 is valid for port line(2)
             only.  Valid range for the CPE port is -26.0 to -6.0."
        ::= { gmcr10glFacEntry 2 }

    gmcr10glFacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmcr10glFacEntry 3 }

    gmcr10glFacSecondaryState OBJECT-TYPE
        SYNTAX SecondaryState
        ACCESS read-only
        STATUS mandatory
        DESCRIPTION
            "Secondary state of port."
        ::= { gmcr10glFacEntry 4 }

    gmcr10glFacOpr OBJECT-TYPE
        SYNTAX DisplayString
        ACCESS read-only
        STATUS mandatory
        DESCRIPTION
            "Nominal value of average optical output power
             of the received signal, or the Optical Power Received
             (OPR) in dBm. gmcr10glFacOpr is valid for port line(1or2)
             only."  
        ::= { gmcr10glFacEntry 5 }

    gmcr10glFacOprLowTh OBJECT-TYPE
        SYNTAX DisplayString
        ACCESS read-write
        STATUS mandatory
        DESCRIPTION
            "Threshold value of OPRlow in dBm.
             The valid range is Min. -20.0 dBm to Max. -0.4 dBm."
        ::= { gmcr10glFacEntry 6 }

    gmcr10glFacOprHighTh OBJECT-TYPE
        SYNTAX DisplayString
        ACCESS read-write
        STATUS mandatory
        DESCRIPTION
            "Threshold value of OPR high in dBm.
             The valid range is Min. 0.4 dBm to Max. 20.0 dBm."
        ::= { gmcr10glFacEntry 7 }

    gmcr10glFacLoopbackState OBJECT-TYPE
        SYNTAX LoopbackState
        ACCESS read-write
        STATUS mandatory
        DESCRIPTION
            "Loopback state of port. Ports must be set OOS before
             they can be placed into loopback."
        ::= { gmcr10glFacEntry 8 }


    --
    -- The elements in the gmcr10glEqptPmCurrTable subgroup of the cardConfiguration group
    --

    gmcr10glEqptPmCurrTable   OBJECT-TYPE
            SYNTAX  SEQUENCE OF Gmcr10glEqptPmCurrEntry
            ACCESS  not-accessible
            STATUS  mandatory
            DESCRIPTION
                    "GMCR10GL current equipment PM table"
            ::= { gmcr10gl 3 }

    gmcr10glEqptPmCurrEntry   OBJECT-TYPE
            SYNTAX  Gmcr10glEqptPmCurrEntry
            ACCESS  not-accessible
            STATUS  mandatory
            DESCRIPTION
                    "GMCR10GL current equipment PM entry format."
            INDEX   { eqptBay, eqptShelf, eqptSlot, gmcr10glEqptPmCurrType }
            ::= { gmcr10glEqptPmCurrTable 1 }

    Gmcr10glEqptPmCurrEntry   ::=
            SEQUENCE 
            {
                gmcr10glEqptPmCurrType         INTEGER,
                gmcr10glEqptPmCurrValue        DisplayString,
                gmcr10glEqptPmCurrValidity     INTEGER,
                gmcr10glEqptPmCurrLocation     INTEGER,
                gmcr10glEqptPmCurrDirection    INTEGER,
                gmcr10glEqptPmCurrDate         DisplayString,
                gmcr10glEqptPmCurrTime         DisplayString
            }

    gmcr10glEqptPmCurrType OBJECT-TYPE
        SYNTAX INTEGER { lbc(2), ltemp(4), opt(5) }
        ACCESS read-only
        STATUS mandatory
        DESCRIPTION
            "Current equipment PM type."
        ::= { gmcr10glEqptPmCurrEntry 1 }

    gmcr10glEqptPmCurrValue OBJECT-TYPE
        SYNTAX DisplayString
        ACCESS read-only
        STATUS mandatory
        DESCRIPTION
            "Current equipment PM value."
        ::= { gmcr10glEqptPmCurrEntry 2 }

    gmcr10glEqptPmCurrValidity OBJECT-TYPE
        SYNTAX INTEGER { false(1), true(2) }
        ACCESS read-only
        STATUS mandatory
        DESCRIPTION
            "Current equipment PM validity."
        ::= { gmcr10glEqptPmCurrEntry 3 }

    gmcr10glEqptPmCurrLocation OBJECT-TYPE
        SYNTAX INTEGER { farEnd(1), nearEnd(2) }
        ACCESS read-only
        STATUS mandatory
        DESCRIPTION
            "Current equipment PM location."
        ::= { gmcr10glEqptPmCurrEntry 4 }

    gmcr10glEqptPmCurrDirection OBJECT-TYPE
        SYNTAX INTEGER { na(1), rcv(2), trmt(3) }
        ACCESS read-only
        STATUS mandatory
        DESCRIPTION
            "Current equipment PM direction."
        ::= { gmcr10glEqptPmCurrEntry 5 }

    gmcr10glEqptPmCurrDate OBJECT-TYPE
        SYNTAX DisplayString
        ACCESS read-only
        STATUS mandatory
        DESCRIPTION
            "Current equipment PM date."
        ::= { gmcr10glEqptPmCurrEntry 6 }

    gmcr10glEqptPmCurrTime OBJECT-TYPE
        SYNTAX DisplayString
        ACCESS read-only
        STATUS mandatory
        DESCRIPTION
            "Current equipment PM time."
        ::= { gmcr10glEqptPmCurrEntry 7 }

    --
    -- The elements in the gmcr10glEqptPmHistTable subgroup of the cardConfiguration group
    --

    gmcr10glEqptPmHistTable   OBJECT-TYPE
            SYNTAX  SEQUENCE OF Gmcr10glEqptPmHistEntry
            ACCESS  not-accessible
            STATUS  mandatory
            DESCRIPTION
                    "GMCR10GL historical equipment PM table"
            ::= { gmcr10gl 4 }

    gmcr10glEqptPmHistEntry   OBJECT-TYPE
            SYNTAX  Gmcr10glEqptPmHistEntry
            ACCESS  not-accessible
            STATUS  mandatory
            DESCRIPTION
                    "GMCR10GL historical equipment PM entry format."
            INDEX   { eqptBay, eqptShelf, eqptSlot, gmcr10glEqptPmHistInterval, gmcr10glEqptPmHistType }
            ::= { gmcr10glEqptPmHistTable 1 }

    Gmcr10glEqptPmHistEntry   ::=
            SEQUENCE 
            {
                gmcr10glEqptPmHistInterval     INTEGER,
                gmcr10glEqptPmHistType         INTEGER,
                gmcr10glEqptPmHistValue        DisplayString,
                gmcr10glEqptPmHistValidity     INTEGER,
                gmcr10glEqptPmHistLocation     INTEGER,
                gmcr10glEqptPmHistDirection    INTEGER,
                gmcr10glEqptPmHistDate         DisplayString,
                gmcr10glEqptPmHistTime         DisplayString
            }

    gmcr10glEqptPmHistInterval OBJECT-TYPE
        SYNTAX INTEGER (1..32)
        ACCESS read-only
        STATUS mandatory
        DESCRIPTION
            "Historical equipment PM interval."
        ::= { gmcr10glEqptPmHistEntry 1 }

    gmcr10glEqptPmHistType OBJECT-TYPE
        SYNTAX INTEGER { lbc(2), ltemp(4), opt(5) }
        ACCESS read-only
        STATUS mandatory
        DESCRIPTION
            "Historical equipment PM type."
        ::= { gmcr10glEqptPmHistEntry 2 }

    gmcr10glEqptPmHistValue OBJECT-TYPE
        SYNTAX DisplayString
        ACCESS read-only
        STATUS mandatory
        DESCRIPTION
            "Historical equipment PM value."
        ::= { gmcr10glEqptPmHistEntry 3 }

    gmcr10glEqptPmHistValidity OBJECT-TYPE
        SYNTAX INTEGER { false(1), true(2) }
        ACCESS read-only
        STATUS mandatory
        DESCRIPTION
            "Historical equipment PM validity."
        ::= { gmcr10glEqptPmHistEntry 4 }

    gmcr10glEqptPmHistLocation OBJECT-TYPE
        SYNTAX INTEGER { farEnd(1), nearEnd(2) }
        ACCESS read-only
        STATUS mandatory
        DESCRIPTION
            "Historical equipment PM location."
        ::= { gmcr10glEqptPmHistEntry 5 }

    gmcr10glEqptPmHistDirection OBJECT-TYPE
        SYNTAX INTEGER { na(1), rcv(2), trmt(3) }
        ACCESS read-only
        STATUS mandatory
        DESCRIPTION
            "Historical equipment PM direction."
        ::= { gmcr10glEqptPmHistEntry 6 }

    gmcr10glEqptPmHistDate OBJECT-TYPE
        SYNTAX DisplayString
        ACCESS read-only
        STATUS mandatory
        DESCRIPTION
            "Historical equipment PM date."
        ::= { gmcr10glEqptPmHistEntry 7 }

    gmcr10glEqptPmHistTime OBJECT-TYPE
        SYNTAX DisplayString
        ACCESS read-only
        STATUS mandatory
        DESCRIPTION
            "Historical equipment PM time."
        ::= { gmcr10glEqptPmHistEntry 8 }

    --
    -- The elements in the gmcr10glFacPmCurrTable subgroup of the cardConfiguration group
    --

    gmcr10glFacPmCurrTable   OBJECT-TYPE
            SYNTAX  SEQUENCE OF Gmcr10glFacPmCurrEntry
            ACCESS  not-accessible
            STATUS  mandatory
            DESCRIPTION
                    "GMCR10GL current facility PM table"
            ::= { gmcr10gl 5 }

    gmcr10glFacPmCurrEntry   OBJECT-TYPE
            SYNTAX  Gmcr10glFacPmCurrEntry
            ACCESS  not-accessible
            STATUS  mandatory
            DESCRIPTION
                    "GMCR10GL current facility PM entry format."
            INDEX   { eqptBay, eqptShelf, eqptSlot, gmcr10glFacPort, gmcr10glFacPmCurrType }
            ::= { gmcr10glFacPmCurrTable 1 }

    Gmcr10glFacPmCurrEntry   ::=
            SEQUENCE 
            {
                gmcr10glFacPmCurrType         INTEGER,
                gmcr10glFacPmCurrValue        DisplayString,
                gmcr10glFacPmCurrOcFacility   INTEGER,
                gmcr10glFacPmCurrValidity     INTEGER,
                gmcr10glFacPmCurrLocation     INTEGER,
                gmcr10glFacPmCurrDirection    INTEGER,
                gmcr10glFacPmCurrDate         DisplayString,
                gmcr10glFacPmCurrTime         DisplayString
            }

    gmcr10glFacPmCurrType OBJECT-TYPE
        SYNTAX INTEGER { opr(8) }
        ACCESS read-only
        STATUS mandatory
        DESCRIPTION
            "Current facility PM type."
        ::= { gmcr10glFacPmCurrEntry 1 }

    gmcr10glFacPmCurrValue OBJECT-TYPE
        SYNTAX DisplayString
        ACCESS read-only
        STATUS mandatory
        DESCRIPTION
            "Current facility PM value."
        ::= { gmcr10glFacPmCurrEntry 2 }

    gmcr10glFacPmCurrOcFacility OBJECT-TYPE
        SYNTAX INTEGER { oc12(1), oc192(2), oc24(3), oc48(4), oc3(5) }
        ACCESS read-only
        STATUS mandatory
        DESCRIPTION
            "Current facility PM OC facility."
        ::= { gmcr10glFacPmCurrEntry 3 }

    gmcr10glFacPmCurrValidity OBJECT-TYPE
        SYNTAX INTEGER { false(1), true(2) }
        ACCESS read-only
        STATUS mandatory
        DESCRIPTION
            "Current facility PM validity."
        ::= { gmcr10glFacPmCurrEntry 4 }

    gmcr10glFacPmCurrLocation OBJECT-TYPE
        SYNTAX INTEGER { farEnd(1), nearEnd(2) }
        ACCESS read-only
        STATUS mandatory
        DESCRIPTION
            "Current facility PM location."
        ::= { gmcr10glFacPmCurrEntry 5 }

    gmcr10glFacPmCurrDirection OBJECT-TYPE
        SYNTAX INTEGER { na(1), rcv(2), trmt(3) }
        ACCESS read-only
        STATUS mandatory
        DESCRIPTION
            "Current facility PM direction."
        ::= { gmcr10glFacPmCurrEntry 6 }

    gmcr10glFacPmCurrDate OBJECT-TYPE
        SYNTAX DisplayString
        ACCESS read-only
        STATUS mandatory
        DESCRIPTION
            "Current facility PM date."
        ::= { gmcr10glFacPmCurrEntry 7 }

    gmcr10glFacPmCurrTime OBJECT-TYPE
        SYNTAX DisplayString
        ACCESS read-only
        STATUS mandatory
        DESCRIPTION
            "Current facility PM time."
        ::= { gmcr10glFacPmCurrEntry 8 }

    --
    -- The elements in the gmcr10glFacPmHistTable subgroup of the cardConfiguration group
    --

    gmcr10glFacPmHistTable   OBJECT-TYPE
            SYNTAX  SEQUENCE OF Gmcr10glFacPmHistEntry
            ACCESS  not-accessible
            STATUS  mandatory
            DESCRIPTION
                    "GMCR10GL historical facility PM table"
            ::= { gmcr10gl 6 }

    gmcr10glFacPmHistEntry   OBJECT-TYPE
            SYNTAX  Gmcr10glFacPmHistEntry
            ACCESS  not-accessible
            STATUS  mandatory
            DESCRIPTION
                    "GMCR10GL historical facility PM entry format."
            INDEX   { eqptBay, eqptShelf, eqptSlot, gmcr10glFacPort, gmcr10glFacPmHistInterval, gmcr10glFacPmHistType }
            ::= { gmcr10glFacPmHistTable 1 }

    Gmcr10glFacPmHistEntry   ::=
            SEQUENCE 
            {
                gmcr10glFacPmHistInterval     INTEGER,
                gmcr10glFacPmHistType         INTEGER,
                gmcr10glFacPmHistValue        DisplayString,
                gmcr10glFacPmHistOcFacility   INTEGER,
                gmcr10glFacPmHistValidity     INTEGER,
                gmcr10glFacPmHistLocation     INTEGER,
                gmcr10glFacPmHistDirection    INTEGER,
                gmcr10glFacPmHistDate         DisplayString,
                gmcr10glFacPmHistTime         DisplayString
            }

    gmcr10glFacPmHistInterval OBJECT-TYPE
        SYNTAX INTEGER (1..32)
        ACCESS read-only
        STATUS mandatory
        DESCRIPTION
            "Historical facility PM interval."
        ::= { gmcr10glFacPmHistEntry 1 }

    gmcr10glFacPmHistType OBJECT-TYPE
        SYNTAX INTEGER { opr(8) }
        ACCESS read-only
        STATUS mandatory
        DESCRIPTION
            "Historical facility PM type."
        ::= { gmcr10glFacPmHistEntry 2 }

    gmcr10glFacPmHistValue OBJECT-TYPE
        SYNTAX DisplayString
        ACCESS read-only
        STATUS mandatory
        DESCRIPTION
            "Historical facility PM value."
        ::= { gmcr10glFacPmHistEntry 3 }

    gmcr10glFacPmHistOcFacility OBJECT-TYPE
        SYNTAX INTEGER { oc12(1), oc192(2), oc24(3), oc48(4), oc3(5) }
        ACCESS read-only
        STATUS mandatory
        DESCRIPTION
            "Historical facility PM OC facility."
        ::= { gmcr10glFacPmHistEntry 4 }

    gmcr10glFacPmHistValidity OBJECT-TYPE
        SYNTAX INTEGER { false(1), true(2) }
        ACCESS read-only
        STATUS mandatory
        DESCRIPTION
            "Historical facility PM validity."
        ::= { gmcr10glFacPmHistEntry 5 }

    gmcr10glFacPmHistLocation OBJECT-TYPE
        SYNTAX INTEGER { farEnd(1), nearEnd(2) }
        ACCESS read-only
        STATUS mandatory
        DESCRIPTION
            "Historical facility PM location."
        ::= { gmcr10glFacPmHistEntry 6 }

    gmcr10glFacPmHistDirection OBJECT-TYPE
        SYNTAX INTEGER { na(1), rcv(2), trmt(3) }
        ACCESS read-only
        STATUS mandatory
        DESCRIPTION
            "Historical facility PM direction."
        ::= { gmcr10glFacPmHistEntry 7 }

    gmcr10glFacPmHistDate OBJECT-TYPE
        SYNTAX DisplayString
        ACCESS read-only
        STATUS mandatory
        DESCRIPTION
            "Historical facility PM date."
        ::= { gmcr10glFacPmHistEntry 8 }

    gmcr10glFacPmHistTime OBJECT-TYPE
        SYNTAX DisplayString
        ACCESS read-only
        STATUS mandatory
        DESCRIPTION
            "Historical facility PM time."
        ::= { gmcr10glFacPmHistEntry 9 }

    --
    -- The elements in the gmcr2g5 subgroup of the cardConfiguration group
    --

    gmcr2g5Table   OBJECT-TYPE
            SYNTAX  SEQUENCE OF Gmcr2g5Entry
            ACCESS  not-accessible
            STATUS  mandatory
            DESCRIPTION
                    "GMCR2G5 module table"
            ::= { gmcr2g5 1 }

    gmcr2g5Entry   OBJECT-TYPE
            SYNTAX  Gmcr2g5Entry
            ACCESS  not-accessible
            STATUS  mandatory
            DESCRIPTION
                    "GMCR2G5 entry format."
            INDEX   { eqptBay, eqptShelf, eqptSlot }
            ::= { gmcr2g5Table 1 }

    Gmcr2g5Entry   ::=
            SEQUENCE 
            {
                gmcr2g5SubType                 DisplayString,
                gmcr2g5ItuNum                  ItuSelection,
                gmcr2g5Apsd                    INTEGER,
                gmcr2g5ClockSource             INTEGER,
                gmcr2g5ClockSelection          INTEGER,
                gmcr2g5Protocol                INTEGER,
                gmcr2g5PrimaryState            INTEGER,
                gmcr2g5SecondaryState          INTEGER,
                gmcr2g5AdminState              INTEGER,
                gmcr2g5PmStatus                INTEGER
            }

    gmcr2g5SubType OBJECT-TYPE
        SYNTAX DisplayString
        ACCESS read-only
        STATUS mandatory
        DESCRIPTION
            "Module sub type."
        ::= { gmcr2g5Entry 1 }

    gmcr2g5ItuNum OBJECT-TYPE
        SYNTAX ItuSelection
        ACCESS read-only
        STATUS mandatory
        DESCRIPTION
            "Module supported ITU channel."
        ::= { gmcr2g5Entry 2 }

    gmcr2g5Apsd      OBJECT-TYPE
        SYNTAX INTEGER { off(1), on(2) }
        ACCESS read-write
        STATUS mandatory
        DESCRIPTION
            "Module Automatic Power Shut Down setting.  The modules's
             primary state must be set OOS to modified this field."
        ::= { gmcr2g5Entry 3 }

    gmcr2g5ClockSource      OBJECT-TYPE
        SYNTAX INTEGER
        {
            extThruLineInt(1),
            thruExtLineInt(2),
            ext(3),
            thru(4),
            loop(5)
        }
        ACCESS read-write
        STATUS mandatory
        DESCRIPTION
            "Module clock timing source setting."
        ::= { gmcr2g5Entry 4 }

    gmcr2g5ClockSelection      OBJECT-TYPE
        SYNTAX INTEGER { auto(1), forced(2) }
        ACCESS read-only
        STATUS mandatory
        DESCRIPTION
            "Module clock timing selection setting.."
        ::= { gmcr2g5Entry 5 }

    gmcr2g5Protocol  OBJECT-TYPE
        SYNTAX INTEGER { sdh(1), sonet(2) }
        ACCESS read-write
        STATUS mandatory
        DESCRIPTION
            "Module PM reporting protocol."
        ::= { gmcr2g5Entry 6 }

    gmcr2g5PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmcr2g5Entry 7 }

    gmcr2g5SecondaryState OBJECT-TYPE
        SYNTAX SecondaryState
        ACCESS read-only
        STATUS mandatory
        DESCRIPTION
            "Secondary state of module."
        ::= { gmcr2g5Entry 8 }

    gmcr2g5AdminState OBJECT-TYPE
        SYNTAX INTEGER { other(1), reset(2) }
        ACCESS read-write
        STATUS mandatory
        DESCRIPTION
            "Administration state of module.  This field is used
             to reset the module.  Reading this field always 
             returns other(1)."
        ::= { gmcr2g5Entry 9 }

    gmcr2g5PmStatus OBJECT-TYPE
        SYNTAX PmState
        ACCESS read-write
        STATUS mandatory
        DESCRIPTION
            "Perfornance monitoring status of module."
        ::= { gmcr2g5Entry 10 }

    --
    -- The elements in the gmcr2g5Facilities subgroup of the configuration group
    --

    gmcr2g5FacTable   OBJECT-TYPE
            SYNTAX  SEQUENCE OF Gmcr2g5FacEntry
            ACCESS  not-accessible
            STATUS  mandatory
            DESCRIPTION
                    "GMCR2G5 facility table."
            ::= { gmcr2g5 2 }

    gmcr2g5FacEntry   OBJECT-TYPE
            SYNTAX  Gmcr2g5FacEntry
            ACCESS  not-accessible
            STATUS  mandatory
            DESCRIPTION
                    "GMCR2G5 facility entry format"
            INDEX   { eqptBay, eqptShelf, eqptSlot, gmcr2g5FacPort }
            ::= { gmcr2g5FacTable 1 }

    Gmcr2g5FacEntry   ::=
            SEQUENCE 
            {
                gmcr2g5FacPort             INTEGER,
                gmcr2g5FacOpr0             DisplayString,
                gmcr2g5FacPrimaryState     INTEGER,
                gmcr2g5FacSecondaryState   INTEGER
            }

    gmcr2g5FacPort OBJECT-TYPE
        SYNTAX INTEGER { cpe(1), line(2) }
        ACCESS read-only
        STATUS mandatory
        DESCRIPTION
            "Port portion of GMCR2G5 facility address."
        ::= { gmcr2g5FacEntry 1 }

    gmcr2g5FacOpr0 OBJECT-TYPE
        SYNTAX DisplayString
        ACCESS read-write
        STATUS mandatory
        DESCRIPTION
            "Nominal value of average optical output power
             of the received signal, or the Optical Power Received
             (OPR) in dBm. The valid range differs based on the
             current port.  The valid range for the RC port (line) 
             is -28.0 to -8.0.  OPR0 is invalid for all other ports."
        ::= { gmcr2g5FacEntry 2 }

    gmcr2g5FacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmcr2g5FacEntry 3 }

    gmcr2g5FacSecondaryState OBJECT-TYPE
        SYNTAX SecondaryState
        ACCESS read-only
        STATUS mandatory
        DESCRIPTION
            "Secondary state of port."
        ::= { gmcr2g5FacEntry 4 }

    --
    -- The elements in the gmcr2g5EqptPmCurrTable subgroup of the cardConfiguration group
    --

    gmcr2g5EqptPmCurrTable   OBJECT-TYPE
            SYNTAX  SEQUENCE OF Gmcr2g5EqptPmCurrEntry
            ACCESS  not-accessible
            STATUS  mandatory
            DESCRIPTION
                    "GMCR2G5 current equipment PM table"
            ::= { gmcr2g5 3 }

    gmcr2g5EqptPmCurrEntry   OBJECT-TYPE
            SYNTAX  Gmcr2g5EqptPmCurrEntry
            ACCESS  not-accessible
            STATUS  mandatory
            DESCRIPTION
                    "GMCR2G5 current equipment PM entry format."
            INDEX   { eqptBay, eqptShelf, eqptSlot, gmcr2g5EqptPmCurrType }
            ::= { gmcr2g5EqptPmCurrTable 1 }

    Gmcr2g5EqptPmCurrEntry   ::=
            SEQUENCE 
            {
                gmcr2g5EqptPmCurrType         INTEGER,
                gmcr2g5EqptPmCurrValue        DisplayString,
                gmcr2g5EqptPmCurrValidity     INTEGER,
                gmcr2g5EqptPmCurrLocation     INTEGER,
                gmcr2g5EqptPmCurrDirection    INTEGER,
                gmcr2g5EqptPmCurrDate         DisplayString,
                gmcr2g5EqptPmCurrTime         DisplayString
            }

    gmcr2g5EqptPmCurrType OBJECT-TYPE
        SYNTAX INTEGER { lbc(2), ltemp(4), opt(5) }
        ACCESS read-only
        STATUS mandatory
        DESCRIPTION
            "Current equipment PM type."
        ::= { gmcr2g5EqptPmCurrEntry 1 }

    gmcr2g5EqptPmCurrValue OBJECT-TYPE
        SYNTAX DisplayString
        ACCESS read-only
        STATUS mandatory
        DESCRIPTION
            "Current equipment PM value."
        ::= { gmcr2g5EqptPmCurrEntry 2 }

    gmcr2g5EqptPmCurrValidity OBJECT-TYPE
        SYNTAX INTEGER { false(1), true(2) }
        ACCESS read-only
        STATUS mandatory
        DESCRIPTION
            "Current equipment PM validity."
        ::= { gmcr2g5EqptPmCurrEntry 3 }

    gmcr2g5EqptPmCurrLocation OBJECT-TYPE
        SYNTAX INTEGER { farEnd(1), nearEnd(2) }
        ACCESS read-only
        STATUS mandatory
        DESCRIPTION
            "Current equipment PM location."
        ::= { gmcr2g5EqptPmCurrEntry 4 }

    gmcr2g5EqptPmCurrDirection OBJECT-TYPE
        SYNTAX INTEGER { na(1), rcv(2), trmt(3) }
        ACCESS read-only
        STATUS mandatory
        DESCRIPTION
            "Current equipment PM direction."
        ::= { gmcr2g5EqptPmCurrEntry 5 }

    gmcr2g5EqptPmCurrDate OBJECT-TYPE
        SYNTAX DisplayString
        ACCESS read-only
        STATUS mandatory
        DESCRIPTION
            "Current equipment PM date."
        ::= { gmcr2g5EqptPmCurrEntry 6 }

    gmcr2g5EqptPmCurrTime OBJECT-TYPE
        SYNTAX DisplayString
        ACCESS read-only
        STATUS mandatory
        DESCRIPTION
            "Current equipment PM time."
        ::= { gmcr2g5EqptPmCurrEntry 7 }

    --
    -- The elements in the gmcr2g5EqptPmHistTable subgroup of the cardConfiguration group
    --

    gmcr2g5EqptPmHistTable   OBJECT-TYPE
            SYNTAX  SEQUENCE OF Gmcr2g5EqptPmHistEntry
            ACCESS  not-accessible
            STATUS  mandatory
            DESCRIPTION
                    "GMCR2G5 historical equipment PM table"
            ::= { gmcr2g5 4 }

    gmcr2g5EqptPmHistEntry   OBJECT-TYPE
            SYNTAX  Gmcr2g5EqptPmHistEntry
            ACCESS  not-accessible
            STATUS  mandatory
            DESCRIPTION
                    "GMCR2G5 historical equipment PM entry format."
            INDEX   { eqptBay, eqptShelf, eqptSlot, gmcr2g5EqptPmHistInterval, gmcr2g5EqptPmHistType }
            ::= { gmcr2g5EqptPmHistTable 1 }

    Gmcr2g5EqptPmHistEntry   ::=
            SEQUENCE 
            {
                gmcr2g5EqptPmHistInterval     INTEGER,
                gmcr2g5EqptPmHistType         INTEGER,
                gmcr2g5EqptPmHistValue        DisplayString,
                gmcr2g5EqptPmHistValidity     INTEGER,
                gmcr2g5EqptPmHistLocation     INTEGER,
                gmcr2g5EqptPmHistDirection    INTEGER,
                gmcr2g5EqptPmHistDate         DisplayString,
                gmcr2g5EqptPmHistTime         DisplayString
            }

    gmcr2g5EqptPmHistInterval OBJECT-TYPE
        SYNTAX INTEGER (1..32)
        ACCESS read-only
        STATUS mandatory
        DESCRIPTION
            "Historical equipment PM interval."
        ::= { gmcr2g5EqptPmHistEntry 1 }

    gmcr2g5EqptPmHistType OBJECT-TYPE
        SYNTAX INTEGER { lbc(2), ltemp(4), opt(5) }
        ACCESS read-only
        STATUS mandatory
        DESCRIPTION
            "Historical equipment PM type."
        ::= { gmcr2g5EqptPmHistEntry 2 }

    gmcr2g5EqptPmHistValue OBJECT-TYPE
        SYNTAX DisplayString
        ACCESS read-only
        STATUS mandatory
        DESCRIPTION
            "Historical equipment PM value."
        ::= { gmcr2g5EqptPmHistEntry 3 }

    gmcr2g5EqptPmHistValidity OBJECT-TYPE
        SYNTAX INTEGER { false(1), true(2) }
        ACCESS read-only
        STATUS mandatory
        DESCRIPTION
            "Historical equipment PM validity."
        ::= { gmcr2g5EqptPmHistEntry 4 }

    gmcr2g5EqptPmHistLocation OBJECT-TYPE
        SYNTAX INTEGER { farEnd(1), nearEnd(2) }
        ACCESS read-only
        STATUS mandatory
        DESCRIPTION
            "Historical equipment PM location."
        ::= { gmcr2g5EqptPmHistEntry 5 }

    gmcr2g5EqptPmHistDirection OBJECT-TYPE
        SYNTAX INTEGER { na(1), rcv(2), trmt(3) }
        ACCESS read-only
        STATUS mandatory
        DESCRIPTION
            "Historical equipment PM direction."
        ::= { gmcr2g5EqptPmHistEntry 6 }

    gmcr2g5EqptPmHistDate OBJECT-TYPE
        SYNTAX DisplayString
        ACCESS read-only
        STATUS mandatory
        DESCRIPTION
            "Historical equipment PM date."
        ::= { gmcr2g5EqptPmHistEntry 7 }

    gmcr2g5EqptPmHistTime OBJECT-TYPE
        SYNTAX DisplayString
        ACCESS read-only
        STATUS mandatory
        DESCRIPTION
            "Historical equipment PM time."
        ::= { gmcr2g5EqptPmHistEntry 8 }

    --
    -- The elements in the gmcr2g5FacPmCurrTable subgroup of the cardConfiguration group
    --

    gmcr2g5FacPmCurrTable   OBJECT-TYPE
            SYNTAX  SEQUENCE OF Gmcr2g5FacPmCurrEntry
            ACCESS  not-accessible
            STATUS  mandatory
            DESCRIPTION
                    "GMCR2G5 current facility PM table"
            ::= { gmcr2g5 5 }

    gmcr2g5FacPmCurrEntry   OBJECT-TYPE
            SYNTAX  Gmcr2g5FacPmCurrEntry
            ACCESS  not-accessible
            STATUS  mandatory
            DESCRIPTION
                    "GMCR2G5 current facility PM entry format."
            INDEX   { eqptBay, eqptShelf, eqptSlot, gmcr2g5FacPort, gmcr2g5FacPmCurrType }
            ::= { gmcr2g5FacPmCurrTable 1 }

    Gmcr2g5FacPmCurrEntry   ::=
            SEQUENCE 
            {
                gmcr2g5FacPmCurrType         INTEGER,
                gmcr2g5FacPmCurrValue        DisplayString,
                gmcr2g5FacPmCurrOcFacility   INTEGER,
                gmcr2g5FacPmCurrValidity     INTEGER,
                gmcr2g5FacPmCurrLocation     INTEGER,
                gmcr2g5FacPmCurrDirection    INTEGER,
                gmcr2g5FacPmCurrDate         DisplayString,
                gmcr2g5FacPmCurrTime         DisplayString
            }

    gmcr2g5FacPmCurrType OBJECT-TYPE
        SYNTAX INTEGER { cvs(4), ess(5), opr(8), sefss(11), sess(12) }
        ACCESS read-only
        STATUS mandatory
        DESCRIPTION
            "Current facility PM type."
        ::= { gmcr2g5FacPmCurrEntry 1 }

    gmcr2g5FacPmCurrValue OBJECT-TYPE
        SYNTAX DisplayString
        ACCESS read-only
        STATUS mandatory
        DESCRIPTION
            "Current facility PM value."
        ::= { gmcr2g5FacPmCurrEntry 2 }

    gmcr2g5FacPmCurrOcFacility OBJECT-TYPE
        SYNTAX INTEGER { oc12(1), oc192(2), oc24(3), oc48(4), oc3(5) }
        ACCESS read-only
        STATUS mandatory
        DESCRIPTION
            "Current facility PM OC facility."
        ::= { gmcr2g5FacPmCurrEntry 3 }

    gmcr2g5FacPmCurrValidity OBJECT-TYPE
        SYNTAX INTEGER { false(1), true(2) }
        ACCESS read-only
        STATUS mandatory
        DESCRIPTION
            "Current facility PM validity."
        ::= { gmcr2g5FacPmCurrEntry 4 }

    gmcr2g5FacPmCurrLocation OBJECT-TYPE
        SYNTAX INTEGER { farEnd(1), nearEnd(2) }
        ACCESS read-only
        STATUS mandatory
        DESCRIPTION
            "Current facility PM location."
        ::= { gmcr2g5FacPmCurrEntry 5 }

    gmcr2g5FacPmCurrDirection OBJECT-TYPE
        SYNTAX INTEGER { na(1), rcv(2), trmt(3) }
        ACCESS read-only
        STATUS mandatory
        DESCRIPTION
            "Current facility PM direction."
        ::= { gmcr2g5FacPmCurrEntry 6 }

    gmcr2g5FacPmCurrDate OBJECT-TYPE
        SYNTAX DisplayString
        ACCESS read-only
        STATUS mandatory
        DESCRIPTION
            "Current facility PM date."
        ::= { gmcr2g5FacPmCurrEntry 7 }

    gmcr2g5FacPmCurrTime OBJECT-TYPE
        SYNTAX DisplayString
        ACCESS read-only
        STATUS mandatory
        DESCRIPTION
            "Current facility PM time."
        ::= { gmcr2g5FacPmCurrEntry 8 }

    --
    -- The elements in the gmcr2g5FacPmHistTable subgroup of the cardConfiguration group
    --

    gmcr2g5FacPmHistTable   OBJECT-TYPE
            SYNTAX  SEQUENCE OF Gmcr2g5FacPmHistEntry
            ACCESS  not-accessible
            STATUS  mandatory
            DESCRIPTION
                    "GMCR2G5 historical facility PM table"
            ::= { gmcr2g5 6 }

    gmcr2g5FacPmHistEntry   OBJECT-TYPE
            SYNTAX  Gmcr2g5FacPmHistEntry
            ACCESS  not-accessible
            STATUS  mandatory
            DESCRIPTION
                    "GMCR2G5 historical facility PM entry format."
            INDEX   { eqptBay, eqptShelf, eqptSlot, gmcr2g5FacPort, gmcr2g5FacPmHistInterval, gmcr2g5FacPmHistType }
            ::= { gmcr2g5FacPmHistTable 1 }

    Gmcr2g5FacPmHistEntry   ::=
            SEQUENCE 
            {
                gmcr2g5FacPmHistInterval     INTEGER,
                gmcr2g5FacPmHistType         INTEGER,
                gmcr2g5FacPmHistValue        DisplayString,
                gmcr2g5FacPmHistOcFacility   INTEGER,
                gmcr2g5FacPmHistValidity     INTEGER,
                gmcr2g5FacPmHistLocation     INTEGER,
                gmcr2g5FacPmHistDirection    INTEGER,
                gmcr2g5FacPmHistDate         DisplayString,
                gmcr2g5FacPmHistTime         DisplayString
            }

    gmcr2g5FacPmHistInterval OBJECT-TYPE
        SYNTAX INTEGER (1..32)
        ACCESS read-only
        STATUS mandatory
        DESCRIPTION
            "Historical facility PM interval."
        ::= { gmcr2g5FacPmHistEntry 1 }

    gmcr2g5FacPmHistType OBJECT-TYPE
        SYNTAX INTEGER { cvs(4), ess(5), opr(8), sefss(11), sess(12) }
        ACCESS read-only
        STATUS mandatory
        DESCRIPTION
            "Historical facility PM type."
        ::= { gmcr2g5FacPmHistEntry 2 }

    gmcr2g5FacPmHistValue OBJECT-TYPE
        SYNTAX DisplayString
        ACCESS read-only
        STATUS mandatory
        DESCRIPTION
            "Historical facility PM value."
        ::= { gmcr2g5FacPmHistEntry 3 }

    gmcr2g5FacPmHistOcFacility OBJECT-TYPE
        SYNTAX INTEGER { oc12(1), oc192(2), oc24(3), oc48(4), oc3(5) }
        ACCESS read-only
        STATUS mandatory
        DESCRIPTION
            "Historical facility PM OC facility."
        ::= { gmcr2g5FacPmHistEntry 4 }

    gmcr2g5FacPmHistValidity OBJECT-TYPE
        SYNTAX INTEGER { false(1), true(2) }
        ACCESS read-only
        STATUS mandatory
        DESCRIPTION
            "Historical facility PM validity."
        ::= { gmcr2g5FacPmHistEntry 5 }

    gmcr2g5FacPmHistLocation OBJECT-TYPE
        SYNTAX INTEGER { farEnd(1), nearEnd(2) }
        ACCESS read-only
        STATUS mandatory
        DESCRIPTION
            "Historical facility PM location."
        ::= { gmcr2g5FacPmHistEntry 6 }

    gmcr2g5FacPmHistDirection OBJECT-TYPE
        SYNTAX INTEGER { na(1), rcv(2), trmt(3) }
        ACCESS read-only
        STATUS mandatory
        DESCRIPTION
            "Historical facility PM direction."
        ::= { gmcr2g5FacPmHistEntry 7 }

    gmcr2g5FacPmHistDate OBJECT-TYPE
        SYNTAX DisplayString
        ACCESS read-only
        STATUS mandatory
        DESCRIPTION
            "Historical facility PM date."
        ::= { gmcr2g5FacPmHistEntry 8 }

    gmcr2g5FacPmHistTime OBJECT-TYPE
        SYNTAX DisplayString
        ACCESS read-only
        STATUS mandatory
        DESCRIPTION
            "Historical facility PM time."
        ::= { gmcr2g5FacPmHistEntry 9 }

    --
    -- The elements in the gmcrf10g subgroup of the cardConfiguration group
    --

    gmcrf10gTable   OBJECT-TYPE
            SYNTAX  SEQUENCE OF Gmcrf10gEntry
            ACCESS  not-accessible
            STATUS  mandatory
            DESCRIPTION
                    "GMCRF10G module table"
            ::= { gmcrf10g 1 }

    gmcrf10gEntry   OBJECT-TYPE
            SYNTAX  Gmcrf10gEntry
            ACCESS  not-accessible
            STATUS  mandatory
            DESCRIPTION
                    "GMCRF10G entry format."
            INDEX   { eqptBay, eqptShelf, eqptSlot }
            ::= { gmcrf10gTable 1 }

    Gmcrf10gEntry   ::=
            SEQUENCE 
            {
                gmcrf10gSubType                 DisplayString,
                gmcrf10gItuNum                  ItuSelection2,
                gmcrf10gApsd                    INTEGER,
                gmcrf10gProtocol                INTEGER,
                gmcrf10gPrimaryState            INTEGER,
                gmcrf10gSecondaryState          INTEGER,
                gmcrf10gAdminState              INTEGER,
                gmcrf10gPmStatus                INTEGER
            }

    gmcrf10gSubType OBJECT-TYPE
        SYNTAX DisplayString
        ACCESS read-only
        STATUS mandatory
        DESCRIPTION
            "Module sub type."
        ::= { gmcrf10gEntry 1 }

    gmcrf10gItuNum    OBJECT-TYPE
        SYNTAX ItuSelection2
        ACCESS read-write
        STATUS mandatory
        DESCRIPTION
            "Module supported ITU channel.  This field is setable
             for modules with LWT subtype only.  Setting this field 
             for modules with any other subtype will return an error."
        ::= { gmcrf10gEntry 2 }

    gmcrf10gApsd      OBJECT-TYPE
        SYNTAX INTEGER { off(1), on(2) }
        ACCESS read-write
        STATUS mandatory
        DESCRIPTION
            "Module Automatic Power Shut Down setting.  The modules's
             primary state must be set OOS to modified this field."
        ::= { gmcrf10gEntry 3 }

    gmcrf10gProtocol  OBJECT-TYPE
        SYNTAX INTEGER { sdh(1), sonet(2) }
        ACCESS read-write
        STATUS mandatory
        DESCRIPTION
            "Module PM reporting protocol."
        ::= { gmcrf10gEntry 4 }

    gmcrf10gPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmcrf10gEntry 5 }

    gmcrf10gSecondaryState OBJECT-TYPE
        SYNTAX SecondaryState
        ACCESS read-only
        STATUS mandatory
        DESCRIPTION
            "Secondary state of module."
        ::= { gmcrf10gEntry 6 }

    gmcrf10gAdminState OBJECT-TYPE
        SYNTAX INTEGER { other(1), reset(2) }
        ACCESS read-write
        STATUS mandatory
        DESCRIPTION
            "Administration state of module.  This field is used
             to reset the module.  Reading this field always 
             returns other(1)."
        ::= { gmcrf10gEntry 7 }

    gmcrf10gPmStatus OBJECT-TYPE
        SYNTAX PmState
        ACCESS read-write
        STATUS mandatory
        DESCRIPTION
            "Perfornance monitoring status of module."
        ::= { gmcrf10gEntry 8 }

    --
    -- The elements in the gmcrf10gFacilities subgroup of the configuration group
    --

    gmcrf10gFacTable   OBJECT-TYPE
            SYNTAX  SEQUENCE OF Gmcrf10gFacEntry
            ACCESS  not-accessible
            STATUS  mandatory
            DESCRIPTION
                    "GMCRF10G facility table."
            ::= { gmcrf10g 2 }

    gmcrf10gFacEntry   OBJECT-TYPE
            SYNTAX  Gmcrf10gFacEntry
            ACCESS  not-accessible
            STATUS  mandatory
            DESCRIPTION
                    "GMCRF10G facility entry format"
            INDEX   { eqptBay, eqptShelf, eqptSlot, gmcrf10gFacPort }
            ::= { gmcrf10gFacTable 1 }

    Gmcrf10gFacEntry   ::=
            SEQUENCE 
            {
                gmcrf10gFacPort             INTEGER,
                gmcrf10gFacOpr0             DisplayString,
                gmcrf10gFacSdTh             DisplayString,
                gmcrf10gFacSfTh             DisplayString,
                gmcrf10gFacPrimaryState     INTEGER,
                gmcrf10gFacSecondaryState   INTEGER,
                gmcrf10gFacLoopbackState    INTEGER,
                gmcrf10gFacOpr              DisplayString,
                gmcrf10gFacOprLowTh         DisplayString,
                gmcrf10gFacOprHighTh        DisplayString
            }

    gmcrf10gFacPort OBJECT-TYPE
        SYNTAX INTEGER { cpe(1), line(2) }
        ACCESS read-only
        STATUS mandatory
        DESCRIPTION
            "Port portion of GMCRF10G facility address."
        ::= { gmcrf10gFacEntry 1 }

    gmcrf10gFacOpr0 OBJECT-TYPE
        SYNTAX DisplayString
        ACCESS read-write
        STATUS mandatory
        DESCRIPTION
            "Nominal value of average optical output power
             of the received signal, or the Optical Power Received
             (OPR) in dBm. The valid range differs based on the
             port. Valid range for the CPE port is -18.0 to 1.0.
             The valid range for the Line port is -26 to -6."
        ::= { gmcrf10gFacEntry 2 }

    gmcrf10gFacSdTh      OBJECT-TYPE
        SYNTAX DisplayString
        ACCESS read-write
        STATUS mandatory
        DESCRIPTION
            "B2 error rate threshold for SD. Entry format is 10e-<exp>.
             Where exp is a value between 5 and 12.  I.e., 10e-11"
        ::= { gmcrf10gFacEntry 3 }

    gmcrf10gFacSfTh    OBJECT-TYPE
        SYNTAX DisplayString
        ACCESS read-write
        STATUS mandatory
        DESCRIPTION
            "B2 error rate threshold for SF. Entry format is 10e-<exp>.
             Where exp is a value between 3 and 9.  I.e., 10e-8"
        ::= { gmcrf10gFacEntry 4 }

    gmcrf10gFacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmcrf10gFacEntry 5 }

    gmcrf10gFacSecondaryState OBJECT-TYPE
        SYNTAX SecondaryState
        ACCESS read-only
        STATUS mandatory
        DESCRIPTION
            "Secondary state of port."
        ::= { gmcrf10gFacEntry 6 }

    gmcrf10gFacLoopbackState OBJECT-TYPE
        SYNTAX LoopbackState
        ACCESS read-write
        STATUS mandatory
        DESCRIPTION
            "Loopback state of port. Ports must be set OOS before they
             can be placed into loopback."
        ::= { gmcrf10gFacEntry 7 }

    gmcrf10gFacOpr OBJECT-TYPE
        SYNTAX DisplayString
        ACCESS read-only
        STATUS mandatory
        DESCRIPTION
            "Nominal value of average optical output power
             of the received signal, or the Optical Power Received
             (OPR) in dBm. gmcrf10gFacOpr is valid for port line(1or2)
             only."  
        ::= { gmcrf10gFacEntry 8 }

    gmcrf10gFacOprLowTh OBJECT-TYPE
        SYNTAX DisplayString
        ACCESS read-write
        STATUS mandatory
        DESCRIPTION
            "Threshold value of OPRlow in dBm.
             The valid range is Min. -20.0 dBm to Max. -0.4 dBm."
        ::= { gmcrf10gFacEntry 9 }

    gmcrf10gFacOprHighTh OBJECT-TYPE
        SYNTAX DisplayString
        ACCESS read-write
        STATUS mandatory
        DESCRIPTION
            "Threshold value of OPR high in dBm.
             The valid range is Min. 0.4 dBm to Max. 20.0 dBm."
        ::= { gmcrf10gFacEntry 10 }

    --
    -- The elements in the gmcrf10gEqptPmCurrTable subgroup of the cardConfiguration group
    --

    gmcrf10gEqptPmCurrTable   OBJECT-TYPE
            SYNTAX  SEQUENCE OF Gmcrf10gEqptPmCurrEntry
            ACCESS  not-accessible
            STATUS  mandatory
            DESCRIPTION
                    "GMCRF10G current equipment PM table"
            ::= { gmcrf10g 3 }

    gmcrf10gEqptPmCurrEntry   OBJECT-TYPE
            SYNTAX  Gmcrf10gEqptPmCurrEntry
            ACCESS  not-accessible
            STATUS  mandatory
            DESCRIPTION
                    "GMCRF10G current equipment PM entry format."
            INDEX   { eqptBay, eqptShelf, eqptSlot, gmcrf10gEqptPmCurrType }
            ::= { gmcrf10gEqptPmCurrTable 1 }

    Gmcrf10gEqptPmCurrEntry   ::=
            SEQUENCE 
            {
                gmcrf10gEqptPmCurrType         INTEGER,
                gmcrf10gEqptPmCurrValue        DisplayString,
                gmcrf10gEqptPmCurrValidity     INTEGER,
                gmcrf10gEqptPmCurrLocation     INTEGER,
                gmcrf10gEqptPmCurrDirection    INTEGER,
                gmcrf10gEqptPmCurrDate         DisplayString,
                gmcrf10gEqptPmCurrTime         DisplayString
            }

    gmcrf10gEqptPmCurrType OBJECT-TYPE
        SYNTAX INTEGER { lbc(2), ltemp(4), opt(5) }
        ACCESS read-only
        STATUS mandatory
        DESCRIPTION
            "Current equipment PM type."
        ::= { gmcrf10gEqptPmCurrEntry 1 }

    gmcrf10gEqptPmCurrValue OBJECT-TYPE
        SYNTAX DisplayString
        ACCESS read-only
        STATUS mandatory
        DESCRIPTION
            "Current equipment PM value."
        ::= { gmcrf10gEqptPmCurrEntry 2 }

    gmcrf10gEqptPmCurrValidity OBJECT-TYPE
        SYNTAX INTEGER { false(1), true(2) }
        ACCESS read-only
        STATUS mandatory
        DESCRIPTION
            "Current equipment PM validity."
        ::= { gmcrf10gEqptPmCurrEntry 3 }

    gmcrf10gEqptPmCurrLocation OBJECT-TYPE
        SYNTAX INTEGER { farEnd(1), nearEnd(2) }
        ACCESS read-only
        STATUS mandatory
        DESCRIPTION
            "Current equipment PM location."
        ::= { gmcrf10gEqptPmCurrEntry 4 }

    gmcrf10gEqptPmCurrDirection OBJECT-TYPE
        SYNTAX INTEGER { na(1), rcv(2), trmt(3) }
        ACCESS read-only
        STATUS mandatory
        DESCRIPTION
            "Current equipment PM direction."
        ::= { gmcrf10gEqptPmCurrEntry 5 }

    gmcrf10gEqptPmCurrDate OBJECT-TYPE
        SYNTAX DisplayString
        ACCESS read-only
        STATUS mandatory
        DESCRIPTION
            "Current equipment PM date."
        ::= { gmcrf10gEqptPmCurrEntry 6 }

    gmcrf10gEqptPmCurrTime OBJECT-TYPE
        SYNTAX DisplayString
        ACCESS read-only
        STATUS mandatory
        DESCRIPTION
            "Current equipment PM time."
        ::= { gmcrf10gEqptPmCurrEntry 7 }

    --
    -- The elements in the gmcrf10gEqptPmHistTable subgroup of the cardConfiguration group
    --

    gmcrf10gEqptPmHistTable   OBJECT-TYPE
            SYNTAX  SEQUENCE OF Gmcrf10gEqptPmHistEntry
            ACCESS  not-accessible
            STATUS  mandatory
            DESCRIPTION
                    "GMCRF10G historical equipment PM table"
            ::= { gmcrf10g 4 }

    gmcrf10gEqptPmHistEntry   OBJECT-TYPE
            SYNTAX  Gmcrf10gEqptPmHistEntry
            ACCESS  not-accessible
            STATUS  mandatory
            DESCRIPTION
                    "GMCRF10G historical equipment PM entry format."
            INDEX   { eqptBay, eqptShelf, eqptSlot, gmcrf10gEqptPmHistInterval, gmcrf10gEqptPmHistType }
            ::= { gmcrf10gEqptPmHistTable 1 }

    Gmcrf10gEqptPmHistEntry   ::=
            SEQUENCE 
            {
                gmcrf10gEqptPmHistInterval     INTEGER,
                gmcrf10gEqptPmHistType         INTEGER,
                gmcrf10gEqptPmHistValue        DisplayString,
                gmcrf10gEqptPmHistValidity     INTEGER,
                gmcrf10gEqptPmHistLocation     INTEGER,
                gmcrf10gEqptPmHistDirection    INTEGER,
                gmcrf10gEqptPmHistDate         DisplayString,
                gmcrf10gEqptPmHistTime         DisplayString
            }

    gmcrf10gEqptPmHistInterval OBJECT-TYPE
        SYNTAX INTEGER (1..32)
        ACCESS read-only
        STATUS mandatory
        DESCRIPTION
            "Historical equipment PM interval."
        ::= { gmcrf10gEqptPmHistEntry 1 }

    gmcrf10gEqptPmHistType OBJECT-TYPE
        SYNTAX INTEGER { lbc(2), ltemp(4), opt(5) }
        ACCESS read-only
        STATUS mandatory
        DESCRIPTION
            "Historical equipment PM type."
        ::= { gmcrf10gEqptPmHistEntry 2 }

    gmcrf10gEqptPmHistValue OBJECT-TYPE
        SYNTAX DisplayString
        ACCESS read-only
        STATUS mandatory
        DESCRIPTION
            "Historical equipment PM value."
        ::= { gmcrf10gEqptPmHistEntry 3 }

    gmcrf10gEqptPmHistValidity OBJECT-TYPE
        SYNTAX INTEGER { false(1), true(2) }
        ACCESS read-only
        STATUS mandatory
        DESCRIPTION
            "Historical equipment PM validity."
        ::= { gmcrf10gEqptPmHistEntry 4 }

    gmcrf10gEqptPmHistLocation OBJECT-TYPE
        SYNTAX INTEGER { farEnd(1), nearEnd(2) }
        ACCESS read-only
        STATUS mandatory
        DESCRIPTION
            "Historical equipment PM location."
        ::= { gmcrf10gEqptPmHistEntry 5 }

    gmcrf10gEqptPmHistDirection OBJECT-TYPE
        SYNTAX INTEGER { na(1), rcv(2), trmt(3) }
        ACCESS read-only
        STATUS mandatory
        DESCRIPTION
            "Historical equipment PM direction."
        ::= { gmcrf10gEqptPmHistEntry 6 }

    gmcrf10gEqptPmHistDate OBJECT-TYPE
        SYNTAX DisplayString
        ACCESS read-only
        STATUS mandatory
        DESCRIPTION
            "Historical equipment PM date."
        ::= { gmcrf10gEqptPmHistEntry 7 }

    gmcrf10gEqptPmHistTime OBJECT-TYPE
        SYNTAX DisplayString
        ACCESS read-only
        STATUS mandatory
        DESCRIPTION
            "Historical equipment PM time."
        ::= { gmcrf10gEqptPmHistEntry 8 }

    --
    -- The elements in the gmcrf10gFacPmCurrTable subgroup of the cardConfiguration group
    --

    gmcrf10gFacPmCurrTable   OBJECT-TYPE
            SYNTAX  SEQUENCE OF Gmcrf10gFacPmCurrEntry
            ACCESS  not-accessible
            STATUS  mandatory
            DESCRIPTION
                    "GMCRF10G current facility PM table"
            ::= { gmcrf10g 5 }

    gmcrf10gFacPmCurrEntry   OBJECT-TYPE
            SYNTAX  Gmcrf10gFacPmCurrEntry
            ACCESS  not-accessible
            STATUS  mandatory
            DESCRIPTION
                    "GMCRF10G current facility PM entry format."
            INDEX   { eqptBay, eqptShelf, eqptSlot, gmcrf10gFacPort, gmcrf10gFacPmCurrType }
            ::= { gmcrf10gFacPmCurrTable 1 }

    Gmcrf10gFacPmCurrEntry   ::=
            SEQUENCE 
            {
                gmcrf10gFacPmCurrType         INTEGER,
                gmcrf10gFacPmCurrValue        DisplayString,
                gmcrf10gFacPmCurrOcFacility   INTEGER,
                gmcrf10gFacPmCurrValidity     INTEGER,
                gmcrf10gFacPmCurrLocation     INTEGER,
                gmcrf10gFacPmCurrDirection    INTEGER,
                gmcrf10gFacPmCurrDate         DisplayString,
                gmcrf10gFacPmCurrTime         DisplayString
            }

    gmcrf10gFacPmCurrType OBJECT-TYPE
        SYNTAX INTEGER { cvs(4), ess(5), opr(8), sefss(11), sess(12) }
        ACCESS read-only
        STATUS mandatory
        DESCRIPTION
            "Current facility PM type."
        ::= { gmcrf10gFacPmCurrEntry 1 }

    gmcrf10gFacPmCurrValue OBJECT-TYPE
        SYNTAX DisplayString
        ACCESS read-only
        STATUS mandatory
        DESCRIPTION
            "Current facility PM value."
        ::= { gmcrf10gFacPmCurrEntry 2 }

    gmcrf10gFacPmCurrOcFacility OBJECT-TYPE
        SYNTAX INTEGER { oc12(1), oc192(2), oc24(3), oc48(4), oc3(5) }
        ACCESS read-only
        STATUS mandatory
        DESCRIPTION
            "Current facility PM OC facility."
        ::= { gmcrf10gFacPmCurrEntry 3 }

    gmcrf10gFacPmCurrValidity OBJECT-TYPE
        SYNTAX INTEGER { false(1), true(2) }
        ACCESS read-only
        STATUS mandatory
        DESCRIPTION
            "Current facility PM validity."
        ::= { gmcrf10gFacPmCurrEntry 4 }

    gmcrf10gFacPmCurrLocation OBJECT-TYPE
        SYNTAX INTEGER { farEnd(1), nearEnd(2) }
        ACCESS read-only
        STATUS mandatory
        DESCRIPTION
            "Current facility PM location."
        ::= { gmcrf10gFacPmCurrEntry 5 }

    gmcrf10gFacPmCurrDirection OBJECT-TYPE
        SYNTAX INTEGER { na(1), rcv(2), trmt(3) }
        ACCESS read-only
        STATUS mandatory
        DESCRIPTION
            "Current facility PM direction."
        ::= { gmcrf10gFacPmCurrEntry 6 }

    gmcrf10gFacPmCurrDate OBJECT-TYPE
        SYNTAX DisplayString
        ACCESS read-only
        STATUS mandatory
        DESCRIPTION
            "Current facility PM date."
        ::= { gmcrf10gFacPmCurrEntry 7 }

    gmcrf10gFacPmCurrTime OBJECT-TYPE
        SYNTAX DisplayString
        ACCESS read-only
        STATUS mandatory
        DESCRIPTION
            "Current facility PM time."
        ::= { gmcrf10gFacPmCurrEntry 8 }

    --
    -- The elements in the gmcrf10gFacPmHistTable subgroup of the cardConfiguration group
    --

    gmcrf10gFacPmHistTable   OBJECT-TYPE
            SYNTAX  SEQUENCE OF Gmcrf10gFacPmHistEntry
            ACCESS  not-accessible
            STATUS  mandatory
            DESCRIPTION
                    "GMCRF10G historical facility PM table"
            ::= { gmcrf10g 6 }

    gmcrf10gFacPmHistEntry   OBJECT-TYPE
            SYNTAX  Gmcrf10gFacPmHistEntry
            ACCESS  not-accessible
            STATUS  mandatory
            DESCRIPTION
                    "GMCRF10G historical facility PM entry format."
            INDEX   { eqptBay, eqptShelf, eqptSlot, gmcrf10gFacPort, gmcrf10gFacPmHistInterval, gmcrf10gFacPmHistType }
            ::= { gmcrf10gFacPmHistTable 1 }

    Gmcrf10gFacPmHistEntry   ::=
            SEQUENCE 
            {
                gmcrf10gFacPmHistInterval     INTEGER,
                gmcrf10gFacPmHistType         INTEGER,
                gmcrf10gFacPmHistValue        DisplayString,
                gmcrf10gFacPmHistOcFacility   INTEGER,
                gmcrf10gFacPmHistValidity     INTEGER,
                gmcrf10gFacPmHistLocation     INTEGER,
                gmcrf10gFacPmHistDirection    INTEGER,
                gmcrf10gFacPmHistDate         DisplayString,
                gmcrf10gFacPmHistTime         DisplayString
            }

    gmcrf10gFacPmHistInterval OBJECT-TYPE
        SYNTAX INTEGER (1..32)
        ACCESS read-only
        STATUS mandatory
        DESCRIPTION
            "Historical facility PM interval."
        ::= { gmcrf10gFacPmHistEntry 1 }

    gmcrf10gFacPmHistType OBJECT-TYPE
        SYNTAX INTEGER { cvs(4), ess(5), opr(8), sefss(11), sess(12) }
        ACCESS read-only
        STATUS mandatory
        DESCRIPTION
            "Historical facility PM type."
        ::= { gmcrf10gFacPmHistEntry 2 }

    gmcrf10gFacPmHistValue OBJECT-TYPE
        SYNTAX DisplayString
        ACCESS read-only
        STATUS mandatory
        DESCRIPTION
            "Historical facility PM value."
        ::= { gmcrf10gFacPmHistEntry 3 }

    gmcrf10gFacPmHistOcFacility OBJECT-TYPE
        SYNTAX INTEGER { oc12(1), oc192(2), oc24(3), oc48(4), oc3(5) }
        ACCESS read-only
        STATUS mandatory
        DESCRIPTION
            "Historical facility PM OC facility."
        ::= { gmcrf10gFacPmHistEntry 4 }

    gmcrf10gFacPmHistValidity OBJECT-TYPE
        SYNTAX INTEGER { false(1), true(2) }
        ACCESS read-only
        STATUS mandatory
        DESCRIPTION
            "Historical facility PM validity."
        ::= { gmcrf10gFacPmHistEntry 5 }

    gmcrf10gFacPmHistLocation OBJECT-TYPE
        SYNTAX INTEGER { farEnd(1), nearEnd(2) }
        ACCESS read-only
        STATUS mandatory
        DESCRIPTION
            "Historical facility PM location."
        ::= { gmcrf10gFacPmHistEntry 6 }

    gmcrf10gFacPmHistDirection OBJECT-TYPE
        SYNTAX INTEGER { na(1), rcv(2), trmt(3) }
        ACCESS read-only
        STATUS mandatory
        DESCRIPTION
            "Historical facility PM direction."
        ::= { gmcrf10gFacPmHistEntry 7 }

    gmcrf10gFacPmHistDate OBJECT-TYPE
        SYNTAX DisplayString
        ACCESS read-only
        STATUS mandatory
        DESCRIPTION
            "Historical facility PM date."
        ::= { gmcrf10gFacPmHistEntry 8 }

    gmcrf10gFacPmHistTime OBJECT-TYPE
        SYNTAX DisplayString
        ACCESS read-only
        STATUS mandatory
        DESCRIPTION
            "Historical facility PM time."
        ::= { gmcrf10gFacPmHistEntry 9 }

    --
    -- The elements in the gmcrf10gl subgroup of the cardConfiguration group
    --

    gmcrf10glTable   OBJECT-TYPE
            SYNTAX  SEQUENCE OF Gmcrf10glEntry
            ACCESS  not-accessible
            STATUS  mandatory
            DESCRIPTION
                    "GMCRF10GL module table"
            ::= { gmcrf10gl 1 }

    gmcrf10glEntry   OBJECT-TYPE
            SYNTAX  Gmcrf10glEntry
            ACCESS  not-accessible
            STATUS  mandatory
            DESCRIPTION
                    "GMCRF10GL entry format."
            INDEX   { eqptBay, eqptShelf, eqptSlot }
            ::= { gmcrf10glTable 1 }

    Gmcrf10glEntry   ::=
            SEQUENCE 
            {
                gmcrf10glSubType                 DisplayString,
                gmcrf10glItuNum                  ItuSelection2,
                gmcrf10glApsd                    INTEGER,
                gmcrf10glProtocol                INTEGER,
                gmcrf10glPrimaryState            INTEGER,
                gmcrf10glSecondaryState          INTEGER,
                gmcrf10glAdminState              INTEGER,
                gmcrf10glPmStatus                INTEGER
            }

    gmcrf10glSubType OBJECT-TYPE
        SYNTAX DisplayString
        ACCESS read-only
        STATUS mandatory
        DESCRIPTION
            "Module sub type."
        ::= { gmcrf10glEntry 1 }

    gmcrf10glItuNum    OBJECT-TYPE
        SYNTAX ItuSelection2
        ACCESS read-write
        STATUS mandatory
        DESCRIPTION
            "Module supported ITU channel.  This field is setable
             for modules with LRT subtype only.  Setting this field 
             for modules with any other subtype will return an error."
        ::= { gmcrf10glEntry 2 }

    gmcrf10glApsd      OBJECT-TYPE
        SYNTAX INTEGER { off(1), on(2) }
        ACCESS read-write
        STATUS mandatory
        DESCRIPTION
            "Module Automatic Power Shut Down setting.  The modules's
             primary state must be set OOS to modified this field."
        ::= { gmcrf10glEntry 3 }

    gmcrf10glProtocol  OBJECT-TYPE
        SYNTAX INTEGER { sdh(1), sonet(2) }
        ACCESS read-write
        STATUS mandatory
        DESCRIPTION
            "Module PM reporting protocol."
        ::= { gmcrf10glEntry 4 }

    gmcrf10glPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmcrf10glEntry 5 }

    gmcrf10glSecondaryState OBJECT-TYPE
        SYNTAX SecondaryState
        ACCESS read-only
        STATUS mandatory
        DESCRIPTION
            "Secondary state of module."
        ::= { gmcrf10glEntry 6 }

    gmcrf10glAdminState OBJECT-TYPE
        SYNTAX INTEGER { other(1), reset(2) }
        ACCESS read-write
        STATUS mandatory
        DESCRIPTION
            "Administration state of module.  This field is used
             to reset the module.  Reading this field always 
             returns other(1)."
        ::= { gmcrf10glEntry 7 }

    gmcrf10glPmStatus OBJECT-TYPE
        SYNTAX PmState
        ACCESS read-write
        STATUS mandatory
        DESCRIPTION
            "Perfornance monitoring status of module."
        ::= { gmcrf10glEntry 8 }

    --
    -- The elements in the gmcrf10glFacilities subgroup of the configuration group
    --

    gmcrf10glFacTable   OBJECT-TYPE
            SYNTAX  SEQUENCE OF Gmcrf10glFacEntry
            ACCESS  not-accessible
            STATUS  mandatory
            DESCRIPTION
                    "GMCRF10GL facility table."
            ::= { gmcrf10gl 2 }

    gmcrf10glFacEntry   OBJECT-TYPE
            SYNTAX  Gmcrf10glFacEntry
            ACCESS  not-accessible
            STATUS  mandatory
            DESCRIPTION
                    "GMCRF10GL facility entry format"
            INDEX   { eqptBay, eqptShelf, eqptSlot, gmcrf10glFacPort }
            ::= { gmcrf10glFacTable 1 }

    Gmcrf10glFacEntry   ::=
            SEQUENCE 
            {
                gmcrf10glFacPort             INTEGER,
                gmcrf10glFacOpr0             DisplayString,
                gmcrf10glFacPrimaryState     INTEGER,
                gmcrf10glFacSecondaryState   INTEGER,
                gmcrf10glFacOpr              DisplayString,
                gmcrf10glFacOprLowTh         DisplayString,
                gmcrf10glFacOprHighTh        DisplayString,
                gmcrf10glFacLoopbackState    INTEGER
            }

    gmcrf10glFacPort OBJECT-TYPE
        SYNTAX INTEGER { cpe(1), line(2) }
        ACCESS read-only
        STATUS mandatory
        DESCRIPTION
            "Port portion of GMCRF10GL facility address."
        ::= { gmcrf10glFacEntry 1 }

    gmcrf10glFacOpr0 OBJECT-TYPE
        SYNTAX DisplayString
        ACCESS read-write
        STATUS mandatory
        DESCRIPTION
            "Nominal value of average optical output power
             of the received signal, or the Optical Power Received
             (OPR) in dBm. gmcrf10glFacOpr0 is valid for port line(2)
             only.  Valid range for the CPE port is -26.0 to -6.0."
        ::= { gmcrf10glFacEntry 2 }

    gmcrf10glFacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmcrf10glFacEntry 3 }

    gmcrf10glFacSecondaryState OBJECT-TYPE
        SYNTAX SecondaryState
        ACCESS read-only
        STATUS mandatory
        DESCRIPTION
            "Secondary state of port."
        ::= { gmcrf10glFacEntry 4 }

    gmcrf10glFacOpr OBJECT-TYPE
        SYNTAX DisplayString
        ACCESS read-only
        STATUS mandatory
        DESCRIPTION
            "Nominal value of average optical output power
             of the received signal, or the Optical Power Received
             (OPR) in dBm. gmcrf10glFacOpr is valid for port line(1or2)
             only."  
        ::= { gmcrf10glFacEntry 5 }

    gmcrf10glFacOprLowTh OBJECT-TYPE
        SYNTAX DisplayString
        ACCESS read-write
        STATUS mandatory
        DESCRIPTION
            "Threshold value of OPRlow in dBm.
             The valid range is Min. -20.0 dBm to Max. -0.4 dBm."
        ::= { gmcrf10glFacEntry 6 }

    gmcrf10glFacOprHighTh OBJECT-TYPE
        SYNTAX DisplayString
        ACCESS read-write
        STATUS mandatory
        DESCRIPTION
            "Threshold value of OPR high in dBm.
             The valid range is Min. 0.4 dBm to Max. 20.0 dBm."
        ::= { gmcrf10glFacEntry 7 }

    gmcrf10glFacLoopbackState OBJECT-TYPE
        SYNTAX LoopbackState
        ACCESS read-write
        STATUS mandatory
        DESCRIPTION
            "Loopback state of port. Ports must be set OOS before
             they can be placed into loopback."
        ::= { gmcrf10glFacEntry 8 }


    --
    -- The elements in the gmcrf10glEqptPmCurrTable subgroup of the cardConfiguration group
    --

    gmcrf10glEqptPmCurrTable   OBJECT-TYPE
            SYNTAX  SEQUENCE OF Gmcrf10glEqptPmCurrEntry
            ACCESS  not-accessible
            STATUS  mandatory
            DESCRIPTION
                    "GMCRF10GL current equipment PM table"
            ::= { gmcrf10gl 3 }

    gmcrf10glEqptPmCurrEntry   OBJECT-TYPE
            SYNTAX  Gmcrf10glEqptPmCurrEntry
            ACCESS  not-accessible
            STATUS  mandatory
            DESCRIPTION
                    "GMCRF10GL current equipment PM entry format."
            INDEX   { eqptBay, eqptShelf, eqptSlot, gmcrf10glEqptPmCurrType }
            ::= { gmcrf10glEqptPmCurrTable 1 }

    Gmcrf10glEqptPmCurrEntry   ::=
            SEQUENCE 
            {
                gmcrf10glEqptPmCurrType         INTEGER,
                gmcrf10glEqptPmCurrValue        DisplayString,
                gmcrf10glEqptPmCurrValidity     INTEGER,
                gmcrf10glEqptPmCurrLocation     INTEGER,
                gmcrf10glEqptPmCurrDirection    INTEGER,
                gmcrf10glEqptPmCurrDate         DisplayString,
                gmcrf10glEqptPmCurrTime         DisplayString
            }

    gmcrf10glEqptPmCurrType OBJECT-TYPE
        SYNTAX INTEGER { lbc(2), ltemp(4), opt(5) }
        ACCESS read-only
        STATUS mandatory
        DESCRIPTION
            "Current equipment PM type."
        ::= { gmcrf10glEqptPmCurrEntry 1 }

    gmcrf10glEqptPmCurrValue OBJECT-TYPE
        SYNTAX DisplayString
        ACCESS read-only
        STATUS mandatory
        DESCRIPTION
            "Current equipment PM value."
        ::= { gmcrf10glEqptPmCurrEntry 2 }

    gmcrf10glEqptPmCurrValidity OBJECT-TYPE
        SYNTAX INTEGER { false(1), true(2) }
        ACCESS read-only
        STATUS mandatory
        DESCRIPTION
            "Current equipment PM validity."
        ::= { gmcrf10glEqptPmCurrEntry 3 }

    gmcrf10glEqptPmCurrLocation OBJECT-TYPE
        SYNTAX INTEGER { farEnd(1), nearEnd(2) }
        ACCESS read-only
        STATUS mandatory
        DESCRIPTION
            "Current equipment PM location."
        ::= { gmcrf10glEqptPmCurrEntry 4 }

    gmcrf10glEqptPmCurrDirection OBJECT-TYPE
        SYNTAX INTEGER { na(1), rcv(2), trmt(3) }
        ACCESS read-only
        STATUS mandatory
        DESCRIPTION
            "Current equipment PM direction."
        ::= { gmcrf10glEqptPmCurrEntry 5 }

    gmcrf10glEqptPmCurrDate OBJECT-TYPE
        SYNTAX DisplayString
        ACCESS read-only
        STATUS mandatory
        DESCRIPTION
            "Current equipment PM date."
        ::= { gmcrf10glEqptPmCurrEntry 6 }

    gmcrf10glEqptPmCurrTime OBJECT-TYPE
        SYNTAX DisplayString
        ACCESS read-only
        STATUS mandatory
        DESCRIPTION
            "Current equipment PM time."
        ::= { gmcrf10glEqptPmCurrEntry 7 }

    --
    -- The elements in the gmcrf10glEqptPmHistTable subgroup of the cardConfiguration group
    --

    gmcrf10glEqptPmHistTable   OBJECT-TYPE
            SYNTAX  SEQUENCE OF Gmcrf10glEqptPmHistEntry
            ACCESS  not-accessible
            STATUS  mandatory
            DESCRIPTION
                    "GMCRF10GL historical equipment PM table"
            ::= { gmcrf10gl 4 }

    gmcrf10glEqptPmHistEntry   OBJECT-TYPE
            SYNTAX  Gmcrf10glEqptPmHistEntry
            ACCESS  not-accessible
            STATUS  mandatory
            DESCRIPTION
                    "GMCRF10GL historical equipment PM entry format."
            INDEX   { eqptBay, eqptShelf, eqptSlot, gmcrf10glEqptPmHistInterval, gmcrf10glEqptPmHistType }
            ::= { gmcrf10glEqptPmHistTable 1 }

    Gmcrf10glEqptPmHistEntry   ::=
            SEQUENCE 
            {
                gmcrf10glEqptPmHistInterval     INTEGER,
                gmcrf10glEqptPmHistType         INTEGER,
                gmcrf10glEqptPmHistValue        DisplayString,
                gmcrf10glEqptPmHistValidity     INTEGER,
                gmcrf10glEqptPmHistLocation     INTEGER,
                gmcrf10glEqptPmHistDirection    INTEGER,
                gmcrf10glEqptPmHistDate         DisplayString,
                gmcrf10glEqptPmHistTime         DisplayString
            }

    gmcrf10glEqptPmHistInterval OBJECT-TYPE
        SYNTAX INTEGER (1..32)
        ACCESS read-only
        STATUS mandatory
        DESCRIPTION
            "Historical equipment PM interval."
        ::= { gmcrf10glEqptPmHistEntry 1 }

    gmcrf10glEqptPmHistType OBJECT-TYPE
        SYNTAX INTEGER { lbc(2), ltemp(4), opt(5) }
        ACCESS read-only
        STATUS mandatory
        DESCRIPTION
            "Historical equipment PM type."
        ::= { gmcrf10glEqptPmHistEntry 2 }

    gmcrf10glEqptPmHistValue OBJECT-TYPE
        SYNTAX DisplayString
        ACCESS read-only
        STATUS mandatory
        DESCRIPTION
            "Historical equipment PM value."
        ::= { gmcrf10glEqptPmHistEntry 3 }

    gmcrf10glEqptPmHistValidity OBJECT-TYPE
        SYNTAX INTEGER { false(1), true(2) }
        ACCESS read-only
        STATUS mandatory
        DESCRIPTION
            "Historical equipment PM validity."
        ::= { gmcrf10glEqptPmHistEntry 4 }

    gmcrf10glEqptPmHistLocation OBJECT-TYPE
        SYNTAX INTEGER { farEnd(1), nearEnd(2) }
        ACCESS read-only
        STATUS mandatory
        DESCRIPTION
            "Historical equipment PM location."
        ::= { gmcrf10glEqptPmHistEntry 5 }

    gmcrf10glEqptPmHistDirection OBJECT-TYPE
        SYNTAX INTEGER { na(1), rcv(2), trmt(3) }
        ACCESS read-only
        STATUS mandatory
        DESCRIPTION
            "Historical equipment PM direction."
        ::= { gmcrf10glEqptPmHistEntry 6 }

    gmcrf10glEqptPmHistDate OBJECT-TYPE
        SYNTAX DisplayString
        ACCESS read-only
        STATUS mandatory
        DESCRIPTION
            "Historical equipment PM date."
        ::= { gmcrf10glEqptPmHistEntry 7 }

    gmcrf10glEqptPmHistTime OBJECT-TYPE
        SYNTAX DisplayString
        ACCESS read-only
        STATUS mandatory
        DESCRIPTION
            "Historical equipment PM time."
        ::= { gmcrf10glEqptPmHistEntry 8 }

    --
    -- The elements in the gmcrf10glFacPmCurrTable subgroup of the cardConfiguration group
    --

    gmcrf10glFacPmCurrTable   OBJECT-TYPE
            SYNTAX  SEQUENCE OF Gmcrf10glFacPmCurrEntry
            ACCESS  not-accessible
            STATUS  mandatory
            DESCRIPTION
                    "GMCRF10GL current facility PM table"
            ::= { gmcrf10gl 5 }

    gmcrf10glFacPmCurrEntry   OBJECT-TYPE
            SYNTAX  Gmcrf10glFacPmCurrEntry
            ACCESS  not-accessible
            STATUS  mandatory
            DESCRIPTION
                    "GMCRF10GL current facility PM entry format."
            INDEX   { eqptBay, eqptShelf, eqptSlot, gmcrf10glFacPort, gmcrf10glFacPmCurrType }
            ::= { gmcrf10glFacPmCurrTable 1 }

    Gmcrf10glFacPmCurrEntry   ::=
            SEQUENCE 
            {
                gmcrf10glFacPmCurrType         INTEGER,
                gmcrf10glFacPmCurrValue        DisplayString,
                gmcrf10glFacPmCurrOcFacility   INTEGER,
                gmcrf10glFacPmCurrValidity     INTEGER,
                gmcrf10glFacPmCurrLocation     INTEGER,
                gmcrf10glFacPmCurrDirection    INTEGER,
                gmcrf10glFacPmCurrDate         DisplayString,
                gmcrf10glFacPmCurrTime         DisplayString
            }

    gmcrf10glFacPmCurrType OBJECT-TYPE
        SYNTAX INTEGER { opr(8) }
        ACCESS read-only
        STATUS mandatory
        DESCRIPTION
            "Current facility PM type."
        ::= { gmcrf10glFacPmCurrEntry 1 }

    gmcrf10glFacPmCurrValue OBJECT-TYPE
        SYNTAX DisplayString
        ACCESS read-only
        STATUS mandatory
        DESCRIPTION
            "Current facility PM value."
        ::= { gmcrf10glFacPmCurrEntry 2 }

    gmcrf10glFacPmCurrOcFacility OBJECT-TYPE
        SYNTAX INTEGER { oc12(1), oc192(2), oc24(3), oc48(4), oc3(5) }
        ACCESS read-only
        STATUS mandatory
        DESCRIPTION
            "Current facility PM OC facility."
        ::= { gmcrf10glFacPmCurrEntry 3 }

    gmcrf10glFacPmCurrValidity OBJECT-TYPE
        SYNTAX INTEGER { false(1), true(2) }
        ACCESS read-only
        STATUS mandatory
        DESCRIPTION
            "Current facility PM validity."
        ::= { gmcrf10glFacPmCurrEntry 4 }

    gmcrf10glFacPmCurrLocation OBJECT-TYPE
        SYNTAX INTEGER { farEnd(1), nearEnd(2) }
        ACCESS read-only
        STATUS mandatory
        DESCRIPTION
            "Current facility PM location."
        ::= { gmcrf10glFacPmCurrEntry 5 }

    gmcrf10glFacPmCurrDirection OBJECT-TYPE
        SYNTAX INTEGER { na(1), rcv(2), trmt(3) }
        ACCESS read-only
        STATUS mandatory
        DESCRIPTION
            "Current facility PM direction."
        ::= { gmcrf10glFacPmCurrEntry 6 }

    gmcrf10glFacPmCurrDate OBJECT-TYPE
        SYNTAX DisplayString
        ACCESS read-only
        STATUS mandatory
        DESCRIPTION
            "Current facility PM date."
        ::= { gmcrf10glFacPmCurrEntry 7 }

    gmcrf10glFacPmCurrTime OBJECT-TYPE
        SYNTAX DisplayString
        ACCESS read-only
        STATUS mandatory
        DESCRIPTION
            "Current facility PM time."
        ::= { gmcrf10glFacPmCurrEntry 8 }

    --
    -- The elements in the gmcrf10glFacPmHistTable subgroup of the cardConfiguration group
    --

    gmcrf10glFacPmHistTable   OBJECT-TYPE
            SYNTAX  SEQUENCE OF Gmcrf10glFacPmHistEntry
            ACCESS  not-accessible
            STATUS  mandatory
            DESCRIPTION
                    "GMCRF10GL historical facility PM table"
            ::= { gmcrf10gl 6 }

    gmcrf10glFacPmHistEntry   OBJECT-TYPE
            SYNTAX  Gmcrf10glFacPmHistEntry
            ACCESS  not-accessible
            STATUS  mandatory
            DESCRIPTION
                    "GMCRF10GL historical facility PM entry format."
            INDEX   { eqptBay, eqptShelf, eqptSlot, gmcrf10glFacPort, gmcrf10glFacPmHistInterval, gmcrf10glFacPmHistType }
            ::= { gmcrf10glFacPmHistTable 1 }

    Gmcrf10glFacPmHistEntry   ::=
            SEQUENCE 
            {
                gmcrf10glFacPmHistInterval     INTEGER,
                gmcrf10glFacPmHistType         INTEGER,
                gmcrf10glFacPmHistValue        DisplayString,
                gmcrf10glFacPmHistOcFacility   INTEGER,
                gmcrf10glFacPmHistValidity     INTEGER,
                gmcrf10glFacPmHistLocation     INTEGER,
                gmcrf10glFacPmHistDirection    INTEGER,
                gmcrf10glFacPmHistDate         DisplayString,
                gmcrf10glFacPmHistTime         DisplayString
            }

    gmcrf10glFacPmHistInterval OBJECT-TYPE
        SYNTAX INTEGER (1..32)
        ACCESS read-only
        STATUS mandatory
        DESCRIPTION
            "Historical facility PM interval."
        ::= { gmcrf10glFacPmHistEntry 1 }

    gmcrf10glFacPmHistType OBJECT-TYPE
        SYNTAX INTEGER { opr(8) }
        ACCESS read-only
        STATUS mandatory
        DESCRIPTION
            "Historical facility PM type."
        ::= { gmcrf10glFacPmHistEntry 2 }

    gmcrf10glFacPmHistValue OBJECT-TYPE
        SYNTAX DisplayString
        ACCESS read-only
        STATUS mandatory
        DESCRIPTION
            "Historical facility PM value."
        ::= { gmcrf10glFacPmHistEntry 3 }

    gmcrf10glFacPmHistOcFacility OBJECT-TYPE
        SYNTAX INTEGER { oc12(1), oc192(2), oc24(3), oc48(4), oc3(5) }
        ACCESS read-only
        STATUS mandatory
        DESCRIPTION
            "Historical facility PM OC facility."
        ::= { gmcrf10glFacPmHistEntry 4 }

    gmcrf10glFacPmHistValidity OBJECT-TYPE
        SYNTAX INTEGER { false(1), true(2) }
        ACCESS read-only
        STATUS mandatory
        DESCRIPTION
            "Historical facility PM validity."
        ::= { gmcrf10glFacPmHistEntry 5 }

    gmcrf10glFacPmHistLocation OBJECT-TYPE
        SYNTAX INTEGER { farEnd(1), nearEnd(2) }
        ACCESS read-only
        STATUS mandatory
        DESCRIPTION
            "Historical facility PM location."
        ::= { gmcrf10glFacPmHistEntry 6 }

    gmcrf10glFacPmHistDirection OBJECT-TYPE
        SYNTAX INTEGER { na(1), rcv(2), trmt(3) }
        ACCESS read-only
        STATUS mandatory
        DESCRIPTION
            "Historical facility PM direction."
        ::= { gmcrf10glFacPmHistEntry 7 }

    gmcrf10glFacPmHistDate OBJECT-TYPE
        SYNTAX DisplayString
        ACCESS read-only
        STATUS mandatory
        DESCRIPTION
            "Historical facility PM date."
        ::= { gmcrf10glFacPmHistEntry 8 }

    gmcrf10glFacPmHistTime OBJECT-TYPE
        SYNTAX DisplayString
        ACCESS read-only
        STATUS mandatory
        DESCRIPTION
            "Historical facility PM time."
        ::= { gmcrf10glFacPmHistEntry 9 }

    --
    -- The elements in the gmdcm subgroup of the cardConfiguration group
    --

    gmdcmTable   OBJECT-TYPE
            SYNTAX  SEQUENCE OF GmdcmEntry
            ACCESS  not-accessible
            STATUS  mandatory
            DESCRIPTION
                    "GMDCM module table"
            ::= { gmdcm 1 }

    gmdcmEntry   OBJECT-TYPE
            SYNTAX  GmdcmEntry
            ACCESS  not-accessible
            STATUS  mandatory
            DESCRIPTION
                    "GMDCM entry format."
            INDEX   { eqptBay, eqptShelf, eqptSlot }
            ::= { gmdcmTable 1 }

    GmdcmEntry   ::=
            SEQUENCE 
            {
                gmdcmDispersion             DisplayString,
                gmdcmInsertionLoss          DisplayString,
                gmdcmPrimaryState           INTEGER,
                gmdcmSecondaryState         INTEGER,
                gmdcmAdminState             INTEGER
            }

    gmdcmDispersion OBJECT-TYPE
        SYNTAX DisplayString
        ACCESS read-only
        STATUS mandatory
        DESCRIPTION
            "Value of the module dispersion."
        ::= { gmdcmEntry 1 }

    gmdcmInsertionLoss OBJECT-TYPE
        SYNTAX DisplayString
        ACCESS read-only
        STATUS mandatory
        DESCRIPTION
            "Value of the module insertion loss."
        ::= { gmdcmEntry 2 }

    gmdcmPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmdcmEntry 3 }

    gmdcmSecondaryState OBJECT-TYPE
        SYNTAX SecondaryState
        ACCESS read-only
        STATUS mandatory
        DESCRIPTION
            "Secondary state of module."
        ::= { gmdcmEntry 4 }

    gmdcmAdminState OBJECT-TYPE
        SYNTAX INTEGER { other(1), reset(2) }
        ACCESS read-write
        STATUS mandatory
        DESCRIPTION
            "Administration state of module.  This field is used
             to reset the module.  Reading this field always 
             returns other(1)."
        ::= { gmdcmEntry 6 }

    --
    -- The elements in the gmdm10 subgroup of the cardConfiguration group
    --

    gmdm10Table   OBJECT-TYPE
            SYNTAX  SEQUENCE OF Gmdm10Entry
            ACCESS  not-accessible
            STATUS  mandatory
            DESCRIPTION
                    "GMDM10 module table"
            ::= { gmdm10 1 }

    gmdm10Entry   OBJECT-TYPE
            SYNTAX  Gmdm10Entry
            ACCESS  not-accessible
            STATUS  mandatory
            DESCRIPTION
                    "GMDM10 entry format."
            INDEX   { eqptBay, eqptShelf, eqptSlot }
            ::= { gmdm10Table 1 }

    Gmdm10Entry   ::=
            SEQUENCE 
            {
                gmdm10SubType                 DisplayString,
                gmdm10ItuNum                  ItuSelection,
                gmdm10ClockSource             INTEGER,
                gmdm10ClockSelection          INTEGER,
                gmdm10Opt0                    DisplayString,
                gmdm10Lbc0                    DisplayString,
                gmdm10ClientApsd              INTEGER,
                gmdm10Protocol                INTEGER,
                gmdm10ActiveTimingSource      INTEGER,
                gmdm10PrimaryState            INTEGER,
                gmdm10SecondaryState          INTEGER,
                gmdm10AdminState              INTEGER,
                gmdm10PmStatus                INTEGER
            }

    gmdm10SubType OBJECT-TYPE
        SYNTAX DisplayString
        ACCESS read-only
        STATUS mandatory
        DESCRIPTION
            "Module sub type."
        ::= { gmdm10Entry 1 }

    gmdm10ItuNum    OBJECT-TYPE
        SYNTAX ItuSelection
        ACCESS read-write
        STATUS mandatory
        DESCRIPTION
            "Module supported ITU channel.  This field is setable
             for modules with LRT subtype only.  Setting this field 
             for modules with any other subtype will return an error."
        ::= { gmdm10Entry 2 }

    gmdm10ClockSource      OBJECT-TYPE
        SYNTAX INTEGER
        {
            illegal(0),
            extInt(1),
            extLineInt(2),
            ext(3),
            line(4),
            int(5),
            intExtLine(6),
            intLineExt(7),
            extIntLine(8),
            lineIntExt(9),
            lineExtInt(10)
        }
        ACCESS read-write
        STATUS mandatory
        DESCRIPTION
            "Module clock timing source setting."
        ::= { gmdm10Entry 3 }

    gmdm10ClockSelection      OBJECT-TYPE
        SYNTAX INTEGER { auto(1), forced(2) }
        ACCESS read-write
        STATUS mandatory
        DESCRIPTION
            "Module clock timing selection setting.."
        ::= { gmdm10Entry 4 }

    gmdm10Opt0      OBJECT-TYPE
        SYNTAX DisplayString
        ACCESS read-only
        STATUS mandatory
        DESCRIPTION
            "Nominal value of average optical output power of the
             transmitter, or the Optical Power Transmitted (OPT)
             in microWatts."
        ::= { gmdm10Entry 5 }

    gmdm10Lbc0      OBJECT-TYPE
        SYNTAX DisplayString
        ACCESS read-write
        STATUS mandatory
        DESCRIPTION
            "Nominal value of the Laser Bias Current (LBC) in mA."
        ::= { gmdm10Entry 6 }

    gmdm10ClientApsd      OBJECT-TYPE
        SYNTAX INTEGER { off(1), on(2) }
        ACCESS read-write
        STATUS mandatory
        DESCRIPTION
            "Enables/disables Client Auto Port Shut Down. 
             If enabled in case of loss of signal at the SONET  
             Rx interface, the FC ports would be shut down."
        ::= { gmdm10Entry 7 }

    gmdm10Protocol  OBJECT-TYPE
        SYNTAX INTEGER { sdh(1), sonet(2) }
        ACCESS read-write
        STATUS mandatory
        DESCRIPTION
            "Module PM reporting protocol."
        ::= { gmdm10Entry 8 }

    gmdm10ActiveTimingSource      OBJECT-TYPE
        SYNTAX INTEGER
        {
            ext(1),
            int(2),
            line(3),
            loop(4),
            primary(5),
            protect1(6),
            protect2(7),
            thru(8),
            unknown(9)
        }
        ACCESS read-only
        STATUS mandatory
        DESCRIPTION
            "Active timing source for the module."
        ::= { gmdm10Entry 9 }

    gmdm10PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmdm10Entry 10 }

    gmdm10SecondaryState OBJECT-TYPE
        SYNTAX SecondaryState
        ACCESS read-only
        STATUS mandatory
        DESCRIPTION
            "Secondary state of module."
        ::= { gmdm10Entry 11 }

    gmdm10AdminState OBJECT-TYPE
        SYNTAX INTEGER { other(1), reset(2) }
        ACCESS read-write
        STATUS mandatory
        DESCRIPTION
            "Administration state of module.  This field is used
             to reset the module.  Reading this field always 
             returns other(1)."
        ::= { gmdm10Entry 12 }

    gmdm10PmStatus OBJECT-TYPE
        SYNTAX PmState
        ACCESS read-write
        STATUS mandatory
        DESCRIPTION
            "Perfornance monitoring status of module."
        ::= { gmdm10Entry 13 }

    --
    -- The elements in the gmdm10Facilities subgroup of the configuration group
    --

    gmdm10FacTable   OBJECT-TYPE
            SYNTAX  SEQUENCE OF Gmdm10FacEntry
            ACCESS  not-accessible
            STATUS  mandatory
            DESCRIPTION
                    "GMDM10 facility table."
            ::= { gmdm10 2 }

    gmdm10FacEntry   OBJECT-TYPE
            SYNTAX  Gmdm10FacEntry
            ACCESS  not-accessible
            STATUS  mandatory
            DESCRIPTION
                    "GMDM10 facility entry format"
            INDEX   { eqptBay, eqptShelf, eqptSlot, gmdm10FacPort }
            ::= { gmdm10FacTable 1 }

    Gmdm10FacEntry   ::=
            SEQUENCE 
            {
                gmdm10FacPort               INTEGER,
                gmdm10FacConfigSpeed        INTEGER,
                gmdm10FacMediaType          INTEGER,
                gmdm10FacLinkStatus         INTEGER,
                gmdm10FacReceiverStatus     INTEGER,
                gmdm10FacFarEndApsd         INTEGER,
                gmdm10FacFarEndLinkStatus   INTEGER,
                gmdm10FacOpr0               DisplayString,
                gmdm10FacPrimaryState       INTEGER,
                gmdm10FacSecondaryState     INTEGER,
                gmdm10FacLoopbackState      INTEGER
            }

    gmdm10FacPort OBJECT-TYPE
        SYNTAX INTEGER
        {
            p1(1),
            p2(2),
            p3(3),
            p4(4),
            p5(5),
            p6(6),
            p7(7),
            p8(8),
            p9(9),
            p10(10),
            line(11)
        }
        ACCESS read-only
        STATUS mandatory
        DESCRIPTION
            "Port portion of GMDM10 facility address."
        ::= { gmdm10FacEntry 1 }

    gmdm10FacConfigSpeed OBJECT-TYPE
        SYNTAX INTEGER { disabled(1), fc1x(2), fc2x(3), gige(4) }
        ACCESS read-write
        STATUS mandatory
        DESCRIPTION
            "The configured speed of the interface.
             fc1x: Fiber channel speed both associated ports.
             fc2x: Twice Fiber channel speed on this port.
             gige: Gigabit Ethernet."
        ::= { gmdm10FacEntry 2 }

    gmdm10FacMediaType OBJECT-TYPE
        SYNTAX INTEGER { wav1310nm(1), wav850nm(2), na(3) }
        ACCESS read-only
        STATUS mandatory
        DESCRIPTION
            "The expected wavelength to be supported by the transceiver."
        ::= { gmdm10FacEntry 3 }

    gmdm10FacLinkStatus OBJECT-TYPE
        SYNTAX INTEGER { linkDown(1), linkUp(2) }
        ACCESS read-only
        STATUS mandatory
        DESCRIPTION
            "Link status."
        ::= { gmdm10FacEntry 4 }

    gmdm10FacReceiverStatus OBJECT-TYPE
        SYNTAX INTEGER { absent(1), disabled(2), faulty(3), mismatch(4), ok(5) }
        ACCESS read-only
        STATUS mandatory
        DESCRIPTION
            "Status of the transceiver.
             absent: Transceiver is not present
             faulty: Transceiver faulty
             disabled: Transceiver is disabled
             ok: Transceiver is ok."
        ::= { gmdm10FacEntry 5 }

    gmdm10FacFarEndApsd OBJECT-TYPE
        SYNTAX INTEGER { off(1), on(2) }
        ACCESS read-write
        STATUS mandatory
        DESCRIPTION
            "Enable/disable Far End Link Auto Port Shut Down. 
             If enabled in case of loss of link at the corresponding 
             far end port, the local FC port would be shut down."
        ::= { gmdm10FacEntry 6 }

    gmdm10FacFarEndLinkStatus OBJECT-TYPE
        SYNTAX INTEGER { linkDown(1), linkUp(2) }
        ACCESS read-only
        STATUS mandatory
        DESCRIPTION
            "Far End Link status"
        ::= { gmdm10FacEntry 7 }

    gmdm10FacOpr0 OBJECT-TYPE
        SYNTAX DisplayString
        ACCESS read-write
        STATUS mandatory
        DESCRIPTION
            "Nominal value of average optical output power
             of the received signal, or the Optical Power Received
             (OPR) in dBm. The valid range differs based on the
             port. Valid range for the line port is -26 to -6.
             OPR0 is invalid for all other ports."
        ::= { gmdm10FacEntry 8 }

    gmdm10FacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmdm10FacEntry 9 }

    gmdm10FacSecondaryState OBJECT-TYPE
        SYNTAX SecondaryState
        ACCESS read-only
        STATUS mandatory
        DESCRIPTION
            "Secondary state of port."
        ::= { gmdm10FacEntry 10 }

    gmdm10FacLoopbackState OBJECT-TYPE
        SYNTAX LoopbackState
        ACCESS read-write
        STATUS mandatory
        DESCRIPTION
            "Loopback state of port. Ports must be set OOS before they
             can be placed into loopback."
        ::= { gmdm10FacEntry 11 }

    --
    -- The elements in the gmdm10EqptPmCurrTable subgroup of the cardConfiguration group
    --

    gmdm10EqptPmCurrTable   OBJECT-TYPE
            SYNTAX  SEQUENCE OF Gmdm10EqptPmCurrEntry
            ACCESS  not-accessible
            STATUS  mandatory
            DESCRIPTION
                    "GMDM10 current equipment PM table"
            ::= { gmdm10 3 }

    gmdm10EqptPmCurrEntry   OBJECT-TYPE
            SYNTAX  Gmdm10EqptPmCurrEntry
            ACCESS  not-accessible
            STATUS  mandatory
            DESCRIPTION
                    "GMDM10 current equipment PM entry format."
            INDEX   { eqptBay, eqptShelf, eqptSlot, gmdm10EqptPmCurrType }
            ::= { gmdm10EqptPmCurrTable 1 }

    Gmdm10EqptPmCurrEntry   ::=
            SEQUENCE 
            {
                gmdm10EqptPmCurrType         INTEGER,
                gmdm10EqptPmCurrValue        DisplayString,
                gmdm10EqptPmCurrValidity     INTEGER,
                gmdm10EqptPmCurrLocation     INTEGER,
                gmdm10EqptPmCurrDirection    INTEGER,
                gmdm10EqptPmCurrDate         DisplayString,
                gmdm10EqptPmCurrTime         DisplayString
            }

    gmdm10EqptPmCurrType OBJECT-TYPE
        SYNTAX INTEGER { lbc(2), ltemp(4), opt(5) }
        ACCESS read-only
        STATUS mandatory
        DESCRIPTION
            "Current equipment PM type."
        ::= { gmdm10EqptPmCurrEntry 1 }

    gmdm10EqptPmCurrValue OBJECT-TYPE
        SYNTAX DisplayString
        ACCESS read-only
        STATUS mandatory
        DESCRIPTION
            "Current equipment PM value."
        ::= { gmdm10EqptPmCurrEntry 2 }

    gmdm10EqptPmCurrValidity OBJECT-TYPE
        SYNTAX INTEGER { false(1), true(2) }
        ACCESS read-only
        STATUS mandatory
        DESCRIPTION
            "Current equipment PM validity."
        ::= { gmdm10EqptPmCurrEntry 3 }

    gmdm10EqptPmCurrLocation OBJECT-TYPE
        SYNTAX INTEGER { farEnd(1), nearEnd(2) }
        ACCESS read-only
        STATUS mandatory
        DESCRIPTION
            "Current equipment PM location."
        ::= { gmdm10EqptPmCurrEntry 4 }

    gmdm10EqptPmCurrDirection OBJECT-TYPE
        SYNTAX INTEGER { na(1), rcv(2), trmt(3) }
        ACCESS read-only
        STATUS mandatory
        DESCRIPTION
            "Current equipment PM direction."
        ::= { gmdm10EqptPmCurrEntry 5 }

    gmdm10EqptPmCurrDate OBJECT-TYPE
        SYNTAX DisplayString
        ACCESS read-only
        STATUS mandatory
        DESCRIPTION
            "Current equipment PM date."
        ::= { gmdm10EqptPmCurrEntry 6 }

    gmdm10EqptPmCurrTime OBJECT-TYPE
        SYNTAX DisplayString
        ACCESS read-only
        STATUS mandatory
        DESCRIPTION
            "Current equipment PM time."
        ::= { gmdm10EqptPmCurrEntry 7 }

    --
    -- The elements in the gmdm10EqptPmHistTable subgroup of the cardConfiguration group
    --

    gmdm10EqptPmHistTable   OBJECT-TYPE
            SYNTAX  SEQUENCE OF Gmdm10EqptPmHistEntry
            ACCESS  not-accessible
            STATUS  mandatory
            DESCRIPTION
                    "GMDM10 historical equipment PM table"
            ::= { gmdm10 4 }

    gmdm10EqptPmHistEntry   OBJECT-TYPE
            SYNTAX  Gmdm10EqptPmHistEntry
            ACCESS  not-accessible
            STATUS  mandatory
            DESCRIPTION
                    "GMDM10 historical equipment PM entry format."
            INDEX   { eqptBay, eqptShelf, eqptSlot, gmdm10EqptPmHistInterval, gmdm10EqptPmHistType }
            ::= { gmdm10EqptPmHistTable 1 }

    Gmdm10EqptPmHistEntry   ::=
            SEQUENCE 
            {
                gmdm10EqptPmHistInterval     INTEGER,
                gmdm10EqptPmHistType         INTEGER,
                gmdm10EqptPmHistValue        DisplayString,
                gmdm10EqptPmHistValidity     INTEGER,
                gmdm10EqptPmHistLocation     INTEGER,
                gmdm10EqptPmHistDirection    INTEGER,
                gmdm10EqptPmHistDate         DisplayString,
                gmdm10EqptPmHistTime         DisplayString
            }

    gmdm10EqptPmHistInterval OBJECT-TYPE
        SYNTAX INTEGER (1..32)
        ACCESS read-only
        STATUS mandatory
        DESCRIPTION
            "Historical equipment PM interval."
        ::= { gmdm10EqptPmHistEntry 1 }

    gmdm10EqptPmHistType OBJECT-TYPE
        SYNTAX INTEGER { lbc(2), ltemp(4), opt(5) }
        ACCESS read-only
        STATUS mandatory
        DESCRIPTION
            "Historical equipment PM type."
        ::= { gmdm10EqptPmHistEntry 2 }

    gmdm10EqptPmHistValue OBJECT-TYPE
        SYNTAX DisplayString
        ACCESS read-only
        STATUS mandatory
        DESCRIPTION
            "Historical equipment PM value."
        ::= { gmdm10EqptPmHistEntry 3 }

    gmdm10EqptPmHistValidity OBJECT-TYPE
        SYNTAX INTEGER { false(1), true(2) }
        ACCESS read-only
        STATUS mandatory
        DESCRIPTION
            "Historical equipment PM validity."
        ::= { gmdm10EqptPmHistEntry 4 }

    gmdm10EqptPmHistLocation OBJECT-TYPE
        SYNTAX INTEGER { farEnd(1), nearEnd(2) }
        ACCESS read-only
        STATUS mandatory
        DESCRIPTION
            "Historical equipment PM location."
        ::= { gmdm10EqptPmHistEntry 5 }

    gmdm10EqptPmHistDirection OBJECT-TYPE
        SYNTAX INTEGER { na(1), rcv(2), trmt(3) }
        ACCESS read-only
        STATUS mandatory
        DESCRIPTION
            "Historical equipment PM direction."
        ::= { gmdm10EqptPmHistEntry 6 }

    gmdm10EqptPmHistDate OBJECT-TYPE
        SYNTAX DisplayString
        ACCESS read-only
        STATUS mandatory
        DESCRIPTION
            "Historical equipment PM date."
        ::= { gmdm10EqptPmHistEntry 7 }

    gmdm10EqptPmHistTime OBJECT-TYPE
        SYNTAX DisplayString
        ACCESS read-only
        STATUS mandatory
        DESCRIPTION
            "Historical equipment PM time."
        ::= { gmdm10EqptPmHistEntry 8 }

    --
    -- The elements in the gmdm10FacPmCurrTable subgroup of the cardConfiguration group
    --

    gmdm10FacPmCurrTable   OBJECT-TYPE
            SYNTAX  SEQUENCE OF Gmdm10FacPmCurrEntry
            ACCESS  not-accessible
            STATUS  mandatory
            DESCRIPTION
                    "GMDM10 current facility PM table"
            ::= { gmdm10 5 }

    gmdm10FacPmCurrEntry   OBJECT-TYPE
            SYNTAX  Gmdm10FacPmCurrEntry
            ACCESS  not-accessible
            STATUS  mandatory
            DESCRIPTION
                    "GMDM10 current facility PM entry format."
            INDEX   { eqptBay, eqptShelf, eqptSlot, gmdm10FacPort, gmdm10FacPmCurrType }
            ::= { gmdm10FacPmCurrTable 1 }

    Gmdm10FacPmCurrEntry   ::=
            SEQUENCE 
            {
                gmdm10FacPmCurrType         INTEGER,
                gmdm10FacPmCurrValue        DisplayString,
                gmdm10FacPmCurrOcFacility   INTEGER,
                gmdm10FacPmCurrValidity     INTEGER,
                gmdm10FacPmCurrLocation     INTEGER,
                gmdm10FacPmCurrDirection    INTEGER,
                gmdm10FacPmCurrDate         DisplayString,
                gmdm10FacPmCurrTime         DisplayString
            }

    gmdm10FacPmCurrType OBJECT-TYPE
        SYNTAX INTEGER { cvs(4), ess(5), opr(8), sefss(11), sess(12) }
        ACCESS read-only
        STATUS mandatory
        DESCRIPTION
            "Current facility PM type."
        ::= { gmdm10FacPmCurrEntry 1 }

    gmdm10FacPmCurrValue OBJECT-TYPE
        SYNTAX DisplayString
        ACCESS read-only
        STATUS mandatory
        DESCRIPTION
            "Current facility PM value."
        ::= { gmdm10FacPmCurrEntry 2 }

    gmdm10FacPmCurrOcFacility OBJECT-TYPE
        SYNTAX INTEGER { oc12(1), oc192(2), oc24(3), oc48(4), oc3(5) }
        ACCESS read-only
        STATUS mandatory
        DESCRIPTION
            "Current facility PM OC facility."
        ::= { gmdm10FacPmCurrEntry 3 }

    gmdm10FacPmCurrValidity OBJECT-TYPE
        SYNTAX INTEGER { false(1), true(2) }
        ACCESS read-only
        STATUS mandatory
        DESCRIPTION
            "Current facility PM validity."
        ::= { gmdm10FacPmCurrEntry 4 }

    gmdm10FacPmCurrLocation OBJECT-TYPE
        SYNTAX INTEGER { farEnd(1), nearEnd(2) }
        ACCESS read-only
        STATUS mandatory
        DESCRIPTION
            "Current facility PM location."
        ::= { gmdm10FacPmCurrEntry 5 }

    gmdm10FacPmCurrDirection OBJECT-TYPE
        SYNTAX INTEGER { na(1), rcv(2), trmt(3) }
        ACCESS read-only
        STATUS mandatory
        DESCRIPTION
            "Current facility PM direction."
        ::= { gmdm10FacPmCurrEntry 6 }

    gmdm10FacPmCurrDate OBJECT-TYPE
        SYNTAX DisplayString
        ACCESS read-only
        STATUS mandatory
        DESCRIPTION
            "Current facility PM date."
        ::= { gmdm10FacPmCurrEntry 7 }

    gmdm10FacPmCurrTime OBJECT-TYPE
        SYNTAX DisplayString
        ACCESS read-only
        STATUS mandatory
        DESCRIPTION
            "Current facility PM time."
        ::= { gmdm10FacPmCurrEntry 8 }

    --
    -- The elements in the gmdm10FacPmHistTable subgroup of the cardConfiguration group
    --

    gmdm10FacPmHistTable   OBJECT-TYPE
            SYNTAX  SEQUENCE OF Gmdm10FacPmHistEntry
            ACCESS  not-accessible
            STATUS  mandatory
            DESCRIPTION
                    "GMDM10 historical facility PM table"
            ::= { gmdm10 6 }

    gmdm10FacPmHistEntry   OBJECT-TYPE
            SYNTAX  Gmdm10FacPmHistEntry
            ACCESS  not-accessible
            STATUS  mandatory
            DESCRIPTION
                    "GMDM10 historical facility PM entry format."
            INDEX   { eqptBay, eqptShelf, eqptSlot, gmdm10FacPort, gmdm10FacPmHistInterval, gmdm10FacPmHistType }
            ::= { gmdm10FacPmHistTable 1 }

    Gmdm10FacPmHistEntry   ::=
            SEQUENCE 
            {
                gmdm10FacPmHistInterval     INTEGER,
                gmdm10FacPmHistType         INTEGER,
                gmdm10FacPmHistValue        DisplayString,
                gmdm10FacPmHistOcFacility   INTEGER,
                gmdm10FacPmHistValidity     INTEGER,
                gmdm10FacPmHistLocation     INTEGER,
                gmdm10FacPmHistDirection    INTEGER,
                gmdm10FacPmHistDate         DisplayString,
                gmdm10FacPmHistTime         DisplayString
            }

    gmdm10FacPmHistInterval OBJECT-TYPE
        SYNTAX INTEGER (1..32)
        ACCESS read-only
        STATUS mandatory
        DESCRIPTION
            "Historical facility PM interval."
        ::= { gmdm10FacPmHistEntry 1 }

    gmdm10FacPmHistType OBJECT-TYPE
        SYNTAX INTEGER { cvs(4), ess(5), opr(8), sefss(11), sess(12) }
        ACCESS read-only
        STATUS mandatory
        DESCRIPTION
            "Historical facility PM type."
        ::= { gmdm10FacPmHistEntry 2 }

    gmdm10FacPmHistValue OBJECT-TYPE
        SYNTAX DisplayString
        ACCESS read-only
        STATUS mandatory
        DESCRIPTION
            "Historical facility PM value."
        ::= { gmdm10FacPmHistEntry 3 }

    gmdm10FacPmHistOcFacility OBJECT-TYPE
        SYNTAX INTEGER { oc12(1), oc192(2), oc24(3), oc48(4), oc3(5) }
        ACCESS read-only
        STATUS mandatory
        DESCRIPTION
            "Historical facility PM OC facility."
        ::= { gmdm10FacPmHistEntry 4 }

    gmdm10FacPmHistValidity OBJECT-TYPE
        SYNTAX INTEGER { false(1), true(2) }
        ACCESS read-only
        STATUS mandatory
        DESCRIPTION
            "Historical facility PM validity."
        ::= { gmdm10FacPmHistEntry 5 }

    gmdm10FacPmHistLocation OBJECT-TYPE
        SYNTAX INTEGER { farEnd(1), nearEnd(2) }
        ACCESS read-only
        STATUS mandatory
        DESCRIPTION
            "Historical facility PM location."
        ::= { gmdm10FacPmHistEntry 6 }

    gmdm10FacPmHistDirection OBJECT-TYPE
        SYNTAX INTEGER { na(1), rcv(2), trmt(3) }
        ACCESS read-only
        STATUS mandatory
        DESCRIPTION
            "Historical facility PM direction."
        ::= { gmdm10FacPmHistEntry 7 }

    gmdm10FacPmHistDate OBJECT-TYPE
        SYNTAX DisplayString
        ACCESS read-only
        STATUS mandatory
        DESCRIPTION
            "Historical facility PM date."
        ::= { gmdm10FacPmHistEntry 8 }

    gmdm10FacPmHistTime OBJECT-TYPE
        SYNTAX DisplayString
        ACCESS read-only
        STATUS mandatory
        DESCRIPTION
            "Historical facility PM time."
        ::= { gmdm10FacPmHistEntry 9 }

    --
    -- The elements in the gmdpm subgroup of the cardConfiguration group
    --

    gmdpmTable   OBJECT-TYPE
            SYNTAX  SEQUENCE OF GmdpmEntry
            ACCESS  not-accessible
            STATUS  mandatory
            DESCRIPTION
                    "GMDPM module table"
            ::= { gmdpm 1 }

    gmdpmEntry   OBJECT-TYPE
            SYNTAX  GmdpmEntry
            ACCESS  not-accessible
            STATUS  mandatory
            DESCRIPTION
                    "GMDPM entry format."
            INDEX   { eqptBay, eqptShelf, eqptSlot }
            ::= { gmdpmTable 1 }

    GmdpmEntry   ::=
            SEQUENCE 
            {
                gmdpmOpMode                 INTEGER,
                gmdpmOprLowSw               INTEGER,
                gmdpmOprLowSwDelay          INTEGER,
                gmdpmWaitToRestore          INTEGER,
                gmdpmSwToFail               INTEGER,
                gmdpmUserLabel              DisplayString,
                gmdpmPrimaryState           INTEGER,
                gmdpmSecondaryState         INTEGER,
                gmdpmAdminState             INTEGER
            }

    gmdpmOpMode OBJECT-TYPE
        SYNTAX INTEGER { nonrevertive(1), revertive(2) }
        ACCESS read-write
        STATUS mandatory
        DESCRIPTION
            "This operation mode will only take effect when the switching state 
             is in autoSW.
                
             non-revertive  - When the switch has been in fiberP (protection line). 
             It will not switch back to fiberW (working line) even working line is 
             restored from failure.
            
             revertive  - When the switch has been in fiberB (protection line). 
             It will switch back to fiberW (working line) after working line is 
             restored from failure."
        ::= { gmdpmEntry 1 }

    gmdpmOprLowSw OBJECT-TYPE
        SYNTAX INTEGER { disabled(1), enabled(2) }
        ACCESS read-write
        STATUS mandatory
        DESCRIPTION
            "This parameter controls whether OPD condition will trigger the 
             switch or not.
            
             enabled  - means OPD switch indicator is on.
             disabled - means OPD switch indicator is off."
        ::= { gmdpmEntry 2 }

    gmdpmOprLowSwDelay OBJECT-TYPE
        SYNTAX INTEGER (1..15360)
        ACCESS read-write
        STATUS mandatory
        DESCRIPTION
            "The OPRlow switching delay time in unit of minutes."
        ::= { gmdpmEntry 3 }

    gmdpmWaitToRestore OBJECT-TYPE
        SYNTAX INTEGER (300..720)
        ACCESS read-write
        STATUS mandatory
        DESCRIPTION
            "The wait-to-restore-time in unit of minutes."
        ::= { gmdpmEntry 4 }

    gmdpmSwToFail OBJECT-TYPE
        SYNTAX INTEGER { disabled(1), enabled(2) }
        ACCESS read-write
        STATUS mandatory
        DESCRIPTION
            "This parameter controls which scheme will be used for force 
             switch case.
            
             enable  - GMDPM can switch to a dead Line.
             disable - GMDPM will not switch to a dead line"
        ::= { gmdpmEntry 5 }

    gmdpmUserLabel OBJECT-TYPE
        SYNTAX DisplayString (SIZE (0..14))
        ACCESS read-write
        STATUS mandatory
        DESCRIPTION
            ""
        ::= { gmdpmEntry 6 }

    gmdpmPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmdpmEntry 7 }

    gmdpmSecondaryState OBJECT-TYPE
        SYNTAX SecondaryState
        ACCESS read-only
        STATUS mandatory
        DESCRIPTION
            "Secondary state of module."
        ::= { gmdpmEntry 8 }

    gmdpmAdminState OBJECT-TYPE
        SYNTAX INTEGER { other(1), reset(2) }
        ACCESS read-write
        STATUS mandatory
        DESCRIPTION
            "Administration state of module.  This field is used
             to reset the module.  Reading this field always 
             returns other(1)."
        ::= { gmdpmEntry 9 }

    --
    -- The elements in the gmdpmFacilities subgroup of the configuration group
    --

    gmdpmFacTable   OBJECT-TYPE
            SYNTAX  SEQUENCE OF GmdpmFacEntry
            ACCESS  not-accessible
            STATUS  mandatory
            DESCRIPTION
                    "GMDPM facility table."
            ::= { gmdpm 2 }

    gmdpmFacEntry   OBJECT-TYPE
            SYNTAX  GmdpmFacEntry
            ACCESS  not-accessible
            STATUS  mandatory
            DESCRIPTION
                    "GMDPM facility entry format"
            INDEX   { eqptBay, eqptShelf, eqptSlot, gmdpmFacPort }
            ::= { gmdpmFacTable 1 }

    GmdpmFacEntry   ::=
            SEQUENCE 
            {
                gmdpmFacPort            INTEGER,
                gmdpmFacInputPwr        DisplayString,
                gmdpmFacOprLossTh       DisplayString,
                gmdpmFacOprLowTh        DisplayString,
                gmdpmFacTrunkStatus     INTEGER,
                gmdpmFacPrimaryState    INTEGER,
                gmdpmFacSecondaryState  INTEGER
            }

    gmdpmFacPort OBJECT-TYPE
        SYNTAX INTEGER { w(1), p(2) }
        ACCESS read-only
        STATUS mandatory
        DESCRIPTION
            "Port portion of GMDPM facility address. The GMDPM port
             number is the same as the module's channel id."
        ::= { gmdpmFacEntry 1 }

    gmdpmFacInputPwr OBJECT-TYPE
        SYNTAX DisplayString
        ACCESS read-only
        STATUS mandatory
        DESCRIPTION
            "Line input power in dBm."
        ::= { gmdpmFacEntry 2 }

    gmdpmFacOprLossTh OBJECT-TYPE
        SYNTAX DisplayString (SIZE(0..8))
        ACCESS read-write
        STATUS mandatory
        DESCRIPTION
            "Fiber trunk threshold value of OPRloss in dBm.
             The valid range is Min. -30.0 dBm to Max. 0.0 dBm."
        ::= { gmdpmFacEntry 3 }

    gmdpmFacOprLowTh OBJECT-TYPE
        SYNTAX DisplayString (SIZE(0..8))
        ACCESS read-write
        STATUS mandatory
        DESCRIPTION
            "Fiber trunk threshold value of OPRlow in dBm.
             The valid range is Min. -30.0 dBm to Max. 0.0 dBm."
        ::= { gmdpmFacEntry 4 }

    gmdpmFacTrunkStatus OBJECT-TYPE
        SYNTAX INTEGER { normal(1), oprloss(2), oprlow(3), oproverload(4) }
        ACCESS read-only
        STATUS mandatory
        DESCRIPTION
            "The state of fiber line for a GMDPM module."
        ::= { gmdpmFacEntry 5 }

    gmdpmFacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmdpmFacEntry 6 }

    gmdpmFacSecondaryState OBJECT-TYPE
        SYNTAX SecondaryState
        ACCESS read-only
        STATUS mandatory
        DESCRIPTION
            "Secondary state of port."
        ::= { gmdpmFacEntry 7 }

    --
    -- The elements in the gmdpmProtnSw subgroup of the configuration group
    --

    gmdpmProtnSwTable   OBJECT-TYPE
            SYNTAX  SEQUENCE OF GmdpmProtnSwEntry
            ACCESS  not-accessible
            STATUS  mandatory
            DESCRIPTION
                    "GMDPM Protection table."
            ::= { gmdpm 3 }

    gmdpmProtnSwEntry   OBJECT-TYPE
            SYNTAX  GmdpmProtnSwEntry
            ACCESS  not-accessible
            STATUS  mandatory
            DESCRIPTION
                    "GMDPM protection switch entry format"
            INDEX   { eqptBay, eqptShelf, eqptSlot }
            ::= { gmdpmProtnSwTable 1 }

    GmdpmProtnSwEntry   ::=
            SEQUENCE 
            {
                gmdpmProtnSwProtnSwCmd          INTEGER,
                gmdpmProtnSwOperationMode       INTEGER,
                gmdpmProtnSwOperatingTrunk      INTEGER,
                gmdpmProtnSwWorkingTrunkStatus  INTEGER,
                gmdpmProtnSwProtnTrunkStatus    INTEGER,
                gmdpmProtnSwProtnSwReason       INTEGER
            }

    gmdpmProtnSwProtnSwCmd OBJECT-TYPE
        SYNTAX INTEGER
        {
            clear(1),
            fsptow(2),
            fswtop(3),
            lockoutp(4),
            msptow(5),
            mswtop(6)
        }
        ACCESS read-write
        STATUS mandatory
        DESCRIPTION
            "The description of GMDPM switch commands are as follows:-  
             
             clear(1): Whenever clear command has been issued, it will 
             change the state to autoSW no matter what the previous state 
             is. In autoSW state, it will base on both line states and the 
             operation mode to determine the final switch position.
                 
             lockOutP(2): This command will cause the switch state to be 
             changed to lockOutP. If the previous switch position is in 
             fiberA, it will stay in fiberW. Otherwise, it will switch 
             from fiberP to fiberW.
                 
             fsWtoP(3): This forced switch command will change the state to 
             forceSW and change the switch position to fiberP if the previous 
             switch state is not in lockoutP or the other forceSw command is
             in effect.
                 
             fsPtoW(4): This forced switch command will change the state to 
             forceSW and change the switch position to fiberW if the previous 
             switch state is not in lockoutP or the other forceSw command is
             in effect.
                 
             msWtoP(5): This manual switch command will change the state to 
             manualSW and change the switch position to fiberP if the previous 
             switch state is not in lockoutP, forceSW or the other manualSw 
             command is in effect.
             
             msPtoW(6): This manual switch command will change the state to 
             manualSW and change the switch position to fiberW if the previous 
             switch state is not in lockoutP, forceSW or the other manualSw 
             command is in effect."
        ::= { gmdpmProtnSwEntry 1 }

    gmdpmProtnSwOperationMode OBJECT-TYPE
        SYNTAX INTEGER
        {
            auto(1),
            frcd(2),
            lockout(3),
            man(4),
            normal(5)
        }
        ACCESS read-only
        STATUS mandatory
        DESCRIPTION
            "GMDPM operation mode description:-  
             autoNoRequest(1): Automatic Switch No Request
             lockoutPrequest(2): Lock out of Protection Request
             forceSwitchWtoP(3): Force Switch from working to protection request
             forceSwitchPtoW(4): Force Switch from protection to working request
             manualSwitchWtoP(5): Manual Switch from working to protection request"
        ::= { gmdpmProtnSwEntry 2 }

    gmdpmProtnSwOperatingTrunk OBJECT-TYPE
        SYNTAX INTEGER { oprTrunk1(1), oprTrunk2(2), unknown(3) }
        ACCESS read-only
        STATUS mandatory
        DESCRIPTION
            "Indicates which trunk is the current working trunk."
        ::= { gmdpmProtnSwEntry 3 }

    gmdpmProtnSwWorkingTrunkStatus OBJECT-TYPE
        SYNTAX INTEGER
        {
            normal(1),
            oprLoss(2),
            oprLow(3),
            oprOverload(4)
        }
        ACCESS read-only
        STATUS mandatory
        DESCRIPTION
            "State of fiber Working Line for a GMDPM module."
        ::= { gmdpmProtnSwEntry 4 }

    gmdpmProtnSwProtnTrunkStatus OBJECT-TYPE
        SYNTAX INTEGER
        {
            normal(1),
            oprLoss(2),
            oprLow(3),
            oprOverload(4)
        }
        ACCESS read-only
        STATUS mandatory
        DESCRIPTION
            "State of fiber Protection Line for a GMDPM module."
        ::= { gmdpmProtnSwEntry 5 }

    gmdpmProtnSwProtnSwReason OBJECT-TYPE
        SYNTAX INTEGER 
        {
            normal(1),
            oprLoss(2),
            oprLow(3),
            oprOverload(4),
            nil(5)
        }
        ACCESS read-only
        STATUS mandatory
        DESCRIPTION
            "reason for protection switch."
        ::= { gmdpmProtnSwEntry 6 }

    --
    -- The elements in the gme1c subgroup of the cardConfiguration group
    --

    gme1cTable   OBJECT-TYPE
            SYNTAX  SEQUENCE OF Gme1cEntry
            ACCESS  not-accessible
            STATUS  mandatory
            DESCRIPTION
                    "GME1C module table"
            ::= { gme1c 1 }

    gme1cEntry   OBJECT-TYPE
            SYNTAX  Gme1cEntry
            ACCESS  not-accessible
            STATUS  mandatory
            DESCRIPTION
                    "GME1C entry format."
            INDEX   { eqptBay, eqptShelf, eqptSlot }
            ::= { gme1cTable 1 }

    Gme1cEntry   ::=
            SEQUENCE 
            {
                gme1cPrimaryState            INTEGER,
                gme1cSecondaryState          INTEGER
            }

    gme1cPrimaryState OBJECT-TYPE
        SYNTAX PrimaryState 
        ACCESS read-write
        STATUS mandatory
        DESCRIPTION
            "Primary state of module."
        ::= { gme1cEntry 1 }

    gme1cSecondaryState OBJECT-TYPE
        SYNTAX SecondaryState
        ACCESS read-only
        STATUS mandatory
        DESCRIPTION
            "Secondary state of module."
        ::= { gme1cEntry 2 }

    --
    -- The elements in the gmeb subgroup of the cardConfiguration group
    --

    gmebTable   OBJECT-TYPE
            SYNTAX  SEQUENCE OF GmebEntry
            ACCESS  not-accessible
            STATUS  mandatory
            DESCRIPTION
                    "GMEB module table"
            ::= { gmeb 1 }

    gmebEntry   OBJECT-TYPE
            SYNTAX  GmebEntry
            ACCESS  not-accessible
            STATUS  mandatory
            DESCRIPTION
                    "GMEB entry format."
            INDEX   { eqptBay, eqptShelf, eqptSlot }
            ::= { gmebTable 1 }

    GmebEntry   ::=
            SEQUENCE 
            {
                gmebSubType                DisplayString,
                gmebPrimaryState           INTEGER,
                gmebSecondaryState         INTEGER,
                gmebAdminState             INTEGER
            }

    gmebSubType OBJECT-TYPE
        SYNTAX DisplayString
        ACCESS read-only
        STATUS mandatory
        DESCRIPTION
            "Module subtype."
        ::= { gmebEntry 1 }

    gmebPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmebEntry 2 }

    gmebSecondaryState OBJECT-TYPE
        SYNTAX SecondaryState
        ACCESS read-only
        STATUS mandatory
        DESCRIPTION
            "Secondary state of module."
        ::= { gmebEntry 3 }

    gmebAdminState OBJECT-TYPE
        SYNTAX INTEGER { other(1), reset(2) }
        ACCESS read-write
        STATUS mandatory
        DESCRIPTION
            "Administration state of module.  This field is used
             to reset the module.  Reading this field always 
             returns other(1)."
        ::= { gmebEntry 4 }

    --
    -- The elements in the gmebFacilities subgroup of the configuration group
    --

    gmebFacTable   OBJECT-TYPE
            SYNTAX  SEQUENCE OF GmebFacEntry
            ACCESS  not-accessible
            STATUS  mandatory
            DESCRIPTION
                    "GMEB facility table."
            ::= { gmeb 2 }

    gmebFacEntry   OBJECT-TYPE
            SYNTAX  GmebFacEntry
            ACCESS  not-accessible
            STATUS  mandatory
            DESCRIPTION
                    "GMEB facility entry format"
            INDEX   { eqptBay, eqptShelf, eqptSlot, gmebFacPort }
            ::= { gmebFacTable 1 }

    GmebFacEntry   ::=
            SEQUENCE 
            {
                gmebFacPort             INTEGER,
                gmebFacDescription      DisplayString,
                gmebFacInsertionLoss    DisplayString
            }

    gmebFacPort OBJECT-TYPE
        SYNTAX INTEGER (1..8)
        ACCESS read-only
        STATUS mandatory
        DESCRIPTION
            "Facility index."
        ::= { gmebFacEntry 1 }

    gmebFacDescription OBJECT-TYPE
        SYNTAX DisplayString
        ACCESS read-only
        STATUS mandatory
        DESCRIPTION
            "Facility description."
        ::= { gmebFacEntry 2 }

    gmebFacInsertionLoss OBJECT-TYPE
        SYNTAX DisplayString
        ACCESS read-only
        STATUS mandatory
        DESCRIPTION
            "Value of the path Insertion Loss."
        ::= { gmebFacEntry 3 }

    --
    -- The elements in the gmer subgroup of the cardConfiguration group
    --

    gmerTable   OBJECT-TYPE
            SYNTAX  SEQUENCE OF GmerEntry
            ACCESS  not-accessible
            STATUS  mandatory
            DESCRIPTION
                    "GMER module table"
            ::= { gmer 1 }

    gmerEntry   OBJECT-TYPE
            SYNTAX  GmerEntry
            ACCESS  not-accessible
            STATUS  mandatory
            DESCRIPTION
                    "GMER entry format."
            INDEX   { eqptBay, eqptShelf, eqptSlot }
            ::= { gmerTable 1 }

    GmerEntry   ::=
            SEQUENCE 
            {
                gmerSubType                DisplayString,
                gmerPrimaryState           INTEGER,
                gmerSecondaryState         INTEGER,
                gmerAdminState             INTEGER
            }

    gmerSubType OBJECT-TYPE
        SYNTAX DisplayString
        ACCESS read-only
        STATUS mandatory
        DESCRIPTION
            "Module subtype."
        ::= { gmerEntry 1 }

    gmerPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmerEntry 2 }

    gmerSecondaryState OBJECT-TYPE
        SYNTAX SecondaryState
        ACCESS read-only
        STATUS mandatory
        DESCRIPTION
            "Secondary state of module."
        ::= { gmerEntry 3 }

    gmerAdminState OBJECT-TYPE
        SYNTAX INTEGER { other(1), reset(2) }
        ACCESS read-write
        STATUS mandatory
        DESCRIPTION
            "Administration state of module.  This field is used
             to reset the module.  Reading this field always 
             returns other(1)."
        ::= { gmerEntry 4 }

    --
    -- The elements in the gmerFacilities subgroup of the configuration group
    --

    gmerFacTable   OBJECT-TYPE
            SYNTAX  SEQUENCE OF GmerFacEntry
            ACCESS  not-accessible
            STATUS  mandatory
            DESCRIPTION
                    "GMER facility table."
            ::= { gmer 2 }

    gmerFacEntry   OBJECT-TYPE
            SYNTAX  GmerFacEntry
            ACCESS  not-accessible
            STATUS  mandatory
            DESCRIPTION
                    "GMER facility entry format"
            INDEX   { eqptBay, eqptShelf, eqptSlot, gmerFacPort }
            ::= { gmerFacTable 1 }

    GmerFacEntry   ::=
            SEQUENCE 
            {
                gmerFacPort             INTEGER,
                gmerFacDescription      DisplayString,
                gmerFacInsertionLoss    DisplayString
            }

    gmerFacPort OBJECT-TYPE
        SYNTAX INTEGER (1..10)
        ACCESS read-only
        STATUS mandatory
        DESCRIPTION
            "Facility index."
        ::= { gmerFacEntry 1 }

    gmerFacDescription OBJECT-TYPE
        SYNTAX DisplayString
        ACCESS read-only
        STATUS mandatory
        DESCRIPTION
            "Facility description."
        ::= { gmerFacEntry 2 }

    gmerFacInsertionLoss OBJECT-TYPE
        SYNTAX DisplayString
        ACCESS read-only
        STATUS mandatory
        DESCRIPTION
            "Value of the path Insertion Loss."
        ::= { gmerFacEntry 3 }

    --
    -- The elements in the gmfti subgroup of the cardConfiguration group
    --

    gmftiTable   OBJECT-TYPE
            SYNTAX  SEQUENCE OF GmftiEntry
            ACCESS  not-accessible
            STATUS  mandatory
            DESCRIPTION
                    "GMFTI module table"
            ::= { gmfti 1 }

    gmftiEntry   OBJECT-TYPE
            SYNTAX  GmftiEntry
            ACCESS  not-accessible
            STATUS  mandatory
            DESCRIPTION
                    "GMFTI entry format."
            INDEX   { eqptBay, eqptShelf, eqptSlot }
            ::= { gmftiTable 1 }

    GmftiEntry   ::=
            SEQUENCE 
            {
                gmftiSubType                 DisplayString,
                gmftiPrimaryState            INTEGER,
                gmftiSecondaryState          INTEGER,
                gmftiAdminState              INTEGER
            }

    gmftiSubType OBJECT-TYPE
        SYNTAX DisplayString
        ACCESS read-only
        STATUS mandatory
        DESCRIPTION
            "Module sub type."
        ::= { gmftiEntry 1 }

    gmftiPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmftiEntry 2 }

    gmftiSecondaryState OBJECT-TYPE
        SYNTAX SecondaryState
        ACCESS read-only
        STATUS mandatory
        DESCRIPTION
            "Secondary state of module."
        ::= { gmftiEntry 3 }

    gmftiAdminState OBJECT-TYPE
        SYNTAX INTEGER { other(1), reset(2) }
        ACCESS read-write
        STATUS mandatory
        DESCRIPTION
            "Administration state of module.  This field is used
             to reset the module.  Reading this field always 
             returns other(1)."
        ::= { gmftiEntry 4 }

    --
    -- The elements in the gmftiFacilities subgroup of the configuration group
    --

    gmftiFacTable   OBJECT-TYPE
            SYNTAX  SEQUENCE OF GmftiFacEntry
            ACCESS  not-accessible
            STATUS  mandatory
            DESCRIPTION
                    "GMFTI facility table."
            ::= { gmfti 2 }

    gmftiFacEntry   OBJECT-TYPE
            SYNTAX  GmftiFacEntry
            ACCESS  not-accessible
            STATUS  mandatory
            DESCRIPTION
                    "GMFTI facility entry format"
            INDEX   { eqptBay, eqptShelf, eqptSlot, gmftiFacPort }
            ::= { gmftiFacTable 1 }

    GmftiFacEntry   ::=
            SEQUENCE 
            {
                gmftiFacPort            INTEGER,
                gmftiFacDescription     DisplayString,
                gmftiFacInsertionLoss   DisplayString
            }

    gmftiFacPort OBJECT-TYPE
        SYNTAX INTEGER (1..10)
        ACCESS read-only
        STATUS mandatory
        DESCRIPTION
            "Facility index."
        ::= { gmftiFacEntry 1 }

    gmftiFacDescription OBJECT-TYPE
        SYNTAX DisplayString
        ACCESS read-only
        STATUS mandatory
        DESCRIPTION
            "Facility description."
        ::= { gmftiFacEntry 2 }

    gmftiFacInsertionLoss OBJECT-TYPE
        SYNTAX DisplayString
        ACCESS read-only
        STATUS mandatory
        DESCRIPTION
            "Value of the path Insertion Loss."
        ::= { gmftiFacEntry 3 }

    --
    -- The elements in the gmmd subgroup of the cardConfiguration group
    --

    gmmdTable   OBJECT-TYPE
            SYNTAX  SEQUENCE OF GmmdEntry
            ACCESS  not-accessible
            STATUS  mandatory
            DESCRIPTION
                    "GMMD module table"
            ::= { gmmd 1 }

    gmmdEntry   OBJECT-TYPE
            SYNTAX  GmmdEntry
            ACCESS  not-accessible
            STATUS  mandatory
            DESCRIPTION
                    "GMMD entry format."
            INDEX   { eqptBay, eqptShelf, eqptSlot }
            ::= { gmmdTable 1 }

    GmmdEntry   ::=
            SEQUENCE 
            {
                gmmdSubType                 DisplayString,
                gmmdPrimaryState            INTEGER,
                gmmdSecondaryState          INTEGER
            }

    gmmdSubType OBJECT-TYPE
        SYNTAX DisplayString
        ACCESS read-only
        STATUS mandatory
        DESCRIPTION
            "Module sub type."
        ::= { gmmdEntry 1 }

    gmmdPrimaryState OBJECT-TYPE
        SYNTAX PrimaryState 
        ACCESS read-write
        STATUS mandatory
        DESCRIPTION
            "Primary state of module."
        ::= { gmmdEntry 2 }

    gmmdSecondaryState OBJECT-TYPE
        SYNTAX SecondaryState
        ACCESS read-only
        STATUS mandatory
        DESCRIPTION
            "Secondary state of module."
        ::= { gmmdEntry 3 }

    --
    -- The elements in the gmmd100 subgroup of the cardConfiguration group
    --

    gmmd100Table   OBJECT-TYPE
            SYNTAX  SEQUENCE OF Gmmd100Entry
            ACCESS  not-accessible
            STATUS  mandatory
            DESCRIPTION
                    "GMMD100 module table"
            ::= { gmmd100 1 }

    gmmd100Entry   OBJECT-TYPE
            SYNTAX  Gmmd100Entry
            ACCESS  not-accessible
            STATUS  mandatory
            DESCRIPTION
                    "GMMD100 entry format."
            INDEX   { eqptBay, eqptShelf, eqptSlot }
            ::= { gmmd100Table 1 }

    Gmmd100Entry   ::=
            SEQUENCE 
            {
                gmmd100GroupId                INTEGER,
                gmmd100PrimaryState           INTEGER,
                gmmd100SecondaryState         INTEGER,
                gmmd100AdminState             INTEGER
            }

    gmmd100GroupId OBJECT-TYPE
        SYNTAX INTEGER { a(1),  b(3),  c(4),  d(5),  e(6),  f(8),  g(9),  h(10),
                         i(11), j(13), k(14), l(15), m(16), n(18), o(19), p(20) }
        ACCESS read-only
        STATUS mandatory
        DESCRIPTION
            "Group Id."
        ::= { gmmd100Entry 1 }

    gmmd100PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmmd100Entry 2 }

    gmmd100SecondaryState OBJECT-TYPE
        SYNTAX SecondaryState
        ACCESS read-only
        STATUS mandatory
        DESCRIPTION
            "Secondary state of module."
        ::= { gmmd100Entry 3 }

    gmmd100AdminState OBJECT-TYPE
        SYNTAX INTEGER { other(1), reset(2) }
        ACCESS read-write
        STATUS mandatory
        DESCRIPTION
            "Administration state of module.  This field is used
             to reset the module.  Reading this field always 
             returns other(1)."
        ::= { gmmd100Entry 4 }

    --
    -- The elements in the gmmd100Facilities subgroup of the configuration group
    --

    gmmd100FacTable   OBJECT-TYPE
            SYNTAX  SEQUENCE OF Gmmd100FacEntry
            ACCESS  not-accessible
            STATUS  mandatory
            DESCRIPTION
                    "GMMD100 facility table."
            ::= { gmmd100 2 }

    gmmd100FacEntry   OBJECT-TYPE
            SYNTAX  Gmmd100FacEntry
            ACCESS  not-accessible
            STATUS  mandatory
            DESCRIPTION
                    "GMMD100 facility entry format"
            INDEX   { eqptBay, eqptShelf, eqptSlot, gmmd100FacPort }
            ::= { gmmd100FacTable 1 }

    Gmmd100FacEntry   ::=
            SEQUENCE 
            {
                gmmd100FacPort              INTEGER,
                gmmd100FacDescription       DisplayString,
                gmmd100FacInsertionLoss     DisplayString
            }

    gmmd100FacPort OBJECT-TYPE
        SYNTAX INTEGER (1..10)
        ACCESS read-only
        STATUS mandatory
        DESCRIPTION
            "Facility index."
        ::= { gmmd100FacEntry 1 }

    gmmd100FacDescription OBJECT-TYPE
        SYNTAX DisplayString
        ACCESS read-only
        STATUS mandatory
        DESCRIPTION
            "Facility description."
        ::= { gmmd100FacEntry 2 }

    gmmd100FacInsertionLoss OBJECT-TYPE
        SYNTAX DisplayString
        ACCESS read-only
        STATUS mandatory
        DESCRIPTION
            "Value of the path Insertion Loss."
        ::= { gmmd100FacEntry 3 }

    --
    -- The elements in the gmmr2g5 subgroup of the cardConfiguration group
    --

    gmmr2g5Table   OBJECT-TYPE
            SYNTAX  SEQUENCE OF Gmmr2g5Entry
            ACCESS  not-accessible
            STATUS  mandatory
            DESCRIPTION
                    "GMMR2G5 module table"
            ::= { gmmr2g5 1 }

    gmmr2g5Entry   OBJECT-TYPE
            SYNTAX  Gmmr2g5Entry
            ACCESS  not-accessible
            STATUS  mandatory
            DESCRIPTION
                    "GMMR2G5 entry format."
            INDEX   { eqptBay, eqptShelf, eqptSlot }
            ::= { gmmr2g5Table 1 }

    Gmmr2g5Entry   ::=
            SEQUENCE 
            {
                gmmr2g5SubType                 DisplayString,
                gmmr2g5ItuNum                  ItuSelection,
                gmmr2g5Apsd                    INTEGER,
                gmmr2g5PrimaryState            INTEGER,
                gmmr2g5SecondaryState          INTEGER,
                gmmr2g5AdminState              INTEGER,
                gmmr2g5PmStatus                INTEGER
            }

    gmmr2g5SubType OBJECT-TYPE
        SYNTAX DisplayString
        ACCESS read-only
        STATUS mandatory
        DESCRIPTION
            "Module sub type."
        ::= { gmmr2g5Entry 1 }

    gmmr2g5ItuNum OBJECT-TYPE
        SYNTAX ItuSelection
        ACCESS read-only
        STATUS mandatory
        DESCRIPTION
            "Module supported ITU channel."
        ::= { gmmr2g5Entry 2 }

    gmmr2g5Apsd      OBJECT-TYPE
        SYNTAX INTEGER { off(1), on(2) }
        ACCESS read-write
        STATUS mandatory
        DESCRIPTION
            "Module Automatic Power Shut Down setting.  The modules's
             primary state must be set OOS to modified this field."
        ::= { gmmr2g5Entry 3 }

    gmmr2g5PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmmr2g5Entry 4 }

    gmmr2g5SecondaryState OBJECT-TYPE
        SYNTAX SecondaryState
        ACCESS read-only
        STATUS mandatory
        DESCRIPTION
            "Secondary state of module."
        ::= { gmmr2g5Entry 5 }

    gmmr2g5AdminState OBJECT-TYPE
        SYNTAX INTEGER { other(1), reset(2) }
        ACCESS read-write
        STATUS mandatory
        DESCRIPTION
            "Administration state of module.  This field is used
             to reset the module.  Reading this field always 
             returns other(1)."
        ::= { gmmr2g5Entry 6 }

    gmmr2g5PmStatus OBJECT-TYPE
        SYNTAX PmState
        ACCESS read-write
        STATUS mandatory
        DESCRIPTION
            "Perfornance monitoring status of module."
        ::= { gmmr2g5Entry 7 }

    --
    -- The elements in the gmmr2g5Facilities subgroup of the configuration group
    --

    gmmr2g5FacTable   OBJECT-TYPE
            SYNTAX  SEQUENCE OF Gmmr2g5FacEntry
            ACCESS  not-accessible
            STATUS  mandatory
            DESCRIPTION
                    "GMMR2G5 facility table."
            ::= { gmmr2g5 2 }

    gmmr2g5FacEntry   OBJECT-TYPE
            SYNTAX  Gmmr2g5FacEntry
            ACCESS  not-accessible
            STATUS  mandatory
            DESCRIPTION
                    "GMMR2G5 facility entry format"
            INDEX   { eqptBay, eqptShelf, eqptSlot, gmmr2g5FacPort }
            ::= { gmmr2g5FacTable 1 }

    Gmmr2g5FacEntry   ::=
            SEQUENCE 
            {
                gmmr2g5FacPort              INTEGER,
                gmmr2g5FacOpr0              DisplayString,
                gmmr2g5FacSfpBitRate        INTEGER,
                gmmr2g5FacSfpWavelength     INTEGER,
                gmmr2g5FacPrimaryState      INTEGER,
                gmmr2g5FacSecondaryState    INTEGER,
                gmmr2g5FacLoopbackState     INTEGER
            }

    gmmr2g5FacPort OBJECT-TYPE
        SYNTAX INTEGER { cpe(1), line(2) }
        ACCESS read-only
        STATUS mandatory
        DESCRIPTION
            "Port portion of GMMR2G5 facility address."
        ::= { gmmr2g5FacEntry 1 }

    gmmr2g5FacOpr0 OBJECT-TYPE
        SYNTAX DisplayString
        ACCESS read-write
        STATUS mandatory
        DESCRIPTION
            "Nominal value of average optical output power
             of the received signal, or the Optical Power Received
             (OPR) in dBm.
             For Client port, the value of '-99.00' indicates that the
             parameter is not-applicable because the client transceiver
             is either absent or has electrical interface or the transceiver
             does not support client side Optical Layer PM.
             Line Port : Minimum: -28.0 dBm Maximum: -8.0 dBm.
             CPE Port : Minimum: -31.0 dBm Maximum: 4.0 dBm."
        ::= { gmmr2g5FacEntry 2 }

    gmmr2g5FacSfpBitRate OBJECT-TYPE
        SYNTAX INTEGER
        {
            na(0),
            auto(1),
            fcx2(2),
            gbex2(3),
            oc12stm4(4),
            oc3stm1(5),
            oc48stm16(6),
            fc(7),
            gbe(8),
            transparent2r(9)
        }
        ACCESS read-write
        STATUS mandatory
        DESCRIPTION
            "To configure the expected BitRate & Protocol to be supported by the transceiver.

                Value           BitRate     Protocol
                ========================================================
                auto            Read from SFP when it is plugged in.
                transparent2R   Don't Care  Don't Care
                FC              1.0625 Gbps Fibre Channel
                FCx2            2.1 Gbps    Fibre Channel
                GBE             1.25 Gbps   Gigabit Ethernet
                GBEx2           2.5 Gbps    Gigabit Ethernet
                OC3STM1         OC-3/STM1   SONET/SDH
                OC12STM4        OC-12/STM4  SONET/SDH
                OC48STM16       OC-48/STM16 SONET/SDH
                
             Settable only for cpe(1)."
        ::= { gmmr2g5FacEntry 3 }

    gmmr2g5FacSfpWavelength      OBJECT-TYPE
        SYNTAX INTEGER
        {
            wav1270nm(1),
            wav1290nm(2),
            wav1310nm(3),
            wav1310nm(4),
            wav1330nm(5),
            wav1350nm(6),
            wav1370nm(7),
            wav1390nm(8),
            wav1410nm(9),
            wav1430nm(10),
            wav1450nm(11),
            wav1470nm(12),
            wav1490nm(13),
            wav1510nm(14),
            wav1530nm(15),
            wav1550nm(16),
            wav1570nm(17),
            wav1590nm(18),
            wav1610nm(19),
            wav850nm(20),
            na(21),
            electrical(22)
        }
        ACCESS read-write
        STATUS mandatory
        DESCRIPTION
            "The wavelength to be supported by the transceiver.  Settable
             only for cpe(1)"
        ::= { gmmr2g5FacEntry 4 }

    gmmr2g5FacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmmr2g5FacEntry 5 }

    gmmr2g5FacSecondaryState OBJECT-TYPE
        SYNTAX SecondaryState
        ACCESS read-only
        STATUS mandatory
        DESCRIPTION
            "Secondary state of port."
        ::= { gmmr2g5FacEntry 6 }

    gmmr2g5FacLoopbackState OBJECT-TYPE
        SYNTAX LoopbackState
        ACCESS read-write
        STATUS mandatory
        DESCRIPTION
            "Loopback state of port. Ports must be set OOS before they
             can be placed into loopback."
        ::= { gmmr2g5FacEntry 7 }

    --
    -- The elements in the gmmr2g5EqptPmCurrTable subgroup of the cardConfiguration group
    --

    gmmr2g5EqptPmCurrTable   OBJECT-TYPE
            SYNTAX  SEQUENCE OF Gmmr2g5EqptPmCurrEntry
            ACCESS  not-accessible
            STATUS  mandatory
            DESCRIPTION
                    "GMMR2G5 current equipment PM table"
            ::= { gmmr2g5 3 }

    gmmr2g5EqptPmCurrEntry   OBJECT-TYPE
            SYNTAX  Gmmr2g5EqptPmCurrEntry
            ACCESS  not-accessible
            STATUS  mandatory
            DESCRIPTION
                    "GMMR2G5 current equipment PM entry format."
            INDEX   { eqptBay, eqptShelf, eqptSlot, gmmr2g5EqptPmCurrType }
            ::= { gmmr2g5EqptPmCurrTable 1 }

    Gmmr2g5EqptPmCurrEntry   ::=
            SEQUENCE 
            {
                gmmr2g5EqptPmCurrType         INTEGER,
                gmmr2g5EqptPmCurrValue        DisplayString,
                gmmr2g5EqptPmCurrValidity     INTEGER,
                gmmr2g5EqptPmCurrLocation     INTEGER,
                gmmr2g5EqptPmCurrDirection    INTEGER,
                gmmr2g5EqptPmCurrDate         DisplayString,
                gmmr2g5EqptPmCurrTime         DisplayString
            }

    gmmr2g5EqptPmCurrType OBJECT-TYPE
        SYNTAX INTEGER { lbc(2), ltemp(4), opt(5) }
        ACCESS read-only
        STATUS mandatory
        DESCRIPTION
            "Current equipment PM type."
        ::= { gmmr2g5EqptPmCurrEntry 1 }

    gmmr2g5EqptPmCurrValue OBJECT-TYPE
        SYNTAX DisplayString
        ACCESS read-only
        STATUS mandatory
        DESCRIPTION
            "Current equipment PM value."
        ::= { gmmr2g5EqptPmCurrEntry 2 }

    gmmr2g5EqptPmCurrValidity OBJECT-TYPE
        SYNTAX INTEGER { false(1), true(2) }
        ACCESS read-only
        STATUS mandatory
        DESCRIPTION
            "Current equipment PM validity."
        ::= { gmmr2g5EqptPmCurrEntry 3 }

    gmmr2g5EqptPmCurrLocation OBJECT-TYPE
        SYNTAX INTEGER { farEnd(1), nearEnd(2) }
        ACCESS read-only
        STATUS mandatory
        DESCRIPTION
            "Current equipment PM location."
        ::= { gmmr2g5EqptPmCurrEntry 4 }

    gmmr2g5EqptPmCurrDirection OBJECT-TYPE
        SYNTAX INTEGER { na(1), rcv(2), trmt(3) }
        ACCESS read-only
        STATUS mandatory
        DESCRIPTION
            "Current equipment PM direction."
        ::= { gmmr2g5EqptPmCurrEntry 5 }

    gmmr2g5EqptPmCurrDate OBJECT-TYPE
        SYNTAX DisplayString
        ACCESS read-only
        STATUS mandatory
        DESCRIPTION
            "Current equipment PM date."
        ::= { gmmr2g5EqptPmCurrEntry 6 }

    gmmr2g5EqptPmCurrTime OBJECT-TYPE
        SYNTAX DisplayString
        ACCESS read-only
        STATUS mandatory
        DESCRIPTION
            "Current equipment PM time."
        ::= { gmmr2g5EqptPmCurrEntry 7 }

    --
    -- The elements in the gmmr2g5EqptPmHistTable subgroup of the cardConfiguration group
    --

    gmmr2g5EqptPmHistTable   OBJECT-TYPE
            SYNTAX  SEQUENCE OF Gmmr2g5EqptPmHistEntry
            ACCESS  not-accessible
            STATUS  mandatory
            DESCRIPTION
                    "GMMR2G5 historical equipment PM table"
            ::= { gmmr2g5 4 }

    gmmr2g5EqptPmHistEntry   OBJECT-TYPE
            SYNTAX  Gmmr2g5EqptPmHistEntry
            ACCESS  not-accessible
            STATUS  mandatory
            DESCRIPTION
                    "GMMR2G5 historical equipment PM entry format."
            INDEX   { eqptBay, eqptShelf, eqptSlot, gmmr2g5EqptPmHistInterval, gmmr2g5EqptPmHistType }
            ::= { gmmr2g5EqptPmHistTable 1 }

    Gmmr2g5EqptPmHistEntry   ::=
            SEQUENCE 
            {
                gmmr2g5EqptPmHistInterval     INTEGER,
                gmmr2g5EqptPmHistType         INTEGER,
                gmmr2g5EqptPmHistValue        DisplayString,
                gmmr2g5EqptPmHistValidity     INTEGER,
                gmmr2g5EqptPmHistLocation     INTEGER,
                gmmr2g5EqptPmHistDirection    INTEGER,
                gmmr2g5EqptPmHistDate         DisplayString,
                gmmr2g5EqptPmHistTime         DisplayString
            }

    gmmr2g5EqptPmHistInterval OBJECT-TYPE
        SYNTAX INTEGER (1..32)
        ACCESS read-only
        STATUS mandatory
        DESCRIPTION
            "Historical equipment PM interval."
        ::= { gmmr2g5EqptPmHistEntry 1 }

    gmmr2g5EqptPmHistType OBJECT-TYPE
        SYNTAX INTEGER { lbc(2), ltemp(4), opt(5) }
        ACCESS read-only
        STATUS mandatory
        DESCRIPTION
            "Historical equipment PM type."
        ::= { gmmr2g5EqptPmHistEntry 2 }

    gmmr2g5EqptPmHistValue OBJECT-TYPE
        SYNTAX DisplayString
        ACCESS read-only
        STATUS mandatory
        DESCRIPTION
            "Historical equipment PM value."
        ::= { gmmr2g5EqptPmHistEntry 3 }

    gmmr2g5EqptPmHistValidity OBJECT-TYPE
        SYNTAX INTEGER { false(1), true(2) }
        ACCESS read-only
        STATUS mandatory
        DESCRIPTION
            "Historical equipment PM validity."
        ::= { gmmr2g5EqptPmHistEntry 4 }

    gmmr2g5EqptPmHistLocation OBJECT-TYPE
        SYNTAX INTEGER { farEnd(1), nearEnd(2) }
        ACCESS read-only
        STATUS mandatory
        DESCRIPTION
            "Historical equipment PM location."
        ::= { gmmr2g5EqptPmHistEntry 5 }

    gmmr2g5EqptPmHistDirection OBJECT-TYPE
        SYNTAX INTEGER { na(1), rcv(2), trmt(3) }
        ACCESS read-only
        STATUS mandatory
        DESCRIPTION
            "Historical equipment PM direction."
        ::= { gmmr2g5EqptPmHistEntry 6 }

    gmmr2g5EqptPmHistDate OBJECT-TYPE
        SYNTAX DisplayString
        ACCESS read-only
        STATUS mandatory
        DESCRIPTION
            "Historical equipment PM date."
        ::= { gmmr2g5EqptPmHistEntry 7 }

    gmmr2g5EqptPmHistTime OBJECT-TYPE
        SYNTAX DisplayString
        ACCESS read-only
        STATUS mandatory
        DESCRIPTION
            "Historical equipment PM time."
        ::= { gmmr2g5EqptPmHistEntry 8 }

    --
    -- The elements in the gmmr2g5FacPmCurrTable subgroup of the cardConfiguration group
    --

    gmmr2g5FacPmCurrTable   OBJECT-TYPE
            SYNTAX  SEQUENCE OF Gmmr2g5FacPmCurrEntry
            ACCESS  not-accessible
            STATUS  mandatory
            DESCRIPTION
                    "GMMR2G5 current facility PM table"
            ::= { gmmr2g5 5 }

    gmmr2g5FacPmCurrEntry   OBJECT-TYPE
            SYNTAX  Gmmr2g5FacPmCurrEntry
            ACCESS  not-accessible
            STATUS  mandatory
            DESCRIPTION
                    "GMMR2G5 current facility PM entry format."
            INDEX   { eqptBay, eqptShelf, eqptSlot, gmmr2g5FacPort, gmmr2g5FacPmCurrType }
            ::= { gmmr2g5FacPmCurrTable 1 }

    Gmmr2g5FacPmCurrEntry   ::=
            SEQUENCE 
            {
                gmmr2g5FacPmCurrType         INTEGER,
                gmmr2g5FacPmCurrValue        DisplayString,
                gmmr2g5FacPmCurrOcFacility   INTEGER,
                gmmr2g5FacPmCurrValidity     INTEGER,
                gmmr2g5FacPmCurrLocation     INTEGER,
                gmmr2g5FacPmCurrDirection    INTEGER,
                gmmr2g5FacPmCurrDate         DisplayString,
                gmmr2g5FacPmCurrTime         DisplayString
            }

    gmmr2g5FacPmCurrType OBJECT-TYPE
        SYNTAX INTEGER { opr(8) }
        ACCESS read-only
        STATUS mandatory
        DESCRIPTION
            "Current facility PM type."
        ::= { gmmr2g5FacPmCurrEntry 1 }

    gmmr2g5FacPmCurrValue OBJECT-TYPE
        SYNTAX DisplayString
        ACCESS read-only
        STATUS mandatory
        DESCRIPTION
            "Current facility PM value."
        ::= { gmmr2g5FacPmCurrEntry 2 }

    gmmr2g5FacPmCurrOcFacility OBJECT-TYPE
        SYNTAX INTEGER { oc12(1), oc192(2), oc24(3), oc48(4), oc3(5) }
        ACCESS read-only
        STATUS mandatory
        DESCRIPTION
            "Current facility PM OC facility."
        ::= { gmmr2g5FacPmCurrEntry 3 }

    gmmr2g5FacPmCurrValidity OBJECT-TYPE
        SYNTAX INTEGER { false(1), true(2) }
        ACCESS read-only
        STATUS mandatory
        DESCRIPTION
            "Current facility PM validity."
        ::= { gmmr2g5FacPmCurrEntry 4 }

    gmmr2g5FacPmCurrLocation OBJECT-TYPE
        SYNTAX INTEGER { farEnd(1), nearEnd(2) }
        ACCESS read-only
        STATUS mandatory
        DESCRIPTION
            "Current facility PM location."
        ::= { gmmr2g5FacPmCurrEntry 5 }

    gmmr2g5FacPmCurrDirection OBJECT-TYPE
        SYNTAX INTEGER { na(1), rcv(2), trmt(3) }
        ACCESS read-only
        STATUS mandatory
        DESCRIPTION
            "Current facility PM direction."
        ::= { gmmr2g5FacPmCurrEntry 6 }

    gmmr2g5FacPmCurrDate OBJECT-TYPE
        SYNTAX DisplayString
        ACCESS read-only
        STATUS mandatory
        DESCRIPTION
            "Current facility PM date."
        ::= { gmmr2g5FacPmCurrEntry 7 }

    gmmr2g5FacPmCurrTime OBJECT-TYPE
        SYNTAX DisplayString
        ACCESS read-only
        STATUS mandatory
        DESCRIPTION
            "Current facility PM time."
        ::= { gmmr2g5FacPmCurrEntry 8 }

    --
    -- The elements in the gmmr2g5FacPmHistTable subgroup of the cardConfiguration group
    --

    gmmr2g5FacPmHistTable   OBJECT-TYPE
            SYNTAX  SEQUENCE OF Gmmr2g5FacPmHistEntry
            ACCESS  not-accessible
            STATUS  mandatory
            DESCRIPTION
                    "GMMR2G5 historical facility PM table"
            ::= { gmmr2g5 6 }

    gmmr2g5FacPmHistEntry   OBJECT-TYPE
            SYNTAX  Gmmr2g5FacPmHistEntry
            ACCESS  not-accessible
            STATUS  mandatory
            DESCRIPTION
                    "GMMR2G5 historical facility PM entry format."
            INDEX   { eqptBay, eqptShelf, eqptSlot, gmmr2g5FacPort, gmmr2g5FacPmHistInterval, gmmr2g5FacPmHistType }
            ::= { gmmr2g5FacPmHistTable 1 }

    Gmmr2g5FacPmHistEntry   ::=
            SEQUENCE 
            {
                gmmr2g5FacPmHistInterval     INTEGER,
                gmmr2g5FacPmHistType         INTEGER,
                gmmr2g5FacPmHistValue        DisplayString,
                gmmr2g5FacPmHistOcFacility   INTEGER,
                gmmr2g5FacPmHistValidity     INTEGER,
                gmmr2g5FacPmHistLocation     INTEGER,
                gmmr2g5FacPmHistDirection    INTEGER,
                gmmr2g5FacPmHistDate         DisplayString,
                gmmr2g5FacPmHistTime         DisplayString
            }

    gmmr2g5FacPmHistInterval OBJECT-TYPE
        SYNTAX INTEGER (1..32)
        ACCESS read-only
        STATUS mandatory
        DESCRIPTION
            "Historical facility PM interval."
        ::= { gmmr2g5FacPmHistEntry 1 }

    gmmr2g5FacPmHistType OBJECT-TYPE
        SYNTAX INTEGER { opr(8) }
        ACCESS read-only
        STATUS mandatory
        DESCRIPTION
            "Historical facility PM type."
        ::= { gmmr2g5FacPmHistEntry 2 }

    gmmr2g5FacPmHistValue OBJECT-TYPE
        SYNTAX DisplayString
        ACCESS read-only
        STATUS mandatory
        DESCRIPTION
            "Historical facility PM value."
        ::= { gmmr2g5FacPmHistEntry 3 }

    gmmr2g5FacPmHistOcFacility OBJECT-TYPE
        SYNTAX INTEGER { oc12(1), oc192(2), oc24(3), oc48(4), oc3(5) }
        ACCESS read-only
        STATUS mandatory
        DESCRIPTION
            "Historical facility PM OC facility."
        ::= { gmmr2g5FacPmHistEntry 4 }

    gmmr2g5FacPmHistValidity OBJECT-TYPE
        SYNTAX INTEGER { false(1), true(2) }
        ACCESS read-only
        STATUS mandatory
        DESCRIPTION
            "Historical facility PM validity."
        ::= { gmmr2g5FacPmHistEntry 5 }

    gmmr2g5FacPmHistLocation OBJECT-TYPE
        SYNTAX INTEGER { farEnd(1), nearEnd(2) }
        ACCESS read-only
        STATUS mandatory
        DESCRIPTION
            "Historical facility PM location."
        ::= { gmmr2g5FacPmHistEntry 6 }

    gmmr2g5FacPmHistDirection OBJECT-TYPE
        SYNTAX INTEGER { na(1), rcv(2), trmt(3) }
        ACCESS read-only
        STATUS mandatory
        DESCRIPTION
            "Historical facility PM direction."
        ::= { gmmr2g5FacPmHistEntry 7 }

    gmmr2g5FacPmHistDate OBJECT-TYPE
        SYNTAX DisplayString
        ACCESS read-only
        STATUS mandatory
        DESCRIPTION
            "Historical facility PM date."
        ::= { gmmr2g5FacPmHistEntry 8 }

    gmmr2g5FacPmHistTime OBJECT-TYPE
        SYNTAX DisplayString
        ACCESS read-only
        STATUS mandatory
        DESCRIPTION
            "Historical facility PM time."
        ::= { gmmr2g5FacPmHistEntry 9 }

    --
    -- The elements in the gmmr4 subgroup of the cardConfiguration group
    --

    gmmr4Table   OBJECT-TYPE
            SYNTAX  SEQUENCE OF Gmmr4Entry
            ACCESS  not-accessible
            STATUS  mandatory
            DESCRIPTION
                    "GMMR4 module table"
            ::= { gmmr4 1 }

    gmmr4Entry   OBJECT-TYPE
            SYNTAX  Gmmr4Entry
            ACCESS  not-accessible
            STATUS  mandatory
            DESCRIPTION
                    "GMMR4 entry format."
            INDEX   { eqptBay, eqptShelf, eqptSlot }
            ::= { gmmr4Table 1 }

    Gmmr4Entry   ::=
            SEQUENCE 
            {
                gmmr4PrimaryState            INTEGER,
                gmmr4SecondaryState          INTEGER,
                gmmr4AdminState              INTEGER
            }

    gmmr4PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmmr4Entry 1 }

    gmmr4SecondaryState OBJECT-TYPE
        SYNTAX SecondaryState
        ACCESS read-only
        STATUS mandatory
        DESCRIPTION
            "Secondary state of module."
        ::= { gmmr4Entry 2 }

    gmmr4AdminState OBJECT-TYPE
        SYNTAX INTEGER { other(1), reset(2) }
        ACCESS read-write
        STATUS mandatory
        DESCRIPTION
            "Administration state of module.  This field is used
             to reset the module.  Reading this field always 
             returns other(1)."
        ::= { gmmr4Entry 3 }

    --
    -- The elements in the gmmr4Facilities subgroup of the configuration group
    --

    gmmr4FacTable   OBJECT-TYPE
            SYNTAX  SEQUENCE OF Gmmr4FacEntry
            ACCESS  not-accessible
            STATUS  mandatory
            DESCRIPTION
                    "GMMR4 facility table."
            ::= { gmmr4 2 }

    gmmr4FacEntry   OBJECT-TYPE
            SYNTAX  Gmmr4FacEntry
            ACCESS  not-accessible
            STATUS  mandatory
            DESCRIPTION
                    "GMMR4 facility entry format"
            INDEX   { eqptBay, eqptShelf, eqptSlot, gmmr4FacPort }
            ::= { gmmr4FacTable 1 }

    Gmmr4FacEntry   ::=
            SEQUENCE 
            {
                gmmr4FacPort                INTEGER,
                gmmr4FacLaserControl        INTEGER,
                gmmr4FacPortMode            INTEGER,
                gmmr4FacRate                INTEGER,
                gmmr4FacApsd                INTEGER,
                gmmr4FacConnectTo           INTEGER,
                gmmr4FacItuNum              ItuSelection2,
                gmmr4FacOprStatus           INTEGER,
                gmmr4FacLaserStatus         INTEGER,
                gmmr4FacClientApsd          INTEGER,
                gmmr4FacReceiverStatus      INTEGER,
                gmmr4FacSignalLocked        INTEGER,
                gmmr4FacOpr0                DisplayString,
                gmmr4FacPrimaryState        INTEGER,
                gmmr4FacSecondaryState      INTEGER
            }

    gmmr4FacPort OBJECT-TYPE
        SYNTAX INTEGER { a1(1), a2(2), a3(3), a4(4), b1(5), b2(6), b3(7), b4(8) }
        ACCESS read-only
        STATUS mandatory
        DESCRIPTION
            "Port portion of GMMR4 facility address."
        ::= { gmmr4FacEntry 1 }

    gmmr4FacLaserControl OBJECT-TYPE
        SYNTAX INTEGER { na(0), off(1), on(2) }
        ACCESS read-write
        STATUS mandatory
        DESCRIPTION
            "Laser Control.
             ON: Turn On the laser of this port.  
             OFF: Turn off the laser.   
             The On/Off of the laser is further controled by APSD."
        ::= { gmmr4FacEntry 2 }

    gmmr4FacPortMode OBJECT-TYPE
        SYNTAX INTEGER
        {
            backup(1),
            loopback(2),
            notassigned(3),
            passthrough(4),
            protection(5),
            working(6)
        }
        ACCESS read-write
        STATUS mandatory
        DESCRIPTION
            "Port Mode of this port. The notassigned(3) state cannot be set."
        ::= { gmmr4FacEntry 3 }

    gmmr4FacRate OBJECT-TYPE
        SYNTAX INTEGER
        {
            fc(1),
            r2(2),
            fcx2(3),
            gigex2(4),
            fcx4(5),
            disabled(6),
            gige(7),
            oc12(8),
            oc3(9),
            oc48(10)
        }
        ACCESS read-write
        STATUS mandatory
        DESCRIPTION
            "The configured speed of the interface."
        ::= { gmmr4FacEntry 4 }

    gmmr4FacApsd OBJECT-TYPE
        SYNTAX INTEGER { disabled(1), enabled(2) }
        ACCESS read-write
        STATUS mandatory
        DESCRIPTION
            "APSD setting."
        ::= { gmmr4FacEntry 5 }

    gmmr4FacConnectTo OBJECT-TYPE
        SYNTAX INTEGER { a1(1), a2(2), a3(3), a4(4), b1(5), b2(6), b3(7), b4(8) }
        ACCESS read-write
        STATUS mandatory
        DESCRIPTION
            "The port to which this port is connected."
        ::= { gmmr4FacEntry 6 }

    gmmr4FacItuNum OBJECT-TYPE
        SYNTAX ItuSelection2
        ACCESS read-write
        STATUS mandatory
        DESCRIPTION
            "The ITU number or client wavelength supported by the SFP."
        ::= { gmmr4FacEntry 7 }

    gmmr4FacOprStatus OBJECT-TYPE
        SYNTAX INTEGER { good(1), los(2) }
        ACCESS read-only
        STATUS mandatory
        DESCRIPTION
            "The current operational state of the interface."
        ::= { gmmr4FacEntry 8 }

    gmmr4FacLaserStatus OBJECT-TYPE
        SYNTAX INTEGER { na(0), off(1), on(2) }
        ACCESS read-only
        STATUS mandatory
        DESCRIPTION
            "Laser Status."
        ::= { gmmr4FacEntry 9 }

    gmmr4FacClientApsd OBJECT-TYPE
        SYNTAX INTEGER { disabled(1), enabled(2) }
        ACCESS read-only
        STATUS mandatory
        DESCRIPTION
            "The client APSD status."
        ::= { gmmr4FacEntry 10 }

    gmmr4FacReceiverStatus OBJECT-TYPE
        SYNTAX INTEGER
        {
            absent(1),
            corrupted(2),
            mismatched(3),
            na(4),
            normal(5),
            present(6),
            unauthorized(7)
        }
        ACCESS read-only
        STATUS mandatory
        DESCRIPTION
            "Status of the transceiver."
        ::= { gmmr4FacEntry 11 }

    gmmr4FacSignalLocked OBJECT-TYPE
        SYNTAX INTEGER { locked(1), notlocked(2) }
        ACCESS read-only
        STATUS mandatory
        DESCRIPTION
            "Loss of Lock status."
        ::= { gmmr4FacEntry 12 }

    gmmr4FacOpr0 OBJECT-TYPE
        SYNTAX DisplayString
        ACCESS read-write
        STATUS mandatory
        DESCRIPTION
            "Nominal value of average optical output power
             of the received signal, or the Optical Power Received
             (OPR) in dBm. The valid range differs based on the
             current port. The valid range is -31 to 4."
        ::= { gmmr4FacEntry 13 }

    gmmr4FacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmmr4FacEntry 14 }

    gmmr4FacSecondaryState OBJECT-TYPE
        SYNTAX SecondaryState
        ACCESS read-only
        STATUS mandatory
        DESCRIPTION
            "Secondary state of port."
        ::= { gmmr4FacEntry 15 }

    --
    -- The elements in the gmmr4Bayilities subgroup of the configuration group
    --

    gmmr4BayTable   OBJECT-TYPE
            SYNTAX  SEQUENCE OF Gmmr4BayEntry
            ACCESS  not-accessible
            STATUS  mandatory
            DESCRIPTION
                    "GMMR4 facility table."
            ::= { gmmr4 3 }

    gmmr4BayEntry   OBJECT-TYPE
            SYNTAX  Gmmr4BayEntry
            ACCESS  not-accessible
            STATUS  mandatory
            DESCRIPTION
                    "GMMR4 facility entry format"
            INDEX   { eqptBay, eqptShelf, eqptSlot, gmmr4BayPort }
            ::= { gmmr4BayTable 1 }

    Gmmr4BayEntry   ::=
            SEQUENCE 
            {
                gmmr4BayPort                INTEGER,
                gmmr4BaySwOprMode           INTEGER,
                gmmr4BayOprLowSwInd         INTEGER,
                gmmr4BayWOprLowTh           DisplayString,
                gmmr4BayPOprLowTh           DisplayString,
                gmmr4BayOprLowSwDelayTime   INTEGER,
                gmmr4BayWaitToRestoreTime   INTEGER,
                gmmr4BayAllowSwToFail       INTEGER,
                gmmr4BaySwMode              INTEGER,
                gmmr4BayWInputPower         DisplayString,
                gmmr4BayPInputPower         DisplayString,
                gmmr4BayPrimaryState        INTEGER,
                gmmr4BaySecondaryState      INTEGER
            }

    gmmr4BayPort OBJECT-TYPE
        SYNTAX INTEGER { a(1), b(2) }
        ACCESS read-only
        STATUS mandatory
        DESCRIPTION
            "Bay portion of GMMR4 facility address."
        ::= { gmmr4BayEntry 1 }

    gmmr4BaySwOprMode OBJECT-TYPE
        SYNTAX INTEGER { nonrevertive(1), revertive(2) }
        ACCESS read-write
        STATUS mandatory
        DESCRIPTION
            "This operation mode will only take effect when the switching state 
             is in autoSW.
            
             non-revertive  - When the switch has been in fiberP (protection line). 
             It will not switch back to fiberW (working line) even working line is 
             restored from failure.
        
             revertive  - When the switch has been in fiberB (protection line). 
             It will switch back to fiberW (working line) after working line is 
             restored from failure"
        ::= { gmmr4BayEntry 2 }

    gmmr4BayOprLowSwInd OBJECT-TYPE
        SYNTAX INTEGER { na(0), off(1), on(2) }
        ACCESS read-write
        STATUS mandatory
        DESCRIPTION
            "This parameter controls whether OPD condition will trigger the 
             switch or not.
            
             on  - means OPD switch indicator is on.
             off - means OPD switch indicator is off."
        ::= { gmmr4BayEntry 3 }

    gmmr4BayWOprLowTh OBJECT-TYPE
        SYNTAX DisplayString
        ACCESS read-write
        STATUS mandatory
        DESCRIPTION
            "Working fiber trunk threshold value of OPRlow in DBm."
        ::= { gmmr4BayEntry 4 }

    gmmr4BayPOprLowTh OBJECT-TYPE
        SYNTAX DisplayString
        ACCESS read-write
        STATUS mandatory
        DESCRIPTION
            "Protection fiber trunk threshold value of OPRlow in DBm."
        ::= { gmmr4BayEntry 5 }

    gmmr4BayOprLowSwDelayTime OBJECT-TYPE
        SYNTAX INTEGER
        ACCESS read-write
        STATUS mandatory
        DESCRIPTION
            "Switching delay time in unit of minutes."
        ::= { gmmr4BayEntry 6 }

    gmmr4BayWaitToRestoreTime OBJECT-TYPE
        SYNTAX INTEGER
        ACCESS read-write
        STATUS mandatory
        DESCRIPTION
            "Wait-to-restore-time in unit of minutes."
        ::= { gmmr4BayEntry 7 }

    gmmr4BayAllowSwToFail OBJECT-TYPE
        SYNTAX INTEGER  { disabled(1), enabled(2) }
        ACCESS read-write
        STATUS mandatory
        DESCRIPTION
            "This parameter controls which scheme will be used for force 
             switch case.
            
             disable(1) - will not switch to a dead line.
             enable(2)  - can switch to a dead line."
        ::= { gmmr4BayEntry 8 }

    gmmr4BaySwMode OBJECT-TYPE
        SYNTAX INTEGER  { disabled(1), enabled(2) }
        ACCESS read-only
        STATUS mandatory
        DESCRIPTION
            "Switch enabled flag.
             disabled(1) - switch has not been set up.
             enabled(2)  - switch is running."
        ::= { gmmr4BayEntry 9 }

    gmmr4BayWInputPower OBJECT-TYPE
        SYNTAX DisplayString
        ACCESS read-only
        STATUS mandatory
        DESCRIPTION
            "Working line input power in dBm."
        ::= { gmmr4BayEntry 10 }

    gmmr4BayPInputPower OBJECT-TYPE
        SYNTAX DisplayString
        ACCESS read-only
        STATUS mandatory
        DESCRIPTION
            "Protection line input power in dBm."
        ::= { gmmr4BayEntry 11 }

    gmmr4BayPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmmr4BayEntry 12 }

    gmmr4BaySecondaryState OBJECT-TYPE
        SYNTAX SecondaryState
        ACCESS read-only
        STATUS mandatory
        DESCRIPTION
            "Secondary state of port."
        ::= { gmmr4BayEntry 13 }

    --
    -- The elements in the gmmr4ProtnSw subgroup of the configuration group
    --

    gmmr4ProtnSwTable   OBJECT-TYPE
            SYNTAX  SEQUENCE OF Gmmr4ProtnSwEntry
            ACCESS  not-accessible
            STATUS  mandatory
            DESCRIPTION
                    "GMMR4 facility table."
            ::= { gmmr4 4 }

    gmmr4ProtnSwEntry   OBJECT-TYPE
            SYNTAX  Gmmr4ProtnSwEntry
            ACCESS  not-accessible
            STATUS  mandatory
            DESCRIPTION
                    "GMMR4 protection switch entry format"
            INDEX   { eqptBay, eqptShelf, eqptSlot, gmmr4ProtnSwBay }
            ::= { gmmr4ProtnSwTable 1 }

    Gmmr4ProtnSwEntry   ::=
            SEQUENCE 
            {
                gmmr4ProtnSwBay                 INTEGER,
                gmmr4ProtnSwProtnSwCmd          INTEGER,
                gmmr4ProtnSwOperationMode       INTEGER,
                gmmr4ProtnSwOperatingTrunk      INTEGER,
                gmmr4ProtnSwWorkingTrunkStatus  INTEGER,
                gmmr4ProtnSwProtnTrunkStatus    INTEGER,
                gmmr4ProtnSwProtnSwReason       INTEGER
            }

    gmmr4ProtnSwBay OBJECT-TYPE
        SYNTAX INTEGER { a(1), b(2) }
        ACCESS read-only
        STATUS mandatory
        DESCRIPTION
            "Bay of retrieved data."
        ::= { gmmr4ProtnSwEntry 1 }

    gmmr4ProtnSwProtnSwCmd OBJECT-TYPE
        SYNTAX INTEGER
        {
            clear(1),
            fsptow(2),
            fswtop(3),
            lockoutp(4),
            msptow(5),
            mswtop(6)
        }
        ACCESS read-write
        STATUS mandatory
        DESCRIPTION
            "The description of GMMR4 switch commands are as follows:-  
             
             clear(1): Whenever clear command has been issued, it will 
             change the state to autoSW no matter what the previous state 
             is. In autoSW state, it will base on both line states and the 
             operation mode to determine the final switch position.
                 
             lockOutP(2): This command will cause the switch state to be 
             changed to lockOutP. If the previous switch position is in 
             fiberA, it will stay in fiberW. Otherwise, it will switch 
             from fiberP to fiberW.
                 
             fsWtoP(3): This forced switch command will change the state to 
             forceSW and change the switch position to fiberP if the previous 
             switch state is not in lockoutP or the other forceSw command is
             in effect.
                 
             fsPtoW(4): This forced switch command will change the state to 
             forceSW and change the switch position to fiberW if the previous 
             switch state is not in lockoutP or the other forceSw command is
             in effect.
                 
             msWtoP(5): This manual switch command will change the state to 
             manualSW and change the switch position to fiberP if the previous 
             switch state is not in lockoutP, forceSW or the other manualSw 
             command is in effect.
             
             msPtoW(6): This manual switch command will change the state to 
             manualSW and change the switch position to fiberW if the previous 
             switch state is not in lockoutP, forceSW or the other manualSw 
             command is in effect."
        ::= { gmmr4ProtnSwEntry 2 }

    gmmr4ProtnSwOperationMode OBJECT-TYPE
        SYNTAX INTEGER
        {
            auto(1),
            frcd(2),
            lockout(3),
            man(4),
            normal(5)
        }
        ACCESS read-only
        STATUS mandatory
        DESCRIPTION
            "GMMR4 operation mode description:-  
             autoNoRequest(1): Automatic Switch No Request
             lockoutPrequest(2): Lock out of Protection Request
             forceSwitchWtoP(3): Force Switch from working to protection request
             forceSwitchPtoW(4): Force Switch from protection to working request
             manualSwitchWtoP(5): Manual Switch from working to protection request"
        ::= { gmmr4ProtnSwEntry 3 }

    gmmr4ProtnSwOperatingTrunk OBJECT-TYPE
        SYNTAX INTEGER { oprTrunk1(1), oprTrunk2(2), unknown(3) }
        ACCESS read-only
        STATUS mandatory
        DESCRIPTION
            "Indicates which trunk is the current working trunk."
        ::= { gmmr4ProtnSwEntry 4 }

    gmmr4ProtnSwWorkingTrunkStatus OBJECT-TYPE
        SYNTAX INTEGER
        {
            normal(1),
            oprLoss(2),
            oprLow(3),
            oprOverload(4)
        }
        ACCESS read-only
        STATUS mandatory
        DESCRIPTION
            "State of fiber Working Line for a GMMR4 module."
        ::= { gmmr4ProtnSwEntry 5 }

    gmmr4ProtnSwProtnTrunkStatus OBJECT-TYPE
        SYNTAX INTEGER
        {
            normal(1),
            oprLoss(2),
            oprLow(3),
            oprOverload(4)
        }
        ACCESS read-only
        STATUS mandatory
        DESCRIPTION
            "State of fiber Protection Line for a GMMR4 module."
        ::= { gmmr4ProtnSwEntry 6 }

    gmmr4ProtnSwProtnSwReason OBJECT-TYPE
        SYNTAX INTEGER 
        {
            normal(1),
            oprLoss(2),
            oprLow(3),
            oprOverload(4),
            nil(5)
        }
        ACCESS read-only
        STATUS mandatory
        DESCRIPTION
            "reason for protection switch."
        ::= { gmmr4ProtnSwEntry 7 }

    --
    -- The elements in the gmoaT4 subgroup of the cardConfiguration group
    --

    gmoaT4Table   OBJECT-TYPE
            SYNTAX  SEQUENCE OF GmoaT4Entry
            ACCESS  not-accessible
            STATUS  mandatory
            DESCRIPTION
                    "GMOA-T4 module table"
            ::= { gmoaT4 1 }

    gmoaT4Entry   OBJECT-TYPE
            SYNTAX  GmoaT4Entry
            ACCESS  not-accessible
            STATUS  mandatory
            DESCRIPTION
                    "GMOA-T4 entry format."
            INDEX   { eqptBay, eqptShelf, eqptSlot }
            ::= { gmoaT4Table 1 }

    GmoaT4Entry   ::=
            SEQUENCE 
            {
                gmoaT4SubType               DisplayString,
                gmoaT4Apr                   INTEGER,
                gmoaT4OprMode               INTEGER,
                gmoaT4Gain                  INTEGER,
                gmoaT4Gain0                 DisplayString,
                gmoaT4Opr0                  DisplayString,
                gmoaT4RftOpr0               DisplayString,
                gmoaT4Opt0                  DisplayString,
                gmoaT4ApsdTh                DisplayString,
                gmoaT4GainHTh               DisplayString,
                gmoaT4GainLTh               DisplayString,
                gmoaT4LbcHTh                INTEGER,
                gmoaT4LTempHTh              INTEGER,
                gmoaT4LTempLTh              INTEGER,
                gmoaT4OprLowTh              DisplayString,
                gmoaT4OprFaultTh            DisplayString,
                gmoaT4RftOprLowTh           DisplayString,
                gmoaT4RftOprFaultTh         DisplayString,
                gmoaT4OptLowTh              DisplayString,
                gmoaT4OptFaultTh            DisplayString,
                gmoaT4OperationalState      INTEGER,
                gmoaT4CaseTemp              INTEGER,
                gmoaT4PrimaryState          INTEGER,
                gmoaT4SecondaryState        INTEGER,
                gmoaT4AdminState            INTEGER,
                gmoaT4PmStatus              INTEGER
            }

    gmoaT4SubType OBJECT-TYPE
        SYNTAX DisplayString
        ACCESS read-only
        STATUS mandatory
        DESCRIPTION
            "Module sub type."
        ::= { gmoaT4Entry 1 }

    gmoaT4Apr OBJECT-TYPE
        SYNTAX INTEGER { off(1), on(2) }
        ACCESS read-write
        STATUS mandatory
        DESCRIPTION
            "Automatic power reduction."
        ::= { gmoaT4Entry 2 }

    gmoaT4OprMode OBJECT-TYPE
        SYNTAX INTEGER { constantgain(1), eyesafe(2), shutdown(3) }
        ACCESS read-write
        STATUS mandatory
        DESCRIPTION
            "Operational Mode of amplifier."
        ::= { gmoaT4Entry 3 }

    gmoaT4Gain OBJECT-TYPE
        SYNTAX INTEGER (12..33)
        ACCESS read-write
        STATUS mandatory
        DESCRIPTION
            "Specifies desired gain in dB. Maximum gain, maximum
             output gain, and input power must be taken into account
             when setting Gain. Applicable only in constant-gain mode.
             The valid range is Min. 12 dB to Max. 33 dB."
        ::= { gmoaT4Entry 4 }

    gmoaT4Gain0 OBJECT-TYPE
        SYNTAX DisplayString (SIZE (0..7))
        ACCESS read-write
        STATUS mandatory
        DESCRIPTION
            "Nominal value of amplifier gain in dB."
        ::= { gmoaT4Entry 5 }

    gmoaT4Opr0 OBJECT-TYPE
        SYNTAX DisplayString (SIZE (0..7))
        ACCESS read-write
        STATUS mandatory
        DESCRIPTION
            "Nominal value of input optical power in dBm."
        ::= { gmoaT4Entry 6 }

    gmoaT4RftOpr0 OBJECT-TYPE
        SYNTAX DisplayString (SIZE (0..7))
        ACCESS read-write
        STATUS mandatory
        DESCRIPTION
            "Nominal value of input optical power in dBm for RFT port"
        ::= { gmoaT4Entry 7 }

    gmoaT4Opt0 OBJECT-TYPE
        SYNTAX DisplayString (SIZE (0..7))
        ACCESS read-write
        STATUS mandatory
        DESCRIPTION
            "Nominal value of output optical power in dBm."
        ::= { gmoaT4Entry 8 }

    gmoaT4ApsdTh OBJECT-TYPE
        SYNTAX DisplayString (SIZE (0..7))
        ACCESS read-write
        STATUS mandatory
        DESCRIPTION
            "Sets the input power level, that is deemed to represent
             amplifier input fiber cut condition.
             When input power level drops below this level, APSD will
             trigger in and the amplifier module will be shutdown.
             When input power level increases from fault condition to
             this level, with hysteresis of +1.0dB, module will operate
             in configured 'gmoaT4OprMode'.
             The valid range is Min. -30.0 dBm to Max. -25.0 dBm."
        ::= { gmoaT4Entry 9 }

    gmoaT4GainHTh OBJECT-TYPE
        SYNTAX DisplayString (SIZE (0..6))
        ACCESS read-write
        STATUS mandatory
        DESCRIPTION
            "Sets the gain margin relative to gmoaT4Gain0,
             that is deemed to be high.
             When 'gmoaT4Gain' increases above 'gmoaT4Gain0'
             by this margin, a trap will be generated.
             When 'gmoaT4Gain' decreases from high condition to
             this level relative to 'gmoaT4Gain0' with hysteresis
             of -0.5dB, a clear trap will be generated.
             The valid range is Min. 1.0 dB to Max. 5.0 dB."
        ::= { gmoaT4Entry 10 }

    gmoaT4GainLTh OBJECT-TYPE
        SYNTAX DisplayString (SIZE (0..6))
        ACCESS read-write
        STATUS mandatory
        DESCRIPTION
            "Sets the gain margin relative to gmoaT4Gain0,
             that is deemed to be low.
             When 'gmoaT4Gain' drops below 'gmoaT4Gain0' by this
             margin, a trap will be generated.
             When 'gmoaT4Gain' increases from low condition to
             this level relative to 'gmoaT4Gain0' with hysteresis
             of +0.5dB, a clear trap will be generated.
             The valid range is Min. -5.0 dB to Max. -1.0 dB."
        ::= { gmoaT4Entry 11 }

    gmoaT4LbcHTh OBJECT-TYPE
        SYNTAX INTEGER
        ACCESS read-only
        STATUS mandatory
        DESCRIPTION
            "Specifies the pump laser current that is deemed to be too high.
             Determined as 95% of End Of Life (EOL) pump current value
             specified by the manufacturer.
             When the pump laser current increases above this value,
             a trap will be generated.
             When the pump laser current decreases from high condition
             to this level with negative hysteresis of 10 mA,
             a clear trap will be generated."
        ::= { gmoaT4Entry 12 }

    gmoaT4LTempHTh OBJECT-TYPE
        SYNTAX INTEGER
        ACCESS read-only
        STATUS mandatory
        DESCRIPTION
            "Manufacturer specified high temperature limit for
             normal operation of laser pump.
             When the pump laser temperature increases above this value,
             a trap will be generated.
             When the pump laser temperature decreases from high condition
             to this level with hysteresis of -2 degree Celsius,
             a clear trap will be generated."
        ::= { gmoaT4Entry 13 }

    gmoaT4LTempLTh OBJECT-TYPE
        SYNTAX INTEGER
        ACCESS read-only
        STATUS mandatory
        DESCRIPTION
            "Manufacturer specified low temperature limit for
             normal operation of laser pump.
             When the pump laser temperature decreases below this value,
             a trap will be generated.
             When the pump laser temperature increases from low condition
             to this level with hysteresis of 2 degree Celsius,
             a clear trap will be generated."
        ::= { gmoaT4Entry 14 }

    gmoaT4OprLowTh OBJECT-TYPE
        SYNTAX DisplayString
        ACCESS read-write
        STATUS mandatory
        DESCRIPTION
            "Sets the input power level relative to
             gmoaT4Opr0, that is deemed to be low.
             When the input power level drops below 'gmoaT4Opr0'
             by this margin, a trap will be generated.
             When the input power level increases from low condition to
             this level, relative to 'gmoaT4Opr0' with
             hysteresis of +1.0dB, a clear trap will be generated.
             The valid range is Min. -5.0 dB to Max. -1.0 dB."
        ::= { gmoaT4Entry 15 }

    gmoaT4OprFaultTh OBJECT-TYPE
        SYNTAX DisplayString
        ACCESS read-write
        STATUS mandatory
        DESCRIPTION
            "Sets the input power level relative to
             gmoaT4Opr0, that is deemed to be too low.
             When the input power level drops below 'gmoaT4Opr0'
             by this margin, a trap will be generated.
             When the input power level increases from fault condition to
             this level, relative to 'gmoaT4Opr0' with
             hysteresis of +1.0dB, a clear trap will be generated.
             The valid range is Min. -10.0 dB to Max. -3.0 dB."
        ::= { gmoaT4Entry 16 }

    gmoaT4RftOprLowTh OBJECT-TYPE
        SYNTAX DisplayString
        ACCESS read-write
        STATUS mandatory
        DESCRIPTION
            "Sets the RFT input power level relative to
             gmoaT4RftOpr0, that is deemed to be low.
             When the input power level drops below 'gmoaT4RftOpr0'
             by this margin, a trap will be generated.
             When the input power level increases from low condition to
             this level, relative to 'gmoaT4RftOpr0' with
             hysteresis of +1.0dB, a clear trap will be generated.
             The valid range is Min. -5.0 dB to Max. -1.0 dB."
        ::= { gmoaT4Entry 17 }

    gmoaT4RftOprFaultTh OBJECT-TYPE
        SYNTAX DisplayString
        ACCESS read-write
        STATUS mandatory
        DESCRIPTION
            "Sets the RFT input power level relative to
             gmoaT4RftOpr0, that is deemed to be too low.
             When the input power level drops below 'gmoaT4RftOpr0'
             by this margin, a trap will be generated.
             When the input power level increases from fault condition to
             this level, relative to 'gmoaT4RftOpr0' with
             hysteresis of +1.0dB, a clear trap will be generated.
             The valid range is Min. -10.0 dB to Max. -3.0 dB."
        ::= { gmoaT4Entry 18 }

    gmoaT4OptLowTh OBJECT-TYPE
        SYNTAX DisplayString (SIZE (0..7))
        ACCESS read-write
        STATUS mandatory
        DESCRIPTION
            "Sets the output power level relative to
             'gmoaT4Opt0', that is deemed to be low.
             When the output power level drops below 'gmoaT4Opt0'
             by this margin, a trap will be generated.
             When the output power level increases from low condition to
             this level, relative to 'gmoaT4Opr0' with
             hysteresis of +1.0dB, a clear trap will be generated.
             The valid range is Min. -5.0 dB to Max. -1.0 dB."
        ::= { gmoaT4Entry 19 }

    gmoaT4OptFaultTh OBJECT-TYPE
        SYNTAX DisplayString (SIZE (0..7))
        ACCESS read-write
        STATUS mandatory
        DESCRIPTION
            "Sets the output power level relative to
             'gmoaT4Opt0', that is deemed to be too low.
             When the output power level drops below 'gmoaT4Opt0'
             by this margin, a trap will be generated.
             When the output power level increases from fault condition to
             this level, relative to 'gmoaT4Opr0' with
             hysteresis of +1.0dB, a clear trap will be generated.
             The valid range is Min. -10.0 dB to Max. -3.0 dB."
        ::= { gmoaT4Entry 20 }

    gmoaT4OperationalState OBJECT-TYPE
        SYNTAX INTEGER { apr(1), apsd(2), manual(3) }
        ACCESS read-only
        STATUS mandatory
        DESCRIPTION
            "Operational State of amplifier."
        ::= { gmoaT4Entry 21 }

    gmoaT4CaseTemp OBJECT-TYPE
        SYNTAX INTEGER
        ACCESS read-only
        STATUS mandatory
        DESCRIPTION
            "Case temperature in degree Celsius."
        ::= { gmoaT4Entry 22 }

    gmoaT4PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmoaT4Entry 23 }

    gmoaT4SecondaryState OBJECT-TYPE
        SYNTAX SecondaryState
        ACCESS read-only
        STATUS mandatory
        DESCRIPTION
            "Secondary state of module."
        ::= { gmoaT4Entry 24 }

    gmoaT4AdminState OBJECT-TYPE
        SYNTAX INTEGER { other(1), reset(2) }
        ACCESS read-write
        STATUS mandatory
        DESCRIPTION
            "Administration state of module.  This field is used
             to reset the module.  Reading this field always 
             returns other(1)."
        ::= { gmoaT4Entry 25 }

    gmoaT4PmStatus OBJECT-TYPE
        SYNTAX PmState
        ACCESS read-write
        STATUS mandatory
        DESCRIPTION
            "Perfornance monitoring status of module."
        ::= { gmoaT4Entry 26 }

    --
    -- The elements in the gmoaT5 subgroup of the cardConfiguration group
    --

    gmoaT5Table   OBJECT-TYPE
            SYNTAX  SEQUENCE OF GmoaT5Entry
            ACCESS  not-accessible
            STATUS  mandatory
            DESCRIPTION
                    "GMOA-T5 module table"
            ::= { gmoaT5 1 }

    gmoaT5Entry   OBJECT-TYPE
            SYNTAX  GmoaT5Entry
            ACCESS  not-accessible
            STATUS  mandatory
            DESCRIPTION
                    "GMOA-T5 entry format."
            INDEX   { eqptBay, eqptShelf, eqptSlot }
            ::= { gmoaT5Table 1 }

    GmoaT5Entry   ::=
            SEQUENCE 
            {
                gmoaT5SubType                 DisplayString,
                gmoaT5Gain                    INTEGER,
                gmoaT5OprMode                 INTEGER,
                gmoaT5OprCtrl                 INTEGER,
                gmoaT5InputPower              DisplayString,
                gmoaT5OutputPower             DisplayString,
                gmoaT5AprStatus               INTEGER,
                gmoaT5RxTrunkStatus           INTEGER,
                gmoaT5PrimaryState            INTEGER,
                gmoaT5SecondaryState          INTEGER,
                gmoaT5AdminState              INTEGER,
                gmoaT5PmStatus                INTEGER
            }

    gmoaT5SubType OBJECT-TYPE
        SYNTAX DisplayString
        ACCESS read-only
        STATUS mandatory
        DESCRIPTION
            "Module sub type."
        ::= { gmoaT5Entry 1 }

    gmoaT5Gain OBJECT-TYPE
        SYNTAX INTEGER
        ACCESS read-write
        STATUS mandatory
        DESCRIPTION
            "Specifies desired gain in dB. Maximum gain, maximum
            output gain, and input power must be taken into account
            when setting Gain. Applicable only in constant-gain mode."
        ::= { gmoaT5Entry 2 }

    gmoaT5OprMode OBJECT-TYPE
        SYNTAX INTEGER { constantcurrent(1), constantgain(2), constantoutputpower(3) }
        ACCESS read-write
        STATUS mandatory
        DESCRIPTION
            "Operational Mode of amplifier."
        ::= { gmoaT5Entry 3 }

    gmoaT5OprCtrl OBJECT-TYPE
        SYNTAX INTEGER { eyesafe(1), normal(2), shutdown(3) }
        ACCESS read-write
        STATUS mandatory
        DESCRIPTION
            "Operational control setting.
             normal(1)   - amplifier operational
             shutdown(2) - off
             eyesafe(3)  - output power is safe to human eye"
        ::= { gmoaT5Entry 4 }

    gmoaT5InputPower OBJECT-TYPE
        SYNTAX DisplayString (SIZE (0..7))
        ACCESS read-only
        STATUS mandatory
        DESCRIPTION
            "Input power in dBm."
        ::= { gmoaT5Entry 5 }

    gmoaT5OutputPower OBJECT-TYPE
        SYNTAX DisplayString (SIZE (0..7))
        ACCESS read-only
        STATUS mandatory
        DESCRIPTION
            "Output power in dBm."
        ::= { gmoaT5Entry 6 }

    gmoaT5AprStatus OBJECT-TYPE
        SYNTAX INTEGER { active(1), na(2), inactive(3) }
        ACCESS read-only
        STATUS mandatory
        DESCRIPTION
            "Indicates if the module is currently in APR state."
        ::= { gmoaT5Entry 7 }

    gmoaT5RxTrunkStatus OBJECT-TYPE
        SYNTAX INTEGER { aprsensing(1), dark(2), light(3), na(4) }
        ACCESS read-only
        STATUS mandatory
        DESCRIPTION
            "The trunk receiver indicates if the input is 
             dark (no light), active (light) or in APR."
        ::= { gmoaT5Entry 8 }

    gmoaT5PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmoaT5Entry 9 }

    gmoaT5SecondaryState OBJECT-TYPE
        SYNTAX SecondaryState
        ACCESS read-only
        STATUS mandatory
        DESCRIPTION
            "Secondary state of module."
        ::= { gmoaT5Entry 10 }

    gmoaT5AdminState OBJECT-TYPE
        SYNTAX INTEGER { other(1), reset(2) }
        ACCESS read-write
        STATUS mandatory
        DESCRIPTION
            "Administration state of module.  This field is used
             to reset the module.  Reading this field always 
             returns other(1)."
        ::= { gmoaT5Entry 11 }

    gmoaT5PmStatus OBJECT-TYPE
        SYNTAX PmState
        ACCESS read-write
        STATUS mandatory
        DESCRIPTION
            "Perfornance monitoring status of module."
        ::= { gmoaT5Entry 12 }

    --
    -- The elements in the gmoaT6 subgroup of the cardConfiguration group
    --

    gmoaT6Table   OBJECT-TYPE
            SYNTAX  SEQUENCE OF GmoaT6Entry
            ACCESS  not-accessible
            STATUS  mandatory
            DESCRIPTION
                    "GMOA-T6 module table"
            ::= { gmoaT6 1 }

    gmoaT6Entry   OBJECT-TYPE
            SYNTAX  GmoaT6Entry
            ACCESS  not-accessible
            STATUS  mandatory
            DESCRIPTION
                    "GMOA-T6 entry format."
            INDEX   { eqptBay, eqptShelf, eqptSlot }
            ::= { gmoaT6Table 1 }

    GmoaT6Entry   ::=
            SEQUENCE 
            {
                gmoaT6SubType                 DisplayString,
                gmoaT6Gain                    INTEGER,
                gmoaT6OprMode                 INTEGER,
                gmoaT6OprCtrl                 INTEGER,
                gmoaT6InputPower              DisplayString,
                gmoaT6OutputPower             DisplayString,
                gmoaT6AprStatus               INTEGER,
                gmoaT6RxTrunkStatus           INTEGER,
                gmoaT6PrimaryState            INTEGER,
                gmoaT6SecondaryState          INTEGER,
                gmoaT6AdminState              INTEGER,
                gmoaT6PmStatus                INTEGER
            }

    gmoaT6SubType OBJECT-TYPE
        SYNTAX DisplayString
        ACCESS read-only
        STATUS mandatory
        DESCRIPTION
            "Module sub type."
        ::= { gmoaT6Entry 1 }

    gmoaT6Gain OBJECT-TYPE
        SYNTAX INTEGER
        ACCESS read-write
        STATUS mandatory
        DESCRIPTION
            "Specifies desired gain in dB. Maximum gain, maximum
            output gain, and input power must be taken into account
            when setting Gain. Applicable only in constant-gain mode."
        ::= { gmoaT6Entry 2 }

    gmoaT6OprMode OBJECT-TYPE
        SYNTAX INTEGER { constantcurrent(1), constantgain(2), constantoutputpower(3) }
        ACCESS read-write
        STATUS mandatory
        DESCRIPTION
            "Operational Mode of amplifier."
        ::= { gmoaT6Entry 3 }

    gmoaT6OprCtrl OBJECT-TYPE
        SYNTAX INTEGER { eyesafe(1), normal(2), shutdown(3) }
        ACCESS read-write
        STATUS mandatory
        DESCRIPTION
            "Operational control setting.
             normal(1)   - amplifier operational
             shutdown(2) - off
             eyesafe(3)  - output power is safe to human eye"
        ::= { gmoaT6Entry 4 }

    gmoaT6InputPower OBJECT-TYPE
        SYNTAX DisplayString (SIZE (0..7))
        ACCESS read-only
        STATUS mandatory
        DESCRIPTION
            "Input power in dBm."
        ::= { gmoaT6Entry 5 }

    gmoaT6OutputPower OBJECT-TYPE
        SYNTAX DisplayString (SIZE (0..7))
        ACCESS read-only
        STATUS mandatory
        DESCRIPTION
            "Output power in dBm."
        ::= { gmoaT6Entry 6 }

    gmoaT6AprStatus OBJECT-TYPE
        SYNTAX INTEGER { active(1), na(2), inactive(3) }
        ACCESS read-only
        STATUS mandatory
        DESCRIPTION
            "Indicates if the module is currently in APR state."
        ::= { gmoaT6Entry 7 }

    gmoaT6RxTrunkStatus OBJECT-TYPE
        SYNTAX INTEGER { aprsensing(1), dark(2), light(3), na(4) }
        ACCESS read-only
        STATUS mandatory
        DESCRIPTION
            "The trunk receiver indicates if the input is 
             dark (no light), active (light) or in APR."
        ::= { gmoaT6Entry 8 }

    gmoaT6PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmoaT6Entry 9 }

    gmoaT6SecondaryState OBJECT-TYPE
        SYNTAX SecondaryState
        ACCESS read-only
        STATUS mandatory
        DESCRIPTION
            "Secondary state of module."
        ::= { gmoaT6Entry 10 }

    gmoaT6AdminState OBJECT-TYPE
        SYNTAX INTEGER { other(1), reset(2) }
        ACCESS read-write
        STATUS mandatory
        DESCRIPTION
            "Administration state of module.  This field is used
             to reset the module.  Reading this field always 
             returns other(1)."
        ::= { gmoaT6Entry 11 }

    gmoaT6PmStatus OBJECT-TYPE
        SYNTAX PmState
        ACCESS read-write
        STATUS mandatory
        DESCRIPTION
            "Perfornance monitoring status of module."
        ::= { gmoaT6Entry 12 }

    --
    -- The elements in the gmox subgroup of the cardConfiguration group
    --

    gmoxTable   OBJECT-TYPE
            SYNTAX  SEQUENCE OF GmoxEntry
            ACCESS  not-accessible
            STATUS  mandatory
            DESCRIPTION
                    "GMOX module table"
            ::= { gmox 1 }

    gmoxEntry   OBJECT-TYPE
            SYNTAX  GmoxEntry
            ACCESS  not-accessible
            STATUS  mandatory
            DESCRIPTION
                    "GMOX entry format."
            INDEX   { eqptBay, eqptShelf, eqptSlot }
            ::= { gmoxTable 1 }

    GmoxEntry   ::=
            SEQUENCE 
            {
                gmoxSubType                 DisplayString,
                gmoxItuNum                  ItuSelection,
                gmoxMaxBitRate              INTEGER,
                gmoxPrimaryState            INTEGER,
                gmoxSecondaryState          INTEGER,
                gmoxAdminState              INTEGER
            }

    gmoxSubType OBJECT-TYPE
        SYNTAX DisplayString (SIZE (0..120))
        ACCESS read-only
        STATUS mandatory
        DESCRIPTION
            "Module sub type."
        ::= { gmoxEntry 1 }

    gmoxItuNum OBJECT-TYPE
        SYNTAX ItuSelection 
        ACCESS read-only
        STATUS mandatory
        DESCRIPTION
            "Module supported ITU channel."
        ::= { gmoxEntry 2 }

    gmoxMaxBitRate OBJECT-TYPE
        SYNTAX INTEGER { unknown(0), oc12(1), oc24(2), oc48(3) }
        ACCESS read-only
        STATUS mandatory
        DESCRIPTION
            "Maximum bit rate supported by module."
        ::= { gmoxEntry 3 }

    gmoxPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmoxEntry 4 }

    gmoxSecondaryState OBJECT-TYPE
        SYNTAX SecondaryState
        ACCESS read-only
        STATUS mandatory
        DESCRIPTION
            "Secondary state of module."
        ::= { gmoxEntry 5 }

    gmoxAdminState OBJECT-TYPE
        SYNTAX INTEGER { other(1), reset(2) }
        ACCESS read-write
        STATUS mandatory
        DESCRIPTION
            "Administration state of module.  This field is used
             to reset the module.  Reading this field always 
             returns other(1)."
        ::= { gmoxEntry 6 }

    --
    -- The elements in the gmox2g5 subgroup of the cardConfiguration group
    --

    gmox2g5Table   OBJECT-TYPE
            SYNTAX  SEQUENCE OF Gmox2g5Entry
            ACCESS  not-accessible
            STATUS  mandatory
            DESCRIPTION
                    "GMOX2G5 module table"
            ::= { gmox2g5 1 }

    gmox2g5Entry   OBJECT-TYPE
            SYNTAX  Gmox2g5Entry
            ACCESS  not-accessible
            STATUS  mandatory
            DESCRIPTION
                    "GMOX2G5 entry format."
            INDEX   { eqptBay, eqptShelf, eqptSlot }
            ::= { gmox2g5Table 1 }

    Gmox2g5Entry   ::=
            SEQUENCE 
            {
                gmox2g5SubType              DisplayString,
                gmox2g5ItuNum               ItuSelection,
                gmox2g5Apsd                 INTEGER,
                gmox2g5MaxBitRate           INTEGER,
                gmox2g5PrimaryState         INTEGER,
                gmox2g5SecondaryState       INTEGER,
                gmox2g5AdminState           INTEGER
            }

    gmox2g5SubType OBJECT-TYPE
        SYNTAX DisplayString (SIZE (0..120))
        ACCESS read-only
        STATUS mandatory
        DESCRIPTION
            "Module sub type."
        ::= { gmox2g5Entry 1 }

    gmox2g5ItuNum OBJECT-TYPE
        SYNTAX ItuSelection 
        ACCESS read-only
        STATUS mandatory
        DESCRIPTION
            "Module ITU number."
        ::= { gmox2g5Entry 2 }

    gmox2g5Apsd      OBJECT-TYPE
        SYNTAX INTEGER { na(0), off(1), on(2) }
        ACCESS read-write
        STATUS mandatory
        DESCRIPTION
            "Module Automatic Power Shut Down setting.  The modules's
             primary state must be set OOS to modified this field."
        ::= { gmox2g5Entry 3 }

    gmox2g5MaxBitRate OBJECT-TYPE
        SYNTAX INTEGER { unknown(0), oc12(1), oc24(2), oc48(3) }
        ACCESS read-only
        STATUS mandatory
        DESCRIPTION
            "Maximum bit rate supported by module."
        ::= { gmox2g5Entry 4 }

    gmox2g5PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmox2g5Entry 5 }

    gmox2g5SecondaryState OBJECT-TYPE
        SYNTAX SecondaryState
        ACCESS read-only
        STATUS mandatory
        DESCRIPTION
            "Secondary state of module."
        ::= { gmox2g5Entry 6 }

    gmox2g5AdminState OBJECT-TYPE
        SYNTAX INTEGER { other(1), reset(2) }
        ACCESS read-write
        STATUS mandatory
        DESCRIPTION
            "Administration state of module.  This field is used
             to reset the module.  Reading this field always 
             returns other(1)."
        ::= { gmox2g5Entry 7 }

    --
    -- The elements in the gmrb subgroup of the cardConfiguration group
    --

    gmrbTable   OBJECT-TYPE
            SYNTAX  SEQUENCE OF GmrbEntry
            ACCESS  not-accessible
            STATUS  mandatory
            DESCRIPTION
                    "GMRB module table"
            ::= { gmrb 1 }

    gmrbEntry   OBJECT-TYPE
            SYNTAX  GmrbEntry
            ACCESS  not-accessible
            STATUS  mandatory
            DESCRIPTION
                    "GMRB entry format."
            INDEX   { eqptBay, eqptShelf, eqptSlot }
            ::= { gmrbTable 1 }

    GmrbEntry   ::=
            SEQUENCE 
            {
                gmrbSubType                DisplayString,
                gmrbPrimaryState           INTEGER,
                gmrbSecondaryState         INTEGER,
                gmrbAdminState             INTEGER
            }

    gmrbSubType OBJECT-TYPE
        SYNTAX DisplayString
        ACCESS read-only
        STATUS mandatory
        DESCRIPTION
            "Module subtype."
        ::= { gmrbEntry 1 }

    gmrbPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmrbEntry 2 }

    gmrbSecondaryState OBJECT-TYPE
        SYNTAX SecondaryState
        ACCESS read-only
        STATUS mandatory
        DESCRIPTION
            "Secondary state of module."
        ::= { gmrbEntry 3 }

    gmrbAdminState OBJECT-TYPE
        SYNTAX INTEGER { other(1), reset(2) }
        ACCESS read-write
        STATUS mandatory
        DESCRIPTION
            "Administration state of module.  This field is used
             to reset the module.  Reading this field always 
             returns other(1)."
        ::= { gmrbEntry 4 }

    --
    -- The elements in the gmrbFacilities subgroup of the configuration group
    --

    gmrbFacTable   OBJECT-TYPE
            SYNTAX  SEQUENCE OF GmrbFacEntry
            ACCESS  not-accessible
            STATUS  mandatory
            DESCRIPTION
                    "GMRB facility table."
            ::= { gmrb 2 }

    gmrbFacEntry   OBJECT-TYPE
            SYNTAX  GmrbFacEntry
            ACCESS  not-accessible
            STATUS  mandatory
            DESCRIPTION
                    "GMRB facility entry format"
            INDEX   { eqptBay, eqptShelf, eqptSlot, gmrbFacPort }
            ::= { gmrbFacTable 1 }

    GmrbFacEntry   ::=
            SEQUENCE 
            {
                gmrbFacPort            INTEGER,
                gmrbFacDescription     DisplayString,
                gmrbFacInsertionLoss   DisplayString
            }

    gmrbFacPort OBJECT-TYPE
        SYNTAX INTEGER (1..6)
        ACCESS read-only
        STATUS mandatory
        DESCRIPTION
            "Facility index."
        ::= { gmrbFacEntry 1 }

    gmrbFacDescription OBJECT-TYPE
        SYNTAX DisplayString
        ACCESS read-only
        STATUS mandatory
        DESCRIPTION
            "Facility description."
        ::= { gmrbFacEntry 2 }

    gmrbFacInsertionLoss OBJECT-TYPE
        SYNTAX DisplayString
        ACCESS read-only
        STATUS mandatory
        DESCRIPTION
            "Value of the path Insertion Loss."
        ::= { gmrbFacEntry 3 }

    --
    -- The elements in the gmsmx2g5 subgroup of the cardConfiguration group
    --

    gmsmx2g5Table   OBJECT-TYPE
            SYNTAX  SEQUENCE OF Gmsmx2g5Entry
            ACCESS  not-accessible
            STATUS  mandatory
            DESCRIPTION
                    "GMSMX2G5 module table"
            ::= { gmsmx2g5 1 }

    gmsmx2g5Entry   OBJECT-TYPE
            SYNTAX  Gmsmx2g5Entry
            ACCESS  not-accessible
            STATUS  mandatory
            DESCRIPTION
                    "GMSMX2G5 entry format."
            INDEX   { eqptBay, eqptShelf, eqptSlot }
            ::= { gmsmx2g5Table 1 }

    Gmsmx2g5Entry   ::=
            SEQUENCE 
            {
                gmsmx2g5SubType                 DisplayString,
                gmsmx2g5ItuNum                  ItuSelection,
                gmsmx2g5ClockSource             INTEGER,
                gmsmx2g5ClockSelection          INTEGER,
                gmsmx2g5Group1Bitrate           INTEGER,
                gmsmx2g5Group2Bitrate           INTEGER,
                gmsmx2g5Group3Bitrate           INTEGER,
                gmsmx2g5Group4Bitrate           INTEGER,
                gmsmx2g5ActiveTimingSource      INTEGER,
                gmsmx2g5Protocol                INTEGER,
                gmsmx2g5PrimaryState            INTEGER,
                gmsmx2g5SecondaryState          INTEGER,
                gmsmx2g5AdminState              INTEGER,
                gmsmx2g5PmStatus                INTEGER
            }

    gmsmx2g5SubType OBJECT-TYPE
        SYNTAX DisplayString
        ACCESS read-only
        STATUS mandatory
        DESCRIPTION
            "Module sub type."
        ::= { gmsmx2g5Entry 1 }

    gmsmx2g5ItuNum OBJECT-TYPE
        SYNTAX ItuSelection
        ACCESS read-only
        STATUS mandatory
        DESCRIPTION
            "Module supported ITU channel."
        ::= { gmsmx2g5Entry 2 }

    gmsmx2g5ClockSource      OBJECT-TYPE
        SYNTAX INTEGER
        {
            extIntLine(1),
            extLineInt(2),
            lineExtInt(3),
            ext(4),
            line(5)
        }
        ACCESS read-write
        STATUS mandatory
        DESCRIPTION
            "Module clock timing source setting."
        ::= { gmsmx2g5Entry 3 }

    gmsmx2g5ClockSelection      OBJECT-TYPE
        SYNTAX INTEGER { auto(1), forced(2) }
        ACCESS read-write
        STATUS mandatory
        DESCRIPTION
            "Module clock timing selection setting.."
        ::= { gmsmx2g5Entry 4 }

    gmsmx2g5Group1Bitrate      OBJECT-TYPE
        SYNTAX INTEGER { oc3(1), oc12(2) }
        ACCESS read-write
        STATUS mandatory
        DESCRIPTION
            "Group 1 Bitrate Configuration"
        ::= { gmsmx2g5Entry 5 }

    gmsmx2g5Group2Bitrate    OBJECT-TYPE
        SYNTAX INTEGER { oc3(1), oc12(2) }
        ACCESS read-write
        STATUS mandatory
        DESCRIPTION
            "Group 2 Bitrate Configuration"
        ::= { gmsmx2g5Entry 6 }

    gmsmx2g5Group3Bitrate    OBJECT-TYPE
        SYNTAX INTEGER { oc3(1), oc12(2) }
        ACCESS read-write
        STATUS mandatory
        DESCRIPTION
            "Group 3 Bitrate Configuration"
        ::= { gmsmx2g5Entry 7 }

    gmsmx2g5Group4Bitrate    OBJECT-TYPE
        SYNTAX INTEGER { oc3(1), oc12(2) }
        ACCESS read-write
        STATUS mandatory
        DESCRIPTION
            "Group 4 Bitrate Configuration"
        ::= { gmsmx2g5Entry 8 }

    gmsmx2g5ActiveTimingSource    OBJECT-TYPE
        SYNTAX INTEGER
        {
            ext(1),
            line(2),
            int(3),
            unknown(4)
        }
        ACCESS read-only
        STATUS mandatory
        DESCRIPTION
            "Active timing source for the module."
        ::= { gmsmx2g5Entry 9 }


    gmsmx2g5Protocol  OBJECT-TYPE
        SYNTAX INTEGER { sdh(1), sonet(2) }
        ACCESS read-write
        STATUS mandatory
        DESCRIPTION
            "Module PM reporting protocol."
        ::= { gmsmx2g5Entry 10 }

    gmsmx2g5PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmsmx2g5Entry 11 }

    gmsmx2g5SecondaryState OBJECT-TYPE
        SYNTAX SecondaryState
        ACCESS read-only
        STATUS mandatory
        DESCRIPTION
            "Secondary state of module."
        ::= { gmsmx2g5Entry 12 }

    gmsmx2g5AdminState OBJECT-TYPE
        SYNTAX INTEGER { other(1), reset(2) }
        ACCESS read-write
        STATUS mandatory
        DESCRIPTION
            "Administration state of module.  This field is used
             to reset the module.  Reading this field always 
             returns other(1)."
        ::= { gmsmx2g5Entry 13 }

    gmsmx2g5PmStatus OBJECT-TYPE
        SYNTAX PmState
        ACCESS read-write
        STATUS mandatory
        DESCRIPTION
            "Perfornance monitoring status of module."
        ::= { gmsmx2g5Entry 14 }

    --
    -- The elements in the gmsmx2g5Facilities subgroup of the configuration group
    --

    gmsmx2g5FacTable   OBJECT-TYPE
            SYNTAX  SEQUENCE OF Gmsmx2g5FacEntry
            ACCESS  not-accessible
            STATUS  mandatory
            DESCRIPTION
                    "GMSMX2G5 facility table."
            ::= { gmsmx2g5 2 }

    gmsmx2g5FacEntry   OBJECT-TYPE
            SYNTAX  Gmsmx2g5FacEntry
            ACCESS  not-accessible
            STATUS  mandatory
            DESCRIPTION
                    "GMSMX2G5 facility entry format"
            INDEX   { eqptBay, eqptShelf, eqptSlot, gmsmx2g5FacPort }
            ::= { gmsmx2g5FacTable 1 }

    Gmsmx2g5FacEntry   ::=
            SEQUENCE 
            {
                gmsmx2g5FacPort             INTEGER,
                gmsmx2g5FacOpr0             DisplayString,
                gmsmx2g5FacPrimaryState     INTEGER,
                gmsmx2g5FacSecondaryState   INTEGER,
                gmsmx2g5FacLoopbackState    INTEGER
            }

    gmsmx2g5FacPort OBJECT-TYPE
        SYNTAX INTEGER { p1(1),   p2(2),   p3(3),   p4(4),   p5(5),   p6(6),   p7(7),   p8(8),   p9(9),
                         p10(10), p11(11), p12(12), p13(13), p14(14), p15(15), p16(16), line(17) }
        ACCESS read-only
        STATUS mandatory
        DESCRIPTION
            "Port portion of GMSMX2G5 facility address."
        ::= { gmsmx2g5FacEntry 1 }

    gmsmx2g5FacOpr0 OBJECT-TYPE
        SYNTAX DisplayString
        ACCESS read-write
        STATUS mandatory
        DESCRIPTION
            "Nominal value of average optical output power
             of the received signal, or the Optical Power Received
             (OPR) in dBm. The valid range differs based on the
             current port. The valid range for the RC port (line) 
             is -28 to -8.  OPR0 is invalid for all other ports."
        ::= { gmsmx2g5FacEntry 2 }

    gmsmx2g5FacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmsmx2g5FacEntry 3 }

    gmsmx2g5FacSecondaryState OBJECT-TYPE
        SYNTAX SecondaryState
        ACCESS read-only
        STATUS mandatory
        DESCRIPTION
            "Secondary state of port."
        ::= { gmsmx2g5FacEntry 4 }

    gmsmx2g5FacLoopbackState OBJECT-TYPE
        SYNTAX LoopbackState
        ACCESS read-write
        STATUS mandatory
        DESCRIPTION
            "Loopback state of port. Ports must be set OOS before they
             can be placed into loopback."
        ::= { gmsmx2g5FacEntry 5 }

    --
    -- The elements in the gmsmx2g5EqptPmCurrTable subgroup of the cardConfiguration group
    --

    gmsmx2g5EqptPmCurrTable   OBJECT-TYPE
            SYNTAX  SEQUENCE OF Gmsmx2g5EqptPmCurrEntry
            ACCESS  not-accessible
            STATUS  mandatory
            DESCRIPTION
                    "GMSMX2G5 current equipment PM table"
            ::= { gmsmx2g5 3 }

    gmsmx2g5EqptPmCurrEntry   OBJECT-TYPE
            SYNTAX  Gmsmx2g5EqptPmCurrEntry
            ACCESS  not-accessible
            STATUS  mandatory
            DESCRIPTION
                    "GMSMX2G5 current equipment PM entry format."
            INDEX   { eqptBay, eqptShelf, eqptSlot, gmsmx2g5EqptPmCurrType }
            ::= { gmsmx2g5EqptPmCurrTable 1 }

    Gmsmx2g5EqptPmCurrEntry   ::=
            SEQUENCE 
            {
                gmsmx2g5EqptPmCurrType         INTEGER,
                gmsmx2g5EqptPmCurrValue        DisplayString,
                gmsmx2g5EqptPmCurrValidity     INTEGER,
                gmsmx2g5EqptPmCurrLocation     INTEGER,
                gmsmx2g5EqptPmCurrDirection    INTEGER,
                gmsmx2g5EqptPmCurrDate         DisplayString,
                gmsmx2g5EqptPmCurrTime         DisplayString
            }

    gmsmx2g5EqptPmCurrType OBJECT-TYPE
        SYNTAX INTEGER { lbc(2), ltemp(4), opt(5) }
        ACCESS read-only
        STATUS mandatory
        DESCRIPTION
            "Current equipment PM type."
        ::= { gmsmx2g5EqptPmCurrEntry 1 }

    gmsmx2g5EqptPmCurrValue OBJECT-TYPE
        SYNTAX DisplayString
        ACCESS read-only
        STATUS mandatory
        DESCRIPTION
            "Current equipment PM value."
        ::= { gmsmx2g5EqptPmCurrEntry 2 }

    gmsmx2g5EqptPmCurrValidity OBJECT-TYPE
        SYNTAX INTEGER { false(1), true(2) }
        ACCESS read-only
        STATUS mandatory
        DESCRIPTION
            "Current equipment PM validity."
        ::= { gmsmx2g5EqptPmCurrEntry 3 }

    gmsmx2g5EqptPmCurrLocation OBJECT-TYPE
        SYNTAX INTEGER { farEnd(1), nearEnd(2) }
        ACCESS read-only
        STATUS mandatory
        DESCRIPTION
            "Current equipment PM location."
        ::= { gmsmx2g5EqptPmCurrEntry 4 }

    gmsmx2g5EqptPmCurrDirection OBJECT-TYPE
        SYNTAX INTEGER { na(1), rcv(2), trmt(3) }
        ACCESS read-only
        STATUS mandatory
        DESCRIPTION
            "Current equipment PM direction."
        ::= { gmsmx2g5EqptPmCurrEntry 5 }

    gmsmx2g5EqptPmCurrDate OBJECT-TYPE
        SYNTAX DisplayString
        ACCESS read-only
        STATUS mandatory
        DESCRIPTION
            "Current equipment PM date."
        ::= { gmsmx2g5EqptPmCurrEntry 6 }

    gmsmx2g5EqptPmCurrTime OBJECT-TYPE
        SYNTAX DisplayString
        ACCESS read-only
        STATUS mandatory
        DESCRIPTION
            "Current equipment PM time."
        ::= { gmsmx2g5EqptPmCurrEntry 7 }

    --
    -- The elements in the gmsmx2g5EqptPmHistTable subgroup of the cardConfiguration group
    --

    gmsmx2g5EqptPmHistTable   OBJECT-TYPE
            SYNTAX  SEQUENCE OF Gmsmx2g5EqptPmHistEntry
            ACCESS  not-accessible
            STATUS  mandatory
            DESCRIPTION
                    "GMSMX2G5 historical equipment PM table"
            ::= { gmsmx2g5 4 }

    gmsmx2g5EqptPmHistEntry   OBJECT-TYPE
            SYNTAX  Gmsmx2g5EqptPmHistEntry
            ACCESS  not-accessible
            STATUS  mandatory
            DESCRIPTION
                    "GMSMX2G5 historical equipment PM entry format."
            INDEX   { eqptBay, eqptShelf, eqptSlot, gmsmx2g5EqptPmHistInterval, gmsmx2g5EqptPmHistType }
            ::= { gmsmx2g5EqptPmHistTable 1 }

    Gmsmx2g5EqptPmHistEntry   ::=
            SEQUENCE 
            {
                gmsmx2g5EqptPmHistInterval     INTEGER,
                gmsmx2g5EqptPmHistType         INTEGER,
                gmsmx2g5EqptPmHistValue        DisplayString,
                gmsmx2g5EqptPmHistValidity     INTEGER,
                gmsmx2g5EqptPmHistLocation     INTEGER,
                gmsmx2g5EqptPmHistDirection    INTEGER,
                gmsmx2g5EqptPmHistDate         DisplayString,
                gmsmx2g5EqptPmHistTime         DisplayString
            }

    gmsmx2g5EqptPmHistInterval OBJECT-TYPE
        SYNTAX INTEGER (1..32)
        ACCESS read-only
        STATUS mandatory
        DESCRIPTION
            "Historical equipment PM interval."
        ::= { gmsmx2g5EqptPmHistEntry 1 }

    gmsmx2g5EqptPmHistType OBJECT-TYPE
        SYNTAX INTEGER { lbc(2), ltemp(4), opt(5) }
        ACCESS read-only
        STATUS mandatory
        DESCRIPTION
            "Historical equipment PM type."
        ::= { gmsmx2g5EqptPmHistEntry 2 }

    gmsmx2g5EqptPmHistValue OBJECT-TYPE
        SYNTAX DisplayString
        ACCESS read-only
        STATUS mandatory
        DESCRIPTION
            "Historical equipment PM value."
        ::= { gmsmx2g5EqptPmHistEntry 3 }

    gmsmx2g5EqptPmHistValidity OBJECT-TYPE
        SYNTAX INTEGER { false(1), true(2) }
        ACCESS read-only
        STATUS mandatory
        DESCRIPTION
            "Historical equipment PM validity."
        ::= { gmsmx2g5EqptPmHistEntry 4 }

    gmsmx2g5EqptPmHistLocation OBJECT-TYPE
        SYNTAX INTEGER { farEnd(1), nearEnd(2) }
        ACCESS read-only
        STATUS mandatory
        DESCRIPTION
            "Historical equipment PM location."
        ::= { gmsmx2g5EqptPmHistEntry 5 }

    gmsmx2g5EqptPmHistDirection OBJECT-TYPE
        SYNTAX INTEGER { na(1), rcv(2), trmt(3) }
        ACCESS read-only
        STATUS mandatory
        DESCRIPTION
            "Historical equipment PM direction."
        ::= { gmsmx2g5EqptPmHistEntry 6 }

    gmsmx2g5EqptPmHistDate OBJECT-TYPE
        SYNTAX DisplayString
        ACCESS read-only
        STATUS mandatory
        DESCRIPTION
            "Historical equipment PM date."
        ::= { gmsmx2g5EqptPmHistEntry 7 }

    gmsmx2g5EqptPmHistTime OBJECT-TYPE
        SYNTAX DisplayString
        ACCESS read-only
        STATUS mandatory
        DESCRIPTION
            "Historical equipment PM time."
        ::= { gmsmx2g5EqptPmHistEntry 8 }

    --
    -- The elements in the gmsmx2g5FacPmCurrTable subgroup of the cardConfiguration group
    --

    gmsmx2g5FacPmCurrTable   OBJECT-TYPE
            SYNTAX  SEQUENCE OF Gmsmx2g5FacPmCurrEntry
            ACCESS  not-accessible
            STATUS  mandatory
            DESCRIPTION
                    "GMSMX2G5 current facility PM table"
            ::= { gmsmx2g5 5 }

    gmsmx2g5FacPmCurrEntry   OBJECT-TYPE
            SYNTAX  Gmsmx2g5FacPmCurrEntry
            ACCESS  not-accessible
            STATUS  mandatory
            DESCRIPTION
                    "GMSMX2G5 current facility PM entry format."
            INDEX   { eqptBay, eqptShelf, eqptSlot, gmsmx2g5FacPort, gmsmx2g5FacPmCurrType }
            ::= { gmsmx2g5FacPmCurrTable 1 }

    Gmsmx2g5FacPmCurrEntry   ::=
            SEQUENCE 
            {
                gmsmx2g5FacPmCurrType         INTEGER,
                gmsmx2g5FacPmCurrValue        DisplayString,
                gmsmx2g5FacPmCurrOcFacility   INTEGER,
                gmsmx2g5FacPmCurrValidity     INTEGER,
                gmsmx2g5FacPmCurrLocation     INTEGER,
                gmsmx2g5FacPmCurrDirection    INTEGER,
                gmsmx2g5FacPmCurrDate         DisplayString,
                gmsmx2g5FacPmCurrTime         DisplayString
            }

    gmsmx2g5FacPmCurrType OBJECT-TYPE
        SYNTAX INTEGER { cvs(4), ess(5), opr(8), sefss(11), sess(12) }
        ACCESS read-only
        STATUS mandatory
        DESCRIPTION
            "Current facility PM type."
        ::= { gmsmx2g5FacPmCurrEntry 1 }

    gmsmx2g5FacPmCurrValue OBJECT-TYPE
        SYNTAX DisplayString
        ACCESS read-only
        STATUS mandatory
        DESCRIPTION
            "Current facility PM value."
        ::= { gmsmx2g5FacPmCurrEntry 2 }

    gmsmx2g5FacPmCurrOcFacility OBJECT-TYPE
        SYNTAX INTEGER { oc12(1), oc192(2), oc24(3), oc48(4), oc3(5) }
        ACCESS read-only
        STATUS mandatory
        DESCRIPTION
            "Current facility PM OC facility."
        ::= { gmsmx2g5FacPmCurrEntry 3 }

    gmsmx2g5FacPmCurrValidity OBJECT-TYPE
        SYNTAX INTEGER { false(1), true(2) }
        ACCESS read-only
        STATUS mandatory
        DESCRIPTION
            "Current facility PM validity."
        ::= { gmsmx2g5FacPmCurrEntry 4 }

    gmsmx2g5FacPmCurrLocation OBJECT-TYPE
        SYNTAX INTEGER { farEnd(1), nearEnd(2) }
        ACCESS read-only
        STATUS mandatory
        DESCRIPTION
            "Current facility PM location."
        ::= { gmsmx2g5FacPmCurrEntry 5 }

    gmsmx2g5FacPmCurrDirection OBJECT-TYPE
        SYNTAX INTEGER { na(1), rcv(2), trmt(3) }
        ACCESS read-only
        STATUS mandatory
        DESCRIPTION
            "Current facility PM direction."
        ::= { gmsmx2g5FacPmCurrEntry 6 }

    gmsmx2g5FacPmCurrDate OBJECT-TYPE
        SYNTAX DisplayString
        ACCESS read-only
        STATUS mandatory
        DESCRIPTION
            "Current facility PM date."
        ::= { gmsmx2g5FacPmCurrEntry 7 }

    gmsmx2g5FacPmCurrTime OBJECT-TYPE
        SYNTAX DisplayString
        ACCESS read-only
        STATUS mandatory
        DESCRIPTION
            "Current facility PM time."
        ::= { gmsmx2g5FacPmCurrEntry 8 }

    --
    -- The elements in the gmsmx2g5FacPmHistTable subgroup of the cardConfiguration group
    --

    gmsmx2g5FacPmHistTable   OBJECT-TYPE
            SYNTAX  SEQUENCE OF Gmsmx2g5FacPmHistEntry
            ACCESS  not-accessible
            STATUS  mandatory
            DESCRIPTION
                    "GMSMX2G5 historical facility PM table"
            ::= { gmsmx2g5 6 }

    gmsmx2g5FacPmHistEntry   OBJECT-TYPE
            SYNTAX  Gmsmx2g5FacPmHistEntry
            ACCESS  not-accessible
            STATUS  mandatory
            DESCRIPTION
                    "GMSMX2G5 historical facility PM entry format."
            INDEX   { eqptBay, eqptShelf, eqptSlot, gmsmx2g5FacPort, gmsmx2g5FacPmHistInterval, gmsmx2g5FacPmHistType }
            ::= { gmsmx2g5FacPmHistTable 1 }

    Gmsmx2g5FacPmHistEntry   ::=
            SEQUENCE 
            {
                gmsmx2g5FacPmHistInterval     INTEGER,
                gmsmx2g5FacPmHistType         INTEGER,
                gmsmx2g5FacPmHistValue        DisplayString,
                gmsmx2g5FacPmHistOcFacility   INTEGER,
                gmsmx2g5FacPmHistValidity     INTEGER,
                gmsmx2g5FacPmHistLocation     INTEGER,
                gmsmx2g5FacPmHistDirection    INTEGER,
                gmsmx2g5FacPmHistDate         DisplayString,
                gmsmx2g5FacPmHistTime         DisplayString
            }

    gmsmx2g5FacPmHistInterval OBJECT-TYPE
        SYNTAX INTEGER (1..32)
        ACCESS read-only
        STATUS mandatory
        DESCRIPTION
            "Historical facility PM interval."
        ::= { gmsmx2g5FacPmHistEntry 1 }

    gmsmx2g5FacPmHistType OBJECT-TYPE
        SYNTAX INTEGER { cvs(4), ess(5), opr(8), sefss(11), sess(12) }
        ACCESS read-only
        STATUS mandatory
        DESCRIPTION
            "Historical facility PM type."
        ::= { gmsmx2g5FacPmHistEntry 2 }

    gmsmx2g5FacPmHistValue OBJECT-TYPE
        SYNTAX DisplayString
        ACCESS read-only
        STATUS mandatory
        DESCRIPTION
            "Historical facility PM value."
        ::= { gmsmx2g5FacPmHistEntry 3 }

    gmsmx2g5FacPmHistOcFacility OBJECT-TYPE
        SYNTAX INTEGER { oc12(1), oc192(2), oc24(3), oc48(4), oc3(5) }
        ACCESS read-only
        STATUS mandatory
        DESCRIPTION
            "Historical facility PM OC facility."
        ::= { gmsmx2g5FacPmHistEntry 4 }

    gmsmx2g5FacPmHistValidity OBJECT-TYPE
        SYNTAX INTEGER { false(1), true(2) }
        ACCESS read-only
        STATUS mandatory
        DESCRIPTION
            "Historical facility PM validity."
        ::= { gmsmx2g5FacPmHistEntry 5 }

    gmsmx2g5FacPmHistLocation OBJECT-TYPE
        SYNTAX INTEGER { farEnd(1), nearEnd(2) }
        ACCESS read-only
        STATUS mandatory
        DESCRIPTION
            "Historical facility PM location."
        ::= { gmsmx2g5FacPmHistEntry 6 }

    gmsmx2g5FacPmHistDirection OBJECT-TYPE
        SYNTAX INTEGER { na(1), rcv(2), trmt(3) }
        ACCESS read-only
        STATUS mandatory
        DESCRIPTION
            "Historical facility PM direction."
        ::= { gmsmx2g5FacPmHistEntry 7 }

    gmsmx2g5FacPmHistDate OBJECT-TYPE
        SYNTAX DisplayString
        ACCESS read-only
        STATUS mandatory
        DESCRIPTION
            "Historical facility PM date."
        ::= { gmsmx2g5FacPmHistEntry 8 }

    gmsmx2g5FacPmHistTime OBJECT-TYPE
        SYNTAX DisplayString
        ACCESS read-only
        STATUS mandatory
        DESCRIPTION
            "Historical facility PM time."
        ::= { gmsmx2g5FacPmHistEntry 9 }

    --
    -- The elements in the gmtm subgroup of the cardConfiguration group
    --

    gmtmTable   OBJECT-TYPE
            SYNTAX  SEQUENCE OF GmtmEntry
            ACCESS  not-accessible
            STATUS  mandatory
            DESCRIPTION
                    "GMTM module table"
            ::= { gmtm 1 }

    gmtmEntry   OBJECT-TYPE
            SYNTAX  GmtmEntry
            ACCESS  not-accessible
            STATUS  mandatory
            DESCRIPTION
                    "GMTM entry format."
            INDEX   { eqptBay, eqptShelf, eqptSlot }
            ::= { gmtmTable 1 }

    GmtmEntry   ::=
            SEQUENCE 
            {
                gmtmClockMode               INTEGER,
                gmtmDivisor                 INTEGER,
                gmtmFreeRunOutput           INTEGER,
                gmtmInputSignal             INTEGER,
                gmtmSsmChannel              INTEGER,
                gmtmSsmMonitor              INTEGER,
                gmtmInputPQL                INTEGER,
                gmtmOutputPQL               INTEGER,
                gmtmIfType                  INTEGER,
                gmtmPrimaryState            INTEGER,
                gmtmSecondaryState          INTEGER,
                gmtmAdminState              INTEGER
            }

    gmtmClockMode OBJECT-TYPE
        SYNTAX INTEGER { external(1), freerun(2), holdover(3) }
        ACCESS read-write
        STATUS mandatory
        DESCRIPTION
            "TCM clock mode setting."
        ::= { gmtmEntry 1 }

    gmtmDivisor OBJECT-TYPE
        SYNTAX INTEGER
        ACCESS read-write
        STATUS mandatory
        DESCRIPTION
            "User read/write divisor used by the frqamer.
             Divisor used to divide the unframed frequence to 8kHz
             If it's framed input signal, the divisor value is fixed:
             In DS1 case, the default value is 193
             In E1 case, the default value is 256
             If it's unframed signal, the value can be changed
             0 can not be used to set to divisor."
        ::= { gmtmEntry 2 }

    gmtmFreeRunOutput OBJECT-TYPE
        SYNTAX INTEGER  { off(1), on(2) }
        ACCESS read-write
        STATUS mandatory
        DESCRIPTION
            "TCM Output signal control"
        ::= { gmtmEntry 3 }

    gmtmInputSignal OBJECT-TYPE
        SYNTAX INTEGER { e1cas(1), e1ccs(2), ds1esf(3), ds1sf(4), unframed(5) }
        ACCESS read-write
        STATUS mandatory
        DESCRIPTION
            "User read/write input signal type."
        ::= { gmtmEntry 4 }

    gmtmSsmChannel OBJECT-TYPE
        SYNTAX INTEGER { na(1), sa4(2), sa5(3), sa6(4), sa7(5), sa8(6) }
        ACCESS read-write
        STATUS mandatory
        DESCRIPTION
            "SSM Channel being selected. Valid only for e1cas(1) and
             e1ccs(2) gmtmInputSignal."
        ::= { gmtmEntry 5 }

    gmtmSsmMonitor OBJECT-TYPE
        SYNTAX INTEGER  { off(1), on(2) }
        ACCESS read-write
        STATUS mandatory
        DESCRIPTION
            "SSM monitoring state."
        ::= { gmtmEntry 6 }

    gmtmInputPQL OBJECT-TYPE
        SYNTAX INTEGER
        {
            dus(1),
            prc(2),
            prs(3),
            res(4),
            sec(5),
            smc(6),
            st2(7),
            st3(8),
            st3e(9),
            st4(10),
            stu(11),
            tnc(12),
            typev(13),
            typevi(14)
        }
        ACCESS read-write
        STATUS mandatory
        DESCRIPTION
            "Input signal Priority Quality Level. The Input PQL
             can only be used when no SSM being received."
        ::= { gmtmEntry 7 }

    gmtmOutputPQL OBJECT-TYPE
        SYNTAX INTEGER
        {
            dus(1),
            prc(2),
            prs(3),
            res(4),
            sec(5),
            smc(6),
            st2(7),
            st3(8),
            st3e(9),
            st4(10),
            stu(11),
            tnc(12),
            typev(13),
            typevi(14)
        }
        ACCESS read-only
        STATUS mandatory
        DESCRIPTION
            "Current output of Priority Quality Level(PQL) 
             from DS1/E1 chip"
        ::= { gmtmEntry 8 }

    gmtmIfType OBJECT-TYPE
        SYNTAX INTEGER { ds1(1), e1r120(2), e1r75(3), none(4) }
        ACCESS read-only
        STATUS mandatory
        DESCRIPTION
            "Input interface type."
        ::= { gmtmEntry 9 }

    gmtmPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmtmEntry 10 }

    gmtmSecondaryState OBJECT-TYPE
        SYNTAX SecondaryState
        ACCESS read-only
        STATUS mandatory
        DESCRIPTION
            "Secondary state of module."
        ::= { gmtmEntry 11 }

    gmtmAdminState OBJECT-TYPE
        SYNTAX INTEGER { other(1), reset(2) }
        ACCESS read-write
        STATUS mandatory
        DESCRIPTION
            "Administration state of module.  This field is used
             to reset the module.  Reading this field always 
             returns other(1)."
        ::= { gmtmEntry 12 }

    --
    -- The elements in the gnc subgroup of the cardConfiguration group
    --

    gncTable   OBJECT-TYPE
            SYNTAX  SEQUENCE OF GncEntry
            ACCESS  not-accessible
            STATUS  mandatory
            DESCRIPTION
                    "GNC table."
            ::= { gnc 1 }

    gncEntry   OBJECT-TYPE
            SYNTAX  GncEntry
            ACCESS  not-accessible
            STATUS  mandatory
            DESCRIPTION
                    "GNC entry format."
            INDEX   { eqptBay, eqptShelf, eqptSlot }
            ::= { gncTable 1 }

    GncEntry   ::=
            SEQUENCE 
            {
                gncPrimaryState            INTEGER,
                gncSecondaryState          INTEGER,
                gncAdminState              INTEGER,
                gncActiveSoftwareVersion   DisplayString,
                gncStandbySoftwareVersion  DisplayString
            }

    gncPrimaryState OBJECT-TYPE
        SYNTAX PrimaryState 
        ACCESS read-only
        STATUS mandatory
        DESCRIPTION
            "Primary state of module."
        ::= { gncEntry 1 }

    gncSecondaryState OBJECT-TYPE
        SYNTAX SecondaryState
        ACCESS read-only
        STATUS mandatory
        DESCRIPTION
            "Secondary state of module."
        ::= { gncEntry 2 }

    gncAdminState OBJECT-TYPE
        SYNTAX INTEGER { other(1), resetToActiveImage(2), resetToStandbyImage(3) }
        ACCESS read-write
        STATUS mandatory
        DESCRIPTION
            "Administration state of module.  This field is used
             to reset the module.  Reading this field always 
             returns other(1)."
        ::= { gncEntry 3 }

    gncActiveSoftwareVersion OBJECT-TYPE
        SYNTAX DisplayString
        ACCESS read-only
        STATUS mandatory
        DESCRIPTION
            "Active software version.  This is the version of the
             software image currently executing."
        ::= { gncEntry 4 }

    gncStandbySoftwareVersion OBJECT-TYPE 
        SYNTAX DisplayString
        ACCESS read-only
        STATUS mandatory
        DESCRIPTION
            "Standby software version.  This is the version of the
             standby software image stored in memory."
        ::= { gncEntry 5 }

    --
    -- The elements in the mgr subgroup of the cardConfiguration group
    --

    mgrTable   OBJECT-TYPE
        SYNTAX  SEQUENCE OF MgrEntry
        ACCESS  not-accessible
        STATUS  mandatory
        DESCRIPTION
            "MGMT table."
            ::= { mgr 1 }

    mgrEntry   OBJECT-TYPE
        SYNTAX  MgrEntry
        ACCESS  not-accessible
        STATUS  mandatory
        DESCRIPTION
            "MGMT entry format."
        INDEX   { eqptBay, eqptShelf, eqptSlot }
        ::= { mgrTable 1 }

    MgrEntry   ::=
            SEQUENCE 
            {
                mgrPrimaryState            INTEGER,
                mgrSecondaryState          INTEGER,
                mgrAdminState              INTEGER
            }

    mgrPrimaryState OBJECT-TYPE
        SYNTAX PrimaryState 
        ACCESS read-write
        STATUS mandatory
        DESCRIPTION
            "Primary state of module."
        ::= { mgrEntry 1 }

    mgrSecondaryState OBJECT-TYPE
        SYNTAX SecondaryState
        ACCESS read-only
        STATUS mandatory
        DESCRIPTION
            "Secondary state of module."
        ::= { mgrEntry 2 }

    mgrAdminState OBJECT-TYPE
        SYNTAX INTEGER { other(1), reset(2) }
        ACCESS read-write
        STATUS mandatory
        DESCRIPTION
            "Administration state of module.  This field is used
             to reset the module.  Reading this field always 
             returns other(1)."
        ::= { mgrEntry 3 }

    --
    -- The elements in the gmosc subgroup of the cardConfiguration group
    --

    gmoscTable   OBJECT-TYPE
            SYNTAX  SEQUENCE OF GmoscEntry
            ACCESS  not-accessible
            STATUS  mandatory
            DESCRIPTION
                    "OSC module table"
            ::= { gmosc 1 }

    gmoscEntry   OBJECT-TYPE
            SYNTAX  GmoscEntry
            ACCESS  not-accessible
            STATUS  mandatory
            DESCRIPTION
                    "OSC entry format."
            INDEX   { eqptBay, eqptShelf, eqptSlot }
            ::= { gmoscTable 1 }

    GmoscEntry   ::=
            SEQUENCE 
            {
                gmoscDirection               DisplayString,
                gmoscPrimaryState            INTEGER,
                gmoscSecondaryState          INTEGER,
                gmoscAdminState              INTEGER
            }

    gmoscDirection OBJECT-TYPE
        SYNTAX DisplayString (SIZE (0..120))
        ACCESS read-write
        STATUS mandatory
        DESCRIPTION
            "User entered string describing the OSC direction."
        ::= { gmoscEntry 1 }

    gmoscPrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmoscEntry 2 }

    gmoscSecondaryState OBJECT-TYPE
        SYNTAX SecondaryState
        ACCESS read-only
        STATUS mandatory
        DESCRIPTION
            "Secondary state of module."
        ::= { gmoscEntry 3 }

    gmoscAdminState OBJECT-TYPE
        SYNTAX INTEGER { other(1), reset(2) }
        ACCESS read-write
        STATUS mandatory
        DESCRIPTION
            "Administration state of module.  This field is used
             to reset the module.  Reading this field always 
             returns other(1)."
        ::= { gmoscEntry 4 }

    --
    -- The elements in the gmosc100 subgroup of the cardConfiguration group
    --

    gmosc100Table   OBJECT-TYPE
            SYNTAX  SEQUENCE OF Gmosc100Entry
            ACCESS  not-accessible
            STATUS  mandatory
            DESCRIPTION
                    "OSC100 module table"
            ::= { gmosc100 1 }

    gmosc100Entry   OBJECT-TYPE
            SYNTAX  Gmosc100Entry
            ACCESS  not-accessible
            STATUS  mandatory
            DESCRIPTION
                    "OSC100 entry format."
            INDEX   { eqptBay, eqptShelf, eqptSlot }
            ::= { gmosc100Table 1 }

    Gmosc100Entry   ::=
            SEQUENCE 
            {
                gmosc100Direction               DisplayString,
                gmosc100EtherSpeed              INTEGER,
                gmosc100Opr                     DisplayString,
                gmosc100Opr0                    DisplayString,
                gmosc100OprLowTh                DisplayString,
                gmosc100PrimaryState            INTEGER,
                gmosc100SecondaryState          INTEGER,
                gmosc100AdminState              INTEGER,
                gmosc100PmStatus                INTEGER
            }

    gmosc100Direction OBJECT-TYPE
        SYNTAX DisplayString (SIZE (0..120))
        ACCESS read-write
        STATUS mandatory
        DESCRIPTION
            "User entered string describing the OSC direction."
        ::= { gmosc100Entry 1 }

    gmosc100EtherSpeed OBJECT-TYPE
        SYNTAX INTEGER { autonegotiate(1), forced100Mbps(2), forced10Mbps(3), transparent(4) }
        ACCESS read-write
        STATUS mandatory
        DESCRIPTION
            "Ethernet operating modes.
             transparent: In this case link partners at both 
                 interfaces are capable of auto-negotiation.
             autonegotiate: The signal rate detected at the remote
                 interface is advertised during auto-negotiation.   
                 Both half & full duplex are also advertised.  
             forced10Mbps: 10Mbps only mode. Link partners select the duplex mode. 
             forced100Mbps: 100Mbps only mode. Link partners select the duplex mode."
        ::= { gmosc100Entry 2 }

    gmosc100Opr OBJECT-TYPE
        SYNTAX DisplayString
        ACCESS read-write
        STATUS mandatory
        DESCRIPTION
            "Optical Power Received (OPR) in dBm."
        ::= { gmosc100Entry 3 }

    gmosc100Opr0 OBJECT-TYPE
        SYNTAX DisplayString
        ACCESS read-write
        STATUS mandatory
        DESCRIPTION
            "Nominal value of average optical input power
             of the received signal (OPR) in dBm.
             Min: -28.0 dBm   Max: -8.0 dBm."
        ::= { gmosc100Entry 4 }

    gmosc100OprLowTh OBJECT-TYPE
        SYNTAX DisplayString
        ACCESS read-write
        STATUS mandatory
        DESCRIPTION
            "Low threshold for OPR in dB with respect to
             the nominal OPR value.
             Min: -5.0 dB   Max: -1.0 dB."
        ::= { gmosc100Entry 5 }

    gmosc100PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmosc100Entry 6 }

    gmosc100SecondaryState OBJECT-TYPE
        SYNTAX SecondaryState
        ACCESS read-only
        STATUS mandatory
        DESCRIPTION
            "Secondary state of module."
        ::= { gmosc100Entry 7 }

    gmosc100AdminState OBJECT-TYPE
        SYNTAX INTEGER { other(1), reset(2) }
        ACCESS read-write
        STATUS mandatory
        DESCRIPTION
            "Administration state of module.  This field is used
             to reset the module.  Reading this field always 
             returns other(1)."
        ::= { gmosc100Entry 8 }

    gmosc100PmStatus OBJECT-TYPE
        SYNTAX PmState
        ACCESS read-write
        STATUS mandatory
        DESCRIPTION
            "Perfornance monitoring status of module."
        ::= { gmosc100Entry 9 }

    --
    -- The elements in the gmosc100EqptPmCurrTable subgroup of the cardConfiguration group
    --

    gmosc100EqptPmCurrTable   OBJECT-TYPE
            SYNTAX  SEQUENCE OF Gmosc100EqptPmCurrEntry
            ACCESS  not-accessible
            STATUS  mandatory
            DESCRIPTION
                    "OSC100 current equipment PM table"
            ::= { gmosc100 2 }

    gmosc100EqptPmCurrEntry   OBJECT-TYPE
            SYNTAX  Gmosc100EqptPmCurrEntry
            ACCESS  not-accessible
            STATUS  mandatory
            DESCRIPTION
                    "OSC100 current equipment PM entry format."
            INDEX   { eqptBay, eqptShelf, eqptSlot, gmosc100EqptPmCurrType }
            ::= { gmosc100EqptPmCurrTable 1 }

    Gmosc100EqptPmCurrEntry   ::=
            SEQUENCE 
            {
                gmosc100EqptPmCurrType         INTEGER,
                gmosc100EqptPmCurrValue        DisplayString,
                gmosc100EqptPmCurrValidity     INTEGER,
                gmosc100EqptPmCurrLocation     INTEGER,
                gmosc100EqptPmCurrDirection    INTEGER,
                gmosc100EqptPmCurrDate         DisplayString,
                gmosc100EqptPmCurrTime         DisplayString
            }

    gmosc100EqptPmCurrType OBJECT-TYPE
        SYNTAX INTEGER { lbc(2), ltemp(4), opt(5), opr(8) }
        ACCESS read-only
        STATUS mandatory
        DESCRIPTION
            "Current equipment PM type."
        ::= { gmosc100EqptPmCurrEntry 1 }

    gmosc100EqptPmCurrValue OBJECT-TYPE
        SYNTAX DisplayString
        ACCESS read-only
        STATUS mandatory
        DESCRIPTION
            "Current equipment PM value."
        ::= { gmosc100EqptPmCurrEntry 2 }

    gmosc100EqptPmCurrValidity OBJECT-TYPE
        SYNTAX INTEGER { false(1), true(2) }
        ACCESS read-only
        STATUS mandatory
        DESCRIPTION
            "Current equipment PM validity."
        ::= { gmosc100EqptPmCurrEntry 3 }

    gmosc100EqptPmCurrLocation OBJECT-TYPE
        SYNTAX INTEGER { farEnd(1), nearEnd(2) }
        ACCESS read-only
        STATUS mandatory
        DESCRIPTION
            "Current equipment PM location."
        ::= { gmosc100EqptPmCurrEntry 4 }

    gmosc100EqptPmCurrDirection OBJECT-TYPE
        SYNTAX INTEGER { na(1), rcv(2), trmt(3) }
        ACCESS read-only
        STATUS mandatory
        DESCRIPTION
            "Current equipment PM direction."
        ::= { gmosc100EqptPmCurrEntry 5 }

    gmosc100EqptPmCurrDate OBJECT-TYPE
        SYNTAX DisplayString
        ACCESS read-only
        STATUS mandatory
        DESCRIPTION
            "Current equipment PM date."
        ::= { gmosc100EqptPmCurrEntry 6 }

    gmosc100EqptPmCurrTime OBJECT-TYPE
        SYNTAX DisplayString
        ACCESS read-only
        STATUS mandatory
        DESCRIPTION
            "Current equipment PM time."
        ::= { gmosc100EqptPmCurrEntry 7 }

    --
    -- The elements in the gmosc100EqptPmHistTable subgroup of the cardConfiguration group
    --

    gmosc100EqptPmHistTable   OBJECT-TYPE
            SYNTAX  SEQUENCE OF Gmosc100EqptPmHistEntry
            ACCESS  not-accessible
            STATUS  mandatory
            DESCRIPTION
                    "OSC100 historical equipment PM table"
            ::= { gmosc100 3 }

    gmosc100EqptPmHistEntry   OBJECT-TYPE
            SYNTAX  Gmosc100EqptPmHistEntry
            ACCESS  not-accessible
            STATUS  mandatory
            DESCRIPTION
                    "OSC100 historical equipment PM entry format."
            INDEX   { eqptBay, eqptShelf, eqptSlot, gmosc100EqptPmHistInterval, gmosc100EqptPmHistType }
            ::= { gmosc100EqptPmHistTable 1 }

    Gmosc100EqptPmHistEntry   ::=
            SEQUENCE 
            {
                gmosc100EqptPmHistInterval     INTEGER,
                gmosc100EqptPmHistType         INTEGER,
                gmosc100EqptPmHistValue        DisplayString,
                gmosc100EqptPmHistValidity     INTEGER,
                gmosc100EqptPmHistLocation     INTEGER,
                gmosc100EqptPmHistDirection    INTEGER,
                gmosc100EqptPmHistDate         DisplayString,
                gmosc100EqptPmHistTime         DisplayString
            }

    gmosc100EqptPmHistInterval OBJECT-TYPE
        SYNTAX INTEGER (1..32)
        ACCESS read-only
        STATUS mandatory
        DESCRIPTION
            "Historical equipment PM interval."
        ::= { gmosc100EqptPmHistEntry 1 }

    gmosc100EqptPmHistType OBJECT-TYPE
        SYNTAX INTEGER { lbc(2), ltemp(4), opt(5), opr(8) }
        ACCESS read-only
        STATUS mandatory
        DESCRIPTION
            "Historical equipment PM type."
        ::= { gmosc100EqptPmHistEntry 2 }

    gmosc100EqptPmHistValue OBJECT-TYPE
        SYNTAX DisplayString
        ACCESS read-only
        STATUS mandatory
        DESCRIPTION
            "Historical equipment PM value."
        ::= { gmosc100EqptPmHistEntry 3 }

    gmosc100EqptPmHistValidity OBJECT-TYPE
        SYNTAX INTEGER { false(1), true(2) }
        ACCESS read-only
        STATUS mandatory
        DESCRIPTION
            "Historical equipment PM validity."
        ::= { gmosc100EqptPmHistEntry 4 }

    gmosc100EqptPmHistLocation OBJECT-TYPE
        SYNTAX INTEGER { farEnd(1), nearEnd(2) }
        ACCESS read-only
        STATUS mandatory
        DESCRIPTION
            "Historical equipment PM location."
        ::= { gmosc100EqptPmHistEntry 5 }

    gmosc100EqptPmHistDirection OBJECT-TYPE
        SYNTAX INTEGER { na(1), rcv(2), trmt(3) }
        ACCESS read-only
        STATUS mandatory
        DESCRIPTION
            "Historical equipment PM direction."
        ::= { gmosc100EqptPmHistEntry 6 }

    gmosc100EqptPmHistDate OBJECT-TYPE
        SYNTAX DisplayString
        ACCESS read-only
        STATUS mandatory
        DESCRIPTION
            "Historical equipment PM date."
        ::= { gmosc100EqptPmHistEntry 7 }

    gmosc100EqptPmHistTime OBJECT-TYPE
        SYNTAX DisplayString
        ACCESS read-only
        STATUS mandatory
        DESCRIPTION
            "Historical equipment PM time."
        ::= { gmosc100EqptPmHistEntry 8 }

    --
    -- The elements in the scf subgroup of the cardConfiguration group
    --

    scfTable   OBJECT-TYPE
            SYNTAX  SEQUENCE OF ScfEntry
            ACCESS  not-accessible
            STATUS  mandatory
            DESCRIPTION
                    "SCF module table"
            ::= { scf 1 }

    scfEntry   OBJECT-TYPE
            SYNTAX  ScfEntry
            ACCESS  not-accessible
            STATUS  mandatory
            DESCRIPTION
                    "SCF entry format."
            INDEX   { eqptBay, eqptShelf, eqptSlot }
            ::= { scfTable 1 }

    ScfEntry   ::=
            SEQUENCE 
            {
                scfPrimaryState            INTEGER,
                scfSecondaryState          INTEGER
            }

    scfPrimaryState OBJECT-TYPE
        SYNTAX PrimaryState 
        ACCESS read-write
        STATUS mandatory
        DESCRIPTION
            "Primary state of module."
        ::= { scfEntry 1 }

    scfSecondaryState OBJECT-TYPE
        SYNTAX SecondaryState
        ACCESS read-only
        STATUS mandatory
        DESCRIPTION
            "Secondary state of module."
        ::= { scfEntry 2 }

    --
    -- The elements in the gmvga subgroup of the cardConfiguration group
    --

    gmvgaTable   OBJECT-TYPE
            SYNTAX  SEQUENCE OF GmvgaEntry
            ACCESS  not-accessible
            STATUS  mandatory
            DESCRIPTION
                    "GMVGA module table"
            ::= { gmvga 1 }

    gmvgaEntry   OBJECT-TYPE
            SYNTAX  GmvgaEntry
            ACCESS  not-accessible
            STATUS  mandatory
            DESCRIPTION
                    "GMVGA entry format."
            INDEX   { eqptBay, eqptShelf, eqptSlot }
            ::= { gmvgaTable 1 }

    GmvgaEntry   ::=
            SEQUENCE 
            {
                gmvgaSubType                DisplayString,
                gmvgaOprMode                INTEGER,
                gmvgaApr                    INTEGER,
                gmvgaGainTilt               DisplayString,
                gmvgaGain                   DisplayString,
                gmvgaActualGain             DisplayString,
                gmvgaOpr                    DisplayString,
                gmvgaOpt                    DisplayString,
                gmvgaNoise                  DisplayString,
                gmvgaOprLowTh               DisplayString,
                gmvgaPrimaryState           INTEGER,
                gmvgaSecondaryState         INTEGER
            }

    gmvgaSubType OBJECT-TYPE
        SYNTAX DisplayString 
        ACCESS read-only
        STATUS mandatory
        DESCRIPTION
            "Module sub type."
        ::= { gmvgaEntry 1 }

    gmvgaOprMode OBJECT-TYPE
        SYNTAX INTEGER { constantgain(1), disabled(2) } 
        ACCESS read-write
        STATUS mandatory
        DESCRIPTION
            "Operational Mode of Amplifier"
        ::= { gmvgaEntry 2 }

    gmvgaApr OBJECT-TYPE
        SYNTAX INTEGER  { off(1), on(2) }
        ACCESS read-write
        STATUS mandatory
        DESCRIPTION
            "Configure APR functionality of the module.
             If enabled, when excess reflection is measured,
             the module will go to eye-safe - disabled(2) mode,
             and output power will be limited to 10dBm"
        ::= { gmvgaEntry 3 }

    gmvgaGainTilt OBJECT-TYPE
        SYNTAX DisplayString 
        ACCESS read-write
        STATUS mandatory
        DESCRIPTION
            "Tilt Value can be set in dB, limits -2dB to +2dB."
        ::= { gmvgaEntry 4 }

    gmvgaGain OBJECT-TYPE
        SYNTAX DisplayString 
        ACCESS read-write
        STATUS mandatory
        DESCRIPTION
            "Specifies desired gain in dB. Maximum gain, maximum
             output gain, and input power must be taken into account
             when setting Gain. Applicable only in constant-gain mode.
             Valid range depends on module subtype:
             T17   - 10.0 dB to 21.5 dB
             T20-4 - 14.0 dB to 19.5 dB
             T20-9 - 14.0 dB to 19.5 dB"
        ::= { gmvgaEntry 5 }

    gmvgaActualGain OBJECT-TYPE
        SYNTAX DisplayString 
        ACCESS read-only
        STATUS mandatory
        DESCRIPTION
            "Actual Gain, in dB, offered by the amplifier."
        ::= { gmvgaEntry 6 }

    gmvgaOpr OBJECT-TYPE
        SYNTAX DisplayString 
        ACCESS read-only
        STATUS mandatory
        DESCRIPTION
            "Module input power in dBm."
        ::= { gmvgaEntry 7 }

    gmvgaOpt OBJECT-TYPE
        SYNTAX DisplayString 
        ACCESS read-only
        STATUS mandatory
        DESCRIPTION
            "Module output power in dBm."
        ::= { gmvgaEntry 8 }

    gmvgaNoise OBJECT-TYPE
        SYNTAX DisplayString 
        ACCESS read-only
        STATUS mandatory
        DESCRIPTION
            "Input Noise Figure in dB."
        ::= { gmvgaEntry 9 }

    gmvgaOprLowTh OBJECT-TYPE
        SYNTAX DisplayString 
        ACCESS read-write
        STATUS mandatory
        DESCRIPTION
            "The absolute input level threshold. If the input power
             drops below this level, the amplifier will shut down
             (disabled).  valid range is -50 dB to 9 dB."
        ::= { gmvgaEntry 10 }

    gmvgaPrimaryState OBJECT-TYPE
        SYNTAX PrimaryState 
        ACCESS read-write
        STATUS mandatory
        DESCRIPTION
            "Primary state of module."
        ::= { gmvgaEntry 11 }

    gmvgaSecondaryState OBJECT-TYPE
        SYNTAX SecondaryState
        ACCESS read-only
        STATUS mandatory
        DESCRIPTION
            "Secondary state of module."
        ::= { gmvgaEntry 12 }

    --
    -- The elements in the gmvoa40 subgroup of the cardConfiguration group
    --

    gmvoa40Table   OBJECT-TYPE
            SYNTAX  SEQUENCE OF Gmvoa40Entry
            ACCESS  not-accessible
            STATUS  mandatory
            DESCRIPTION
                    "GMVOA40 module table"
            ::= { gmvoa40 1 }

    gmvoa40Entry   OBJECT-TYPE
            SYNTAX  Gmvoa40Entry
            ACCESS  not-accessible
            STATUS  mandatory
            DESCRIPTION
                    "GMVOA40 entry format."
            INDEX   { eqptBay, eqptShelf, eqptSlot }
            ::= { gmvoa40Table 1 }

    Gmvoa40Entry   ::=
            SEQUENCE 
            {
                gmvoa40PrimaryState           INTEGER,
                gmvoa40SecondaryState         INTEGER,
                gmvoa40AdminState             INTEGER
            }

    gmvoa40PrimaryState OBJECT-TYPE
        SYNTAX PrimaryState 
        ACCESS read-write
        STATUS mandatory
        DESCRIPTION
            "Primary state of module."
        ::= { gmvoa40Entry 1 }

    gmvoa40SecondaryState OBJECT-TYPE
        SYNTAX SecondaryState
        ACCESS read-only
        STATUS mandatory
        DESCRIPTION
            "Secondary state of module."
        ::= { gmvoa40Entry 2 }

    gmvoa40AdminState OBJECT-TYPE
        SYNTAX INTEGER { other(1), reset(2) }
        ACCESS read-write
        STATUS mandatory
        DESCRIPTION
            "Administration state of module.  This field is used
             to reset the module.  Reading this field always 
             returns other(1)."
        ::= { gmvoa40Entry 3 }

    --
    -- The elements in the gmvoa40Facilities subgroup of the configuration group
    --

    gmvoa40FacTable   OBJECT-TYPE
            SYNTAX  SEQUENCE OF Gmvoa40FacEntry
            ACCESS  not-accessible
            STATUS  mandatory
            DESCRIPTION
                    "GMVOA40 facility table."
            ::= { gmvoa40 2 }

    gmvoa40FacEntry   OBJECT-TYPE
            SYNTAX  Gmvoa40FacEntry
            ACCESS  not-accessible
            STATUS  mandatory
            DESCRIPTION
                    "GMVOA40 facility entry format"
            INDEX   { eqptBay, eqptShelf, eqptSlot, gmvoa40FacPort }
            ::= { gmvoa40FacTable 1 }

    Gmvoa40FacEntry   ::=
            SEQUENCE 
            {
                gmvoa40FacPort             INTEGER,
                gmvoa40Label               DisplayString,
                gmvoa40OperState           INTEGER,
                gmvoa40EnableTca           INTEGER,
                gmvoa40CfgOpr              DisplayString,
                gmvoa40CfgOffset           DisplayString,
                gmvoa40SigDetectThres      DisplayString,
                gmvoa40MaxSignalThres      DisplayString,
                gmvoa40MinSignalThres      DisplayString,
                gmvoa40Opt                 DisplayString,
                gmvoa40Opr                 DisplayString,
                gmvoa40FacPrimaryState     INTEGER,
                gmvoa40FacSecondaryState   INTEGER
            }

    gmvoa40FacPort OBJECT-TYPE
        SYNTAX INTEGER (1..40)
        ACCESS read-only
        STATUS mandatory
        DESCRIPTION
            "Port portion of GMVOA40 facility address."
        ::= { gmvoa40FacEntry 1 }

    gmvoa40Label OBJECT-TYPE
        SYNTAX DisplayString
        ACCESS read-write
        STATUS mandatory
        DESCRIPTION
            "Per port label."
        ::= { gmvoa40FacEntry 2 }

    gmvoa40OperState OBJECT-TYPE
        SYNTAX INTEGER { off(1), on(2) }
        ACCESS read-write
        STATUS mandatory
        DESCRIPTION
            "The current operational state of the port."
        ::= { gmvoa40FacEntry 3 }

    gmvoa40EnableTca OBJECT-TYPE
        SYNTAX INTEGER { off(1), on(2) }
        ACCESS read-write
        STATUS mandatory
        DESCRIPTION
            "Controls the generation of Threshold Crossing Alarms."
        ::= { gmvoa40FacEntry 4 }

    gmvoa40CfgOpr OBJECT-TYPE
        SYNTAX DisplayString
        ACCESS read-write
        STATUS mandatory
        DESCRIPTION
            "Target output power for the port.  Valid range is
             -40.0 dBm to 10.0 dBm."
        ::= { gmvoa40FacEntry 5 }

    gmvoa40CfgOffset OBJECT-TYPE
        SYNTAX DisplayString
        ACCESS read-write
        STATUS mandatory
        DESCRIPTION
            "Offset is Pwr measured at the GMVOA-40 output port
             minus Pwr at the down stream Reference Point. If
             there is amplification, the offset will be negative.
             Valid range is -40.0 dB to 99.9 dB."
        ::= { gmvoa40FacEntry 6 }

    gmvoa40SigDetectThres OBJECT-TYPE
        SYNTAX DisplayString
        ACCESS read-write
        STATUS mandatory
        DESCRIPTION
            "Minimum power level in dBm for which a channel
             is considered to be present.  Valid range is
             -50.0 dBm to 10.0 dBm."
        ::= { gmvoa40FacEntry 7 }

    gmvoa40MaxSignalThres OBJECT-TYPE
        SYNTAX DisplayString
        ACCESS read-write
        STATUS mandatory
        DESCRIPTION
            "Output pwr exceeding this value triggers an Alarm.
            Valid range is 1.0 dBm to 10.0 dBm."
        ::= { gmvoa40FacEntry 8 }

    gmvoa40MinSignalThres OBJECT-TYPE
        SYNTAX DisplayString
        ACCESS read-write
        STATUS mandatory
        DESCRIPTION
            "Output pwr drops below this value triggers an Alarm.
             Valid range is -10.0 dBm to -1.0 dBm."
        ::= { gmvoa40FacEntry 9 }

    gmvoa40Opt OBJECT-TYPE
        SYNTAX DisplayString
        ACCESS read-only
        STATUS mandatory
        DESCRIPTION
            "Current optical power at the port output."
        ::= { gmvoa40FacEntry 10 }

    gmvoa40Opr OBJECT-TYPE
        SYNTAX DisplayString
        ACCESS read-only
        STATUS mandatory
        DESCRIPTION
            "Estimated current optical power at the input port."
        ::= { gmvoa40FacEntry 11 }

    gmvoa40FacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmvoa40FacEntry 12 }

    gmvoa40FacSecondaryState OBJECT-TYPE
        SYNTAX SecondaryState
        ACCESS read-only
        STATUS mandatory
        DESCRIPTION
            "Secondary state of port."
        ::= { gmvoa40FacEntry 13 }

    --
    -- The elements in the gmroadm subgroup of the cardConfiguration group
    --

    gmroadmTable   OBJECT-TYPE
            SYNTAX  SEQUENCE OF GmroadmEntry
            ACCESS  not-accessible
            STATUS  mandatory
            DESCRIPTION
                    "GMROADM module table"
            ::= { gmroadm 1 }

    gmroadmEntry   OBJECT-TYPE
            SYNTAX  GmroadmEntry
            ACCESS  not-accessible
            STATUS  mandatory
            DESCRIPTION
                    "GMROADM entry format."
            INDEX   { eqptBay, eqptShelf, eqptSlot }
            ::= { gmroadmTable 1 }

    GmroadmEntry   ::=
            SEQUENCE 
            {
                gmroadmSubType                 DisplayString,
                gmroadmRoadmMode               INTEGER,
                gmroadmRoadmStatus             INTEGER,
                gmroadmChanFailThres           DisplayString,
                gmroadmChanDegradeThres        DisplayString,
                gmroadmChanHyst                DisplayString,
                gmroadmExpRxFailThres          DisplayString,
                gmroadmExpRxDegradeThres       DisplayString,
                gmroadmExpRxHyst               DisplayString,
                gmroadmExpRxPower              DisplayString,
                gmroadmExpTxPower              DisplayString,
                gmroadmLineRxFailThres         DisplayString,
                gmroadmLineRxDegradeThres      DisplayString,
                gmroadmLineRxHyst              DisplayString,
                gmroadmLineRxPower             DisplayString,
                gmroadmLineTxFailThres         DisplayString,
                gmroadmLineTxDegradeThres      DisplayString,
                gmroadmLineTxHyst              DisplayString,
                gmroadmLineTxPower             DisplayString,
                gmroadmPrimaryState            INTEGER,
                gmroadmSecondaryState          INTEGER,
                gmroadmAdminState              INTEGER
            }

    gmroadmSubType OBJECT-TYPE
        SYNTAX DisplayString
        ACCESS read-only
        STATUS mandatory
        DESCRIPTION
            "Module sub type."
        ::= { gmroadmEntry 1 }

    gmroadmRoadmMode OBJECT-TYPE
        SYNTAX INTEGER
        {
            attenuation(1),
            power(2)
        }
        ACCESS read-write
        STATUS mandatory
        DESCRIPTION
            "ROADM operational mode."
        ::= { gmroadmEntry 2 }

    gmroadmRoadmStatus      OBJECT-TYPE
        SYNTAX INTEGER
        {
            normal(1),
            warmup(2)
        }
        ACCESS read-only
        STATUS mandatory
        DESCRIPTION
            "Current ROADM status"
        ::= { gmroadmEntry 3 }

    gmroadmChanFailThres      OBJECT-TYPE
        SYNTAX DisplayString
        ACCESS read-write
        STATUS mandatory
        DESCRIPTION
            "LOS per channel threshold power at Line Out in dBm, 
             alowed values -35 to +4 dBm."
        ::= { gmroadmEntry 4 }

    gmroadmChanDegradeThres      OBJECT-TYPE
        SYNTAX DisplayString
        ACCESS read-write
        STATUS mandatory
        DESCRIPTION
            "Degrade per channel threshold power at Line Out in dBm, 
             alowed values -35 to +4 dBm."
        ::= { gmroadmEntry 5 }

    gmroadmChanHyst      OBJECT-TYPE
        SYNTAX DisplayString
        ACCESS read-write
        STATUS mandatory
        DESCRIPTION
            "LOS per channel hysterysis in dB, alowed values -3 to +3 dBm."
        ::= { gmroadmEntry 6 }

    gmroadmExpRxFailThres      OBJECT-TYPE
        SYNTAX DisplayString
        ACCESS read-write
        STATUS mandatory
        DESCRIPTION
            "LOS of Express Input threshold in dBm, 
             alowed values -35 to +4 dBm."
        ::= { gmroadmEntry 7 }

    gmroadmExpRxDegradeThres      OBJECT-TYPE
        SYNTAX DisplayString
        ACCESS read-write
        STATUS mandatory
        DESCRIPTION
            "Degrade of Express Input threshold in dBm, 
             alowed values -35 to +4 dBm."
        ::= { gmroadmEntry 8 }

    gmroadmExpRxHyst      OBJECT-TYPE
        SYNTAX DisplayString
        ACCESS read-write
        STATUS mandatory
        DESCRIPTION
            "LOS of Express Input hysterysis in dB, alowed values -3 to +3 dBm."
        ::= { gmroadmEntry 9 }

    gmroadmExpRxPower      OBJECT-TYPE
        SYNTAX DisplayString
        ACCESS read-only
        STATUS mandatory
        DESCRIPTION
            "Express Input Power Reading in dBm."
        ::= { gmroadmEntry 10 }

    gmroadmExpTxPower      OBJECT-TYPE
        SYNTAX DisplayString
        ACCESS read-only
        STATUS mandatory
        DESCRIPTION
            "Exprees Output Power reading in dBm."
        ::= { gmroadmEntry 11 }

    gmroadmLineRxFailThres      OBJECT-TYPE
        SYNTAX DisplayString
        ACCESS read-write
        STATUS mandatory
        DESCRIPTION
            "LOS of Line Input threshold power in dB, 
             alowed values -35 to +4 dBm."
        ::= { gmroadmEntry 12 }

    gmroadmLineRxDegradeThres      OBJECT-TYPE
        SYNTAX DisplayString
        ACCESS read-write
        STATUS mandatory
        DESCRIPTION
            "Degrade of Line Input threshold power in dB,
             alowed values -35 to +4 dBm."
        ::= { gmroadmEntry 13 }

    gmroadmLineRxHyst      OBJECT-TYPE
        SYNTAX DisplayString
        ACCESS read-write
        STATUS mandatory
        DESCRIPTION
            "LOS of Line Input hysterysis in dB,
             alowed values -3 to +3 dBm."
        ::= { gmroadmEntry 14 }

    gmroadmLineRxPower      OBJECT-TYPE
        SYNTAX DisplayString
        ACCESS read-only
        STATUS mandatory
        DESCRIPTION
            "Line Input Power reading in dBm."
        ::= { gmroadmEntry 15 }

    gmroadmLineTxFailThres      OBJECT-TYPE
        SYNTAX DisplayString
        ACCESS read-write
        STATUS mandatory
        DESCRIPTION
            "LOS of Line Output threshold in dB,
             alowed values -35 to +4 dBm."
        ::= { gmroadmEntry 16 }

    gmroadmLineTxDegradeThres      OBJECT-TYPE
        SYNTAX DisplayString
        ACCESS read-write
        STATUS mandatory
        DESCRIPTION
            "Degrade of Line Output threshold in dB,
             alowed values -35 to +4 dBm."
        ::= { gmroadmEntry 17 }

    gmroadmLineTxHyst      OBJECT-TYPE
        SYNTAX DisplayString
        ACCESS read-write
        STATUS mandatory
        DESCRIPTION
            "LOS of Line Output hysterysis in dB,
             alowed values -3 to +3 dBm."
        ::= { gmroadmEntry 18 }

    gmroadmLineTxPower      OBJECT-TYPE
        SYNTAX DisplayString
        ACCESS read-only
        STATUS mandatory
        DESCRIPTION
            "Line Output Power reading in dBm."
        ::= { gmroadmEntry 19 }

    gmroadmPrimaryState OBJECT-TYPE
        SYNTAX PrimaryState 
        ACCESS read-write
        STATUS mandatory
        DESCRIPTION
            "Primary state of module."
        ::= { gmroadmEntry 20 }

    gmroadmSecondaryState OBJECT-TYPE
        SYNTAX SecondaryState
        ACCESS read-only
        STATUS mandatory
        DESCRIPTION
            "Secondary state of module."
        ::= { gmroadmEntry 21 }

    gmroadmAdminState OBJECT-TYPE
        SYNTAX INTEGER { other(1), reset(2) }
        ACCESS read-write
        STATUS mandatory
        DESCRIPTION
            "Administration state of module.  This field is used
             to reset the module.  Reading this field always 
             returns other(1)."
        ::= { gmroadmEntry 22 }

    --
    -- The elements in the gmroadmFacilities subgroup of the configuration group
    --

    gmroadmFacTable   OBJECT-TYPE
            SYNTAX  SEQUENCE OF GmroadmFacEntry
            ACCESS  not-accessible
            STATUS  mandatory
            DESCRIPTION
                    "GMROADM facility table."
            ::= { gmroadm 2 }

    gmroadmFacEntry   OBJECT-TYPE
            SYNTAX  GmroadmFacEntry
            ACCESS  not-accessible
            STATUS  mandatory
            DESCRIPTION
                    "GMROADM facility entry format"
            INDEX   { eqptBay, eqptShelf, eqptSlot, gmroadmFacPort }
            ::= { gmroadmFacTable 1 }

    GmroadmFacEntry   ::=
            SEQUENCE 
            {
                gmroadmFacPort             INTEGER,
                gmroadmItuNum              ItuSelection2,
                gmroadmSwitchState         INTEGER,
                gmroadmCfgAtten            DisplayString,
                gmroadmActualAtten         DisplayString,
                gmroadmCfgPower            DisplayString,
                gmroadmActualPower         DisplayString,
                gmroadmError               DisplayString,
                gmroadmFacPrimaryState     INTEGER,
                gmroadmFacSecondaryState   INTEGER
            }

    gmroadmFacPort OBJECT-TYPE
        SYNTAX INTEGER (1..40)
        ACCESS read-only
        STATUS mandatory
        DESCRIPTION
            "Port portion of GMROADM facility address."
        ::= { gmroadmFacEntry 1 }

    gmroadmItuNum OBJECT-TYPE
        SYNTAX ItuSelection2
        ACCESS read-only
        STATUS mandatory
        DESCRIPTION
            "Channel ITU number, 20 to 59 for standard ITU channels, or 
             19.5 to 58.5 for 50GHz shifted Roadm."
        ::= { gmroadmFacEntry 2 }

    gmroadmSwitchState OBJECT-TYPE
        SYNTAX INTEGER
        {
            add(1),
            off(2),
            propactive(3),
            propall(4),
            propvalue(5),
            thru(6)
        }
        ACCESS read-write
        STATUS mandatory
        DESCRIPTION
            "Switch State: Thru, Add or Off, allow also function of propagate switch position
             to all channels (it will activate channels that are currently 'OFF', or to 
             active channels (only affects active channels), or propagate a channel 
             value to active channels only."
        ::= { gmroadmFacEntry 3 }

    gmroadmCfgAtten OBJECT-TYPE
        SYNTAX DisplayString
        ACCESS read-write
        STATUS mandatory
        DESCRIPTION
            "Attenuator setting per channel, can be set only available in Attenuation mode.
             allowed values: 0 to 20dB."
        ::= { gmroadmFacEntry 4 }

    gmroadmActualAtten OBJECT-TYPE
        SYNTAX DisplayString
        ACCESS read-only
        STATUS mandatory
        DESCRIPTION
            "Attenuator actual value per channel, only valid in power mode 0 - 20 dB."
        ::= { gmroadmFacEntry 5 }

    gmroadmCfgPower OBJECT-TYPE
        SYNTAX DisplayString
        ACCESS read-write
        STATUS mandatory
        DESCRIPTION
            "LineOut output power set value per channel (only available in power mode), 
             allowed values -35.0 to +4.0dBm."
        ::= { gmroadmFacEntry 6 }

    gmroadmActualPower OBJECT-TYPE
        SYNTAX DisplayString
        ACCESS read-only
        STATUS mandatory
        DESCRIPTION
            "LineOut output power actual value per channel in dBm."
        ::= { gmroadmFacEntry 7 }

    gmroadmError OBJECT-TYPE
        SYNTAX DisplayString
        ACCESS read-only
        STATUS mandatory
        DESCRIPTION
            "LineOut output power error (set - actual) per channel in dBm."
        ::= { gmroadmFacEntry 8 }


    gmroadmFacPrimaryState OBJECT-TYPE
        SYNTAX PrimaryState 
        ACCESS read-write
        STATUS mandatory
        DESCRIPTION
            "Primary state of port.  All port primary states must
             be OOS to set the module primary state OOS.  The module
             primary state must be IS in order to set port primary
             states to IS."
        ::= { gmroadmFacEntry 9 }

    gmroadmFacSecondaryState OBJECT-TYPE
        SYNTAX SecondaryState
        ACCESS read-only
        STATUS mandatory
        DESCRIPTION
            "Secondary state of port."
        ::= { gmroadmFacEntry 10 }

    --
    -- The elements in the gmei80 subgroup of the cardConfiguration group
    --

    gmei80Table   OBJECT-TYPE
            SYNTAX  SEQUENCE OF Gmei80Entry
            ACCESS  not-accessible
            STATUS  mandatory
            DESCRIPTION
                    "GMEI80 module table"
            ::= { gmei80 1 }

    gmei80Entry   OBJECT-TYPE
            SYNTAX  Gmei80Entry
            ACCESS  not-accessible
            STATUS  mandatory
            DESCRIPTION
                    "GMEI80 entry format."
            INDEX   { eqptBay, eqptShelf, eqptSlot }
            ::= { gmei80Table 1 }

    Gmei80Entry   ::=
            SEQUENCE 
            {
                gmei80PrimaryState           INTEGER,
                gmei80SecondaryState         INTEGER,
                gmei80AdminState             INTEGER
            }

    gmei80PrimaryState OBJECT-TYPE
        SYNTAX PrimaryState 
        ACCESS read-write
        STATUS mandatory
        DESCRIPTION
            "Primary state of module. All port primary states must
             be OOS to set the module primary state OOS.  The module
             primary state must be IS in order to set port primary
             states to IS."
        ::= { gmei80Entry 1 }

    gmei80SecondaryState OBJECT-TYPE
        SYNTAX SecondaryState
        ACCESS read-only
        STATUS mandatory
        DESCRIPTION
            "Secondary state of module."
        ::= { gmei80Entry 2 }

    gmei80AdminState OBJECT-TYPE
        SYNTAX INTEGER { other(1), reset(2) }
        ACCESS read-write
        STATUS mandatory
        DESCRIPTION
            "Administration state of module.  This field is used
             to reset the module.  Reading this field always 
             returns other(1)."
        ::= { gmei80Entry 3 }

    --
    -- The elements in the gmei80Facilities subgroup of the configuration group
    --

    gmei80FacTable   OBJECT-TYPE
            SYNTAX  SEQUENCE OF Gmei80FacEntry
            ACCESS  not-accessible
            STATUS  mandatory
            DESCRIPTION
                    "GMEI80 facility table."
            ::= { gmei80 2 }

    gmei80FacEntry   OBJECT-TYPE
            SYNTAX  Gmei80FacEntry
            ACCESS  not-accessible
            STATUS  mandatory
            DESCRIPTION
                    "GMEI80 facility entry format"
            INDEX   { eqptBay, eqptShelf, eqptSlot, gmei80FacPort }
            ::= { gmei80FacTable 1 }

    Gmei80FacEntry   ::=
            SEQUENCE 
            {
                gmei80FacPort            INTEGER,
                gmei80FacDescription     DisplayString,
                gmei80FacInsertionLoss   DisplayString
            }

    gmei80FacPort OBJECT-TYPE
        SYNTAX INTEGER (1..2)
        ACCESS read-only
        STATUS mandatory
        DESCRIPTION
            "Facility index."
        ::= { gmei80FacEntry 1 }

    gmei80FacDescription OBJECT-TYPE
        SYNTAX DisplayString
        ACCESS read-only
        STATUS mandatory
        DESCRIPTION
            "Facility description."
        ::= { gmei80FacEntry 2 }

    gmei80FacInsertionLoss OBJECT-TYPE
        SYNTAX DisplayString
        ACCESS read-only
        STATUS mandatory
        DESCRIPTION
            "Value of the path Insertion Loss."
        ::= { gmei80FacEntry 3 }

    --
    -- The elements in the users subgroup of the configuration group
    --

    userTable   OBJECT-TYPE
            SYNTAX  SEQUENCE OF UserEntry
            ACCESS  not-accessible
            STATUS  mandatory
            DESCRIPTION
                    ""
            ::= { users 1 }

    userEntry   OBJECT-TYPE
            SYNTAX  UserEntry
            ACCESS  not-accessible
            STATUS  mandatory
            DESCRIPTION
                    ""
            INDEX   { userId }
            ::= { userTable 1 }

    UserEntry   ::=
            SEQUENCE 
            {
                userId                      INTEGER,
                userLoginId                 DisplayString,
                userPassword                DisplayString,
                userSecLevel                INTEGER,
                userIdleTimeoutEnabled      INTEGER,
                userIdleTimeout             INTEGER,
                userPwdAging                INTEGER,
                userStatus                  INTEGER
            }

    userId    OBJECT-TYPE
        SYNTAX INTEGER
        ACCESS read-only
        STATUS mandatory
        DESCRIPTION
            "User Id."
        ::= { userEntry 1 }

    userLoginId    OBJECT-TYPE
        SYNTAX DisplayString
        ACCESS read-only
        STATUS mandatory
        DESCRIPTION
            "User login Id."
        ::= { userEntry 2 }

    userPassword    OBJECT-TYPE
        SYNTAX DisplayString
        ACCESS read-only
        STATUS mandatory
        DESCRIPTION
            "User password."
        ::= { userEntry 3 }

    userSecLevel    OBJECT-TYPE
        SYNTAX INTEGER  { read-only(1), read-write(2), admin(3) }
        ACCESS read-only
        STATUS mandatory
        DESCRIPTION
            "User security level."
        ::= { userEntry 4 }

    userIdleTimeoutEnabled    OBJECT-TYPE
        SYNTAX INTEGER  { yes(1), no(2) }
        ACCESS read-only
        STATUS mandatory
        DESCRIPTION
            "Enables/disabled user session idle timer."
        ::= { userEntry 5 }

    userIdleTimeout    OBJECT-TYPE
        SYNTAX INTEGER  (5..30)
        ACCESS read-only
        STATUS mandatory
        DESCRIPTION
            "User session idle timeout."
        ::= { userEntry 6 }

    userPwdAging    OBJECT-TYPE
        SYNTAX INTEGER  { enabled(1), disabled(2) }
        ACCESS read-only
        STATUS mandatory
        DESCRIPTION
            "Enables/disables password aging.  If password aging is
             enabled the user account will expire and be disabled
             after 45 days."
        ::= { userEntry 7 }

    userStatus    OBJECT-TYPE
        SYNTAX INTEGER  { active(1), inactive(2) }
        ACCESS read-only
        STATUS mandatory
        DESCRIPTION
            "Show whether the user is logged in active) or not (inactive)."
        ::= { userEntry 8 }

    --
    -- The elements in the events subgroup of the configuration group
    --

    eventDescription    OBJECT-TYPE
        SYNTAX DisplayString
        ACCESS read-only
        STATUS mandatory
        DESCRIPTION
            "Used in traps to include a string description of the trap. 
             A GET on this element will not return a value."
        ::= { events 1 }

    eventSeverity    OBJECT-TYPE
        SYNTAX INTEGER { critical(1), major(2), minor(3), warning(4), normal(5) }
        ACCESS read-only
        STATUS mandatory
        DESCRIPTION
            "Used in traps to include the trap severity. 
             A GET on this element will not return a value."
        ::= { events 2 }

    eventSpecificInfo    OBJECT-TYPE
        SYNTAX DisplayString
        ACCESS read-only
        STATUS mandatory
        DESCRIPTION
            "Used in traps to include additional trap specific information. 
             A GET on this element will not return a value."
        ::= { events 3 }

    --
    -- Enterprise traps supported by the GNC MIB.
    --

    otm32TL1AutonomousTrap  TRAP-TYPE
            ENTERPRISE  otm32
            VARIABLES { eventDescription, eventSeverity, eventSpecificInfo }
            DESCRIPTION
                "TL1 autonomous output generated by the GNC. The trap is
                 only generated when TL1 trap output is enabled through
                 the TL1 interface.  eventSpecificInfo contains the TL1
                 output."
            ::= 1

    otm32SysNameChangedTrap  TRAP-TYPE
            ENTERPRISE  otm32
            VARIABLES { eventDescription, eventSeverity }
            DESCRIPTION
                "System name has modified."
            ::= 2

    otm32SysDateChangedTrap  TRAP-TYPE
            ENTERPRISE  otm32
            VARIABLES { eventDescription, eventSeverity }
            DESCRIPTION
                "System date was modified."
            ::= 3

    otm32SysTimeChangedTrap  TRAP-TYPE
            ENTERPRISE  otm32
            VARIABLES { eventDescription, eventSeverity }
            DESCRIPTION
                "System time was modified."
            ::= 4

    otm32IpAddressChangedTrap  TRAP-TYPE
            ENTERPRISE  otm32
            VARIABLES { eventDescription, eventSeverity, gncSysIpAddress }
            DESCRIPTION
                "GNC IP address was change.  gncSysIpAddress contains the
                 GNC's previous IP address."
            ::= 5

    otm32NetmaskChangedTrap  TRAP-TYPE
            ENTERPRISE  otm32
            VARIABLES { eventDescription, eventSeverity }
            DESCRIPTION
                "GNC netmask was modified."
            ::= 6

    otm32DefaultGateChangedTrap  TRAP-TYPE
            ENTERPRISE  otm32
            VARIABLES { eventDescription, eventSeverity }
            DESCRIPTION
                "GNC default gateway was modified."
            ::= 7

    otm32VlanChangedTrap  TRAP-TYPE
            ENTERPRISE  otm32
            VARIABLES { eventDescription, eventSeverity }
            DESCRIPTION
                "GNC VLAn was modified."
            ::= 8

    otm32NtpServerChangedTrap  TRAP-TYPE
            ENTERPRISE  otm32
            VARIABLES { eventDescription, eventSeverity }
            DESCRIPTION
                "NTP server IP address was modified."
            ::= 9

    otm32NtpEnabledTrap  TRAP-TYPE
            ENTERPRISE  otm32
            VARIABLES { eventDescription, eventSeverity }
            DESCRIPTION
                "NTP was enabled."
            ::= 10

    otm32NtpDisabledTrap  TRAP-TYPE
            ENTERPRISE  otm32
            VARIABLES { eventDescription, eventSeverity }
            DESCRIPTION
                "NTP was disabled."
            ::= 11

    otm32NtpIntervalChangedTrap  TRAP-TYPE
            ENTERPRISE  otm32
            VARIABLES { eventDescription, eventSeverity }
            DESCRIPTION
                "NTP request interval was modified."
            ::= 12

    otm32NtpForceSetChangedTrap  TRAP-TYPE
            ENTERPRISE  otm32
            VARIABLES { eventDescription, eventSeverity }
            DESCRIPTION
                "NTP force set parameter was modified."
            ::= 13

    otm32SpanningTreePriorityChangedTrap  TRAP-TYPE
            ENTERPRISE  otm32
            VARIABLES { eventDescription, eventSeverity }
            DESCRIPTION
                "Spanning tree priority was modified."
            ::= 14

    otm32SpanningTreeHellotimeChangedTrap  TRAP-TYPE
            ENTERPRISE  otm32
            VARIABLES { eventDescription, eventSeverity }
            DESCRIPTION
                "Spanning tree hello time was modified."
            ::= 15

    otm32TraphostAddedTrap  TRAP-TYPE
            ENTERPRISE  otm32
            VARIABLES { eventDescription, eventSeverity, gncHostIndex, gncHostAddress }
            DESCRIPTION
                "SNMP trap host was added. gncHostIndex contains the 
                 index of the host added. gncHostAddress contains the
                 host address added."
            ::= 16

    otm32traphostDeletedTrap  TRAP-TYPE
            ENTERPRISE  otm32
            VARIABLES { eventDescription, eventSeverity, gncHostIndex, gncHostAddress }
            DESCRIPTION
                "SNMP trap host was deleted. gncHostIndex contains the 
                 index of the host deleted. gncHostAddress contains the
                 host address deleted."
            ::= 17

    otm32TraphostPortChangedTrap  TRAP-TYPE
            ENTERPRISE  otm32
            VARIABLES { eventDescription, eventSeverity, gncHostIndex }
            DESCRIPTION
                "Trap host port was modified. gncHostIndex contains the
                 index of the host modifed."
            ::= 18

    otm32TraphostCommunityChangedTrap  TRAP-TYPE
            ENTERPRISE  otm32
            VARIABLES { eventDescription, eventSeverity, gncHostIndex }
            DESCRIPTION
                "Trap host community string was modified. gncHostIndex
                 contains the index of the host modified."
            ::= 19

    otm32SoftwareDownloadStartedTrap  TRAP-TYPE
            ENTERPRISE  otm32
            VARIABLES { eventDescription, eventSeverity }
            DESCRIPTION
                "Software download was started."
            ::= 20

    otm32SoftwareDownloadCompletedTrap  TRAP-TYPE
            ENTERPRISE  otm32
            VARIABLES { eventDescription, eventSeverity }
            DESCRIPTION
                "Software download has completed successfully."
            ::= 21

    otm32SoftwareDownloadFailedTrap  TRAP-TYPE
            ENTERPRISE  otm32
            VARIABLES { eventDescription, eventSeverity }
            DESCRIPTION
                "An error occurred during a software download."
            ::= 22

    otm32ModuleDownloadStartedTrap  TRAP-TYPE
            ENTERPRISE  otm32
            VARIABLES { eventDescription, eventSeverity }
            DESCRIPTION
                "Module download was started."
            ::= 23

    otm32ModuleDownloadCompletedTrap  TRAP-TYPE
            ENTERPRISE  otm32
            VARIABLES { eventDescription, eventSeverity }
            DESCRIPTION
                "Module download has completed successfully."
            ::= 24

    otm32ModuleDownloadFailedTrap  TRAP-TYPE
            ENTERPRISE  otm32
            VARIABLES { eventDescription, eventSeverity }
            DESCRIPTION
                "An error occurred during a module download."
            ::= 25

    otm32CardDetectTrap  TRAP-TYPE
            ENTERPRISE  otm32
            VARIABLES { eventDescription, eventSeverity, eqptBay, eqptShelf, eqptSlot, eqptCardType }
            DESCRIPTION
                "Card was detected. eqptBay, eqptShelf, eqptSlot, and eqptCardType
                 contain the cards bay, shelf, slot, and card type."
            ::= 100

    otm32CardAddedTrap  TRAP-TYPE
            ENTERPRISE  otm32
            VARIABLES { eventDescription, eventSeverity, eqptBay, eqptShelf, eqptSlot, eqptCardType }
            DESCRIPTION
                "Card was added. eqptBay, eqptShelf, eqptSlot, and eqptCardType
                 contain the cards bay, shelf, slot, and card type."
            ::= 101

    otm32CardDeletedTrap  TRAP-TYPE
            ENTERPRISE  otm32
            VARIABLES { eventDescription, eventSeverity, eqptBay, eqptShelf, eqptSlot, eqptCardType }
            DESCRIPTION
                "Card was deleted. eqptBay, eqptShelf, eqptSlot, and eqptCardType
                 contain the cards bay, shelf, slot, and card type."
            ::= 102

    otm32CardLostTrap  TRAP-TYPE
            ENTERPRISE  otm32
            VARIABLES { eventDescription, eventSeverity, eqptBay, eqptShelf, eqptSlot, eqptCardType }
            DESCRIPTION
                "Card was lost or removed. eqptBay, eqptShelf, eqptSlot, and eqptCardType
                 contain the cards bay, shelf, slot, and card type."
            ::= 103

    otm32CardResetTrap  TRAP-TYPE
            ENTERPRISE  otm32
            VARIABLES { eventDescription, eventSeverity, eqptBay, eqptShelf, eqptSlot, eqptCardType }
            DESCRIPTION
                "Card was reset. eqptBay, eqptShelf, eqptSlot, and eqptCardType
                 contain the cards bay, shelf, slot, and card type."
            ::= 104
    otm32CardMismatchTrap  TRAP-TYPE
            ENTERPRISE  otm32
            VARIABLES { eventDescription, eventSeverity, eqptBay, eqptShelf, eqptSlot, eqptCardType }
            DESCRIPTION
                "Card is in mismatch, either due to a different card is plugged or due to difference
                 in config exists between GNC and the card. eqptBay, eqptShelf, eqptSlot, and eqptCardType
                 contain the cards bay, shelf, slot, and card type."
            ::= 105
    otm32CardConfigChangedTrap  TRAP-TYPE
            ENTERPRISE  otm32
            VARIABLES { eventDescription, eventSeverity, eqptBay, eqptShelf, eqptSlot, eqptCardType }
            DESCRIPTION
                "Card config is changed in either eqipment or facility or both parameters. 
                 eqptBay, eqptShelf, eqptSlot, and eqptCardType contain the cards bay, shelf, 
                 slot, and card type."
            ::= 106
END
