--
-- genIntfTranslationTable.mib
-- MIB generated by MG-SOFT Visual MIB Builder Version 3.0 Build 285
-- Thursday, February 24, 2011 at 01:43:03
--

    ZHONE-INTERFACE-TRANSLATION-MIB DEFINITIONS ::= BEGIN
 
        IMPORTS
            IANAifType            
                FROM IANAifType-MIB            
            ifEntry, InterfaceIndex            
                FROM IF-MIB            
            Integer32, Unsigned32, OBJECT-TYPE, MODULE-IDENTITY, OBJECT-IDENTITY, 
            NOTIFICATION-TYPE            
                FROM SNMPv2-SMI            
            TruthValue            
                FROM SNMPv2-TC            
            zhoneInterfaceTranslation, zhoneShelfIndex, zhoneSlotIndex, zhoneModules, zhoneShelfIndex, 
            zhoneSlotIndex            
                FROM Zhone            
            ZhoneShelfValue, ZhoneSlotValue, ZhoneRowStatus, ZhoneIfType            
                FROM Zhone-TC;
    
    
-- NOTE: The markup for the If_Translate_Record also includes three fields that
-- are defined in rfc2233.mib.
-- 
-- This markup creates the interface translation record.  It is indexed by ifIndex.
-- 
-- 
-- This markup creates the interface configuration defaults table.  It is indexed
-- by card type and interface type.
-- 
-- 
        -- 1.3.6.1.4.1.5504.6.6
        zhoneInterfaceTrans MODULE-IDENTITY 
            LAST-UPDATED "201102241138Z"		-- February 24, 2011 at 11:38 GMT
            ORGANIZATION 
                "Zhone Technologies, Inc."
            CONTACT-INFO 
                "  Postal: 
                           Zhone Technologies, Inc.
                           @ Zhone Way
                           7001 Oakport Street
                           Oakland, CA  94621
                           USA
                Toll-Free: +1 877-ZHONE20 (+1 877-946-6320)
                      Tel: +1-510-777-7000
                      Fax: +1-510-777-7001
                   E-mail: support@zhone.com"
            DESCRIPTION 
                "Defines translation tables that provide the translation
                to and from shelf/slot/port/subport <-> interface number.
                Both table are created whenever an ifIndex is created. The
                ifStackDefaultTable is used to provide a roadmap of stack 
                bindings, and to supply default ifAdminStatus values for new 
                rows of the ifTable."
            REVISION "201102240138Z"		-- February 24, 2011 at 01:38 GMT
            DESCRIPTION 
                "Changed the range of field redundancyParam1 -2147483648 to 2147483647"
            REVISION "201004091504Z"		-- April 09, 2010 at 15:04 GMT
            DESCRIPTION 
                "Add lineRedTraps"
            REVISION "201004021429Z"		-- April 02, 2010 at 14:29 GMT
            DESCRIPTION 
                "Renamed 'ifType' to 'xxxifTypexxx' since ZMS can 
                accidentaly compile in this deprecated object
                instead of MIB2 'ifType' object."
            REVISION "201003101119Z"		-- March 10, 2010 at 11:19 GMT
            DESCRIPTION 
                "Add zhoneLineRedStatusTable
                Document redundancyParam1"
            REVISION "200809282315Z"		-- September 28, 2008 at 23:15 GMT
            DESCRIPTION 
                "V01.01.05 - Add zhoneDescriptionTable.
                            Add zhoneIfXDescriptionIndex.
                            Add zhoneIfXDescriptionIndexNext."
            REVISION "200701261823Z"		-- January 26, 2007 at 18:23 GMT
            DESCRIPTION 
                "V01.01.04 - add shelf, slot, port and
                subport aliases to zhoneIfXEntry to allow
                user to create physical if-translate record."
            REVISION "200405261553Z"		-- May 26, 2004 at 15:53 GMT
            DESCRIPTION 
                "V01.01.03 - add redundancyParam1."
            REVISION "200106281307Z"		-- June 28, 2001 at 13:07 GMT
            DESCRIPTION 
                "V01.01.02 - fix the 17 slot limit problem"
            REVISION "200105231102Z"		-- May 23, 2001 at 11:02 GMT
            DESCRIPTION 
                "V01.01.01 - Deprecated physicalToIfIndexTable and
                replaced it with zhonePhysicalToIfIndexTable."
            REVISION "200105111525Z"		-- May 11, 2001 at 15:25 GMT
            DESCRIPTION 
                "V01.01.00 - Added physicalFlag and ifTypeExtension records"
            REVISION "200009201200Z"		-- September 20, 2000 at 12:00 GMT
            DESCRIPTION 
                "V01.00.01 - Added markup for Physical-to-IfIndex Record"
            REVISION "200009121111Z"		-- September 12, 2000 at 11:11 GMT
            DESCRIPTION 
                "V01.00.00 - Initial Release"
            ::= { zhoneModules 6 }

        
    
    
--
-- Node definitions
--
    
        -- 1.3.6.1.4.1.5504.3.5.1
        ifIndexNext OBJECT-TYPE
            SYNTAX InterfaceIndex
            MAX-ACCESS read-only
            STATUS current
            DESCRIPTION
                "Contains the next available ifIndex."
            ::= { zhoneInterfaceTranslation 1 }

        
        -- 1.3.6.1.4.1.5504.3.5.2
        physicalToIfIndexTable OBJECT-TYPE
            SYNTAX SEQUENCE OF PhysicalToIfIndexEntry
            MAX-ACCESS not-accessible
            STATUS deprecated
            DESCRIPTION
                "Table to translate from shelf/slot/physical port/subport
                to the interface number (zhoneIfIndex).  The physical
                port is the port number on the card selected by
                shelf/slot.  The role of subport may vary depending on
                the card type, but is included to allow maximum
                flexibility and future exhancements.
                
                This table has been replaced by a zhonePhysicalToIfIndexTable.
                The objects in this table have been replaced by zhonePortIndex,
                zhoneSubPortIndex, zhonePhysicalIfIndex, zhoneIfType, and
                zhoneIfTypeExtension."
            ::= { zhoneInterfaceTranslation 2 }

        
        -- 1.3.6.1.4.1.5504.3.5.2.1
        physicalToIfIndexEntry OBJECT-TYPE
            SYNTAX PhysicalToIfIndexEntry
            MAX-ACCESS not-accessible
            STATUS deprecated
            DESCRIPTION
                "The physical table is indexed by shelf/slot/physical port
                /subport.  In instances where there is no subport the 
                value of subport should be set to zero.
                
                This entry has been replaced by zhonePhysicalToIfIndexEntry."
            INDEX { zhoneShelfIndex, zhoneSlotIndex, pportIndex, subPortIndex }
            ::= { physicalToIfIndexTable 1 }

        
        PhysicalToIfIndexEntry ::=
            SEQUENCE { 
                pportIndex
                    Integer32,
                subPortIndex
                    Integer32,
                zhoneIfIndex
                    InterfaceIndex,
                xxxifTypexxx
                    IANAifType
             }

        -- 1.3.6.1.4.1.5504.3.5.2.1.1
        pportIndex OBJECT-TYPE
            SYNTAX Integer32 (0..2147483647)
            MAX-ACCESS not-accessible
            STATUS deprecated
            DESCRIPTION
                "The port number of the physical port on the card or 
                device.  The numbering should start at 1 for the first 
                port on the device and proceed sequentially.
                
                This object has been replaced by zhonePortIndex."
            ::= { physicalToIfIndexEntry 1 }

        
        -- 1.3.6.1.4.1.5504.3.5.2.1.2
        subPortIndex OBJECT-TYPE
            SYNTAX Integer32 (0..2147483647)
            MAX-ACCESS not-accessible
            STATUS deprecated
            DESCRIPTION
                "This entry provides flexibility to define more than one
                interface on a port.  The most common use of subport will
                be to handle structured TDM lines allowing for example an
                interface number to be assign to each DS1 in a DS3.  
                
                Subport may also be used to handle other situations where
                a physical port contains more than one inetrface.  This
                object has replaced by zhoneSubPortIndex."
            ::= { physicalToIfIndexEntry 2 }

        
        -- 1.3.6.1.4.1.5504.3.5.2.1.3
        zhoneIfIndex OBJECT-TYPE
            SYNTAX InterfaceIndex
            MAX-ACCESS read-only
            STATUS deprecated
            DESCRIPTION
                "The interface number of the pport or pport/subport that
                uniquely identifies the interface across the system.
                
                This object has been replaced by zhonePhysicalIfIndex."
            REFERENCE
                "RFC 2233 - The Interfaces Group MIB using SMIv2"
            ::= { physicalToIfIndexEntry 3 }

        
        -- 1.3.6.1.4.1.5504.3.5.2.1.4
        xxxifTypexxx OBJECT-TYPE
            SYNTAX IANAifType
            MAX-ACCESS read-only
            STATUS deprecated
            DESCRIPTION
                "The type of interface.  Additional values for ifType
                are assigned by the Internet Assigned Numbers
                Authority (IANA), through updating the syntax of the
                IANAifType textual convention.
                
                This object has replaced by zhoneIfType.
                "
            REFERENCE
                "RFC 2233 - The Interfaces Group MIB using SMIv2"
            ::= { physicalToIfIndexEntry 4 }

        
        -- 1.3.6.1.4.1.5504.3.5.3
        ifIndexToPhysicalTable OBJECT-TYPE
            SYNTAX SEQUENCE OF IfIndexToPhysicalEntry
            MAX-ACCESS not-accessible
            STATUS current
            DESCRIPTION
                "Table to translate from interface number (zhoneIfIndex)
                to the physical location and port (including subport
                where defined).
                
                zhoneShelfNumber is the number of the shelf on which the
                port is located and can have a value from 1-255, 
                
                zhoneSlotNumber is the card slot on which card with the
                physical port is located and currently has a value of
                1-18.
                
                The pportNumber identifies the specific physical
                port on the card beginning with port 1.
                
                subPortNumber issued to define multiple interfaces on
                a port as required, if the identified port has a single
                interface number, subport will be set to zero.
                "
            ::= { zhoneInterfaceTranslation 3 }

        
        -- 1.3.6.1.4.1.5504.3.5.3.1
        ifIndexToPhysicalEntry OBJECT-TYPE
            SYNTAX IfIndexToPhysicalEntry
            MAX-ACCESS not-accessible
            STATUS current
            DESCRIPTION
                "The table is indexed by the zhoneIfidndex of the
                desired interface."
            INDEX { zhoneIfIndex }
            ::= { ifIndexToPhysicalTable 1 }

        
        IfIndexToPhysicalEntry ::=
            SEQUENCE { 
                zhoneShelfNumber
                    ZhoneShelfValue,
                zhoneSlotNumber
                    ZhoneSlotValue,
                pportNumber
                    Integer32,
                subPortNumber
                    Integer32,
                ifaceType
                    IANAifType,
                ifaceTypeExtension
                    ZhoneIfType
             }

        -- 1.3.6.1.4.1.5504.3.5.3.1.1
        zhoneShelfNumber OBJECT-TYPE
            SYNTAX ZhoneShelfValue
            MAX-ACCESS read-only
            STATUS current
            DESCRIPTION
                "The zhoneShelfNumber is the physical address or number of
                the shelf for the desired interface.  A Zhone system is
                limited to a maximum of 255 shelves.  The first shelf in 
                a system is shelf 1, "
            ::= { ifIndexToPhysicalEntry 1 }

        
-- 
        -- 1.3.6.1.4.1.5504.3.5.3.1.2
        zhoneSlotNumber OBJECT-TYPE
            SYNTAX ZhoneSlotValue
            MAX-ACCESS read-only
            STATUS current
            DESCRIPTION
                "The zhoneSlotNumber is the physical slot number on which
                the card containing the port or interface is located. 
                Zhone shelves are currently limited to 30 slots numbered
                1-30.  
                
                Note that daughter boards do not have slot numbers."
            ::= { ifIndexToPhysicalEntry 2 }

        
        -- 1.3.6.1.4.1.5504.3.5.3.1.3
        pportNumber OBJECT-TYPE
            SYNTAX Integer32 (0..2147483647)
            MAX-ACCESS read-only
            STATUS current
            DESCRIPTION
                "The pportNumber defines the phyiscal port number on the
                selected shelf/slot (card).  Port numbering begins with
                port 1 and ports are numbered sequentially. pportNumber
                0 is invalid unless the ifIndex is for an interface that
                is not bound to a physical port."
            ::= { ifIndexToPhysicalEntry 3 }

        
        -- 1.3.6.1.4.1.5504.3.5.3.1.4
        subPortNumber OBJECT-TYPE
            SYNTAX Integer32 (0..2147483647)
            MAX-ACCESS read-only
            STATUS current
            DESCRIPTION
                "The subPortNumber is used to identify multiple logical
                ports on a physical that require their own interface
                number, e.g. DS1s on a DS3 port.
                
                Note that multiple protocol layers such as IP over ATM
                do not require unique interface numbers and are handled 
                by the standard ifStackTable mechanism.
                
                Subport 0 is reserved to designate that a physical port
                has no subport and hence a single interface number.
                "
            REFERENCE
                "RFC 2233 - The Interfaces Group MIB using SMIv2"
            ::= { ifIndexToPhysicalEntry 4 }

        
        -- 1.3.6.1.4.1.5504.3.5.3.1.5
        ifaceType OBJECT-TYPE
            SYNTAX IANAifType
            MAX-ACCESS read-only
            STATUS current
            DESCRIPTION
                "The type of interface.  Additional values for ifType
                are assigned by the Internet Assigned Numbers
                Authority (IANA), through updating the syntax of the
                IANAifType textual convention."
            ::= { ifIndexToPhysicalEntry 5 }

        
        -- 1.3.6.1.4.1.5504.3.5.3.1.6
        ifaceTypeExtension OBJECT-TYPE
            SYNTAX ZhoneIfType
            MAX-ACCESS read-only
            STATUS current
            DESCRIPTION
                "This field is used to specify the zhone-proprietary 
                interface type when necessary.  For example, if the 
                interface is a line-group, iftype is set to 'IANAIFTYPE_OTHER'
                and ifTypeExtension is set to 'ZHONEIFTYPE_LINEGROUP'.
                By default ifTypeExtension is set to 'ZHONEIFTYPE_NONE(0)'."
            ::= { ifIndexToPhysicalEntry 6 }

        
        -- 1.3.6.1.4.1.5504.3.5.4
        ifStackDefaultTable OBJECT-TYPE
            SYNTAX SEQUENCE OF IfStackDefaultEntry
            MAX-ACCESS not-accessible
            STATUS current
            DESCRIPTION
                "This table defines the default ifTable vales and
                stack arrangements (bindings) and unit numbers based on
                types of cards and ifTypes."
            ::= { zhoneInterfaceTranslation 4 }

        
        -- 1.3.6.1.4.1.5504.3.5.4.1
        ifStackDefaultEntry OBJECT-TYPE
            SYNTAX IfStackDefaultEntry
            MAX-ACCESS not-accessible
            STATUS current
            DESCRIPTION
                "This table contains the unit/card type, the ifType of 
                the 'from' layer (ifStkDefUpperIfType) and the ifType 
                of the 'to' layer (ifStkDefLowerIfType) and the number 
                of units for each association.
                Also the Default value ifAdminStatus in ifTable.
                A value must be supplied for all fields except ifStkDefAdminStatus
                to create a new row."
            REFERENCE
                "RFC 2233 - The Interfaces Group MIB using SMIv2"
            INDEX { ifStkDefUpperType, ifStkDefLowerType, ifStkDefCardType }
            ::= { ifStackDefaultTable 1 }

        
        IfStackDefaultEntry ::=
            SEQUENCE { 
                ifStkDefCardType
                    Integer32,
                ifStkDefUpperType
                    IANAifType,
                ifStkDefLowerType
                    IANAifType,
                ifStkDefUnits
                    Integer32,
                ifStkDefAdminStatus
                    INTEGER,
                ifStkDefRowStatus
                    ZhoneRowStatus
             }

        -- 1.3.6.1.4.1.5504.3.5.4.1.1
        ifStkDefCardType OBJECT-TYPE
            SYNTAX Integer32 (0..2147483647)
            MAX-ACCESS not-accessible
            STATUS current
            DESCRIPTION
                "The numerical representation of unit/card type as specified in
                zhoneCardResourcesModule where cardZhoneType has the following 
                defined values: unknownType(1), interShelf(2), infoServices(3),
                hdsl2(10),sechtor100(1001),zedge64(2001), and zplex10(3001). Other
                values may be used.
                "
            ::= { ifStackDefaultEntry 1 }

        
        -- 1.3.6.1.4.1.5504.3.5.4.1.2
        ifStkDefUpperType OBJECT-TYPE
            SYNTAX IANAifType
            MAX-ACCESS not-accessible
            STATUS current
            DESCRIPTION
                "The value of ifType corresponding to the higher 
                sublayer of the relationship, i.e., the sublayer that 
                runs on top of the sublayer identified by the 
                corresponding instance of ifStkDefLowerType."
            ::= { ifStackDefaultEntry 2 }

        
        -- 1.3.6.1.4.1.5504.3.5.4.1.3
        ifStkDefLowerType OBJECT-TYPE
            SYNTAX IANAifType
            MAX-ACCESS not-accessible
            STATUS current
            DESCRIPTION
                "The value of ifType corresponding to the default lower
                sublayer of the relationship, i.e., the sublayer that 
                runs under the sublayer identified by the 
                corresponding instance of ifStkDefUpperType."
            ::= { ifStackDefaultEntry 3 }

        
        -- 1.3.6.1.4.1.5504.3.5.4.1.4
        ifStkDefUnits OBJECT-TYPE
            SYNTAX Integer32 (0..2147483647)
            UNITS "count"
            MAX-ACCESS read-create
            STATUS current
            DESCRIPTION
                "Number of units for this association which indicates the number of
                ifindexes created for this particular iftype pair on this card type 
                such as 48 creations for the initial version of the HDSL2 card.
                "
            ::= { ifStackDefaultEntry 4 }

        
        -- 1.3.6.1.4.1.5504.3.5.4.1.5
        ifStkDefAdminStatus OBJECT-TYPE
            SYNTAX INTEGER
                {
                up(1),
                down(2),
                testing(3)
                }
            MAX-ACCESS read-create
            STATUS current
            DESCRIPTION
                "Default value for ifAdminStatus in ifTable for the UPPPER ifindex
                associated with the ifStkDefUpperType."
            DEFVAL { down }
            ::= { ifStackDefaultEntry 5 }

        
        -- 1.3.6.1.4.1.5504.3.5.4.1.6
        ifStkDefRowStatus OBJECT-TYPE
            SYNTAX ZhoneRowStatus
            MAX-ACCESS read-create
            STATUS current
            DESCRIPTION
                "Row status used to create and/or remove rows from this table."
            ::= { ifStackDefaultEntry 6 }

        
        -- 1.3.6.1.4.1.5504.3.5.5
        ifInverseStackTable OBJECT-TYPE
            SYNTAX SEQUENCE OF IfInverseStackEntry
            MAX-ACCESS not-accessible
            STATUS current
            DESCRIPTION
                "
                This is the inverse ifstacktable in that the index
                scheme is lower.higher as opposed to higher.lower as
                defined in rfc2233. Comments and information is 
                copied here for clarity.
                
                Information on a particular relationship between two
                sub-layers, specifying that one sub-layer runs on
                'top' of the other sub-layer.  Each sub-layer
                corresponds to a conceptual row in the ifTable.
                
                Use of this table is solely for management stations
                to walk the table (getnext) from the lower
                physical port (ifindex) up the stack."
            ::= { zhoneInterfaceTranslation 5 }

        
        -- 1.3.6.1.4.1.5504.3.5.5.1
        ifInverseStackEntry OBJECT-TYPE
            SYNTAX IfInverseStackEntry
            MAX-ACCESS not-accessible
            STATUS current
            DESCRIPTION
                "The table containing information on the relationships
                between the multiple sub-layers of network interfaces.
                In particular, it contains information on which sub-
                layers run 'on top of' which other sub-layers, where
                each sub-layer corresponds to a conceptual row in the
                ifTable.  For example, when the sub-layer with ifIndex
                value x runs over the sub-layer with ifIndex value y,
                then this table contains:
                
                ifStackStatus.y.x=active
                
                For each ifIndex value, I, which identifies an active
                interface, there are always at least two instantiated
                rows in this table associated with I.  For one of
                these rows, I is the value of ifStackHigherLayer; for
                the other, I is the value of ifStackLowerLayer.  (If I
                is not involved in multiplexing, then these are the
                only two rows associated with I.)
                
                For example, two rows exist even for an interface
                which has no others stacked on top or below it:
                
                ifStackStatus.0.x=active
                ifStackStatus.x.0=active
                
                A corresponding entry in this mib is made whenever an
                entry is made in the standard ifStackTable. Thus,
                deletion, creation, and modification is not possible on
                this table."
            INDEX { ifInverseStackLowerLayer, ifInverseStackHigherLayer }
            ::= { ifInverseStackTable 1 }

        
        IfInverseStackEntry ::=
            SEQUENCE { 
                ifInverseStackLowerLayer
                    InterfaceIndex,
                ifInverseStackHigherLayer
                    InterfaceIndex,
                ifInverseStackStatus
                    INTEGER
             }

        -- 1.3.6.1.4.1.5504.3.5.5.1.1
        ifInverseStackLowerLayer OBJECT-TYPE
            SYNTAX InterfaceIndex
            MAX-ACCESS not-accessible
            STATUS current
            DESCRIPTION
                "The value of ifIndex corresponding to the lower sub-
                layer of the relationship, i.e., the sub-layer which
                runs 'below' the sub-layer identified by the
                corresponding instance of ifInverseStackHigherLayer.  If
                there is no lower sub-layer, then this object has the
                value 0.
                "
            ::= { ifInverseStackEntry 1 }

        
        -- 1.3.6.1.4.1.5504.3.5.5.1.2
        ifInverseStackHigherLayer OBJECT-TYPE
            SYNTAX InterfaceIndex
            MAX-ACCESS not-accessible
            STATUS current
            DESCRIPTION
                "The value of ifIndex corresponding to the higher
                sub-layer of the relationship, i.e., the sub-layer
                which runs on 'top' of the sub-layer identified by the
                corresponding instance of ifStackLowerLayer.  If there
                is no higher sub-layer (below the internetwork layer),
                then this object has the value 0.
                "
            ::= { ifInverseStackEntry 2 }

        
        -- 1.3.6.1.4.1.5504.3.5.5.1.3
        ifInverseStackStatus OBJECT-TYPE
            SYNTAX INTEGER { active(1) }
            MAX-ACCESS read-only
            STATUS current
            DESCRIPTION
                "Status of this entry. If the entry
                exists, this value must be 1."
            ::= { ifInverseStackEntry 3 }

        
        -- 1.3.6.1.4.1.5504.3.5.6
        zhoneIfXTable OBJECT-TYPE
            SYNTAX SEQUENCE OF ZhoneIfXEntry
            MAX-ACCESS not-accessible
            STATUS current
            DESCRIPTION
                "This table contains additional objects for the interface table.
                Each row corresponds to a conceptual row in the ifTable."
            ::= { zhoneInterfaceTranslation 6 }

        
        -- 1.3.6.1.4.1.5504.3.5.6.1
        zhoneIfXEntry OBJECT-TYPE
            SYNTAX ZhoneIfXEntry
            MAX-ACCESS not-accessible
            STATUS current
            DESCRIPTION
                "An entry containing additional management information
                applicable to a particular interface."
            AUGMENTS { ifEntry }
            ::= { zhoneIfXTable 1 }

        
        ZhoneIfXEntry ::=
            SEQUENCE { 
                physicalFlag
                    TruthValue,
                ifTypeExtension
                    ZhoneIfType,
                redundancyParam1
                    Integer32,
                zhoneIfXEntryIfTypeAlias
                    IANAifType,
                zhoneIfXEntryRowStatus
                    ZhoneRowStatus,
                zhoneIfXEntryShelfAlias
                    Integer32,
                zhoneIfXEntrySlotAlias
                    Integer32,
                zhoneIfXEntryPortAlias
                    Integer32,
                zhoneIfXEntrySubportAlias
                    Integer32,
                zhoneIfXDescriptionIndex
                    Integer32
             }

-- 
        -- 1.3.6.1.4.1.5504.3.5.6.1.1
        physicalFlag OBJECT-TYPE
            SYNTAX TruthValue
            MAX-ACCESS read-create
            STATUS current
            DESCRIPTION
                "The flag is set to 'true(1)' if the ifIndex
                represents the physical layer.  Otherwise the
                flag is set to 'false(2)'."
            DEFVAL { false }
            ::= { zhoneIfXEntry 1 }

        
-- 
        -- 1.3.6.1.4.1.5504.3.5.6.1.2
        ifTypeExtension OBJECT-TYPE
            SYNTAX ZhoneIfType
            MAX-ACCESS read-create
            STATUS current
            DESCRIPTION
                "This field is used to specify the zhone-proprietary 
                interface type when necessary.  For example, if the 
                interface is a line-group, iftype is set to 'IANAIFTYPE_OTHER'
                and ifTypeExtension is set to 'ZHONEIFTYPE_LINEGROUP'.
                By default ifTypeExtension is set to 'ZHONEIFTYPE_NONE(0)'."
            ::= { zhoneIfXEntry 2 }

        
-- 
        -- 1.3.6.1.4.1.5504.3.5.6.1.3
        redundancyParam1 OBJECT-TYPE
            SYNTAX Integer32 (-2147483648..2147483647)
            MAX-ACCESS read-create
            STATUS current
            DESCRIPTION
                "For linegroups, this value contains information 
                about line redundancy as follows:
                
                0x8000     bit set => switchover on failure
                0x7FFF     number of seconds to wait before switchover
                0x40000000 bit set => revert after switchover
                0x3FFF0000 these 4 bits contains the number of seconds 
                                      to wait before reverting
                0x80000000 bit set => disable transmit on standby
                
                For physical interfaces:
                0x00000001 bit set => secondary member of a 
                                      protection pair
                           bit clear => primary member, or standalone"
            ::= { zhoneIfXEntry 3 }

        
        -- 1.3.6.1.4.1.5504.3.5.6.1.4
        zhoneIfXEntryIfTypeAlias OBJECT-TYPE
            SYNTAX IANAifType
            MAX-ACCESS read-create
            STATUS current
            DESCRIPTION
                "This object maps to ifType object within the ifEntry
                table.  This object is used when creating a new
                row in the ifEntry table since ifType is read-only."
            ::= { zhoneIfXEntry 4 }

        
        -- 1.3.6.1.4.1.5504.3.5.6.1.5
        zhoneIfXEntryRowStatus OBJECT-TYPE
            SYNTAX ZhoneRowStatus
            MAX-ACCESS read-create
            STATUS current
            DESCRIPTION
                "This object is used to create and delete rows within the
                ifEntry table since ifEntry is standard and does not
                have a Row Status object.
                
                Currently, only ifType value of 'other' is allowed to be
                created via SNMP."
            ::= { zhoneIfXEntry 5 }

        
        -- 1.3.6.1.4.1.5504.3.5.6.1.6
        zhoneIfXEntryShelfAlias OBJECT-TYPE
            SYNTAX Integer32 (0..1)
            MAX-ACCESS read-create
            STATUS current
            DESCRIPTION
                "Writeable shelf number.
                This object maps to the read-only object zhoneShelfNumber."
            ::= { zhoneIfXEntry 6 }

        
        -- 1.3.6.1.4.1.5504.3.5.6.1.7
        zhoneIfXEntrySlotAlias OBJECT-TYPE
            SYNTAX Integer32 (0..33)
            MAX-ACCESS read-create
            STATUS current
            DESCRIPTION
                "Writeable slot number.
                This object maps to the read-only object zhoneSlotNumber."
            ::= { zhoneIfXEntry 7 }

        
        -- 1.3.6.1.4.1.5504.3.5.6.1.8
        zhoneIfXEntryPortAlias OBJECT-TYPE
            SYNTAX Integer32
            MAX-ACCESS read-create
            STATUS current
            DESCRIPTION
                "Writeable port number.
                This object maps to the read-only object zhonePortNumber."
            ::= { zhoneIfXEntry 8 }

        
        -- 1.3.6.1.4.1.5504.3.5.6.1.9
        zhoneIfXEntrySubportAlias OBJECT-TYPE
            SYNTAX Integer32
            MAX-ACCESS read-create
            STATUS current
            DESCRIPTION
                "Writeable subport number.
                This object maps to the read-only object zhoneSubPortNumber."
            ::= { zhoneIfXEntry 9 }

        
        -- 1.3.6.1.4.1.5504.3.5.6.1.10
        zhoneIfXDescriptionIndex OBJECT-TYPE
            SYNTAX Integer32 (0..2147483647)
            MAX-ACCESS read-create
            STATUS current
            DESCRIPTION
                "Index value of a zhoneDescriptionEntry.  Zero indicates
                no reference to zhoneDescriptionEntry."
            ::= { zhoneIfXEntry 10 }

        
        -- 1.3.6.1.4.1.5504.3.5.7
        zhonePhysicalToIfIndexTable OBJECT-TYPE
            SYNTAX SEQUENCE OF ZhonePhysicalToIfIndexEntry
            MAX-ACCESS not-accessible
            STATUS current
            DESCRIPTION
                "Table to translate from shelf/slot/physical port/subport/
                iftype/iftype-extension to the interface number 
                (zhonePhysicalIfIndex).  The physical port is the port number 
                on the card selected by shelf/slot.  The role of subport may 
                vary depending on the card type, but is included to allow 
                maximum flexibility and future exhancements.  Iftype-extension
                is searched when iftype is set to 'ZHONEIFTYPE_NONE(0)'."
            ::= { zhoneInterfaceTranslation 7 }

        
        -- 1.3.6.1.4.1.5504.3.5.7.1
        zhonePhysicalToIfIndexEntry OBJECT-TYPE
            SYNTAX ZhonePhysicalToIfIndexEntry
            MAX-ACCESS not-accessible
            STATUS current
            DESCRIPTION
                "The physical table is indexed by shelf/slot/physical port
                /subport/iftype/iftype-extension.  In instances where there 
                is no subport the value of subport should be set to zero."
            INDEX { zhoneShelfIndex, zhoneSlotIndex, zhonePortIndex, zhoneSubPortIndex, zhoneIfType, 
                zhoneIfTypeExtension }
            ::= { zhonePhysicalToIfIndexTable 1 }

        
        ZhonePhysicalToIfIndexEntry ::=
            SEQUENCE { 
                zhonePortIndex
                    Integer32,
                zhoneSubPortIndex
                    Integer32,
                zhoneIfType
                    IANAifType,
                zhoneIfTypeExtension
                    ZhoneIfType,
                zhonePhysicalIfIndex
                    InterfaceIndex
             }

        -- 1.3.6.1.4.1.5504.3.5.7.1.1
        zhonePortIndex OBJECT-TYPE
            SYNTAX Integer32 (0..2147483647)
            MAX-ACCESS not-accessible
            STATUS current
            DESCRIPTION
                "The port number of the physical port on the card or 
                device.  The numbering should start at 1 for the first 
                port on the device and proceed sequentially."
            ::= { zhonePhysicalToIfIndexEntry 1 }

        
        -- 1.3.6.1.4.1.5504.3.5.7.1.2
        zhoneSubPortIndex OBJECT-TYPE
            SYNTAX Integer32 (0..2147483647)
            MAX-ACCESS not-accessible
            STATUS current
            DESCRIPTION
                "This entry provides flexibility to define more than one
                interface on a port.  The most common use of subport will
                be to handle structured TDM lines allowing for example an
                interface number to be assign to each DS1 in a DS3.  
                
                Subport may also be used to handle other situations where
                a physical port contains more than one inetrface."
            ::= { zhonePhysicalToIfIndexEntry 2 }

        
        -- 1.3.6.1.4.1.5504.3.5.7.1.4
        zhoneIfType OBJECT-TYPE
            SYNTAX IANAifType
            MAX-ACCESS not-accessible
            STATUS current
            DESCRIPTION
                "The type of interface.  Additional values for ifType
                are assigned by the Internet Assigned Numbers
                Authority (IANA), through updating the syntax of the
                IANAifType textual convention.
                "
            REFERENCE
                "RFC 2233 - The Interfaces Group MIB using SMIv2"
            ::= { zhonePhysicalToIfIndexEntry 4 }

        
        -- 1.3.6.1.4.1.5504.3.5.7.1.5
        zhoneIfTypeExtension OBJECT-TYPE
            SYNTAX ZhoneIfType
            MAX-ACCESS not-accessible
            STATUS current
            DESCRIPTION
                "This field is used to specify the zhone-proprietary 
                interface type when necessary.  For example, if the 
                interface is a line-group, iftype is set to 'IANAIFTYPE_OTHER'
                and ifTypeExtension is set to 'ZHONEIFTYPE_LINEGROUP'.
                By default ifTypeExtension is set to 'ZHONEIFTYPE_NONE(0)'."
            ::= { zhonePhysicalToIfIndexEntry 5 }

        
        -- 1.3.6.1.4.1.5504.3.5.7.1.6
        zhonePhysicalIfIndex OBJECT-TYPE
            SYNTAX InterfaceIndex
            MAX-ACCESS read-only
            STATUS current
            DESCRIPTION
                "The interface number of the pport or pport/subport that
                uniquely identifies the interface across the system."
            REFERENCE
                "RFC 2233 - The Interfaces Group MIB using SMIv2"
            ::= { zhonePhysicalToIfIndexEntry 6 }

        
        -- 1.3.6.1.4.1.5504.3.5.8
        zhoneDescriptionTable OBJECT-TYPE
            SYNTAX SEQUENCE OF ZhoneDescriptionEntry
            MAX-ACCESS not-accessible
            STATUS current
            DESCRIPTION
                "Table of description entries."
            ::= { zhoneInterfaceTranslation 8 }

        
        -- 1.3.6.1.4.1.5504.3.5.8.1
        zhoneDescriptionEntry OBJECT-TYPE
            SYNTAX ZhoneDescriptionEntry
            MAX-ACCESS not-accessible
            STATUS current
            DESCRIPTION
                "Descritpion entry."
            INDEX { zhoneIfXDescriptionIndex }
            ::= { zhoneDescriptionTable 1 }

        
        ZhoneDescriptionEntry ::=
            SEQUENCE { 
                zhoneDescriptionRowStatus
                    ZhoneRowStatus,
                zhoneDescriptionText
                    OCTET STRING
             }

        -- 1.3.6.1.4.1.5504.3.5.8.1.1
        zhoneDescriptionRowStatus OBJECT-TYPE
            SYNTAX ZhoneRowStatus
            MAX-ACCESS read-create
            STATUS current
            DESCRIPTION
                "Row status object."
            ::= { zhoneDescriptionEntry 1 }

        
        -- 1.3.6.1.4.1.5504.3.5.8.1.2
        zhoneDescriptionText OBJECT-TYPE
            SYNTAX OCTET STRING (SIZE (0..64))
            MAX-ACCESS read-create
            STATUS current
            DESCRIPTION
                "Description object used as free format text description.
                Contains readable characters, with the following exclusions:
                1. Double quotes
                2. Carriage Returns
                3. Line Feeds
                4. Carat
                
                Maximum number of characters is 64, including any NULL terminator."
            ::= { zhoneDescriptionEntry 2 }

        
        -- 1.3.6.1.4.1.5504.3.5.9
        zhoneIfXDescriptionIndexNext OBJECT-TYPE
            SYNTAX Unsigned32
            MAX-ACCESS read-only
            STATUS current
            DESCRIPTION
                "Returns the next available zhoneIfXDescriptionIndex."
            ::= { zhoneInterfaceTranslation 9 }

        
        -- 1.3.6.1.4.1.5504.3.5.10
        zhoneLineRedStatusTable OBJECT-TYPE
            SYNTAX SEQUENCE OF ZhoneLineRedStatusEntry
            MAX-ACCESS not-accessible
            STATUS current
            DESCRIPTION
                "Line redundancy information"
            ::= { zhoneInterfaceTranslation 10 }

        
        -- 1.3.6.1.4.1.5504.3.5.10.1
        zhoneLineRedStatusEntry OBJECT-TYPE
            SYNTAX ZhoneLineRedStatusEntry
            MAX-ACCESS not-accessible
            STATUS current
            DESCRIPTION
                "Line redundancy information for on line"
            INDEX { zhoneIfIndex }
            ::= { zhoneLineRedStatusTable 1 }

        
        ZhoneLineRedStatusEntry ::=
            SEQUENCE { 
                zhoneLineRedStatusFunction
                    INTEGER,
                zhoneLineRedOpStatus
                    INTEGER
             }

        -- 1.3.6.1.4.1.5504.3.5.10.1.1
        zhoneLineRedStatusFunction OBJECT-TYPE
            SYNTAX INTEGER
                {
                inactive(1),
                standby(2),
                active(3),
                unavailable(4)
                }
            MAX-ACCESS read-only
            STATUS current
            DESCRIPTION
                "Current redundancy function as returned from LineRR.
                . inactive means registered but neither active nor 
                  standby
                . standby means this is the protection line in a pair.
                . active means either standalone or the working line
                  in a protection pair.
                . unavailable means not registered with LineRR"
            ::= { zhoneLineRedStatusEntry 1 }

        
        -- 1.3.6.1.4.1.5504.3.5.10.1.2
        zhoneLineRedOpStatus OBJECT-TYPE
            SYNTAX INTEGER
                {
                active(1),
                oos(2),
                trafficDisabled(3),
                unavailable(4)
                }
            MAX-ACCESS read-only
            STATUS current
            DESCRIPTION
                "Line status
                . active means line is up as standalone or the
                  working line in a redundant pair.
                . oos means line is down
                . trafficDisabled means up as standby
                . unavailable means not registered with LineRR"
            ::= { zhoneLineRedStatusEntry 2 }

        
        -- 1.3.6.1.4.1.5504.3.5.11
        zhoneLineRedTraps OBJECT-IDENTITY
            STATUS current
            DESCRIPTION 
                "Traps for facility redundancy"
            ::= { zhoneInterfaceTranslation 11 }

        
        -- 1.3.6.1.4.1.5504.3.5.11.0
        zhoneLineRedTrapsPrefix OBJECT-IDENTITY
            STATUS current
            DESCRIPTION 
                "Add zero in OID for traps."
            ::= { zhoneLineRedTraps 0 }

        
        -- 1.3.6.1.4.1.5504.3.5.11.0.1
        zhoneLineRedundancyUnsafe NOTIFICATION-TYPE
            STATUS current
            DESCRIPTION 
                "Sent when configured peer is not traffic-disabled"
            ::= { zhoneLineRedTrapsPrefix 1 }

        
        -- 1.3.6.1.4.1.5504.3.5.11.0.2
        zhoneLineRedundancySafe NOTIFICATION-TYPE
            STATUS current
            DESCRIPTION 
                "Sent when both lines in a facility-redundant pair
                have become redundancy ready."
            ::= { zhoneLineRedTrapsPrefix 2 }

        
    
    END

--
-- genIntfTranslationTable.mib
--
