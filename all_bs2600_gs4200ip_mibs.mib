IANAifType-MIB DEFINITIONS ::= BEGIN

   IMPORTS
       MODULE-IDENTITY, mib-2      FROM SNMPv2-SMI
       TEXTUAL-CONVENTION          FROM SNMPv2-TC;

   ianaifType MODULE-IDENTITY
       LAST-UPDATED "200308180000Z"  -- Aug 18, 2003
       ORGANIZATION "IANA"
       CONTACT-INFO "        Internet Assigned Numbers Authority

                     Postal: ICANN
                             4676 Admiralty Way, Suite 330
                             Marina del Rey, CA 90292

                     Tel:    +1 310 823 9358
                     E-Mail: iana@iana.org"

       DESCRIPTION  "This MIB module defines the IANAifType Textual
                     Convention, and thus the enumerated values of
                     the ifType object defined in MIB-II's ifTable."

       REVISION     "200308180000Z"  -- Aug 18, 2003
       DESCRIPTION  "Registration of new IANAifType
                    224."

       REVISION     "200308070000Z"  -- Aug 7, 2003
       DESCRIPTION  "Registration of new IANAifTypes
                    222 and 223."

       REVISION     "200303180000Z"  -- Mar 18, 2003
       DESCRIPTION  "Registration of new IANAifType
                    221."

       REVISION     "200301130000Z"  -- Jan 13, 2003
       DESCRIPTION  "Registration of new IANAifType
                    220."

       REVISION     "200210170000Z"  -- Oct 17, 2002
       DESCRIPTION  "Registration of new IANAifType
                    219."
	   
	   REVISION     "200207160000Z"  -- Jul 16, 2002
       DESCRIPTION  "Registration of new IANAifTypes
                    217 and 218."

       REVISION     "200207100000Z"  -- Jul 10, 2002
       DESCRIPTION  "Registration of new IANAifTypes
                    215 and 216."

       REVISION     "200206190000Z"  -- Jun 19, 2002
       DESCRIPTION  "Registration of new IANAifType
                    214."
	   
       REVISION     "200201040000Z"  -- Jan 4, 2002
       DESCRIPTION  "Registration of new IANAifTypes
                    211, 212 and 213."

       REVISION     "200112200000Z"  -- Dec 20, 2001
       DESCRIPTION  "Registration of new IANAifTypes
                    209 and 210."

       REVISION     "200111150000Z"  -- Nov 15, 2001
       DESCRIPTION  "Registration of new IANAifTypes
                    207 and 208."


       REVISION     "200111060000Z"  -- Nov 6, 2001
       DESCRIPTION  "Registration of new IANAifType
                    206."


       REVISION     "200111020000Z"  -- Nov 2, 2001
       DESCRIPTION  "Registration of new IANAifType
                    205."


       REVISION     "200110160000Z"  -- Oct 16, 2001
       DESCRIPTION  "Registration of new IANAifTypes
                    199, 200, 201, 202, 203, and 204."


       REVISION     "200109190000Z"  -- Sept 19, 2001
       DESCRIPTION  "Registration of new IANAifType
                    198."

       REVISION     "200105110000Z"  -- May 11, 2001
       DESCRIPTION  "Registration of new IANAifType
                    197."

       
       REVISION     "200101120000Z"  -- Jan 12, 2001
       DESCRIPTION  "Registration of new IANAifTypes
                    195 and 196."

       REVISION     "200012190000Z"  -- Dec 19, 2000
       DESCRIPTION  "Registration of new IANAifTypes
                    193 and 194."

       REVISION     "200012070000Z"  -- Dec 07, 2000
       DESCRIPTION  "Registration of new IANAifTypes
                    191 and 192."

       REVISION     "200012040000Z"  -- Dec 04, 2000
       DESCRIPTION  "Registration of new IANAifType
                    190."

       REVISION     "200010170000Z"  -- Oct 17, 2000
       DESCRIPTION  "Registration of new IANAifTypes
                    188 and 189."  

       REVISION     "200010020000Z"  -- Oct 02, 2000
       DESCRIPTION  "Registration of new IANAifType 187." 

       REVISION     "200009010000Z"  -- Sept 01, 2000
       DESCRIPTION  "Registration of new IANAifTypes
                     184, 185, and 186."			

       REVISION     "200008240000Z"  -- Aug 24, 2000
       DESCRIPTION  "Registration of new IANAifType 183." 

       REVISION     "200008230000Z"  -- Aug 23, 2000
       DESCRIPTION  "Registration of new IANAifTypes
                     174-182."

       REVISION     "200008220000Z"  -- Aug 22, 2000
       DESCRIPTION  "Registration of new IANAifTypes 170,
                     171, 172 and 173."

       REVISION     "200004250000Z"  -- Apr 25, 2000
       DESCRIPTION  "Registration of new IANAifTypes 168 and 169."       
	

       REVISION     "200003060000Z"  -- Mar 6, 2000
       DESCRIPTION  "Fixed a missing semi-colon in the IMPORT.
                     Also cleaned up the REVISION log a bit.
                     It is not complete, but from now on it will
                     be maintained and kept up to date with each
                     change to this MIB module."

       REVISION     "199910081430Z"  -- Oct 08, 1999
       DESCRIPTION  "Include new name assignments up to cnr(85).
                     This is the first version available via the WWW
                     at: ftp://ftp.isi.edu/mib/ianaiftype.mib"

       REVISION     "199401310000Z"  -- Jan 31, 1994
       DESCRIPTION  "Initial version of this MIB as published in
                     RFC 1573."

       ::= { mib-2 30 }


   IANAifType ::= TEXTUAL-CONVENTION
       STATUS       current
       DESCRIPTION
               "This data type is used as the syntax of the ifType
               object in the (updated) definition of MIB-II's
               ifTable.

               The definition of this textual convention with the
               addition of newly assigned values is published
               periodically by the IANA, in either the Assigned
               Numbers RFC, or some derivative of it specific to
               Internet Network Management number assignments.  (The
               latest arrangements can be obtained by contacting the
               IANA.)

               Requests for new values should be made to IANA via
               email (iana@iana.org).

               The relationship between the assignment of ifType
               values and of OIDs to particular media-specific MIBs
               is solely the purview of IANA and is subject to change
               without notice.  Quite often, a media-specific MIB's
               OID-subtree assignment within MIB-II's 'transmission'
               subtree will be the same as its ifType value.
               However, in some circumstances this will not be the
               case, and implementors must not pre-assume any
               specific relationship between ifType values and
               transmission subtree OIDs."
       SYNTAX  INTEGER {
                   other(1),          -- none of the following
                   regular1822(2),
                   hdh1822(3),
                   ddnX25(4),
                   rfc877x25(5),
                   ethernetCsmacd(6),
                   iso88023Csmacd(7),
                   iso88024TokenBus(8),
                   iso88025TokenRing(9),
                   iso88026Man(10),
                   starLan(11),
                   proteon10Mbit(12),
                   proteon80Mbit(13),
                   hyperchannel(14),
                   fddi(15),
                   lapb(16),
                   sdlc(17),
                   ds1(18),            -- DS1-MIB
                   e1(19),             -- Obsolete see DS1-MIB
                   basicISDN(20),
                   primaryISDN(21),
                   propPointToPointSerial(22), -- proprietary serial
                   ppp(23),
                   softwareLoopback(24),
                   eon(25),            -- CLNP over IP 
                   ethernet3Mbit(26),
                   nsip(27),           -- XNS over IP
                   slip(28),           -- generic SLIP
                   ultra(29),          -- ULTRA technologies
                   ds3(30),            -- DS3-MIB
                   sip(31),            -- SMDS, coffee
                   frameRelay(32),     -- DTE only. 
                   rs232(33),
                   para(34),           -- parallel-port
                   arcnet(35),         -- arcnet
                   arcnetPlus(36),     -- arcnet plus
                   atm(37),            -- ATM cells
                   miox25(38),
                   sonet(39),          -- SONET or SDH 
                   x25ple(40),
                   iso88022llc(41),
                   localTalk(42),
                   smdsDxi(43),
                   frameRelayService(44),  -- FRNETSERV-MIB
                   v35(45),
                   hssi(46),
                   hippi(47),
                   modem(48),          -- Generic modem
                   aal5(49),           -- AAL5 over ATM
                   sonetPath(50),
                   sonetVT(51),
                   smdsIcip(52),       -- SMDS InterCarrier Interface
                   propVirtual(53),    -- proprietary virtual/internal
                   propMultiplexor(54),-- proprietary multiplexing
                   ieee80212(55),      -- 100BaseVG
                   fibreChannel(56),   -- Fibre Channel
                   hippiInterface(57), -- HIPPI interfaces     
                   frameRelayInterconnect(58), -- Obsolete use either
                                       -- frameRelay(32) or 
                                       -- frameRelayService(44).
                   aflane8023(59),     -- ATM Emulated LAN for 802.3
                   aflane8025(60),     -- ATM Emulated LAN for 802.5
                   cctEmul(61),        -- ATM Emulated circuit          
                   fastEther(62),      -- Fast Ethernet (100BaseT)
                   isdn(63),           -- ISDN and X.25           
                   v11(64),            -- CCITT V.11/X.21             
                   v36(65),            -- CCITT V.36                  
                   g703at64k(66),      -- CCITT G703 at 64Kbps
                   g703at2mb(67),      -- Obsolete see DS1-MIB
                   qllc(68),           -- SNA QLLC                    
                   fastEtherFX(69),    -- Fast Ethernet (100BaseFX)   
                   channel(70),        -- channel                     
                   ieee80211(71),      -- radio spread spectrum       
	           ibm370parChan(72),  -- IBM System 360/370 OEMI Channel
                   escon(73),          -- IBM Enterprise Systems Connection
                   dlsw(74),           -- Data Link Switching
                   isdns(75),          -- ISDN S/T interface
                   isdnu(76),          -- ISDN U interface
                   lapd(77),           -- Link Access Protocol D
                   ipSwitch(78),       -- IP Switching Objects
                   rsrb(79),           -- Remote Source Route Bridging
                   atmLogical(80),     -- ATM Logical Port
                   ds0(81),            -- Digital Signal Level 0
                   ds0Bundle(82),      -- group of ds0s on the same ds1
                   bsc(83),            -- Bisynchronous Protocol
                   async(84),          -- Asynchronous Protocol
                   cnr(85),            -- Combat Net Radio
                   iso88025Dtr(86),    -- ISO 802.5r DTR
                   eplrs(87),          -- Ext Pos Loc Report Sys
                   arap(88),           -- Appletalk Remote Access Protocol
                   propCnls(89),       -- Proprietary Connectionless Protocol
                   hostPad(90),        -- CCITT-ITU X.29 PAD Protocol
                   termPad(91),        -- CCITT-ITU X.3 PAD Facility
                   frameRelayMPI(92),  -- Multiproto Interconnect over FR
                   x213(93),           -- CCITT-ITU X213
                   adsl(94),           -- Asymmetric Digital Subscriber Loop
                   radsl(95),          -- Rate-Adapt. Digital Subscriber Loop
                   sdsl(96),           -- Symmetric Digital Subscriber Loop
                   vdsl(97),           -- Very H-Speed Digital Subscrib. Loop
                   iso88025CRFPInt(98), -- ISO 802.5 CRFP
                   myrinet(99),        -- Myricom Myrinet
                   voiceEM(100),       -- voice recEive and transMit
                   voiceFXO(101),      -- voice Foreign Exchange Office
                   voiceFXS(102),      -- voice Foreign Exchange Station
                   voiceEncap(103),    -- voice encapsulation
                   voiceOverIp(104),   -- voice over IP encapsulation
                   atmDxi(105),        -- ATM DXI
                   atmFuni(106),       -- ATM FUNI
		   atmIma (107),       -- ATM IMA		   
                   pppMultilinkBundle(108), -- PPP Multilink Bundle
                   ipOverCdlc (109),   -- IBM ipOverCdlc
		   ipOverClaw (110),   -- IBM Common Link Access to Workstn
                   stackToStack (111), -- IBM stackToStack
                   virtualIpAddress (112), -- IBM VIPA
		   mpc (113),          -- IBM multi-protocol channel support
		   ipOverAtm (114),    -- IBM ipOverAtm
		   iso88025Fiber (115), -- ISO 802.5j Fiber Token Ring
		   tdlc (116),	       -- IBM twinaxial data link control
		   gigabitEthernet (117), -- Gigabit Ethernet
		   hdlc (118),         -- HDLC
		   lapf (119),	       -- LAP F
		   v37 (120),	       -- V.37
		   x25mlp (121),       -- Multi-Link Protocol
		   x25huntGroup (122), -- X25 Hunt Group
		   trasnpHdlc (123),   -- Transp HDLC
		   interleave (124),   -- Interleave channel
		   fast (125),         -- Fast channel
		   ip (126),	       -- IP (for APPN HPR in IP networks)
		   docsCableMaclayer (127),  -- CATV Mac Layer
		   docsCableDownstream (128), -- CATV Downstream interface
		   docsCableUpstream (129),  -- CATV Upstream interface
		   a12MppSwitch (130), -- Avalon Parallel Processor
		   tunnel (131),       -- Encapsulation interface
		   coffee (132),       -- coffee pot
		   ces (133),          -- Circuit Emulation Service
		   atmSubInterface (134), -- ATM Sub Interface
		   l2vlan (135),       -- Layer 2 Virtual LAN using 802.1Q
		   l3ipvlan (136),     -- Layer 3 Virtual LAN using IP
		   l3ipxvlan (137),    -- Layer 3 Virtual LAN using IPX
		   digitalPowerline (138), -- IP over Power Lines	
		   mediaMailOverIp (139), -- Multimedia Mail over IP
		   dtm (140),        -- Dynamic syncronous Transfer Mode
		   dcn (141),    -- Data Communications Network
		   ipForward (142),    -- IP Forwarding Interface
		   msdsl (143),       -- Multi-rate Symmetric DSL
		   ieee1394 (144), -- IEEE1394 High Performance Serial Bus
		   if-gsn (145),       --   HIPPI-6400 
		   dvbRccMacLayer (146), -- DVB-RCC MAC Layer
		   dvbRccDownstream (147),  -- DVB-RCC Downstream Channel
		   dvbRccUpstream (148),  -- DVB-RCC Upstream Channel
		   atmVirtual (149),   -- ATM Virtual Interface
		   mplsTunnel (150),   -- MPLS Tunnel Virtual Interface
		   srp (151),	-- Spatial Reuse Protocol	
		   voiceOverAtm (152),  -- Voice Over ATM
		   voiceOverFrameRelay (153),   -- Voice Over Frame Relay 
		   idsl (154),		-- Digital Subscriber Loop over ISDN
		   compositeLink (155),  -- Avici Composite Link Interface
		   ss7SigLink (156),     -- SS7 Signaling Link 
		   propWirelessP2P (157),  --  Prop. P2P wireless interface
		   frForward (158),    -- Frame Forward Interface
		   rfc1483 (159),	-- Multiprotocol over ATM AAL5
		   usb (160),		-- USB Interface
		   ieee8023adLag (161),  -- IEEE 802.3ad Link Aggregate
                   bgppolicyaccounting (162), -- BGP Policy Accounting
                   frf16MfrBundle (163), -- FRF .16 Multilink Frame Relay 
                   h323Gatekeeper (164), -- H323 Gatekeeper
                   h323Proxy (165), -- H323 Voice and Video Proxy
                   mpls (166), -- MPLS                   
                   mfSigLink (167), -- Multi-frequency signaling link
                   hdsl2 (168), -- High Bit-Rate DSL - 2nd generation
                   shdsl (169), -- Multirate HDSL2
                   ds1FDL (170), -- Facility Data Link 4Kbps on a DS1
                   pos (171), -- Packet over SONET/SDH Interface
                   dvbAsiIn (172), -- DVB-ASI Input
                   dvbAsiOut (173), -- DVB-ASI Output 
                   plc (174), -- Power Line Communtications
                   nfas (175), -- Non Facility Associated Signaling
                   tr008 (176), -- TR008
                   gr303RDT (177), -- Remote Digital Terminal
                   gr303IDT (178), -- Integrated Digital Terminal
                   isup (179), -- ISUP
                   propDocsWirelessMaclayer (180), -- prop/Maclayer
                   propDocsWirelessDownstream (181), -- prop/Downstream
                   propDocsWirelessUpstream (182), -- prop/Upstream
                   hiperlan2 (183), -- HIPERLAN Type 2 Radio Interface
                   propBWAp2Mp (184), -- PropBroadbandWirelessAccesspt2multipt
                   sonetOverheadChannel (185), -- SONET Overhead Channel
                   digitalWrapperOverheadChannel (186), -- Digital Wrapper
                   aal2 (187), -- ATM adaptation layer 2
                   radioMAC (188), -- MAC layer over radio links
                   atmRadio (189), -- ATM over radio links   
                   imt (190), -- Inter Machine Trunks
                   mvl (191), -- Multiple Virtual Lines DSL
                   reachDSL (192), -- Long Reach DSL
                   frDlciEndPt (193), -- Frame Relay DLCI End Point
                   atmVciEndPt (194), -- ATM VCI End Point
                   opticalChannel (195), -- Optical Channel
                   opticalTransport (196), -- Optical Transport
                   propAtm (197), --  Proprietary ATM       
                   voiceOverCable (198), -- Voice Over Cable Interface
                   infiniband (199), -- Infiniband
                   teLink (200), -- TE Link
                   q2931 (201), -- Q.2931
                   virtualTg (202), -- Virtual Trunk Group
                   sipTg (203), -- SIP Trunk Group
                   sipSig (204), -- SIP Signaling   
                   docsCableUpstreamChannel (205), -- CATV Upstream Channel
                   econet (206), -- Acorn Econet
                   pon155 (207), -- FSAN 155Mb Symetrical PON interface
                   pon622 (208), -- FSAN622Mb Symetrical PON interface
                   bridge (209), -- Transparent bridge interface
                   linegroup (210), -- Interface common to multiple lines		   
                   voiceEMFGD (211), -- voice E&M Feature Group D
                   voiceFGDEANA (212), -- voice FGD Exchange Access North American
                   voiceDID (213), -- voice Direct Inward Dialing
                   mpegTransport (214), -- MPEG transport interface
                   sixToFour (215), -- 6to4 interface
                   gtp (216), -- GTP (GPRS Tunneling Protocol)
                   pdnEtherLoop1 (217), -- Paradyne EtherLoop 1
                   pdnEtherLoop2 (218), -- Paradyne EtherLoop 2
                   opticalChannelGroup (219), -- Optical Channel Group
                   homepna (220), -- HomePNA ITU-T G.989				   
                   gfp (221), -- Generic Framing Procedure (GFP)
                   ciscoISLvlan (222), -- Layer 2 Virtual LAN using Cisco ISL
                   actelisMetaLOOP (223), -- Acteleis proprietary MetaLOOP High Speed Link 
                   fcipLink (224) -- FCIP Link 
    			   }

   END










IP-MIB DEFINITIONS ::= BEGIN

IMPORTS
    MODULE-IDENTITY, OBJECT-TYPE, Integer32,
    Counter32, IpAddress, mib-2        FROM SNMPv2-SMI
    PhysAddress                        FROM SNMPv2-TC
    MODULE-COMPLIANCE, OBJECT-GROUP    FROM SNMPv2-CONF;

ipMIB MODULE-IDENTITY
    LAST-UPDATED "9411010000Z"
    ORGANIZATION "IETF SNMPv2 Working Group"
    CONTACT-INFO
            "        Keith McCloghrie

             Postal: Cisco Systems, Inc.
                     170 West Tasman Drive
                     San Jose, CA  95134-1706
                     US

             Phone:  +1 408 526 5260
             Email:  kzm@cisco.com"


    DESCRIPTION
            "The MIB module for managing IP and ICMP implementations,
            but excluding their management of IP routes."
    REVISION      "9103310000Z"
    DESCRIPTION
            "The initial revision of this MIB module was part of MIB-
            II."
    ::= { mib-2 48}

-- the IP group

ip       OBJECT IDENTIFIER ::= { mib-2 4 }

ipForwarding OBJECT-TYPE
    SYNTAX      INTEGER {
                    forwarding(1),    -- acting as a router
                    notForwarding(2)  -- NOT acting as a router
                }
    MAX-ACCESS  read-write
    STATUS      current
    DESCRIPTION
            "The indication of whether this entity is acting as an IP
            router in respect to the forwarding of datagrams received
            by, but not addressed to, this entity.  IP routers forward
            datagrams.  IP hosts do not (except those source-routed via
            the host)."
    ::= { ip 1 }

ipDefaultTTL OBJECT-TYPE
    SYNTAX      INTEGER (1..255)
    MAX-ACCESS  read-write
    STATUS      current
    DESCRIPTION
            "The default value inserted into the Time-To-Live field of
            the IP header of datagrams originated at this entity,
            whenever a TTL value is not supplied by the transport layer
            protocol."
    ::= { ip 2 }

ipInReceives OBJECT-TYPE
    SYNTAX      Counter32
    MAX-ACCESS  read-only
    STATUS      current
    DESCRIPTION
            "The total number of input datagrams received from
            interfaces, including those received in error."
    ::= { ip 3 }


ipInHdrErrors OBJECT-TYPE
    SYNTAX      Counter32
    MAX-ACCESS  read-only
    STATUS      current
    DESCRIPTION
            "The number of input datagrams discarded due to errors in
            their IP headers, including bad checksums, version number
            mismatch, other format errors, time-to-live exceeded, errors
            discovered in processing their IP options, etc."
    ::= { ip 4 }

ipInAddrErrors OBJECT-TYPE
    SYNTAX      Counter32
    MAX-ACCESS  read-only
    STATUS      current
    DESCRIPTION
            "The number of input datagrams discarded because the IP
            address in their IP header's destination field was not a
            valid address to be received at this entity.  This count
            includes invalid addresses (e.g., 0.0.0.0) and addresses of
            unsupported Classes (e.g., Class E).  For entities which are
            not IP routers and therefore do not forward datagrams, this
            counter includes datagrams discarded because the destination
            address was not a local address."
    ::= { ip 5 }

ipForwDatagrams OBJECT-TYPE
    SYNTAX      Counter32
    MAX-ACCESS  read-only
    STATUS      current
    DESCRIPTION
            "The number of input datagrams for which this entity was not
            their final IP destination, as a result of which an attempt
            was made to find a route to forward them to that final
            destination.  In entities which do not act as IP routers,
            this counter will include only those packets which were
            Source-Routed via this entity, and the Source-Route option
            processing was successful."
    ::= { ip 6 }

ipInUnknownProtos OBJECT-TYPE
    SYNTAX      Counter32
    MAX-ACCESS  read-only
    STATUS      current
    DESCRIPTION
            "The number of locally-addressed datagrams received
            successfully but discarded because of an unknown or
            unsupported protocol."


    ::= { ip 7 }

ipInDiscards OBJECT-TYPE
    SYNTAX      Counter32
    MAX-ACCESS  read-only
    STATUS      current
    DESCRIPTION
            "The number of input IP datagrams for which no problems were
            encountered to prevent their continued processing, but which
            were discarded (e.g., for lack of buffer space).  Note that
            this counter does not include any datagrams discarded while
            awaiting re-assembly."
    ::= { ip 8 }

ipInDelivers OBJECT-TYPE
    SYNTAX      Counter32
    MAX-ACCESS  read-only
    STATUS      current
    DESCRIPTION
            "The total number of input datagrams successfully delivered
            to IP user-protocols (including ICMP)."
    ::= { ip 9 }

ipOutRequests OBJECT-TYPE
    SYNTAX      Counter32
    MAX-ACCESS  read-only
    STATUS      current
    DESCRIPTION
            "The total number of IP datagrams which local IP user-
            protocols (including ICMP) supplied to IP in requests for
            transmission.  Note that this counter does not include any
            datagrams counted in ipForwDatagrams."
    ::= { ip 10 }

ipOutDiscards OBJECT-TYPE
    SYNTAX      Counter32
    MAX-ACCESS  read-only
    STATUS      current
    DESCRIPTION
            "The number of output IP datagrams for which no problem was
            encountered to prevent their transmission to their
            destination, but which were discarded (e.g., for lack of
            buffer space).  Note that this counter would include
            datagrams counted in ipForwDatagrams if any such packets met
            this (discretionary) discard criterion."
    ::= { ip 11 }

ipOutNoRoutes OBJECT-TYPE


    SYNTAX      Counter32
    MAX-ACCESS  read-only
    STATUS      current
    DESCRIPTION
            "The number of IP datagrams discarded because no route could
            be found to transmit them to their destination.  Note that
            this counter includes any packets counted in ipForwDatagrams
            which meet this `no-route' criterion.  Note that this
            includes any datagrams which a host cannot route because all
            of its default routers are down."
    ::= { ip 12 }

ipReasmTimeout OBJECT-TYPE
    SYNTAX      Integer32
    MAX-ACCESS  read-only
    STATUS      current
    DESCRIPTION
            "The maximum number of seconds which received fragments are
            held while they are awaiting reassembly at this entity."
    ::= { ip 13 }

ipReasmReqds OBJECT-TYPE
    SYNTAX      Counter32
    MAX-ACCESS  read-only
    STATUS      current
    DESCRIPTION
            "The number of IP fragments received which needed to be
            reassembled at this entity."
    ::= { ip 14 }

ipReasmOKs OBJECT-TYPE
    SYNTAX      Counter32
    MAX-ACCESS  read-only
    STATUS      current
    DESCRIPTION
            "The number of IP datagrams successfully re-assembled."
    ::= { ip 15 }

ipReasmFails OBJECT-TYPE
    SYNTAX      Counter32
    MAX-ACCESS  read-only
    STATUS      current
    DESCRIPTION
            "The number of failures detected by the IP re-assembly
            algorithm (for whatever reason: timed out, errors, etc).
            Note that this is not necessarily a count of discarded IP
            fragments since some algorithms (notably the algorithm in
            RFC 815) can lose track of the number of fragments by


            combining them as they are received."
    ::= { ip 16 }

ipFragOKs OBJECT-TYPE
    SYNTAX      Counter32
    MAX-ACCESS  read-only
    STATUS      current
    DESCRIPTION
            "The number of IP datagrams that have been successfully
            fragmented at this entity."
    ::= { ip 17 }

ipFragFails OBJECT-TYPE
    SYNTAX      Counter32
    MAX-ACCESS  read-only
    STATUS      current
    DESCRIPTION
            "The number of IP datagrams that have been discarded because
            they needed to be fragmented at this entity but could not
            be, e.g., because their Don't Fragment flag was set."
    ::= { ip 18 }

ipFragCreates OBJECT-TYPE
    SYNTAX      Counter32
    MAX-ACCESS  read-only
    STATUS      current
    DESCRIPTION
            "The number of IP datagram fragments that have been
            generated as a result of fragmentation at this entity."
    ::= { ip 19 }

-- the IP address table

ipAddrTable OBJECT-TYPE
    SYNTAX      SEQUENCE OF IpAddrEntry
    MAX-ACCESS  not-accessible
    STATUS      current
    DESCRIPTION
            "The table of addressing information relevant to this
            entity's IP addresses."
    ::= { ip 20 }

ipAddrEntry OBJECT-TYPE
    SYNTAX      IpAddrEntry
    MAX-ACCESS  not-accessible
    STATUS      current
    DESCRIPTION
            "The addressing information for one of this entity's IP


            addresses."
    INDEX      { ipAdEntAddr }
    ::= { ipAddrTable 1 }

IpAddrEntry ::= SEQUENCE {
        ipAdEntAddr          IpAddress,
        ipAdEntIfIndex       INTEGER,
        ipAdEntNetMask       IpAddress,
        ipAdEntBcastAddr     INTEGER,
        ipAdEntReasmMaxSize  INTEGER
    }

ipAdEntAddr OBJECT-TYPE
    SYNTAX      IpAddress
    MAX-ACCESS  read-only
    STATUS      current
    DESCRIPTION
            "The IP address to which this entry's addressing information
            pertains."
    ::= { ipAddrEntry 1 }

ipAdEntIfIndex OBJECT-TYPE
    SYNTAX      INTEGER (1..2147483647)
    MAX-ACCESS  read-only
    STATUS      current
    DESCRIPTION
            "The index value which uniquely identifies the interface to
            which this entry is applicable.  The interface identified by
            a particular value of this index is the same interface as
            identified by the same value of RFC 1573's ifIndex."
    ::= { ipAddrEntry 2 }

ipAdEntNetMask OBJECT-TYPE
    SYNTAX      IpAddress
    MAX-ACCESS  read-only
    STATUS      current
    DESCRIPTION
            "The subnet mask associated with the IP address of this
            entry.  The value of the mask is an IP address with all the
            network bits set to 1 and all the hosts bits set to 0."
    ::= { ipAddrEntry 3 }

ipAdEntBcastAddr OBJECT-TYPE
    SYNTAX      INTEGER (0..1)
    MAX-ACCESS  read-only
    STATUS      current
    DESCRIPTION
            "The value of the least-significant bit in the IP broadcast


            address used for sending datagrams on the (logical)
            interface associated with the IP address of this entry.  For
            example, when the Internet standard all-ones broadcast
            address is used, the value will be 1.  This value applies to
            both the subnet and network broadcasts addresses used by the
            entity on this (logical) interface."
    ::= { ipAddrEntry 4 }

ipAdEntReasmMaxSize OBJECT-TYPE
    SYNTAX      INTEGER (0..65535)
    MAX-ACCESS  read-only
    STATUS      current
    DESCRIPTION
            "The size of the largest IP datagram which this entity can
            re-assemble from incoming IP fragmented datagrams received
            on this interface."
    ::= { ipAddrEntry 5 }

-- ipRouteTable  ::=   { ip 21 }        obsolete

-- the IP Address Translation table

-- The Address Translation tables contain the IpAddress to
-- "physical" address equivalences.  Some interfaces do not
-- use translation tables for determining address
-- equivalences (e.g., DDN-X.25 has an algorithmic method);
-- if all interfaces are of this type, then the Address
-- Translation table is empty, i.e., has zero entries.

ipNetToMediaTable OBJECT-TYPE
    SYNTAX      SEQUENCE OF IpNetToMediaEntry
    MAX-ACCESS  not-accessible
    STATUS      current
    DESCRIPTION
            "The IP Address Translation table used for mapping from IP
            addresses to physical addresses."
    ::= { ip 22 }

ipNetToMediaEntry OBJECT-TYPE
    SYNTAX      IpNetToMediaEntry
    MAX-ACCESS  not-accessible
    STATUS      current
    DESCRIPTION
            "Each entry contains one IpAddress to `physical' address
            equivalence."
    INDEX       { ipNetToMediaIfIndex,
                  ipNetToMediaNetAddress }


    ::= { ipNetToMediaTable 1 }

IpNetToMediaEntry ::= SEQUENCE {
        ipNetToMediaIfIndex      INTEGER,
        ipNetToMediaPhysAddress  PhysAddress,
        ipNetToMediaNetAddress   IpAddress,
        ipNetToMediaType         INTEGER
    }

ipNetToMediaIfIndex OBJECT-TYPE
    SYNTAX      INTEGER (1..2147483647)
    MAX-ACCESS  read-create
    STATUS      current
    DESCRIPTION
            "The interface on which this entry's equivalence is
            effective.  The interface identified by a particular value
            of this index is the same interface as identified by the
            same value of RFC 1573's ifIndex."
    ::= { ipNetToMediaEntry 1 }

ipNetToMediaPhysAddress OBJECT-TYPE
    SYNTAX      PhysAddress
    MAX-ACCESS  read-create
    STATUS      current
    DESCRIPTION
            "The media-dependent `physical' address."
    ::= { ipNetToMediaEntry 2 }

ipNetToMediaNetAddress OBJECT-TYPE
    SYNTAX      IpAddress
    MAX-ACCESS  read-create
    STATUS      current
    DESCRIPTION
            "The IpAddress corresponding to the media-dependent
            `physical' address."
    ::= { ipNetToMediaEntry 3 }

ipNetToMediaType OBJECT-TYPE
    SYNTAX      INTEGER {
                other(1),        -- none of the following
                invalid(2),      -- an invalidated mapping
                dynamic(3),
                static(4)
            }
    MAX-ACCESS  read-create
    STATUS      current
    DESCRIPTION
            "The type of mapping.


            Setting this object to the value invalid(2) has the effect
            of invalidating the corresponding entry in the
            ipNetToMediaTable.  That is, it effectively disassociates
            the interface identified with said entry from the mapping
            identified with said entry.  It is an implementation-
            specific matter as to whether the agent removes an
            invalidated entry from the table.  Accordingly, management
            stations must be prepared to receive tabular information
            from agents that corresponds to entries not currently in
            use.  Proper interpretation of such entries requires
            examination of the relevant ipNetToMediaType object."
    ::= { ipNetToMediaEntry 4 }

ipRoutingDiscards OBJECT-TYPE
    SYNTAX      Counter32
    MAX-ACCESS  read-only
    STATUS      current
    DESCRIPTION
            "The number of routing entries which were chosen to be
            discarded even though they are valid.  One possible reason
            for discarding such an entry could be to free-up buffer
            space for other routing entries."
    ::= { ip 23 }

-- the ICMP group

icmp     OBJECT IDENTIFIER ::= { mib-2 5 }

icmpInMsgs OBJECT-TYPE
    SYNTAX      Counter32
    MAX-ACCESS  read-only
    STATUS      current
    DESCRIPTION
            "The total number of ICMP messages which the entity
            received.  Note that this counter includes all those counted
            by icmpInErrors."
    ::= { icmp 1 }

icmpInErrors OBJECT-TYPE
    SYNTAX      Counter32
    MAX-ACCESS  read-only
    STATUS      current
    DESCRIPTION
            "The number of ICMP messages which the entity received but
            determined as having ICMP-specific errors (bad ICMP
            checksums, bad length, etc.)."
    ::= { icmp 2 }


icmpInDestUnreachs OBJECT-TYPE
    SYNTAX      Counter32
    MAX-ACCESS  read-only
    STATUS      current
    DESCRIPTION
            "The number of ICMP Destination Unreachable messages
            received."
    ::= { icmp 3 }

icmpInTimeExcds OBJECT-TYPE
    SYNTAX      Counter32
    MAX-ACCESS  read-only
    STATUS      current
    DESCRIPTION
            "The number of ICMP Time Exceeded messages received."
    ::= { icmp 4 }

icmpInParmProbs OBJECT-TYPE
    SYNTAX      Counter32
    MAX-ACCESS  read-only
    STATUS      current
    DESCRIPTION
            "The number of ICMP Parameter Problem messages received."
    ::= { icmp 5 }

icmpInSrcQuenchs OBJECT-TYPE
    SYNTAX      Counter32
    MAX-ACCESS  read-only
    STATUS      current
    DESCRIPTION
            "The number of ICMP Source Quench messages received."
    ::= { icmp 6 }

icmpInRedirects OBJECT-TYPE
    SYNTAX      Counter32
    MAX-ACCESS  read-only
    STATUS      current
    DESCRIPTION
            "The number of ICMP Redirect messages received."
    ::= { icmp 7 }

icmpInEchos OBJECT-TYPE
    SYNTAX      Counter32
    MAX-ACCESS  read-only
    STATUS      current
    DESCRIPTION
            "The number of ICMP Echo (request) messages received."
    ::= { icmp 8 }


icmpInEchoReps OBJECT-TYPE
    SYNTAX      Counter32
    MAX-ACCESS  read-only
    STATUS      current
    DESCRIPTION
            "The number of ICMP Echo Reply messages received."
    ::= { icmp 9 }

icmpInTimestamps OBJECT-TYPE
    SYNTAX      Counter32
    MAX-ACCESS  read-only
    STATUS      current
    DESCRIPTION
            "The number of ICMP Timestamp (request) messages received."
    ::= { icmp 10 }

icmpInTimestampReps OBJECT-TYPE
    SYNTAX      Counter32
    MAX-ACCESS  read-only
    STATUS      current
    DESCRIPTION
            "The number of ICMP Timestamp Reply messages received."
    ::= { icmp 11 }

icmpInAddrMasks OBJECT-TYPE
    SYNTAX      Counter32
    MAX-ACCESS  read-only
    STATUS      current
    DESCRIPTION
            "The number of ICMP Address Mask Request messages received."
    ::= { icmp 12 }

icmpInAddrMaskReps OBJECT-TYPE
    SYNTAX      Counter32
    MAX-ACCESS  read-only
    STATUS      current
    DESCRIPTION
            "The number of ICMP Address Mask Reply messages received."
    ::= { icmp 13 }

icmpOutMsgs OBJECT-TYPE
    SYNTAX      Counter32
    MAX-ACCESS  read-only
    STATUS      current
    DESCRIPTION
            "The total number of ICMP messages which this entity
            attempted to send.  Note that this counter includes all
            those counted by icmpOutErrors."


    ::= { icmp 14 }

icmpOutErrors OBJECT-TYPE
    SYNTAX      Counter32
    MAX-ACCESS  read-only
    STATUS      current
    DESCRIPTION
            "The number of ICMP messages which this entity did not send
            due to problems discovered within ICMP such as a lack of
            buffers.  This value should not include errors discovered
            outside the ICMP layer such as the inability of IP to route
            the resultant datagram.  In some implementations there may
            be no types of error which contribute to this counter's
            value."
    ::= { icmp 15 }

icmpOutDestUnreachs OBJECT-TYPE
    SYNTAX      Counter32
    MAX-ACCESS  read-only
    STATUS      current
    DESCRIPTION
            "The number of ICMP Destination Unreachable messages sent."
    ::= { icmp 16 }

icmpOutTimeExcds OBJECT-TYPE
    SYNTAX      Counter32
    MAX-ACCESS  read-only
    STATUS      current
    DESCRIPTION
            "The number of ICMP Time Exceeded messages sent."
    ::= { icmp 17 }

icmpOutParmProbs OBJECT-TYPE
    SYNTAX      Counter32
    MAX-ACCESS  read-only
    STATUS      current
    DESCRIPTION
            "The number of ICMP Parameter Problem messages sent."
    ::= { icmp 18 }

icmpOutSrcQuenchs OBJECT-TYPE
    SYNTAX      Counter32
    MAX-ACCESS  read-only
    STATUS      current
    DESCRIPTION
            "The number of ICMP Source Quench messages sent."
    ::= { icmp 19 }


icmpOutRedirects OBJECT-TYPE
    SYNTAX      Counter32
    MAX-ACCESS  read-only
    STATUS      current
    DESCRIPTION
            "The number of ICMP Redirect messages sent.  For a host,
            this object will always be zero, since hosts do not send
            redirects."
    ::= { icmp 20 }

icmpOutEchos OBJECT-TYPE
    SYNTAX      Counter32
    MAX-ACCESS  read-only
    STATUS      current
    DESCRIPTION
            "The number of ICMP Echo (request) messages sent."
    ::= { icmp 21 }

icmpOutEchoReps OBJECT-TYPE
    SYNTAX      Counter32
    MAX-ACCESS  read-only
    STATUS      current
    DESCRIPTION
            "The number of ICMP Echo Reply messages sent."
    ::= { icmp 22 }

icmpOutTimestamps OBJECT-TYPE
    SYNTAX      Counter32
    MAX-ACCESS  read-only
    STATUS      current
    DESCRIPTION
            "The number of ICMP Timestamp (request) messages sent."
    ::= { icmp 23 }

icmpOutTimestampReps OBJECT-TYPE
    SYNTAX      Counter32
    MAX-ACCESS  read-only
    STATUS      current
    DESCRIPTION
            "The number of ICMP Timestamp Reply messages sent."
    ::= { icmp 24 }

icmpOutAddrMasks OBJECT-TYPE
    SYNTAX      Counter32
    MAX-ACCESS  read-only
    STATUS      current
    DESCRIPTION
            "The number of ICMP Address Mask Request messages sent."


    ::= { icmp 25 }

icmpOutAddrMaskReps OBJECT-TYPE
    SYNTAX      Counter32
    MAX-ACCESS  read-only
    STATUS      current
    DESCRIPTION
            "The number of ICMP Address Mask Reply messages sent."
    ::= { icmp 26 }

-- conformance information

ipMIBConformance OBJECT IDENTIFIER ::= { ipMIB 2 }

ipMIBCompliances OBJECT IDENTIFIER ::= { ipMIBConformance 1 }
ipMIBGroups      OBJECT IDENTIFIER ::= { ipMIBConformance 2 }

-- compliance statements

ipMIBCompliance MODULE-COMPLIANCE
    STATUS  current
    DESCRIPTION
            "The compliance statement for SNMPv2 entities which
            implement IP."
    MODULE  -- this module
        MANDATORY-GROUPS { ipGroup,
                           icmpGroup }
    ::= { ipMIBCompliances 1 }

-- units of conformance

ipGroup OBJECT-GROUP
    OBJECTS   { ipForwarding, ipDefaultTTL, ipInReceives,
                ipInHdrErrors, ipInAddrErrors,
                ipForwDatagrams, ipInUnknownProtos,
                ipInDiscards, ipInDelivers, ipOutRequests,
                ipOutDiscards, ipOutNoRoutes,
                ipReasmTimeout, ipReasmReqds, ipReasmOKs,
                ipReasmFails, ipFragOKs,
                ipFragFails, ipFragCreates,
                ipAdEntAddr, ipAdEntIfIndex, ipAdEntNetMask,
                ipAdEntBcastAddr, ipAdEntReasmMaxSize,
                ipNetToMediaIfIndex, ipNetToMediaPhysAddress,
                ipNetToMediaNetAddress, ipNetToMediaType,
                ipRoutingDiscards }
    STATUS    current
    DESCRIPTION


            "The ip group of objects providing for basic management of
            IP entities, exclusive of the management of IP routes."
    ::= { ipMIBGroups 1 }

icmpGroup OBJECT-GROUP
    OBJECTS   { icmpInMsgs, icmpInErrors,
                icmpInDestUnreachs, icmpInTimeExcds,
                icmpInParmProbs, icmpInSrcQuenchs,
                icmpInRedirects, icmpInEchos,
                icmpInEchoReps, icmpInTimestamps,
                icmpInTimestampReps, icmpInAddrMasks,
                icmpInAddrMaskReps, icmpOutMsgs,
                icmpOutErrors, icmpOutDestUnreachs,
                icmpOutTimeExcds, icmpOutParmProbs,
                icmpOutSrcQuenchs, icmpOutRedirects,
                icmpOutEchos, icmpOutEchoReps,
                icmpOutTimestamps, icmpOutTimestampReps,
                icmpOutAddrMasks, icmpOutAddrMaskReps }
    STATUS    current
    DESCRIPTION
            "The icmp group of objects providing ICMP statistics."
    ::= { ipMIBGroups 2 }

END

ENTITY-MIB DEFINITIONS ::= BEGIN

IMPORTS
    MODULE-IDENTITY, OBJECT-TYPE, mib-2, NOTIFICATION-TYPE
        FROM SNMPv2-SMI
    TDomain, TAddress, TEXTUAL-CONVENTION,
    AutonomousType, RowPointer, TimeStamp, TruthValue
        FROM SNMPv2-TC
    MODULE-COMPLIANCE, OBJECT-GROUP, NOTIFICATION-GROUP
        FROM SNMPv2-CONF
    SnmpAdminString
        FROM SNMP-FRAMEWORK-MIB;

entityMIB MODULE-IDENTITY
    LAST-UPDATED "9912070000Z" -- December 7, 1999
    ORGANIZATION "IETF ENTMIB Working Group"
    CONTACT-INFO
            "        WG E-mail: entmib@cisco.com
                  Subscribe: majordomo@cisco.com
                         msg body: subscribe entmib

                     Keith McCloghrie
                     ENTMIB Working Group Chair
                     Cisco Systems Inc.
                     170 West Tasman Drive
                     San Jose, CA 95134
                     +1 408-526-5260
                     kzm@cisco.com

                     Andy Bierman
                     ENTMIB Working Group Editor
                     Cisco Systems Inc.
                     170 West Tasman Drive
                     San Jose, CA 95134
                     +1 408-527-3711
                     abierman@cisco.com"
    DESCRIPTION
            "The MIB module for representing multiple logical
            entities supported by a single SNMP agent."
    REVISION        "9912070000Z"
    DESCRIPTION
            "Initial Version of Entity MIB (Version 2).
             This revision obsoletes RFC 2037.
             This version published as RFC 2737."
    REVISION        "9610310000Z"
    DESCRIPTION


            "Initial version (version 1), published as
             RFC 2037."
    ::= { mib-2 47 }

entityMIBObjects OBJECT IDENTIFIER ::= { entityMIB 1 }

-- MIB contains four groups
entityPhysical OBJECT IDENTIFIER ::= { entityMIBObjects 1 }
entityLogical  OBJECT IDENTIFIER ::= { entityMIBObjects 2 }
entityMapping  OBJECT IDENTIFIER ::= { entityMIBObjects 3 }
entityGeneral  OBJECT IDENTIFIER ::= { entityMIBObjects 4 }

-- Textual Conventions
PhysicalIndex ::= TEXTUAL-CONVENTION
    STATUS            current
    DESCRIPTION
            "An arbitrary value which uniquely identifies the physical
            entity.  The value should be a small positive integer; index
            values for different physical entities are not necessarily
            contiguous."
    SYNTAX INTEGER (1..2147483647)

PhysicalClass ::= TEXTUAL-CONVENTION
    STATUS            current
    DESCRIPTION
            "An enumerated value which provides an indication of the
            general hardware type of a particular physical entity.
            There are no restrictions as to the number of
            entPhysicalEntries of each entPhysicalClass, which must be
            instantiated by an agent.

            The enumeration 'other' is applicable if the physical entity
            class is known, but does not match any of the supported
            values.

            The enumeration 'unknown' is applicable if the physical
            entity class is unknown to the agent.

            The enumeration 'chassis' is applicable if the physical
            entity class is an overall container for networking
            equipment.  Any class of physical entity except a stack may
            be contained within a chassis, and a chassis may only be
            contained within a stack.

            The enumeration 'backplane' is applicable if the physical
            entity class is some sort of device for aggregating and
            forwarding networking traffic, such as a shared backplane in
            a modular ethernet switch.  Note that an agent may model a


            backplane as a single physical entity, which is actually
            implemented as multiple discrete physical components (within
            a chassis or stack).

            The enumeration 'container' is applicable if the physical
            entity class is capable of containing one or more removable
            physical entities, possibly of different types. For example,
            each (empty or full) slot in a chassis will be modeled as a
            container. Note that all removable physical entities should
            be modeled within a container entity, such as field-
            replaceable modules, fans, or power supplies.  Note that all
            known containers should be modeled by the agent, including
            empty containers.

            The enumeration 'powerSupply' is applicable if the physical
            entity class is a power-supplying component.

            The enumeration 'fan' is applicable if the physical entity
            class is a fan or other heat-reduction component.

            The enumeration 'sensor' is applicable if the physical
            entity class is some sort of sensor, such as a temperature
            sensor within a router chassis.

            The enumeration 'module' is applicable if the physical
            entity class is some sort of self-contained sub-system.  If
            it is removable, then it should be modeled within a
            container entity, otherwise it should be modeled directly
            within another physical entity (e.g., a chassis or another
            module).

            The enumeration 'port' is applicable if the physical entity
            class is some sort of networking port, capable of receiving
            and/or transmitting networking traffic.

            The enumeration 'stack' is applicable if the physical entity
            class is some sort of super-container (possibly virtual),
            intended to group together multiple chassis entities.  A
            stack may be realized by a 'virtual' cable, a real
            interconnect cable, attached to multiple chassis, or may in
            fact be comprised of multiple interconnect cables. A stack
            should not be modeled within any other physical entities,
            but a stack may be contained within another stack.  Only
            chassis entities should be contained within a stack."
    SYNTAX      INTEGER  {
       other(1),
       unknown(2),
       chassis(3),


       backplane(4),
       container(5),     -- e.g., chassis slot or daughter-card holder
       powerSupply(6),
       fan(7),
       sensor(8),
       module(9),        -- e.g., plug-in card or daughter-card
       port(10),
       stack(11)         -- e.g., stack of multiple chassis entities
    }

SnmpEngineIdOrNone ::= TEXTUAL-CONVENTION
    STATUS            current
    DESCRIPTION
            "A specially formatted SnmpEngineID string for use with the
            Entity MIB.

            If an instance of an object of SYNTAX SnmpEngineIdOrNone has
            a non-zero length, then the object encoding and semantics
            are defined by the SnmpEngineID textual convention (see RFC
            2571 [RFC2571]).

            If an instance of an object of SYNTAX SnmpEngineIdOrNone
            contains a zero-length string, then no appropriate
            SnmpEngineID is associated with the logical entity (i.e.,
            SNMPv3 not supported)."
    SYNTAX OCTET STRING (SIZE(0..32)) -- empty string or SnmpEngineID

--           The Physical Entity Table
entPhysicalTable OBJECT-TYPE
    SYNTAX      SEQUENCE OF EntPhysicalEntry
    MAX-ACCESS  not-accessible
    STATUS      current
    DESCRIPTION
            "This table contains one row per physical entity.  There is
            always at least one row for an 'overall' physical entity."
    ::= { entityPhysical 1 }

entPhysicalEntry       OBJECT-TYPE
    SYNTAX      EntPhysicalEntry
    MAX-ACCESS  not-accessible
    STATUS      current
    DESCRIPTION
            "Information about a particular physical entity.

            Each entry provides objects (entPhysicalDescr,
            entPhysicalVendorType, and entPhysicalClass) to help an NMS
            identify and characterize the entry, and objects
            (entPhysicalContainedIn and entPhysicalParentRelPos) to help


            an NMS relate the particular entry to other entries in this
            table."
    INDEX   { entPhysicalIndex }
    ::= { entPhysicalTable 1 }

EntPhysicalEntry ::= SEQUENCE {
      entPhysicalIndex          PhysicalIndex,
      entPhysicalDescr          SnmpAdminString,
      entPhysicalVendorType     AutonomousType,
      entPhysicalContainedIn    INTEGER,
      entPhysicalClass          PhysicalClass,
      entPhysicalParentRelPos   INTEGER,
      entPhysicalName           SnmpAdminString,
      entPhysicalHardwareRev    SnmpAdminString,
      entPhysicalFirmwareRev    SnmpAdminString,
      entPhysicalSoftwareRev    SnmpAdminString,
      entPhysicalSerialNum      SnmpAdminString,
      entPhysicalMfgName        SnmpAdminString,
      entPhysicalModelName      SnmpAdminString,
      entPhysicalAlias          SnmpAdminString,
      entPhysicalAssetID        SnmpAdminString,
      entPhysicalIsFRU          TruthValue
}

entPhysicalIndex    OBJECT-TYPE
    SYNTAX      PhysicalIndex
    MAX-ACCESS  not-accessible
    STATUS      current
    DESCRIPTION
            "The index for this entry."
    ::= { entPhysicalEntry 1 }

entPhysicalDescr OBJECT-TYPE
    SYNTAX      SnmpAdminString
    MAX-ACCESS  read-only
    STATUS      current
    DESCRIPTION
            "A textual description of physical entity.  This object
            should contain a string which identifies the manufacturer's
            name for the physical entity, and should be set to a
            distinct value for each version or model of the physical
            entity. "
    ::= { entPhysicalEntry 2 }

entPhysicalVendorType OBJECT-TYPE
    SYNTAX      AutonomousType
    MAX-ACCESS  read-only
    STATUS      current


    DESCRIPTION
            "An indication of the vendor-specific hardware type of the
            physical entity.  Note that this is different from the
            definition of MIB-II's sysObjectID.

            An agent should set this object to a enterprise-specific
            registration identifier value indicating the specific
            equipment type in detail.  The associated instance of
            entPhysicalClass is used to indicate the general type of
            hardware device.

            If no vendor-specific registration identifier exists for
            this physical entity, or the value is unknown by this agent,
            then the value { 0 0 } is returned."
    ::= { entPhysicalEntry 3 }

entPhysicalContainedIn OBJECT-TYPE
    SYNTAX      INTEGER (0..2147483647)
    MAX-ACCESS  read-only
    STATUS      current
    DESCRIPTION
            "The value of entPhysicalIndex for the physical entity which
            'contains' this physical entity.  A value of zero indicates
            this physical entity is not contained in any other physical
            entity.  Note that the set of 'containment' relationships
            define a strict hierarchy; that is, recursion is not
            allowed.

            In the event a physical entity is contained by more than one
            physical entity (e.g., double-wide modules), this object
            should identify the containing entity with the lowest value
            of entPhysicalIndex."
    ::= { entPhysicalEntry 4 }

entPhysicalClass OBJECT-TYPE
    SYNTAX      PhysicalClass
    MAX-ACCESS  read-only
    STATUS      current
    DESCRIPTION
            "An indication of the general hardware type of the physical
            entity.

            An agent should set this object to the standard enumeration
            value which most accurately indicates the general class of
            the physical entity, or the primary class if there is more
            than one.

            If no appropriate standard registration identifier exists


            for this physical entity, then the value 'other(1)' is
            returned. If the value is unknown by this agent, then the
            value 'unknown(2)' is returned."
    ::= { entPhysicalEntry 5 }

entPhysicalParentRelPos OBJECT-TYPE
    SYNTAX      INTEGER (-1..2147483647)
    MAX-ACCESS  read-only
    STATUS      current
    DESCRIPTION
            "An indication of the relative position of this 'child'
            component among all its 'sibling' components. Sibling
            components are defined as entPhysicalEntries which share the
            same instance values of each of the entPhysicalContainedIn
            and entPhysicalClass objects.

            An NMS can use this object to identify the relative ordering
            for all sibling components of a particular parent
            (identified by the entPhysicalContainedIn instance in each
            sibling entry).

            This value should match any external labeling of the
            physical component if possible. For example, for a container
            (e.g., card slot) labeled as 'slot #3',
            entPhysicalParentRelPos should have the value '3'.  Note
            that the entPhysicalEntry for the module plugged in slot 3
            should have an entPhysicalParentRelPos value of '1'.

            If the physical position of this component does not match
            any external numbering or clearly visible ordering, then
            user documentation or other external reference material
            should be used to determine the parent-relative position. If
            this is not possible, then the the agent should assign a
            consistent (but possibly arbitrary) ordering to a given set
            of 'sibling' components, perhaps based on internal
            representation of the components.

            If the agent cannot determine the parent-relative position
            for some reason, or if the associated value of
            entPhysicalContainedIn is '0', then the value '-1' is
            returned. Otherwise a non-negative integer is returned,
            indicating the parent-relative position of this physical
            entity.

            Parent-relative ordering normally starts from '1' and
            continues to 'N', where 'N' represents the highest
            positioned child entity.  However, if the physical entities
            (e.g., slots) are labeled from a starting position of zero,


            then the first sibling should be associated with a
            entPhysicalParentRelPos value of '0'.  Note that this
            ordering may be sparse or dense, depending on agent
            implementation.

            The actual values returned are not globally meaningful, as
            each 'parent' component may use different numbering
            algorithms. The ordering is only meaningful among siblings
            of the same parent component.

            The agent should retain parent-relative position values
            across reboots, either through algorithmic assignment or use
            of non-volatile storage."
    ::= { entPhysicalEntry 6 }

entPhysicalName OBJECT-TYPE
    SYNTAX      SnmpAdminString
    MAX-ACCESS  read-only
    STATUS      current
    DESCRIPTION
            "The textual name of the physical entity.  The value of this
            object should be the name of the component as assigned by
            the local device and should be suitable for use in commands
            entered at the device's `console'.  This might be a text
            name, such as `console' or a simple component number (e.g.,
            port or module number), such as `1', depending on the
            physical component naming syntax of the device.

            If there is no local name, or this object is otherwise not
            applicable, then this object contains a zero-length string.

            Note that the value of entPhysicalName for two physical
            entities will be the same in the event that the console
            interface does not distinguish between them, e.g., slot-1
            and the card in slot-1."
    ::= { entPhysicalEntry 7 }

entPhysicalHardwareRev    OBJECT-TYPE
    SYNTAX      SnmpAdminString
    MAX-ACCESS  read-only
    STATUS      current
    DESCRIPTION
            "The vendor-specific hardware revision string for the
            physical entity.  The preferred value is the hardware
            revision identifier actually printed on the component itself
            (if present).

            Note that if revision information is stored internally in a


            non-printable (e.g., binary) format, then the agent must
            convert such information to a printable format, in an
            implementation-specific manner.

            If no specific hardware revision string is associated with
            the physical component, or this information is unknown to
            the agent, then this object will contain a zero-length
            string."
    ::= { entPhysicalEntry 8 }

entPhysicalFirmwareRev    OBJECT-TYPE
    SYNTAX      SnmpAdminString
    MAX-ACCESS  read-only
    STATUS      current
    DESCRIPTION
            "The vendor-specific firmware revision string for the
            physical entity.

            Note that if revision information is stored internally in a
            non-printable (e.g., binary) format, then the agent must
            convert such information to a printable format, in an
            implementation-specific manner.

            If no specific firmware programs are associated with the
            physical component, or this information is unknown to the
            agent, then this object will contain a zero-length string."
    ::= { entPhysicalEntry 9 }

entPhysicalSoftwareRev    OBJECT-TYPE
    SYNTAX      SnmpAdminString
    MAX-ACCESS  read-only
    STATUS      current
    DESCRIPTION
            "The vendor-specific software revision string for the
            physical entity.

            Note that if revision information is stored internally in a
            non-printable (e.g., binary) format, then the agent must
            convert such information to a printable format, in an
            implementation-specific manner.

            If no specific software programs are associated with the
            physical component, or this information is unknown to the
            agent, then this object will contain a zero-length string."
    ::= { entPhysicalEntry 10 }

entPhysicalSerialNum   OBJECT-TYPE
    SYNTAX      SnmpAdminString (SIZE (0..32))


    MAX-ACCESS  read-write
    STATUS      current
    DESCRIPTION
            "The vendor-specific serial number string for the physical
            entity.  The preferred value is the serial number string
            actually printed on the component itself (if present).

            On the first instantiation of an physical entity, the value
            of entPhysicalSerialNum associated with that entity is set
            to the correct vendor-assigned serial number, if this
            information is available to the agent.  If a serial number
            is unknown or non-existent, the entPhysicalSerialNum will be
            set to a zero-length string instead.

            Note that implementations which can correctly identify the
            serial numbers of all installed physical entities do not
            need to provide write access to the entPhysicalSerialNum
            object. Agents which cannot provide non-volatile storage for
            the entPhysicalSerialNum strings are not required to
            implement write access for this object.

            Not every physical component will have a serial number, or
            even need one.  Physical entities for which the associated
            value of the entPhysicalIsFRU object is equal to 'false(2)'
            (e.g., the repeater ports within a repeater module), do not
            need their own unique serial number. An agent does not have
            to provide write access for such entities, and may return a
            zero-length string.

            If write access is implemented for an instance of
            entPhysicalSerialNum, and a value is written into the
            instance, the agent must retain the supplied value in the
            entPhysicalSerialNum instance associated with the same
            physical entity for as long as that entity remains
            instantiated. This includes instantiations across all re-
            initializations/reboots of the network management system,
            including those which result in a change of the physical
            entity's entPhysicalIndex value."
    ::= { entPhysicalEntry 11 }

entPhysicalMfgName   OBJECT-TYPE
    SYNTAX      SnmpAdminString
    MAX-ACCESS  read-only
    STATUS      current
    DESCRIPTION
            "The name of the manufacturer of this physical component.
            The preferred value is the manufacturer name string actually
            printed on the component itself (if present).


            Note that comparisons between instances of the
            entPhysicalModelName, entPhysicalFirmwareRev,
            entPhysicalSoftwareRev, and the entPhysicalSerialNum
            objects, are only meaningful amongst entPhysicalEntries with
            the same value of entPhysicalMfgName.

            If the manufacturer name string associated with the physical
            component is unknown to the agent, then this object will
            contain a zero-length string."
    ::= { entPhysicalEntry 12 }

entPhysicalModelName   OBJECT-TYPE
    SYNTAX      SnmpAdminString
    MAX-ACCESS  read-only
    STATUS      current
    DESCRIPTION
            "The vendor-specific model name identifier string associated
            with this physical component.  The preferred value is the
            customer-visible part number, which may be printed on the
            component itself.

            If the model name string associated with the physical
            component is unknown to the agent, then this object will
            contain a zero-length string."
    ::= { entPhysicalEntry 13 }

entPhysicalAlias    OBJECT-TYPE
    SYNTAX      SnmpAdminString (SIZE (0..32))
    MAX-ACCESS  read-write
    STATUS      current
    DESCRIPTION
            "This object is an 'alias' name for the physical entity as
            specified by a network manager, and provides a non-volatile
            'handle' for the physical entity.

            On the first instantiation of an physical entity, the value
            of entPhysicalAlias associated with that entity is set to
            the zero-length string.  However, agent may set the value to
            a locally unique default value, instead of a zero-length
            string.

            If write access is implemented for an instance of
            entPhysicalAlias, and a value is written into the instance,
            the agent must retain the supplied value in the
            entPhysicalAlias instance associated with the same physical
            entity for as long as that entity remains instantiated.
            This includes instantiations across all re-
            initializations/reboots of the network management system,


            including those which result in a change of the physical
            entity's entPhysicalIndex value."
    ::= { entPhysicalEntry 14 }

entPhysicalAssetID OBJECT-TYPE
    SYNTAX      SnmpAdminString (SIZE (0..32))
    MAX-ACCESS  read-write
    STATUS      current
    DESCRIPTION
            "This object is a user-assigned asset tracking identifier
            for the physical entity as specified by a network manager,
            and provides non-volatile storage of this information.

            On the first instantiation of an physical entity, the value
            of entPhysicalAssetID associated with that entity is set to
            the zero-length string.

            Not every physical component will have a asset tracking
            identifier, or even need one.  Physical entities for which
            the associated value of the entPhysicalIsFRU object is equal
            to 'false(2)' (e.g., the repeater ports within a repeater
            module), do not need their own unique asset tracking
            identifier. An agent does not have to provide write access
            for such entities, and may instead return a zero-length
            string.

            If write access is implemented for an instance of
            entPhysicalAssetID, and a value is written into the
            instance, the agent must retain the supplied value in the
            entPhysicalAssetID instance associated with the same
            physical entity for as long as that entity remains
            instantiated.  This includes instantiations across all re-
            initializations/reboots of the network management system,
            including those which result in a change of the physical
            entity's entPhysicalIndex value.

            If no asset tracking information is associated with the
            physical component, then this object will contain a zero-
            length string."
    ::= { entPhysicalEntry 15 }

entPhysicalIsFRU OBJECT-TYPE
    SYNTAX      TruthValue
    MAX-ACCESS  read-only
    STATUS      current
    DESCRIPTION
            "This object indicates whether or not this physical entity
            is considered a 'field replaceable unit' by the vendor.  If


            this object contains the value 'true(1)' then this
            entPhysicalEntry identifies a field replaceable unit.  For
            all entPhysicalEntries which represent components that are
            permanently contained within a field replaceable unit, the
            value 'false(2)' should be returned for this object."

    ::= { entPhysicalEntry 16 }

--           The Logical Entity Table
entLogicalTable OBJECT-TYPE
    SYNTAX      SEQUENCE OF EntLogicalEntry
    MAX-ACCESS  not-accessible
    STATUS      current
    DESCRIPTION
            "This table contains one row per logical entity.  For agents
            which implement more than one naming scope, at least one
            entry must exist. Agents which instantiate all MIB objects
            within a single naming scope are not required to implement
            this table."
    ::= { entityLogical 1 }

entLogicalEntry       OBJECT-TYPE
    SYNTAX      EntLogicalEntry
    MAX-ACCESS  not-accessible
    STATUS      current
    DESCRIPTION
            "Information about a particular logical entity.  Entities
            may be managed by this agent or other SNMP agents (possibly)
            in the same chassis."
    INDEX       { entLogicalIndex }
    ::= { entLogicalTable 1 }

EntLogicalEntry ::= SEQUENCE {
      entLogicalIndex            INTEGER,
      entLogicalDescr            SnmpAdminString,
      entLogicalType             AutonomousType,
      entLogicalCommunity        OCTET STRING,
      entLogicalTAddress         TAddress,
      entLogicalTDomain          TDomain,
      entLogicalContextEngineID  SnmpEngineIdOrNone,
      entLogicalContextName      SnmpAdminString
}

entLogicalIndex OBJECT-TYPE
    SYNTAX      INTEGER (1..2147483647)
    MAX-ACCESS  not-accessible
    STATUS      current
    DESCRIPTION


            "The value of this object uniquely identifies the logical
            entity. The value should be a small positive integer; index
            values for different logical entities are are not
            necessarily contiguous."
    ::= { entLogicalEntry 1 }

entLogicalDescr OBJECT-TYPE
    SYNTAX      SnmpAdminString
    MAX-ACCESS  read-only
    STATUS      current
    DESCRIPTION
            "A textual description of the logical entity.  This object
            should contain a string which identifies the manufacturer's
            name for the logical entity, and should be set to a distinct
            value for each version of the logical entity. "
    ::= { entLogicalEntry 2 }

entLogicalType OBJECT-TYPE
    SYNTAX      AutonomousType
    MAX-ACCESS  read-only
    STATUS      current
    DESCRIPTION
            "An indication of the type of logical entity.  This will
            typically be the OBJECT IDENTIFIER name of the node in the
            SMI's naming hierarchy which represents the major MIB
            module, or the majority of the MIB modules, supported by the
            logical entity.  For example:
               a logical entity of a regular host/router -> mib-2
               a logical entity of a 802.1d bridge -> dot1dBridge
               a logical entity of a 802.3 repeater -> snmpDot3RptrMgmt
            If an appropriate node in the SMI's naming hierarchy cannot
            be identified, the value 'mib-2' should be used."
    ::= { entLogicalEntry 3 }

entLogicalCommunity OBJECT-TYPE
    SYNTAX      OCTET STRING (SIZE (0..255))
    MAX-ACCESS  read-only
    STATUS      deprecated
    DESCRIPTION
            "An SNMPv1 or SNMPv2C community-string which can be used to
            access detailed management information for this logical
            entity.  The agent should allow read access with this
            community string (to an appropriate subset of all managed
            objects) and may also return a community string based on the
            privileges of the request used to read this object.  Note
            that an agent may return a community string with read-only
            privileges, even if this object is accessed with a read-
            write community string. However, the agent must take care


            not to return a community string which allows more
            privileges than the community string used to access this
            object.

            A compliant SNMP agent may wish to conserve naming scopes by
            representing multiple logical entities in a single 'default'
            naming scope.  This is possible when the logical entities
            represented by the same value of entLogicalCommunity have no
            object instances in common.  For example, 'bridge1' and
            'repeater1' may be part of the main naming scope, but at
            least one additional community string is needed to represent
            'bridge2' and 'repeater2'.

            Logical entities 'bridge1' and 'repeater1' would be
            represented by sysOREntries associated with the 'default'
            naming scope.

            For agents not accessible via SNMPv1 or SNMPv2C, the value
            of this object is the empty string.  This object may also
            contain an empty string if a community string has not yet
            been assigned by the agent, or no community string with
            suitable access rights can be returned for a particular SNMP
            request.

            Note that this object is deprecated. Agents which implement
            SNMPv3 access should use the entLogicalContextEngineID and
            entLogicalContextName objects to identify the context
            associated with each logical entity.  SNMPv3 agents may
            return a zero-length string for this object, or may continue
            to return a community string (e.g., tri-lingual agent
            support)."
    ::= { entLogicalEntry 4 }

entLogicalTAddress OBJECT-TYPE
    SYNTAX      TAddress
    MAX-ACCESS  read-only
    STATUS      current
    DESCRIPTION
            "The transport service address by which the logical entity
            receives network management traffic, formatted according to
            the corresponding value of entLogicalTDomain.

            For snmpUDPDomain, a TAddress is 6 octets long, the initial
            4 octets containing the IP-address in network-byte order and
            the last 2 containing the UDP port in network-byte order.
            Consult 'Transport Mappings for Version 2 of the Simple
            Network Management Protocol' (RFC 1906 [RFC1906]) for
            further information on snmpUDPDomain."


    ::= { entLogicalEntry 5 }

entLogicalTDomain OBJECT-TYPE
    SYNTAX      TDomain
    MAX-ACCESS  read-only
    STATUS      current
    DESCRIPTION
            "Indicates the kind of transport service by which the
            logical entity receives network management traffic.
            Possible values for this object are presently found in the
            Transport Mappings for SNMPv2 document (RFC 1906
            [RFC1906])."
    ::= { entLogicalEntry 6 }

entLogicalContextEngineID    OBJECT-TYPE
    SYNTAX      SnmpEngineIdOrNone
    MAX-ACCESS  read-only
    STATUS      current
    DESCRIPTION
            "The authoritative contextEngineID that can be used to send
            an SNMP message concerning information held by this logical
            entity, to the address specified by the associated
            'entLogicalTAddress/entLogicalTDomain' pair.

            This object, together with the associated
            entLogicalContextName object, defines the context associated
            with a particular logical entity, and allows access to SNMP
            engines identified by a contextEngineId and contextName
            pair.

            If no value has been configured by the agent, a zero-length
            string is returned, or the agent may choose not to
            instantiate this object at all."
    ::= { entLogicalEntry 7 }

entLogicalContextName    OBJECT-TYPE
    SYNTAX      SnmpAdminString
    MAX-ACCESS  read-only
    STATUS      current
    DESCRIPTION
            "The contextName that can be used to send an SNMP message
            concerning information held by this logical entity, to the
            address specified by the associated
            'entLogicalTAddress/entLogicalTDomain' pair.

            This object, together with the associated
            entLogicalContextEngineID object, defines the context
            associated with a particular logical entity, and allows


            access to SNMP engines identified by a contextEngineId and
            contextName pair.

            If no value has been configured by the agent, a zero-length
            string is returned, or the agent may choose not to
            instantiate this object at all."
    ::= { entLogicalEntry 8 }

entLPMappingTable OBJECT-TYPE
    SYNTAX      SEQUENCE OF EntLPMappingEntry
    MAX-ACCESS  not-accessible
    STATUS      current
    DESCRIPTION
            "This table contains zero or more rows of logical entity to
            physical equipment associations. For each logical entity
            known by this agent, there are zero or more mappings to the
            physical resources which are used to realize that logical
            entity.

            An agent should limit the number and nature of entries in
            this table such that only meaningful and non-redundant
            information is returned. For example, in a system which
            contains a single power supply, mappings between logical
            entities and the power supply are not useful and should not
            be included.

            Also, only the most appropriate physical component which is
            closest to the root of a particular containment tree should
            be identified in an entLPMapping entry.

            For example, suppose a bridge is realized on a particular
            module, and all ports on that module are ports on this
            bridge. A mapping between the bridge and the module would be
            useful, but additional mappings between the bridge and each
            of the ports on that module would be redundant (since the
            entPhysicalContainedIn hierarchy can provide the same
            information). If, on the other hand, more than one bridge
            was utilizing ports on this module, then mappings between
            each bridge and the ports it used would be appropriate.

            Also, in the case of a single backplane repeater, a mapping
            for the backplane to the single repeater entity is not
            necessary."
    ::= { entityMapping 1 }

entLPMappingEntry       OBJECT-TYPE
    SYNTAX      EntLPMappingEntry
    MAX-ACCESS  not-accessible


    STATUS      current
    DESCRIPTION
            "Information about a particular logical entity to physical
            equipment association. Note that the nature of the
            association is not specifically identified in this entry.
            It is expected that sufficient information exists in the
            MIBs used to manage a particular logical entity to infer how
            physical component information is utilized."
    INDEX       { entLogicalIndex, entLPPhysicalIndex }
    ::= { entLPMappingTable 1 }

EntLPMappingEntry ::= SEQUENCE {
      entLPPhysicalIndex         PhysicalIndex
}

entLPPhysicalIndex OBJECT-TYPE
    SYNTAX      PhysicalIndex
    MAX-ACCESS  read-only
    STATUS      current
    DESCRIPTION
            "The value of this object identifies the index value of a
            particular entPhysicalEntry associated with the indicated
            entLogicalEntity."
    ::= { entLPMappingEntry 1 }

-- logical entity/component to alias table
entAliasMappingTable OBJECT-TYPE
    SYNTAX      SEQUENCE OF EntAliasMappingEntry
    MAX-ACCESS  not-accessible
    STATUS      current
    DESCRIPTION
            "This table contains zero or more rows, representing
            mappings of logical entity and physical component to
            external MIB identifiers.  Each physical port in the system
            may be associated with a mapping to an external identifier,
            which itself is associated with a particular logical
            entity's naming scope.  A 'wildcard' mechanism is provided
            to indicate that an identifier is associated with more than
            one logical entity."
    ::= { entityMapping 2 }

entAliasMappingEntry       OBJECT-TYPE
    SYNTAX      EntAliasMappingEntry
    MAX-ACCESS  not-accessible
    STATUS      current
    DESCRIPTION
            "Information about a particular physical equipment, logical
            entity to external identifier binding. Each logical


            entity/physical component pair may be associated with one
            alias mapping.  The logical entity index may also be used as
            a 'wildcard' (refer to the entAliasLogicalIndexOrZero object
            DESCRIPTION clause for details.)

            Note that only entPhysicalIndex values which represent
            physical ports (i.e. associated entPhysicalClass value is
            'port(10)') are permitted to exist in this table."
    INDEX { entPhysicalIndex, entAliasLogicalIndexOrZero }
    ::= { entAliasMappingTable 1 }

EntAliasMappingEntry ::= SEQUENCE {
      entAliasLogicalIndexOrZero        INTEGER,
      entAliasMappingIdentifier          RowPointer
}

entAliasLogicalIndexOrZero OBJECT-TYPE
    SYNTAX      INTEGER (0..2147483647)
    MAX-ACCESS  not-accessible
    STATUS      current
    DESCRIPTION
            "The value of this object identifies the logical entity
            which defines the naming scope for the associated instance
            of the 'entAliasMappingIdentifier' object.

            If this object has a non-zero value, then it identifies the
            logical entity named by the same value of entLogicalIndex.

            If this object has a value of zero, then the mapping between
            the physical component and the alias identifier for this
            entAliasMapping entry is associated with all unspecified
            logical entities. That is, a value of zero (the default
            mapping) identifies any logical entity which does not have
            an explicit entry in this table for a particular
            entPhysicalIndex/entAliasMappingIdentifier pair.

            For example, to indicate that a particular interface (e.g.,
            physical component 33) is identified by the same value of
            ifIndex for all logical entities, the following instance
            might exist:

                    entAliasMappingIdentifier.33.0 = ifIndex.5

            In the event an entPhysicalEntry is associated differently
            for some logical entities, additional entAliasMapping
            entries may exist, e.g.:

                    entAliasMappingIdentifier.33.0 = ifIndex.6


                    entAliasMappingIdentifier.33.4 =  ifIndex.1
                    entAliasMappingIdentifier.33.5 =  ifIndex.1
                    entAliasMappingIdentifier.33.10 = ifIndex.12

            Note that entries with non-zero entAliasLogicalIndexOrZero
            index values have precedence over any zero-indexed entry. In
            this example, all logical entities except 4, 5, and 10,
            associate physical entity 33 with ifIndex.6."
    ::= { entAliasMappingEntry 1 }

entAliasMappingIdentifier OBJECT-TYPE
    SYNTAX      RowPointer
    MAX-ACCESS  read-only
    STATUS      current
    DESCRIPTION
            "The value of this object identifies a particular conceptual
            row associated with the indicated entPhysicalIndex and
            entLogicalIndex pair.

            Since only physical ports are modeled in this table, only
            entries which represent interfaces or ports are allowed.  If
            an ifEntry exists on behalf of a particular physical port,
            then this object should identify the associated 'ifEntry'.
            For repeater ports, the appropriate row in the
            'rptrPortGroupTable' should be identified instead.

            For example, suppose a physical port was represented by
            entPhysicalEntry.3, entLogicalEntry.15 existed for a
            repeater, and entLogicalEntry.22 existed for a bridge.  Then
            there might be two related instances of
            entAliasMappingIdentifier:
               entAliasMappingIdentifier.3.15 == rptrPortGroupIndex.5.2
               entAliasMappingIdentifier.3.22 == ifIndex.17
            It is possible that other mappings (besides interfaces and
            repeater ports) may be defined in the future, as required.

            Bridge ports are identified by examining the Bridge MIB and
            appropriate ifEntries associated with each 'dot1dBasePort',
            and are thus not represented in this table."
    ::= { entAliasMappingEntry 2 }

-- physical mapping table
entPhysicalContainsTable OBJECT-TYPE
    SYNTAX      SEQUENCE OF EntPhysicalContainsEntry
    MAX-ACCESS  not-accessible
    STATUS      current
    DESCRIPTION
            "A table which exposes the container/'containee'


            relationships between physical entities. This table provides
            all the information found by constructing the virtual
            containment tree for a given entPhysicalTable, but in a more
            direct format.

            In the event a physical entity is contained by more than one
            other physical entity (e.g., double-wide modules), this
            table should include these additional mappings, which cannot
            be represented in the entPhysicalTable virtual containment
            tree."
    ::= { entityMapping 3 }

entPhysicalContainsEntry OBJECT-TYPE
    SYNTAX      EntPhysicalContainsEntry
    MAX-ACCESS  not-accessible
    STATUS      current
    DESCRIPTION
            "A single container/'containee' relationship."
    INDEX       { entPhysicalIndex, entPhysicalChildIndex }
    ::= { entPhysicalContainsTable 1 }

EntPhysicalContainsEntry ::= SEQUENCE {
      entPhysicalChildIndex     PhysicalIndex
}

entPhysicalChildIndex OBJECT-TYPE
    SYNTAX      PhysicalIndex
    MAX-ACCESS  read-only
    STATUS      current
    DESCRIPTION
            "The value of entPhysicalIndex for the contained physical
            entity."
    ::= { entPhysicalContainsEntry 1 }

-- last change time stamp for the whole MIB
entLastChangeTime OBJECT-TYPE
    SYNTAX      TimeStamp
    MAX-ACCESS  read-only
    STATUS      current
    DESCRIPTION
            "The value of sysUpTime at the time a conceptual row is
            created, modified, or deleted in any of these tables:
                    - entPhysicalTable
                    - entLogicalTable
                    - entLPMappingTable
                    - entAliasMappingTable
                    - entPhysicalContainsTable
            "


    ::= { entityGeneral 1 }

-- Entity MIB Trap Definitions
entityMIBTraps      OBJECT IDENTIFIER ::= { entityMIB 2 }
entityMIBTrapPrefix OBJECT IDENTIFIER ::= { entityMIBTraps 0 }

entConfigChange NOTIFICATION-TYPE
    STATUS             current
    DESCRIPTION
            "An entConfigChange notification is generated when the value
            of entLastChangeTime changes. It can be utilized by an NMS
            to trigger logical/physical entity table maintenance polls.

            An agent should not generate more than one entConfigChange
            'notification-event' in a given time interval (five seconds
            is the suggested default).  A 'notification-event' is the
            transmission of a single trap or inform PDU to a list of
            notification destinations.

            If additional configuration changes occur within the
            throttling period, then notification-events for these
            changes should be suppressed by the agent until the current
            throttling period expires.  At the end of a throttling
            period, one notification-event should be generated if any
            configuration changes occurred since the start of the
            throttling period. In such a case, another throttling period
            is started right away.

            An NMS should periodically check the value of
            entLastChangeTime to detect any missed entConfigChange
            notification-events, e.g., due to throttling or transmission
            loss."
   ::= { entityMIBTrapPrefix 1 }

-- conformance information
entityConformance OBJECT IDENTIFIER ::= { entityMIB 3 }

entityCompliances OBJECT IDENTIFIER ::= { entityConformance 1 }
entityGroups      OBJECT IDENTIFIER ::= { entityConformance 2 }

-- compliance statements
entityCompliance MODULE-COMPLIANCE
    STATUS  deprecated
    DESCRIPTION
            "The compliance statement for SNMP entities which implement
            version 1 of the Entity MIB."
    MODULE  -- this module
        MANDATORY-GROUPS {


                           entityPhysicalGroup,
                           entityLogicalGroup,
                           entityMappingGroup,
                           entityGeneralGroup,
                           entityNotificationsGroup
        }
    ::= { entityCompliances 1 }

entity2Compliance MODULE-COMPLIANCE
    STATUS  current
    DESCRIPTION
            "The compliance statement for SNMP entities which implement
            version 2 of the Entity MIB."
    MODULE  -- this module
        MANDATORY-GROUPS {
                           entityPhysicalGroup,
                           entityPhysical2Group,
                           entityGeneralGroup,
                           entityNotificationsGroup
        }
        GROUP entityLogical2Group
        DESCRIPTION
            "Implementation of this group is not mandatory for agents
            which model all MIB object instances within a single naming
            scope."

        GROUP entityMappingGroup
        DESCRIPTION
            "Implementation of the entPhysicalContainsTable is mandatory
            for all agents.  Implementation of the entLPMappingTable and
            entAliasMappingTables are not mandatory for agents which
            model all MIB object instances within a single naming scope.

            Note that the entAliasMappingTable may be useful for all
            agents, however implementation of the entityLogicalGroup or
            entityLogical2Group is required to support this table."

        OBJECT entPhysicalSerialNum
        MIN-ACCESS   not-accessible
        DESCRIPTION
            "Read and write access is not required for agents which
            cannot identify serial number information for physical
            entities, and/or cannot provide non-volatile storage for
            NMS-assigned serial numbers.

            Write access is not required for agents which can identify
            serial number information for physical entities, but cannot
            provide non-volatile storage for NMS-assigned serial


            numbers.

            Write access is not required for physical entities for
            physical entities for which the associated value of the
            entPhysicalIsFRU object is equal to 'false(2)'."

        OBJECT entPhysicalAlias
        MIN-ACCESS   read-only
        DESCRIPTION
            "Write access is required only if the associated
            entPhysicalClass value is equal to 'chassis(3)'."

        OBJECT entPhysicalAssetID
        MIN-ACCESS   not-accessible
        DESCRIPTION
            "Read and write access is not required for agents which
            cannot provide non-volatile storage for NMS-assigned asset
            identifiers.

            Write access is not required for physical entities for which
            the associated value of entPhysicalIsFRU is equal to
            'false(2)'."
    ::= { entityCompliances 2 }

-- MIB groupings
entityPhysicalGroup    OBJECT-GROUP
    OBJECTS {
              entPhysicalDescr,
              entPhysicalVendorType,
              entPhysicalContainedIn,
              entPhysicalClass,
              entPhysicalParentRelPos,
              entPhysicalName
            }
    STATUS  current
    DESCRIPTION
            "The collection of objects which are used to represent
            physical system components, for which a single agent
            provides management information."
    ::= { entityGroups 1 }

entityLogicalGroup    OBJECT-GROUP
    OBJECTS {
              entLogicalDescr,
              entLogicalType,
              entLogicalCommunity,
              entLogicalTAddress,
              entLogicalTDomain


            }
    STATUS  deprecated
    DESCRIPTION
            "The collection of objects which are used to represent the
            list of logical entities for which a single agent provides
            management information."
    ::= { entityGroups 2 }

entityMappingGroup    OBJECT-GROUP
    OBJECTS {
              entLPPhysicalIndex,
              entAliasMappingIdentifier,
              entPhysicalChildIndex
            }
    STATUS  current
    DESCRIPTION
            "The collection of objects which are used to represent the
            associations between multiple logical entities, physical
            components, interfaces, and port identifiers for which a
            single agent provides management information."
    ::= { entityGroups 3 }

entityGeneralGroup    OBJECT-GROUP
    OBJECTS {
              entLastChangeTime
            }
    STATUS  current
    DESCRIPTION
            "The collection of objects which are used to represent
            general entity information for which a single agent provides
            management information."
    ::= { entityGroups 4 }

entityNotificationsGroup NOTIFICATION-GROUP
    NOTIFICATIONS { entConfigChange }
    STATUS        current
    DESCRIPTION
            "The collection of notifications used to indicate Entity MIB
            data consistency and general status information."
    ::= { entityGroups 5 }

entityPhysical2Group    OBJECT-GROUP
    OBJECTS {
              entPhysicalHardwareRev,
              entPhysicalFirmwareRev,
              entPhysicalSoftwareRev,
              entPhysicalSerialNum,
              entPhysicalMfgName,


              entPhysicalModelName,
              entPhysicalAlias,
              entPhysicalAssetID,
              entPhysicalIsFRU
            }

    STATUS  current
    DESCRIPTION
            "The collection of objects which are used to represent
            physical system components, for which a single agent
            provides management information.  This group augments the
            objects contained in the entityPhysicalGroup."
    ::= { entityGroups 6 }

entityLogical2Group    OBJECT-GROUP
    OBJECTS {
              entLogicalDescr,
              entLogicalType,
              entLogicalTAddress,
              entLogicalTDomain,
              entLogicalContextEngineID,
              entLogicalContextName
            }
    STATUS  current
    DESCRIPTION
            "The collection of objects which are used to represent the
            list of logical entities for which a single SNMP entity
            provides management information."
    ::= { entityGroups 7 }

END

ENTITY-SENSOR-MIB DEFINITIONS ::= BEGIN

IMPORTS
        MODULE-IDENTITY, OBJECT-TYPE,
        Integer32, Unsigned32, mib-2
                FROM SNMPv2-SMI
        MODULE-COMPLIANCE, OBJECT-GROUP
                FROM SNMPv2-CONF
        TEXTUAL-CONVENTION, TimeStamp
                FROM SNMPv2-TC
        entPhysicalIndex, entityPhysicalGroup
                FROM ENTITY-MIB
        SnmpAdminString
                FROM SNMP-FRAMEWORK-MIB;

entitySensorMIB MODULE-IDENTITY
    LAST-UPDATED    "200212160000Z"
    ORGANIZATION    "IETF Entity MIB Working Group"
    CONTACT-INFO
            "        Andy Bierman
                     Cisco Systems, Inc.
                Tel: +1 408-527-3711
             E-mail: abierman@cisco.com
             Postal: 170 West Tasman Drive
                     San Jose, CA USA 95134

                     Dan Romascanu
                     Avaya Inc.
                Tel: +972-3-645-8414
              Email: dromasca@avaya.com
             Postal: Atidim technology Park, Bldg. #3
                     Tel Aviv, Israel, 61131

                     K.C. Norseth
                     L-3 Communications
                Tel: +1 801-594-2809
              Email: kenyon.c.norseth@L-3com.com
             Postal: 640 N. 2200 West.


                     Salt Lake City, Utah 84116-0850

             Send comments to <entmib@ietf.org>
             Mailing list subscription info:
               http://www.ietf.org/mailman/listinfo/entmib "
    DESCRIPTION
            "This module defines Entity MIB extensions for physical
             sensors.

             Copyright (C) The Internet Society (2002). This version
             of this MIB module is part of RFC 3433; see the RFC
             itself for full legal notices."

    REVISION        "200212160000Z"
    DESCRIPTION
            "Initial version of the Entity Sensor MIB module, published
             as RFC 3433."
    ::= { mib-2 99 }

entitySensorObjects              OBJECT IDENTIFIER
     ::= { entitySensorMIB 1 }

-- entitySensorNotifications        OBJECT IDENTIFIER
--     ::= { entitySensorMIB 2 }
entitySensorConformance          OBJECT IDENTIFIER
     ::= { entitySensorMIB 3 }

--
-- Textual Conventions
--

EntitySensorDataType ::= TEXTUAL-CONVENTION
    STATUS       current
    DESCRIPTION
            "An object using this data type represents the Entity Sensor
            measurement data type associated with a physical sensor
            value. The actual data units are determined by examining an
            object of this type together with the associated
            EntitySensorDataScale object.

            An object of this type SHOULD be defined together with
            objects of type EntitySensorDataScale and
            EntitySensorPrecision.  Together, associated objects of
            these three types are used to identify the semantics of an
            object of type EntitySensorValue.


            Valid values are:

               other(1):        a measure other than those listed below
               unknown(2):      unknown measurement, or arbitrary,
                                relative numbers
               voltsAC(3):      electric potential
               voltsDC(4):      electric potential
               amperes(5):      electric current
               watts(6):        power
               hertz(7):        frequency
               celsius(8):      temperature
               percentRH(9):    percent relative humidity
               rpm(10):         shaft revolutions per minute
               cmm(11),:        cubic meters per minute (airflow)
               truthvalue(12):  value takes { true(1), false(2) }

            "
    SYNTAX INTEGER {
        other(1),
        unknown(2),
        voltsAC(3),
        voltsDC(4),
        amperes(5),
        watts(6),
        hertz(7),
        celsius(8),
        percentRH(9),
        rpm(10),
        cmm(11),
        truthvalue(12)
    }

EntitySensorDataScale ::= TEXTUAL-CONVENTION
    STATUS       current
    DESCRIPTION
            "An object using this data type represents a data scaling
            factor, represented with an International System of Units
            (SI) prefix.  The actual data units are determined by
            examining an object of this type together with the
            associated EntitySensorDataType object.

            An object of this type SHOULD be defined together with
            objects of type EntitySensorDataType and
            EntitySensorPrecision.  Together, associated objects of
            these three types are used to identify the semantics of an
            object of type EntitySensorValue."
    REFERENCE
            "The International System of Units (SI),


            National Institute of Standards and Technology,
            Spec. Publ. 330, August 1991."
    SYNTAX INTEGER {
        yocto(1),   -- 10^-24
        zepto(2),   -- 10^-21
        atto(3),    -- 10^-18
        femto(4),   -- 10^-15
        pico(5),    -- 10^-12
        nano(6),    -- 10^-9
        micro(7),   -- 10^-6
        milli(8),   -- 10^-3
        units(9),   -- 10^0
        kilo(10),   -- 10^3
        mega(11),   -- 10^6
        giga(12),   -- 10^9
        tera(13),   -- 10^12
        exa(14),    -- 10^15
        peta(15),   -- 10^18
        zetta(16),  -- 10^21
        yotta(17)   -- 10^24
    }

EntitySensorPrecision ::= TEXTUAL-CONVENTION
    STATUS       current
    DESCRIPTION
            "An object using this data type represents a sensor
            precision range.

            An object of this type SHOULD be defined together with
            objects of type EntitySensorDataType and
            EntitySensorDataScale.  Together, associated objects of
            these three types are used to identify the semantics of an
            object of type EntitySensorValue.

            If an object of this type contains a value in the range 1 to
            9, it represents the number of decimal places in the
            fractional part of an associated EntitySensorValue fixed-
            point number.

            If an object of this type contains a value in the range -8
            to -1, it represents the number of accurate digits in the
            associated EntitySensorValue fixed-point number.

            The value zero indicates the associated EntitySensorValue
            object is not a fixed-point number.

            Agent implementors must choose a value for the associated
            EntitySensorPrecision object so that the precision and


            accuracy of the associated EntitySensorValue object is
            correctly indicated.

            For example, a physical entity representing a temperature
            sensor that can measure 0 degrees to 100 degrees C in 0.1
            degree increments, +/- 0.05 degrees, would have an
            EntitySensorPrecision value of '1', an EntitySensorDataScale
            value of 'units(9)', and an EntitySensorValue ranging from
            '0' to '1000'.  The EntitySensorValue would be interpreted
            as 'degrees C * 10'."
    SYNTAX Integer32 (-8..9)

EntitySensorValue ::= TEXTUAL-CONVENTION
    STATUS       current
    DESCRIPTION
            "An object using this data type represents an Entity Sensor
            value.
            An object of this type SHOULD be defined together with
            objects of type EntitySensorDataType, EntitySensorDataScale
            and EntitySensorPrecision.  Together, associated objects of
            those three types are used to identify the semantics of an
            object of this data type.

            The semantics of an object using this data type are
            determined by the value of the associated
            EntitySensorDataType object.

            If the associated EntitySensorDataType object is equal to
            'voltsAC(3)', 'voltsDC(4)', 'amperes(5)', 'watts(6),
            'hertz(7)', 'celsius(8)', or 'cmm(11)', then an object of
            this type MUST contain a fixed point number ranging from
            -999,999,999 to +999,999,999.  The value -1000000000
            indicates an underflow error. The value +1000000000
            indicates an overflow error.  The EntitySensorPrecision
            indicates how many fractional digits are represented in the
            associated EntitySensorValue object.

            If the associated EntitySensorDataType object is equal to
            'percentRH(9)', then an object of this type MUST contain a
            number ranging from 0 to 100.

            If the associated EntitySensorDataType object is equal to
            'rpm(10)', then an object of this type MUST contain a number
            ranging from -999,999,999 to +999,999,999.

            If the associated EntitySensorDataType object is equal to
            'truthvalue(12)', then an object of this type MUST contain
            either the value 'true(1)' or the value 'false(2)'.


            If the associated EntitySensorDataType object is equal to
            'other(1)' or unknown(2)', then an object of this type MUST
            contain a number ranging from -1000000000 to 1000000000."
    SYNTAX Integer32 (-1000000000..1000000000)

EntitySensorStatus ::= TEXTUAL-CONVENTION
    STATUS       current
    DESCRIPTION
            "An object using this data type represents the operational
            status of a physical sensor.

            The value 'ok(1)' indicates that the agent can obtain the
            sensor value.

            The value 'unavailable(2)' indicates that the agent
            presently cannot obtain the sensor value.

            The value 'nonoperational(3)' indicates that the agent
            believes the sensor is broken.  The sensor could have a hard
            failure (disconnected wire), or a soft failure such as out-
            of-range, jittery, or wildly fluctuating readings."
    SYNTAX INTEGER {
        ok(1),
        unavailable(2),
        nonoperational(3)
    }

--
-- Entity Sensor Table
--

entPhySensorTable OBJECT-TYPE
    SYNTAX        SEQUENCE OF EntPhySensorEntry
    MAX-ACCESS    not-accessible
    STATUS        current
    DESCRIPTION
            "This table contains one row per physical sensor represented
            by an associated row in the entPhysicalTable."
    ::= { entitySensorObjects 1 }

entPhySensorEntry OBJECT-TYPE
    SYNTAX        EntPhySensorEntry
    MAX-ACCESS    not-accessible
    STATUS        current
    DESCRIPTION
            "Information about a particular physical sensor.


            An entry in this table describes the present reading of a
            sensor, the measurement units and scale, and sensor
            operational status.

            Entries are created in this table by the agent.  An entry
            for each physical sensor SHOULD be created at the same time
            as the associated entPhysicalEntry.  An entry SHOULD be
            destroyed if the associated entPhysicalEntry is destroyed."
    INDEX  { entPhysicalIndex }    -- SPARSE-AUGMENTS
    ::= { entPhySensorTable 1 }

EntPhySensorEntry ::= SEQUENCE {
        entPhySensorType            EntitySensorDataType,
        entPhySensorScale           EntitySensorDataScale,
        entPhySensorPrecision       EntitySensorPrecision,
        entPhySensorValue           EntitySensorValue,
        entPhySensorOperStatus      EntitySensorStatus,
        entPhySensorUnitsDisplay    SnmpAdminString,
        entPhySensorValueTimeStamp  TimeStamp,
        entPhySensorValueUpdateRate Unsigned32
}

entPhySensorType OBJECT-TYPE
    SYNTAX        EntitySensorDataType
    MAX-ACCESS    read-only
    STATUS        current
    DESCRIPTION
            "The type of data returned by the associated
            entPhySensorValue object.

            This object SHOULD be set by the agent during entry
            creation, and the value SHOULD NOT change during operation."
    ::= { entPhySensorEntry 1 }

entPhySensorScale OBJECT-TYPE
    SYNTAX        EntitySensorDataScale
    MAX-ACCESS    read-only
    STATUS        current
    DESCRIPTION
            "The exponent to apply to values returned by the associated
            entPhySensorValue object.

            This object SHOULD be set by the agent during entry
            creation, and the value SHOULD NOT change during operation."
    ::= { entPhySensorEntry 2 }


entPhySensorPrecision OBJECT-TYPE
    SYNTAX        EntitySensorPrecision
    MAX-ACCESS    read-only
    STATUS        current
    DESCRIPTION
            "The number of decimal places of precision in fixed-point
            sensor values returned by the associated entPhySensorValue
            object.

            This object SHOULD be set to '0' when the associated
            entPhySensorType value is not a fixed-point type: e.g.,
            'percentRH(9)', 'rpm(10)', 'cmm(11)', or 'truthvalue(12)'.

            This object SHOULD be set by the agent during entry
            creation, and the value SHOULD NOT change during operation."
    ::= { entPhySensorEntry 3 }

entPhySensorValue OBJECT-TYPE
    SYNTAX        EntitySensorValue
    MAX-ACCESS    read-only
    STATUS        current
    DESCRIPTION
            "The most recent measurement obtained by the agent for this
            sensor.

            To correctly interpret the value of this object, the
            associated entPhySensorType, entPhySensorScale, and
            entPhySensorPrecision objects must also be examined."
    ::= { entPhySensorEntry 4 }

entPhySensorOperStatus OBJECT-TYPE
    SYNTAX        EntitySensorStatus
    MAX-ACCESS    read-only
    STATUS        current
    DESCRIPTION
            "The operational status of the sensor."
    ::= { entPhySensorEntry 5 }

entPhySensorUnitsDisplay OBJECT-TYPE
    SYNTAX      SnmpAdminString
    MAX-ACCESS  read-only
    STATUS      current
    DESCRIPTION
            "A textual description of the data units that should be used
            in the display of entPhySensorValue."
    ::= { entPhySensorEntry 6 }


entPhySensorValueTimeStamp OBJECT-TYPE
    SYNTAX        TimeStamp
    MAX-ACCESS    read-only
    STATUS        current
    DESCRIPTION
            "The value of sysUpTime at the time the status and/or value
            of this sensor was last obtained by the agent."
    ::= { entPhySensorEntry 7 }

entPhySensorValueUpdateRate  OBJECT-TYPE
    SYNTAX        Unsigned32
    UNITS         "milliseconds"
    MAX-ACCESS    read-only
    STATUS        current
    DESCRIPTION
            "An indication of the frequency that the agent updates the
            associated entPhySensorValue object, representing in
            milliseconds.

            The value zero indicates:

                - the sensor value is updated on demand (e.g.,
                  when polled by the agent for a get-request),
                - the sensor value is updated when the sensor
                  value changes (event-driven),
                - the agent does not know the update rate.

            "
    ::= { entPhySensorEntry 8 }

--
-- Conformance Section
--

entitySensorCompliances OBJECT IDENTIFIER
    ::= { entitySensorConformance 1 }
entitySensorGroups      OBJECT IDENTIFIER
    ::= { entitySensorConformance 2 }

entitySensorCompliance MODULE-COMPLIANCE
    STATUS  current
    DESCRIPTION
            "Describes the requirements for conformance to the Entity
            Sensor MIB module."
    MODULE  -- this module
        MANDATORY-GROUPS { entitySensorValueGroup }


    MODULE ENTITY-MIB
        MANDATORY-GROUPS { entityPhysicalGroup }

    ::= { entitySensorCompliances 1 }

-- Object Groups

entitySensorValueGroup OBJECT-GROUP
    OBJECTS {
             entPhySensorType,
             entPhySensorScale,
             entPhySensorPrecision,
             entPhySensorValue,
             entPhySensorOperStatus,
             entPhySensorUnitsDisplay,
             entPhySensorValueTimeStamp,
             entPhySensorValueUpdateRate
    }
    STATUS  current
    DESCRIPTION
            "A collection of objects representing physical entity sensor
            information."
    ::= { entitySensorGroups 1 }

END

IF-MIB DEFINITIONS ::= BEGIN

IMPORTS
    MODULE-IDENTITY, OBJECT-TYPE, Counter32, Gauge32, Counter64,
    Integer32, TimeTicks, mib-2,
    NOTIFICATION-TYPE                        FROM SNMPv2-SMI
    TEXTUAL-CONVENTION, DisplayString,
    PhysAddress, TruthValue, RowStatus,
    TimeStamp, AutonomousType, TestAndIncr   FROM SNMPv2-TC
    MODULE-COMPLIANCE, OBJECT-GROUP,
    NOTIFICATION-GROUP                       FROM SNMPv2-CONF
    snmpTraps                                FROM SNMPv2-MIB
    IANAifType                               FROM IANAifType-MIB;

ifMIB MODULE-IDENTITY
    LAST-UPDATED "200006140000Z"
    ORGANIZATION "IETF Interfaces MIB Working Group"
    CONTACT-INFO
            "   Keith McCloghrie
                Cisco Systems, Inc.
                170 West Tasman Drive
                San Jose, CA  95134-1706
                US

                408-526-5260
                kzm@cisco.com"
    DESCRIPTION
            "The MIB module to describe generic objects for network
            interface sub-layers.  This MIB is an updated version of
            MIB-II's ifTable, and incorporates the extensions defined in
            RFC 1229."


    REVISION      "200006140000Z"
    DESCRIPTION
            "Clarifications agreed upon by the Interfaces MIB WG, and
            published as RFC 2863."
    REVISION      "199602282155Z"
    DESCRIPTION
            "Revisions made by the Interfaces MIB WG, and published in
            RFC 2233."
    REVISION      "199311082155Z"
    DESCRIPTION
            "Initial revision, published as part of RFC 1573."
    ::= { mib-2 31 }

ifMIBObjects OBJECT IDENTIFIER ::= { ifMIB 1 }

interfaces   OBJECT IDENTIFIER ::= { mib-2 2 }

--
-- Textual Conventions
--

-- OwnerString has the same semantics as used in RFC 1271

OwnerString ::= TEXTUAL-CONVENTION
    DISPLAY-HINT "255a"
    STATUS       deprecated
    DESCRIPTION
            "This data type is used to model an administratively
            assigned name of the owner of a resource.  This information
            is taken from the NVT ASCII character set.  It is suggested
            that this name contain one or more of the following: ASCII
            form of the manager station's transport address, management
            station name (e.g., domain name), network management
            personnel's name, location, or phone number.  In some cases
            the agent itself will be the owner of an entry.  In these
            cases, this string shall be set to a string starting with
            'agent'."
    SYNTAX       OCTET STRING (SIZE(0..255))

-- InterfaceIndex contains the semantics of ifIndex and should be used
-- for any objects defined in other MIB modules that need these semantics.

InterfaceIndex ::= TEXTUAL-CONVENTION
    DISPLAY-HINT "d"
    STATUS       current
    DESCRIPTION


            "A unique value, greater than zero, for each interface or
            interface sub-layer in the managed system.  It is
            recommended that values are assigned contiguously starting
            from 1.  The value for each interface sub-layer must remain
            constant at least from one re-initialization of the entity's
            network management system to the next re-initialization."
    SYNTAX       Integer32 (1..2147483647)

InterfaceIndexOrZero ::= TEXTUAL-CONVENTION
    DISPLAY-HINT "d"
    STATUS       current
    DESCRIPTION
            "This textual convention is an extension of the
            InterfaceIndex convention.  The latter defines a greater
            than zero value used to identify an interface or interface
            sub-layer in the managed system.  This extension permits the
            additional value of zero.  the value zero is object-specific
            and must therefore be defined as part of the description of
            any object which uses this syntax.  Examples of the usage of
            zero might include situations where interface was unknown,
            or when none or all interfaces need to be referenced."
    SYNTAX       Integer32 (0..2147483647)

ifNumber  OBJECT-TYPE
    SYNTAX      Integer32
    MAX-ACCESS  read-only
    STATUS      current
    DESCRIPTION
            "The number of network interfaces (regardless of their
            current state) present on this system."
    ::= { interfaces 1 }

ifTableLastChange  OBJECT-TYPE
    SYNTAX      TimeTicks
    MAX-ACCESS  read-only
    STATUS      current
    DESCRIPTION
            "The value of sysUpTime at the time of the last creation or
            deletion of an entry in the ifTable.  If the number of
            entries has been unchanged since the last re-initialization
            of the local network management subsystem, then this object
            contains a zero value."
    ::= { ifMIBObjects 5 }

-- the Interfaces table

-- The Interfaces table contains information on the entity's


-- interfaces.  Each sub-layer below the internetwork-layer
-- of a network interface is considered to be an interface.

ifTable OBJECT-TYPE
    SYNTAX      SEQUENCE OF IfEntry
    MAX-ACCESS  not-accessible
    STATUS      current
    DESCRIPTION
            "A list of interface entries.  The number of entries is
            given by the value of ifNumber."
    ::= { interfaces 2 }

ifEntry OBJECT-TYPE
    SYNTAX      IfEntry
    MAX-ACCESS  not-accessible
    STATUS      current
    DESCRIPTION
            "An entry containing management information applicable to a
            particular interface."
    INDEX   { ifIndex }
    ::= { ifTable 1 }

IfEntry ::=
    SEQUENCE {
        ifIndex                 InterfaceIndex,
        ifDescr                 DisplayString,
        ifType                  IANAifType,
        ifMtu                   Integer32,
        ifSpeed                 Gauge32,
        ifPhysAddress           PhysAddress,
        ifAdminStatus           INTEGER,
        ifOperStatus            INTEGER,
        ifLastChange            TimeTicks,
        ifInOctets              Counter32,
        ifInUcastPkts           Counter32,
        ifInNUcastPkts          Counter32,  -- deprecated
        ifInDiscards            Counter32,
        ifInErrors              Counter32,
        ifInUnknownProtos       Counter32,
        ifOutOctets             Counter32,
        ifOutUcastPkts          Counter32,
        ifOutNUcastPkts         Counter32,  -- deprecated
        ifOutDiscards           Counter32,
        ifOutErrors             Counter32,
        ifOutQLen               Gauge32,    -- deprecated
        ifSpecific              OBJECT IDENTIFIER -- deprecated
    }


ifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { ifEntry 1 }

ifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { ifEntry 2 }

ifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { ifEntry 3 }

ifMtu OBJECT-TYPE
    SYNTAX      Integer32
    MAX-ACCESS  read-only
    STATUS      current
    DESCRIPTION
            "The size of the largest packet which can be sent/received
            on the interface, specified in octets.  For interfaces that
            are used for transmitting network datagrams, this is the
            size of the largest network datagram that can be sent on the
            interface."
    ::= { ifEntry 4 }

ifSpeed OBJECT-TYPE


    SYNTAX      Gauge32
    MAX-ACCESS  read-only
    STATUS      current
    DESCRIPTION
            "An estimate of the interface's current bandwidth in bits
            per second.  For interfaces which do not vary in bandwidth
            or for those where no accurate estimation can be made, this
            object should contain the nominal bandwidth.  If the
            bandwidth of the interface is greater than the maximum value
            reportable by this object then this object should report its
            maximum value (4,294,967,295) and ifHighSpeed must be used
            to report the interace's speed.  For a sub-layer which has
            no concept of bandwidth, this object should be zero."
    ::= { ifEntry 5 }

ifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { ifEntry 6 }

ifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { ifEntry 7 }


ifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { ifEntry 8 }

ifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { ifEntry 9 }

ifInOctets OBJECT-TYPE
    SYNTAX      Counter32
    MAX-ACCESS  read-only
    STATUS      current
    DESCRIPTION
            "The total number of octets received on the interface,


            including framing characters.

            Discontinuities in the value of this counter can occur at
            re-initialization of the management system, and at other
            times as indicated by the value of
            ifCounterDiscontinuityTime."
    ::= { ifEntry 10 }

ifInUcastPkts OBJECT-TYPE
    SYNTAX      Counter32
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { ifEntry 11 }

ifInNUcastPkts OBJECT-TYPE
    SYNTAX  Counter32
    MAX-ACCESS  read-only
    STATUS      deprecated
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { ifEntry 12 }

ifInDiscards OBJECT-TYPE
    SYNTAX      Counter32
    MAX-ACCESS  read-only
    STATUS      current
    DESCRIPTION
            "The number of inbound packets which were chosen to be
            discarded even though no errors had been detected to prevent


            their being deliverable to a higher-layer protocol.  One
            possible reason for discarding such a packet could be to
            free up buffer space.

            Discontinuities in the value of this counter can occur at
            re-initialization of the management system, and at other
            times as indicated by the value of
            ifCounterDiscontinuityTime."
    ::= { ifEntry 13 }

ifInErrors OBJECT-TYPE
    SYNTAX      Counter32
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { ifEntry 14 }

ifInUnknownProtos OBJECT-TYPE
    SYNTAX      Counter32
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { ifEntry 15 }


ifOutOctets OBJECT-TYPE
    SYNTAX      Counter32
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { ifEntry 16 }

ifOutUcastPkts OBJECT-TYPE
    SYNTAX      Counter32
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { ifEntry 17 }

ifOutNUcastPkts OBJECT-TYPE
    SYNTAX      Counter32
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { ifEntry 18 }


ifOutDiscards OBJECT-TYPE
    SYNTAX      Counter32
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { ifEntry 19 }

ifOutErrors OBJECT-TYPE
    SYNTAX      Counter32
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { ifEntry 20 }

ifOutQLen OBJECT-TYPE
    SYNTAX      Gauge32
    MAX-ACCESS  read-only
    STATUS      deprecated
    DESCRIPTION
            "The length of the output packet queue (in packets)."
    ::= { ifEntry 21 }

ifSpecific OBJECT-TYPE
    SYNTAX      OBJECT IDENTIFIER
    MAX-ACCESS  read-only
    STATUS      deprecated
    DESCRIPTION
            "A reference to MIB definitions specific to the particular
            media being used to realize the interface.  It is


            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { ifEntry 22 }

--
--   Extension to the interface table
--
-- This table replaces the ifExtnsTable table.
--

ifXTable        OBJECT-TYPE
    SYNTAX      SEQUENCE OF IfXEntry
    MAX-ACCESS  not-accessible
    STATUS      current
    DESCRIPTION
            "A list of interface entries.  The number of entries is
            given by the value of ifNumber.  This table contains
            additional objects for the interface table."
    ::= { ifMIBObjects 1 }

ifXEntry        OBJECT-TYPE
    SYNTAX      IfXEntry
    MAX-ACCESS  not-accessible
    STATUS      current
    DESCRIPTION
            "An entry containing additional management information
            applicable to a particular interface."
    AUGMENTS    { ifEntry }
    ::= { ifXTable 1 }

IfXEntry ::=
    SEQUENCE {
        ifName                  DisplayString,
        ifInMulticastPkts       Counter32,
        ifInBroadcastPkts       Counter32,
        ifOutMulticastPkts      Counter32,
        ifOutBroadcastPkts      Counter32,
        ifHCInOctets            Counter64,
        ifHCInUcastPkts         Counter64,
        ifHCInMulticastPkts     Counter64,


        ifHCInBroadcastPkts     Counter64,
        ifHCOutOctets           Counter64,
        ifHCOutUcastPkts        Counter64,
        ifHCOutMulticastPkts    Counter64,
        ifHCOutBroadcastPkts    Counter64,
        ifLinkUpDownTrapEnable  INTEGER,
        ifHighSpeed             Gauge32,
        ifPromiscuousMode       TruthValue,
        ifConnectorPresent      TruthValue,
        ifAlias                 DisplayString,
        ifCounterDiscontinuityTime TimeStamp
    }

ifName OBJECT-TYPE
    SYNTAX      DisplayString
    MAX-ACCESS  read-only
    STATUS      current
    DESCRIPTION
            "The textual name of the interface.  The value of this
            object should be the name of the interface as assigned by
            the local device and should be suitable for use in commands
            entered at the device's `console'.  This might be a text
            name, such as `le0' or a simple port number, such as `1',
            depending on the interface naming syntax of the device.  If
            several entries in the ifTable together represent a single
            interface as named by the device, then each will have the
            same value of ifName.  Note that for an agent which responds
            to SNMP queries concerning an interface on some other
            (proxied) device, then the value of ifName for such an
            interface is the proxied device's local name for it.

            If there is no local name, or this object is otherwise not
            applicable, then this object contains a zero-length string."
    ::= { ifXEntry 1 }

ifInMulticastPkts OBJECT-TYPE
    SYNTAX      Counter32
    MAX-ACCESS  read-only
    STATUS      current
    DESCRIPTION
            "The number of packets, delivered by this sub-layer to a
            higher (sub-)layer, which were addressed to a multicast
            address at this sub-layer.  For a MAC layer protocol, this
            includes both Group and Functional addresses.

            Discontinuities in the value of this counter can occur at
            re-initialization of the management system, and at other


            times as indicated by the value of
            ifCounterDiscontinuityTime."
    ::= { ifXEntry 2 }

ifInBroadcastPkts OBJECT-TYPE
    SYNTAX      Counter32
    MAX-ACCESS  read-only
    STATUS      current
    DESCRIPTION
            "The number of packets, delivered by this sub-layer to a
            higher (sub-)layer, which were addressed to a broadcast
            address at this sub-layer.

            Discontinuities in the value of this counter can occur at
            re-initialization of the management system, and at other
            times as indicated by the value of
            ifCounterDiscontinuityTime."
    ::= { ifXEntry 3 }

ifOutMulticastPkts OBJECT-TYPE
    SYNTAX      Counter32
    MAX-ACCESS  read-only
    STATUS      current
    DESCRIPTION
            "The total number of packets that higher-level protocols
            requested be transmitted, and which were addressed to a
            multicast address at this sub-layer, including those that
            were discarded or not sent.  For a MAC layer protocol, this
            includes both Group and Functional addresses.

            Discontinuities in the value of this counter can occur at
            re-initialization of the management system, and at other
            times as indicated by the value of
            ifCounterDiscontinuityTime."
    ::= { ifXEntry 4 }

ifOutBroadcastPkts OBJECT-TYPE
    SYNTAX      Counter32
    MAX-ACCESS  read-only
    STATUS      current
    DESCRIPTION
            "The total number of packets that higher-level protocols
            requested be transmitted, and which were addressed to a
            broadcast address at this sub-layer, including those that
            were discarded or not sent.

            Discontinuities in the value of this counter can occur at
            re-initialization of the management system, and at other


            times as indicated by the value of
            ifCounterDiscontinuityTime."
    ::= { ifXEntry 5 }

--
-- High Capacity Counter objects.  These objects are all
-- 64 bit versions of the "basic" ifTable counters.  These
-- objects all have the same basic semantics as their 32-bit
-- counterparts, however, their syntax has been extended
-- to 64 bits.
--

ifHCInOctets OBJECT-TYPE
    SYNTAX      Counter64
    MAX-ACCESS  read-only
    STATUS      current
    DESCRIPTION
            "The total number of octets received on the interface,
            including framing characters.  This object is a 64-bit
            version of ifInOctets.

            Discontinuities in the value of this counter can occur at
            re-initialization of the management system, and at other
            times as indicated by the value of
            ifCounterDiscontinuityTime."
    ::= { ifXEntry 6 }

ifHCInUcastPkts OBJECT-TYPE
    SYNTAX      Counter64
    MAX-ACCESS  read-only
    STATUS      current
    DESCRIPTION
            "The number of packets, delivered by this sub-layer to a
            higher (sub-)layer, which were not addressed to a multicast
            or broadcast address at this sub-layer.  This object is a
            64-bit version of ifInUcastPkts.

            Discontinuities in the value of this counter can occur at
            re-initialization of the management system, and at other
            times as indicated by the value of
            ifCounterDiscontinuityTime."
    ::= { ifXEntry 7 }

ifHCInMulticastPkts OBJECT-TYPE
    SYNTAX      Counter64
    MAX-ACCESS  read-only
    STATUS      current
    DESCRIPTION


            "The number of packets, delivered by this sub-layer to a
            higher (sub-)layer, which were addressed to a multicast
            address at this sub-layer.  For a MAC layer protocol, this
            includes both Group and Functional addresses.  This object
            is a 64-bit version of ifInMulticastPkts.

            Discontinuities in the value of this counter can occur at
            re-initialization of the management system, and at other
            times as indicated by the value of
            ifCounterDiscontinuityTime."
    ::= { ifXEntry 8 }

ifHCInBroadcastPkts OBJECT-TYPE
    SYNTAX      Counter64
    MAX-ACCESS  read-only
    STATUS      current
    DESCRIPTION
            "The number of packets, delivered by this sub-layer to a
            higher (sub-)layer, which were addressed to a broadcast
            address at this sub-layer.  This object is a 64-bit version
            of ifInBroadcastPkts.

            Discontinuities in the value of this counter can occur at
            re-initialization of the management system, and at other
            times as indicated by the value of
            ifCounterDiscontinuityTime."
    ::= { ifXEntry 9 }

ifHCOutOctets OBJECT-TYPE
    SYNTAX      Counter64
    MAX-ACCESS  read-only
    STATUS      current
    DESCRIPTION
            "The total number of octets transmitted out of the
            interface, including framing characters.  This object is a
            64-bit version of ifOutOctets.

            Discontinuities in the value of this counter can occur at
            re-initialization of the management system, and at other
            times as indicated by the value of
            ifCounterDiscontinuityTime."
    ::= { ifXEntry 10 }

ifHCOutUcastPkts OBJECT-TYPE
    SYNTAX      Counter64
    MAX-ACCESS  read-only
    STATUS      current
    DESCRIPTION


            "The total number of packets that higher-level protocols
            requested be transmitted, and which were not addressed to a
            multicast or broadcast address at this sub-layer, including
            those that were discarded or not sent.  This object is a
            64-bit version of ifOutUcastPkts.

            Discontinuities in the value of this counter can occur at
            re-initialization of the management system, and at other
            times as indicated by the value of
            ifCounterDiscontinuityTime."
    ::= { ifXEntry 11 }

ifHCOutMulticastPkts OBJECT-TYPE
    SYNTAX      Counter64
    MAX-ACCESS  read-only
    STATUS      current
    DESCRIPTION
            "The total number of packets that higher-level protocols
            requested be transmitted, and which were addressed to a
            multicast address at this sub-layer, including those that
            were discarded or not sent.  For a MAC layer protocol, this
            includes both Group and Functional addresses.  This object
            is a 64-bit version of ifOutMulticastPkts.

            Discontinuities in the value of this counter can occur at
            re-initialization of the management system, and at other
            times as indicated by the value of
            ifCounterDiscontinuityTime."
    ::= { ifXEntry 12 }

ifHCOutBroadcastPkts OBJECT-TYPE
    SYNTAX      Counter64
    MAX-ACCESS  read-only
    STATUS      current
    DESCRIPTION
            "The total number of packets that higher-level protocols
            requested be transmitted, and which were addressed to a
            broadcast address at this sub-layer, including those that
            were discarded or not sent.  This object is a 64-bit version
            of ifOutBroadcastPkts.

            Discontinuities in the value of this counter can occur at
            re-initialization of the management system, and at other
            times as indicated by the value of
            ifCounterDiscontinuityTime."
    ::= { ifXEntry 13 }

ifLinkUpDownTrapEnable  OBJECT-TYPE


    SYNTAX      INTEGER { enabled(1), disabled(2) }
    MAX-ACCESS  read-write
    STATUS      current
    DESCRIPTION
            "Indicates whether linkUp/linkDown traps should be generated
            for this interface.

            By default, this object should have the value enabled(1) for
            interfaces which do not operate on 'top' of any other
            interface (as defined in the ifStackTable), and disabled(2)
            otherwise."
    ::= { ifXEntry 14 }

ifHighSpeed OBJECT-TYPE
    SYNTAX      Gauge32
    MAX-ACCESS  read-only
    STATUS      current
    DESCRIPTION
            "An estimate of the interface's current bandwidth in units
            of 1,000,000 bits per second.  If this object reports a
            value of `n' then the speed of the interface is somewhere in
            the range of `n-500,000' to `n+499,999'.  For interfaces
            which do not vary in bandwidth or for those where no
            accurate estimation can be made, this object should contain
            the nominal bandwidth.  For a sub-layer which has no concept
            of bandwidth, this object should be zero."
    ::= { ifXEntry 15 }

ifPromiscuousMode  OBJECT-TYPE
    SYNTAX      TruthValue
    MAX-ACCESS  read-write
    STATUS      current
    DESCRIPTION
            "This object has a value of false(2) if this interface only
            accepts packets/frames that are addressed to this station.
            This object has a value of true(1) when the station accepts
            all packets/frames transmitted on the media.  The value
            true(1) is only legal on certain types of media.  If legal,
            setting this object to a value of true(1) may require the
            interface to be reset before becoming effective.

            The value of ifPromiscuousMode does not affect the reception
            of broadcast and multicast packets/frames by the interface."
    ::= { ifXEntry 16 }

ifConnectorPresent   OBJECT-TYPE
    SYNTAX      TruthValue
    MAX-ACCESS  read-only


    STATUS      current
    DESCRIPTION
            "This object has the value 'true(1)' if the interface
            sublayer has a physical connector and the value 'false(2)'
            otherwise."
    ::= { ifXEntry 17 }

ifAlias   OBJECT-TYPE
    SYNTAX      DisplayString (SIZE(0..64))
    MAX-ACCESS  read-write
    STATUS      current
    DESCRIPTION
            "This object is an 'alias' name for the interface as
            specified by a network manager, and provides a non-volatile
            'handle' for the interface.

            On the first instantiation of an interface, the value of
            ifAlias associated with that interface is the zero-length
            string.  As and when a value is written into an instance of
            ifAlias through a network management set operation, then the
            agent must retain the supplied value in the ifAlias instance
            associated with the same interface for as long as that
            interface remains instantiated, including across all re-
            initializations/reboots of the network management system,
            including those which result in a change of the interface's
            ifIndex value.

            An example of the value which a network manager might store
            in this object for a WAN interface is the (Telco's) circuit
            number/identifier of the interface.

            Some agents may support write-access only for interfaces
            having particular values of ifType.  An agent which supports
            write access to this object is required to keep the value in
            non-volatile storage, but it may limit the length of new
            values depending on how much storage is already occupied by
            the current values for other interfaces."
    ::= { ifXEntry 18 }

ifCounterDiscontinuityTime OBJECT-TYPE
    SYNTAX      TimeStamp
    MAX-ACCESS  read-only
    STATUS      current
    DESCRIPTION
            "The value of sysUpTime on the most recent occasion at which
            any one or more of this interface's counters suffered a
            discontinuity.  The relevant counters are the specific
            instances associated with this interface of any Counter32 or


            Counter64 object contained in the ifTable or ifXTable.  If
            no such discontinuities have occurred since the last re-
            initialization of the local management subsystem, then this
            object contains a zero value."
    ::= { ifXEntry 19 }

--           The Interface Stack Group
--
-- Implementation of this group is optional, but strongly recommended
-- for all systems
--

ifStackTable  OBJECT-TYPE
     SYNTAX        SEQUENCE OF IfStackEntry
     MAX-ACCESS    not-accessible
     STATUS        current
     DESCRIPTION
            "The table containing information on the relationships
            between the multiple sub-layers of network interfaces.  In
            particular, it contains information on which sub-layers run
            'on top of' which other sub-layers, where each sub-layer
            corresponds to a conceptual row in the ifTable.  For
            example, when the sub-layer with ifIndex value x runs over
            the sub-layer with ifIndex value y, then this table
            contains:

              ifStackStatus.x.y=active

            For each ifIndex value, I, which identifies an active
            interface, there are always at least two instantiated rows
            in this table associated with I.  For one of these rows, I
            is the value of ifStackHigherLayer; for the other, I is the
            value of ifStackLowerLayer.  (If I is not involved in
            multiplexing, then these are the only two rows associated
            with I.)

            For example, two rows exist even for an interface which has
            no others stacked on top or below it:

              ifStackStatus.0.x=active
              ifStackStatus.x.0=active "
     ::= { ifMIBObjects 2 }

ifStackEntry  OBJECT-TYPE
     SYNTAX        IfStackEntry
     MAX-ACCESS    not-accessible
     STATUS        current


     DESCRIPTION
            "Information on a particular relationship between two sub-
            layers, specifying that one sub-layer runs on 'top' of the
            other sub-layer.  Each sub-layer corresponds to a conceptual
            row in the ifTable."
     INDEX { ifStackHigherLayer, ifStackLowerLayer }
     ::= { ifStackTable 1 }

IfStackEntry ::=
    SEQUENCE {
        ifStackHigherLayer  InterfaceIndexOrZero,
        ifStackLowerLayer   InterfaceIndexOrZero,
        ifStackStatus       RowStatus
     }

ifStackHigherLayer  OBJECT-TYPE
     SYNTAX        InterfaceIndexOrZero
     MAX-ACCESS    not-accessible
     STATUS        current
     DESCRIPTION
            "The value of ifIndex corresponding to the higher sub-layer
            of the relationship, i.e., the sub-layer which runs on 'top'
            of the sub-layer identified by the corresponding instance of
            ifStackLowerLayer.  If there is no higher sub-layer (below
            the internetwork layer), then this object has the value 0."
     ::= { ifStackEntry 1 }

ifStackLowerLayer  OBJECT-TYPE
     SYNTAX        InterfaceIndexOrZero
     MAX-ACCESS    not-accessible
     STATUS        current
     DESCRIPTION
            "The value of ifIndex corresponding to the lower sub-layer
            of the relationship, i.e., the sub-layer which runs 'below'
            the sub-layer identified by the corresponding instance of
            ifStackHigherLayer.  If there is no lower sub-layer, then
            this object has the value 0."
     ::= { ifStackEntry 2 }

ifStackStatus  OBJECT-TYPE
    SYNTAX         RowStatus
    MAX-ACCESS     read-create
    STATUS         current
    DESCRIPTION


            "The status of the relationship between two sub-layers.

            Changing the value of this object from 'active' to
            'notInService' or 'destroy' will likely have consequences up
            and down the interface stack.  Thus, write access to this
            object is likely to be inappropriate for some types of
            interfaces, and many implementations will choose not to
            support write-access for any type of interface."
    ::= { ifStackEntry 3 }

ifStackLastChange OBJECT-TYPE
    SYNTAX         TimeTicks
    MAX-ACCESS     read-only
    STATUS         current
    DESCRIPTION
            "The value of sysUpTime at the time of the last change of
            the (whole) interface stack.  A change of the interface
            stack is defined to be any creation, deletion, or change in
            value of any instance of ifStackStatus.  If the interface
            stack has been unchanged since the last re-initialization of
            the local network management subsystem, then this object
            contains a zero value."
    ::= { ifMIBObjects 6 }

--   Generic Receive Address Table
--
-- This group of objects is mandatory for all types of
-- interfaces which can receive packets/frames addressed to
-- more than one address.
--
-- This table replaces the ifExtnsRcvAddr table.  The main
-- difference is that this table makes use of the RowStatus
-- textual convention, while ifExtnsRcvAddr did not.

ifRcvAddressTable  OBJECT-TYPE
    SYNTAX      SEQUENCE OF IfRcvAddressEntry
    MAX-ACCESS  not-accessible
    STATUS      current
    DESCRIPTION
            "This table contains an entry for each address (broadcast,
            multicast, or uni-cast) for which the system will receive
            packets/frames on a particular interface, except as follows:

            - for an interface operating in promiscuous mode, entries
            are only required for those addresses for which the system
            would receive frames were it not operating in promiscuous
            mode.


            - for 802.5 functional addresses, only one entry is
            required, for the address which has the functional address
            bit ANDed with the bit mask of all functional addresses for
            which the interface will accept frames.

            A system is normally able to use any unicast address which
            corresponds to an entry in this table as a source address."
    ::= { ifMIBObjects 4 }

ifRcvAddressEntry  OBJECT-TYPE
    SYNTAX      IfRcvAddressEntry
    MAX-ACCESS  not-accessible
    STATUS      current
    DESCRIPTION
            "A list of objects identifying an address for which the
            system will accept packets/frames on the particular
            interface identified by the index value ifIndex."
    INDEX  { ifIndex, ifRcvAddressAddress }
    ::= { ifRcvAddressTable 1 }

IfRcvAddressEntry ::=
    SEQUENCE {
        ifRcvAddressAddress   PhysAddress,
        ifRcvAddressStatus    RowStatus,
        ifRcvAddressType      INTEGER
    }

ifRcvAddressAddress OBJECT-TYPE
    SYNTAX      PhysAddress
    MAX-ACCESS  not-accessible
    STATUS      current
    DESCRIPTION
            "An address for which the system will accept packets/frames
            on this entry's interface."
    ::= { ifRcvAddressEntry 1 }

ifRcvAddressStatus OBJECT-TYPE
    SYNTAX      RowStatus
    MAX-ACCESS  read-create
    STATUS      current
    DESCRIPTION
            "This object is used to create and delete rows in the
            ifRcvAddressTable."

    ::= { ifRcvAddressEntry 2 }

ifRcvAddressType OBJECT-TYPE
    SYNTAX      INTEGER {


                    other(1),
                    volatile(2),
                    nonVolatile(3)
                }

    MAX-ACCESS  read-create
    STATUS      current
    DESCRIPTION
            "This object has the value nonVolatile(3) for those entries
            in the table which are valid and will not be deleted by the
            next restart of the managed system.  Entries having the
            value volatile(2) are valid and exist, but have not been
            saved, so that will not exist after the next restart of the
            managed system.  Entries having the value other(1) are valid
            and exist but are not classified as to whether they will
            continue to exist after the next restart."

    DEFVAL  { volatile }
    ::= { ifRcvAddressEntry 3 }

-- definition of interface-related traps.

linkDown NOTIFICATION-TYPE
    OBJECTS { ifIndex, ifAdminStatus, ifOperStatus }
    STATUS  current
    DESCRIPTION
            "A linkDown trap signifies that the SNMP entity, acting in
            an agent role, has detected that the ifOperStatus object for
            one of its communication links is about to enter the down
            state from some other state (but not from the notPresent
            state).  This other state is indicated by the included value
            of ifOperStatus."
    ::= { snmpTraps 3 }

linkUp NOTIFICATION-TYPE
    OBJECTS { ifIndex, ifAdminStatus, ifOperStatus }
    STATUS  current
    DESCRIPTION
            "A linkUp trap signifies that the SNMP entity, acting in an
            agent role, has detected that the ifOperStatus object for
            one of its communication links left the down state and
            transitioned into some other state (but not into the
            notPresent state).  This other state is indicated by the
            included value of ifOperStatus."
    ::= { snmpTraps 4 }

-- conformance information


ifConformance OBJECT IDENTIFIER ::= { ifMIB 2 }

ifGroups      OBJECT IDENTIFIER ::= { ifConformance 1 }
ifCompliances OBJECT IDENTIFIER ::= { ifConformance 2 }

-- compliance statements

ifCompliance3 MODULE-COMPLIANCE
    STATUS  current
    DESCRIPTION
            "The compliance statement for SNMP entities which have
            network interfaces."

    MODULE  -- this module
        MANDATORY-GROUPS { ifGeneralInformationGroup,
                           linkUpDownNotificationsGroup }

-- The groups:
--        ifFixedLengthGroup
--        ifHCFixedLengthGroup
--        ifPacketGroup
--        ifHCPacketGroup
--        ifVHCPacketGroup
-- are mutually exclusive; at most one of these groups is implemented
-- for a particular interface.  When any of these groups is implemented
-- for a particular interface, then ifCounterDiscontinuityGroup must
-- also be implemented for that interface.

        GROUP       ifFixedLengthGroup
        DESCRIPTION
            "This group is mandatory for those network interfaces which
            are character-oriented or transmit data in fixed-length
            transmission units, and for which the value of the
            corresponding instance of ifSpeed is less than or equal to
            20,000,000 bits/second."

        GROUP       ifHCFixedLengthGroup
        DESCRIPTION
            "This group is mandatory for those network interfaces which
            are character-oriented or transmit data in fixed-length
            transmission units, and for which the value of the
            corresponding instance of ifSpeed is greater than 20,000,000
            bits/second."

        GROUP       ifPacketGroup
        DESCRIPTION


            "This group is mandatory for those network interfaces which
            are packet-oriented, and for which the value of the
            corresponding instance of ifSpeed is less than or equal to
            20,000,000 bits/second."

        GROUP       ifHCPacketGroup
        DESCRIPTION
            "This group is mandatory only for those network interfaces
            which are packet-oriented and for which the value of the
            corresponding instance of ifSpeed is greater than 20,000,000
            bits/second but less than or equal to 650,000,000
            bits/second."

        GROUP       ifVHCPacketGroup
        DESCRIPTION
            "This group is mandatory only for those network interfaces
            which are packet-oriented and for which the value of the
            corresponding instance of ifSpeed is greater than
            650,000,000 bits/second."

        GROUP       ifCounterDiscontinuityGroup
        DESCRIPTION
            "This group is mandatory for those network interfaces that
            are required to maintain counters (i.e., those for which one
            of the ifFixedLengthGroup, ifHCFixedLengthGroup,
            ifPacketGroup, ifHCPacketGroup, or ifVHCPacketGroup is
            mandatory)."

        GROUP       ifRcvAddressGroup
        DESCRIPTION
            "The applicability of this group MUST be defined by the
            media-specific MIBs.  Media-specific MIBs must define the
            exact meaning, use, and semantics of the addresses in this
            group."

        OBJECT      ifLinkUpDownTrapEnable
        MIN-ACCESS  read-only
        DESCRIPTION
            "Write access is not required."

        OBJECT      ifPromiscuousMode
        MIN-ACCESS  read-only
        DESCRIPTION
            "Write access is not required."

        OBJECT       ifAdminStatus


        SYNTAX       INTEGER { up(1), down(2) }
        MIN-ACCESS   read-only
        DESCRIPTION
            "Write access is not required, nor is support for the value
            testing(3)."

        OBJECT       ifAlias
        MIN-ACCESS   read-only
        DESCRIPTION
            "Write access is not required."

    ::= { ifCompliances 3 }

-- units of conformance

ifGeneralInformationGroup    OBJECT-GROUP
    OBJECTS { ifIndex, ifDescr, ifType, ifSpeed, ifPhysAddress,
              ifAdminStatus, ifOperStatus, ifLastChange,
              ifLinkUpDownTrapEnable, ifConnectorPresent,
              ifHighSpeed, ifName, ifNumber, ifAlias,
              ifTableLastChange }
    STATUS  current
    DESCRIPTION
            "A collection of objects providing information applicable to
            all network interfaces."
    ::= { ifGroups 10 }

-- the following five groups are mutually exclusive; at most
-- one of these groups is implemented for any interface

ifFixedLengthGroup    OBJECT-GROUP
    OBJECTS { ifInOctets, ifOutOctets, ifInUnknownProtos,
              ifInErrors, ifOutErrors }
    STATUS  current
    DESCRIPTION
            "A collection of objects providing information specific to
            non-high speed (non-high speed interfaces transmit and
            receive at speeds less than or equal to 20,000,000
            bits/second) character-oriented or fixed-length-transmission
            network interfaces."
    ::= { ifGroups 2 }

ifHCFixedLengthGroup    OBJECT-GROUP
    OBJECTS { ifHCInOctets, ifHCOutOctets,
              ifInOctets, ifOutOctets, ifInUnknownProtos,
              ifInErrors, ifOutErrors }
    STATUS  current
    DESCRIPTION


            "A collection of objects providing information specific to
            high speed (greater than 20,000,000 bits/second) character-
            oriented or fixed-length-transmission network interfaces."
    ::= { ifGroups 3 }

ifPacketGroup    OBJECT-GROUP
    OBJECTS { ifInOctets, ifOutOctets, ifInUnknownProtos,
              ifInErrors, ifOutErrors,
              ifMtu, ifInUcastPkts, ifInMulticastPkts,
              ifInBroadcastPkts, ifInDiscards,
              ifOutUcastPkts, ifOutMulticastPkts,
              ifOutBroadcastPkts, ifOutDiscards,
              ifPromiscuousMode }
    STATUS  current
    DESCRIPTION
            "A collection of objects providing information specific to
            non-high speed (non-high speed interfaces transmit and
            receive at speeds less than or equal to 20,000,000
            bits/second) packet-oriented network interfaces."
    ::= { ifGroups 4 }

ifHCPacketGroup    OBJECT-GROUP
    OBJECTS { ifHCInOctets, ifHCOutOctets,
              ifInOctets, ifOutOctets, ifInUnknownProtos,
              ifInErrors, ifOutErrors,
              ifMtu, ifInUcastPkts, ifInMulticastPkts,
              ifInBroadcastPkts, ifInDiscards,
              ifOutUcastPkts, ifOutMulticastPkts,
              ifOutBroadcastPkts, ifOutDiscards,
              ifPromiscuousMode }
    STATUS  current
    DESCRIPTION
            "A collection of objects providing information specific to
            high speed (greater than 20,000,000 bits/second but less
            than or equal to 650,000,000 bits/second) packet-oriented
            network interfaces."
    ::= { ifGroups 5 }

ifVHCPacketGroup    OBJECT-GROUP
    OBJECTS { ifHCInUcastPkts, ifHCInMulticastPkts,
              ifHCInBroadcastPkts, ifHCOutUcastPkts,
              ifHCOutMulticastPkts, ifHCOutBroadcastPkts,
              ifHCInOctets, ifHCOutOctets,
              ifInOctets, ifOutOctets, ifInUnknownProtos,
              ifInErrors, ifOutErrors,
              ifMtu, ifInUcastPkts, ifInMulticastPkts,
              ifInBroadcastPkts, ifInDiscards,
              ifOutUcastPkts, ifOutMulticastPkts,


              ifOutBroadcastPkts, ifOutDiscards,
              ifPromiscuousMode }
    STATUS  current
    DESCRIPTION
            "A collection of objects providing information specific to
            higher speed (greater than 650,000,000 bits/second) packet-
            oriented network interfaces."
    ::= { ifGroups 6 }

ifRcvAddressGroup    OBJECT-GROUP
    OBJECTS { ifRcvAddressStatus, ifRcvAddressType }
    STATUS  current
    DESCRIPTION
            "A collection of objects providing information on the
            multiple addresses which an interface receives."
    ::= { ifGroups 7 }

ifStackGroup2    OBJECT-GROUP
    OBJECTS { ifStackStatus, ifStackLastChange }
    STATUS  current
    DESCRIPTION
            "A collection of objects providing information on the
            layering of MIB-II interfaces."
    ::= { ifGroups 11 }

ifCounterDiscontinuityGroup  OBJECT-GROUP
    OBJECTS { ifCounterDiscontinuityTime }
    STATUS  current
    DESCRIPTION
            "A collection of objects providing information specific to
            interface counter discontinuities."
    ::= { ifGroups 13 }

linkUpDownNotificationsGroup  NOTIFICATION-GROUP
    NOTIFICATIONS { linkUp, linkDown }
    STATUS  current
    DESCRIPTION
            "The notifications which indicate specific changes in the
            value of ifOperStatus."
    ::= { ifGroups 14 }

-- Deprecated Definitions - Objects

--
--    The Interface Test Table
--
-- This group of objects is optional.  However, a media-specific


-- MIB may make implementation of this group mandatory.
--
-- This table replaces the ifExtnsTestTable
--

ifTestTable   OBJECT-TYPE
    SYNTAX      SEQUENCE OF IfTestEntry
    MAX-ACCESS  not-accessible
    STATUS      deprecated
    DESCRIPTION
            "This table contains one entry per interface.  It defines
            objects which allow a network manager to instruct an agent
            to test an interface for various faults.  Tests for an
            interface are defined in the media-specific MIB for that
            interface.  After invoking a test, the object ifTestResult
            can be read to determine the outcome.  If an agent can not
            perform the test, ifTestResult is set to so indicate.  The
            object ifTestCode can be used to provide further test-
            specific or interface-specific (or even enterprise-specific)
            information concerning the outcome of the test.  Only one
            test can be in progress on each interface at any one time.
            If one test is in progress when another test is invoked, the
            second test is rejected.  Some agents may reject a test when
            a prior test is active on another interface.

            Before starting a test, a manager-station must first obtain
            'ownership' of the entry in the ifTestTable for the
            interface to be tested.  This is accomplished with the
            ifTestId and ifTestStatus objects as follows:

          try_again:
              get (ifTestId, ifTestStatus)
              while (ifTestStatus != notInUse)
                  /*
                   * Loop while a test is running or some other
                   * manager is configuring a test.
                   */
                  short delay
                  get (ifTestId, ifTestStatus)
              }

              /*
               * Is not being used right now -- let's compete
               * to see who gets it.
               */
              lock_value = ifTestId

              if ( set(ifTestId = lock_value, ifTestStatus = inUse,


                       ifTestOwner = 'my-IP-address') == FAILURE)
                  /*
                   * Another manager got the ifTestEntry -- go
                   * try again
                   */
                  goto try_again;

              /*
               * I have the lock
               */
              set up any test parameters.

              /*
               * This starts the test
               */
              set(ifTestType = test_to_run);

              wait for test completion by polling ifTestResult

              when test completes, agent sets ifTestResult
                   agent also sets ifTestStatus = 'notInUse'

              retrieve any additional test results, and ifTestId

              if (ifTestId == lock_value+1) results are valid

            A manager station first retrieves the value of the
            appropriate ifTestId and ifTestStatus objects, periodically
            repeating the retrieval if necessary, until the value of
            ifTestStatus is 'notInUse'.  The manager station then tries
            to set the same ifTestId object to the value it just
            retrieved, the same ifTestStatus object to 'inUse', and the
            corresponding ifTestOwner object to a value indicating
            itself.  If the set operation succeeds then the manager has
            obtained ownership of the ifTestEntry, and the value of the
            ifTestId object is incremented by the agent (per the
            semantics of TestAndIncr).  Failure of the set operation
            indicates that some other manager has obtained ownership of
            the ifTestEntry.

            Once ownership is obtained, any test parameters can be
            setup, and then the test is initiated by setting ifTestType.
            On completion of the test, the agent sets ifTestStatus to
            'notInUse'.  Once this occurs, the manager can retrieve the
            results.  In the (rare) event that the invocation of tests
            by two network managers were to overlap, then there would be
            a possibility that the first test's results might be
            overwritten by the second test's results prior to the first


            results being read.  This unlikely circumstance can be
            detected by a network manager retrieving ifTestId at the
            same time as retrieving the test results, and ensuring that
            the results are for the desired request.

            If ifTestType is not set within an abnormally long period of
            time after ownership is obtained, the agent should time-out
            the manager, and reset the value of the ifTestStatus object
            back to 'notInUse'.  It is suggested that this time-out
            period be 5 minutes.

            In general, a management station must not retransmit a
            request to invoke a test for which it does not receive a
            response; instead, it properly inspects an agent's MIB to
            determine if the invocation was successful.  Only if the
            invocation was unsuccessful, is the invocation request
            retransmitted.

            Some tests may require the interface to be taken off-line in
            order to execute them, or may even require the agent to
            reboot after completion of the test.  In these
            circumstances, communication with the management station
            invoking the test may be lost until after completion of the
            test.  An agent is not required to support such tests.
            However, if such tests are supported, then the agent should
            make every effort to transmit a response to the request
            which invoked the test prior to losing communication.  When
            the agent is restored to normal service, the results of the
            test are properly made available in the appropriate objects.
            Note that this requires that the ifIndex value assigned to
            an interface must be unchanged even if the test causes a
            reboot.  An agent must reject any test for which it cannot,
            perhaps due to resource constraints, make available at least
            the minimum amount of information after that test
            completes."
    ::= { ifMIBObjects 3 }

ifTestEntry OBJECT-TYPE
    SYNTAX       IfTestEntry
    MAX-ACCESS   not-accessible
    STATUS       deprecated
    DESCRIPTION
            "An entry containing objects for invoking tests on an
            interface."
    AUGMENTS  { ifEntry }
    ::= { ifTestTable 1 }

IfTestEntry ::=


    SEQUENCE {
        ifTestId           TestAndIncr,
        ifTestStatus       INTEGER,
        ifTestType         AutonomousType,
        ifTestResult       INTEGER,
        ifTestCode         OBJECT IDENTIFIER,
        ifTestOwner        OwnerString
    }

ifTestId         OBJECT-TYPE
    SYNTAX       TestAndIncr
    MAX-ACCESS   read-write
    STATUS       deprecated
    DESCRIPTION
            "This object identifies the current invocation of the
            interface's test."
    ::= { ifTestEntry 1 }

ifTestStatus     OBJECT-TYPE
    SYNTAX       INTEGER { notInUse(1), inUse(2) }
    MAX-ACCESS   read-write
    STATUS       deprecated
    DESCRIPTION
            "This object indicates whether or not some manager currently
            has the necessary 'ownership' required to invoke a test on
            this interface.  A write to this object is only successful
            when it changes its value from 'notInUse(1)' to 'inUse(2)'.
            After completion of a test, the agent resets the value back
            to 'notInUse(1)'."
    ::= { ifTestEntry 2 }

ifTestType       OBJECT-TYPE
    SYNTAX       AutonomousType
    MAX-ACCESS   read-write
    STATUS       deprecated
    DESCRIPTION
            "A control variable used to start and stop operator-
            initiated interface tests.  Most OBJECT IDENTIFIER values
            assigned to tests are defined elsewhere, in association with
            specific types of interface.  However, this document assigns
            a value for a full-duplex loopback test, and defines the
            special meanings of the subject identifier:

                noTest  OBJECT IDENTIFIER ::= { 0 0 }

            When the value noTest is written to this object, no action
            is taken unless a test is in progress, in which case the
            test is aborted.  Writing any other value to this object is


            only valid when no test is currently in progress, in which
            case the indicated test is initiated.

            When read, this object always returns the most recent value
            that ifTestType was set to.  If it has not been set since
            the last initialization of the network management subsystem
            on the agent, a value of noTest is returned."
    ::= { ifTestEntry 3 }

ifTestResult  OBJECT-TYPE
    SYNTAX       INTEGER {
                     none(1),          -- no test yet requested
                     success(2),
                     inProgress(3),
                     notSupported(4),
                     unAbleToRun(5),   -- due to state of system
                     aborted(6),
                     failed(7)
                 }
    MAX-ACCESS   read-only
    STATUS       deprecated
    DESCRIPTION
            "This object contains the result of the most recently
            requested test, or the value none(1) if no tests have been
            requested since the last reset.  Note that this facility
            provides no provision for saving the results of one test
            when starting another, as could be required if used by
            multiple managers concurrently."
    ::= { ifTestEntry 4 }

ifTestCode  OBJECT-TYPE
    SYNTAX       OBJECT IDENTIFIER
    MAX-ACCESS   read-only
    STATUS       deprecated
    DESCRIPTION
            "This object contains a code which contains more specific
            information on the test result, for example an error-code
            after a failed test.  Error codes and other values this
            object may take are specific to the type of interface and/or
            test.  The value may have the semantics of either the
            AutonomousType or InstancePointer textual conventions as
            defined in RFC 2579.  The identifier:

                testCodeUnknown  OBJECT IDENTIFIER ::= { 0 0 }

            is defined for use if no additional result code is
            available."
    ::= { ifTestEntry 5 }


ifTestOwner      OBJECT-TYPE
    SYNTAX       OwnerString
    MAX-ACCESS   read-write
    STATUS       deprecated
    DESCRIPTION
            "The entity which currently has the 'ownership' required to
            invoke a test on this interface."
    ::= { ifTestEntry 6 }

-- Deprecated Definitions - Groups

ifGeneralGroup    OBJECT-GROUP
    OBJECTS { ifDescr, ifType, ifSpeed, ifPhysAddress,
              ifAdminStatus, ifOperStatus, ifLastChange,
              ifLinkUpDownTrapEnable, ifConnectorPresent,
              ifHighSpeed, ifName }
    STATUS  deprecated
    DESCRIPTION
            "A collection of objects deprecated in favour of
            ifGeneralInformationGroup."
    ::= { ifGroups 1 }

ifTestGroup    OBJECT-GROUP
    OBJECTS { ifTestId, ifTestStatus, ifTestType,
              ifTestResult, ifTestCode, ifTestOwner }
    STATUS  deprecated
    DESCRIPTION
            "A collection of objects providing the ability to invoke
            tests on an interface."
    ::= { ifGroups 8 }

ifStackGroup    OBJECT-GROUP
    OBJECTS { ifStackStatus }
    STATUS  deprecated
    DESCRIPTION
            "The previous collection of objects providing information on
            the layering of MIB-II interfaces."
    ::= { ifGroups 9 }

ifOldObjectsGroup    OBJECT-GROUP
    OBJECTS { ifInNUcastPkts, ifOutNUcastPkts,
              ifOutQLen, ifSpecific }
    STATUS  deprecated
    DESCRIPTION


            "The collection of objects deprecated from the original MIB-
            II interfaces group."
    ::= { ifGroups 12 }

-- Deprecated Definitions - Compliance

ifCompliance MODULE-COMPLIANCE
    STATUS  deprecated
    DESCRIPTION
            "A compliance statement defined in a previous version of
            this MIB module, for SNMP entities which have network
            interfaces."

    MODULE  -- this module
        MANDATORY-GROUPS { ifGeneralGroup, ifStackGroup }

        GROUP       ifFixedLengthGroup
        DESCRIPTION
            "This group is mandatory for all network interfaces which
            are character-oriented or transmit data in fixed-length
            transmission units."

        GROUP       ifHCFixedLengthGroup
        DESCRIPTION
            "This group is mandatory only for those network interfaces
            which are character-oriented or transmit data in fixed-
            length transmission units, and for which the value of the
            corresponding instance of ifSpeed is greater than 20,000,000
            bits/second."

        GROUP       ifPacketGroup
        DESCRIPTION
            "This group is mandatory for all network interfaces which
            are packet-oriented."

        GROUP       ifHCPacketGroup
        DESCRIPTION
            "This group is mandatory only for those network interfaces
            which are packet-oriented and for which the value of the
            corresponding instance of ifSpeed is greater than
            650,000,000 bits/second."

        GROUP       ifTestGroup
        DESCRIPTION
            "This group is optional.  Media-specific MIBs which require
            interface tests are strongly encouraged to use this group
            for invoking tests and reporting results.  A medium specific
            MIB which has mandatory tests may make implementation of


            this group mandatory."

        GROUP       ifRcvAddressGroup
        DESCRIPTION
            "The applicability of this group MUST be defined by the
            media-specific MIBs.  Media-specific MIBs must define the
            exact meaning, use, and semantics of the addresses in this
            group."

        OBJECT      ifLinkUpDownTrapEnable
        MIN-ACCESS  read-only
        DESCRIPTION
            "Write access is not required."

        OBJECT      ifPromiscuousMode
        MIN-ACCESS  read-only
        DESCRIPTION
            "Write access is not required."

        OBJECT      ifStackStatus
        SYNTAX      INTEGER { active(1) } -- subset of RowStatus
        MIN-ACCESS  read-only
        DESCRIPTION
            "Write access is not required, and only one of the six
            enumerated values for the RowStatus textual convention need
            be supported, specifically: active(1)."

        OBJECT       ifAdminStatus
        SYNTAX       INTEGER { up(1), down(2) }
        MIN-ACCESS   read-only
        DESCRIPTION
            "Write access is not required, nor is support for the value
            testing(3)."
    ::= { ifCompliances 1 }

ifCompliance2 MODULE-COMPLIANCE
    STATUS      deprecated
    DESCRIPTION
            "A compliance statement defined in a previous version of
            this MIB module, for SNMP entities which have network
            interfaces."

    MODULE  -- this module
        MANDATORY-GROUPS { ifGeneralInformationGroup, ifStackGroup2,
                           ifCounterDiscontinuityGroup }

        GROUP       ifFixedLengthGroup
        DESCRIPTION


            "This group is mandatory for all network interfaces which
            are character-oriented or transmit data in fixed-length
            transmission units."

        GROUP       ifHCFixedLengthGroup
        DESCRIPTION
            "This group is mandatory only for those network interfaces
            which are character-oriented or transmit data in fixed-
            length transmission units, and for which the value of the
            corresponding instance of ifSpeed is greater than 20,000,000
            bits/second."

        GROUP       ifPacketGroup
        DESCRIPTION
            "This group is mandatory for all network interfaces which
            are packet-oriented."

        GROUP       ifHCPacketGroup
        DESCRIPTION
            "This group is mandatory only for those network interfaces
            which are packet-oriented and for which the value of the
            corresponding instance of ifSpeed is greater than
            650,000,000 bits/second."

        GROUP       ifRcvAddressGroup
        DESCRIPTION
            "The applicability of this group MUST be defined by the
            media-specific MIBs.  Media-specific MIBs must define the
            exact meaning, use, and semantics of the addresses in this
            group."

        OBJECT      ifLinkUpDownTrapEnable
        MIN-ACCESS  read-only
        DESCRIPTION
            "Write access is not required."

        OBJECT      ifPromiscuousMode
        MIN-ACCESS  read-only
        DESCRIPTION
            "Write access is not required."

        OBJECT      ifStackStatus
        SYNTAX      INTEGER { active(1) } -- subset of RowStatus
        MIN-ACCESS  read-only
        DESCRIPTION
            "Write access is not required, and only one of the six
            enumerated values for the RowStatus textual convention need
            be supported, specifically: active(1)."


        OBJECT       ifAdminStatus
        SYNTAX       INTEGER { up(1), down(2) }
        MIN-ACCESS   read-only
        DESCRIPTION
            "Write access is not required, nor is support for the value
            testing(3)."

        OBJECT       ifAlias
        MIN-ACCESS   read-only
        DESCRIPTION
            "Write access is not required."

    ::= { ifCompliances 2 }

END

IP-FORWARD-MIB DEFINITIONS ::= BEGIN

IMPORTS
    MODULE-IDENTITY, OBJECT-TYPE, IpAddress, Integer32, Gauge32
        FROM SNMPv2-SMI
    RowStatus
        FROM SNMPv2-TC
    ip
        FROM RFC1213-MIB
    MODULE-COMPLIANCE, OBJECT-GROUP
        FROM SNMPv2-CONF;

ipForward MODULE-IDENTITY
    LAST-UPDATED "9609190000Z"     -- Thu Sep 26 16:34:47 PDT 1996
    ORGANIZATION "IETF OSPF Working Group"
    CONTACT-INFO
     "        Fred Baker
      Postal: Cisco Systems
              519 Lado Drive
              Santa Barbara, California 93111

      Phone:  +1 805 681 0115
      Email:  fred@cisco.com
      "
    DESCRIPTION
            "The MIB module for the display of CIDR multipath IP Routes."
    REVISION      "9609190000Z"
    DESCRIPTION
            "Revisions made by the OSPF WG."
    ::= { ip 24 }

ipCidrRouteNumber OBJECT-TYPE
    SYNTAX   Gauge32
    MAX-ACCESS read-only
    STATUS   current
    DESCRIPTION
       "The number of current ipCidrRouteTable entries
       that are not invalid."
    ::= { ipForward 3 }

--  IP CIDR Route Table

--  The IP CIDR Route Table obsoletes and replaces the ipRoute
--  Table current in MIB-I and MIB-II and the IP Forwarding Table.
--  It adds knowledge of the autonomous system of the next hop,
--  multiple next hops, and policy routing, and Classless
--  Inter-Domain Routing.

ipCidrRouteTable OBJECT-TYPE
    SYNTAX   SEQUENCE OF IpCidrRouteEntry
    MAX-ACCESS not-accessible
    STATUS   current
    DESCRIPTION
       "This entity's IP Routing table."
    REFERENCE
       "RFC 1213 Section 6.6, The IP Group"
    ::= { ipForward 4 }

ipCidrRouteEntry OBJECT-TYPE
    SYNTAX   IpCidrRouteEntry
    MAX-ACCESS not-accessible
    STATUS   current
    DESCRIPTION
       "A particular route to  a  particular  destina-
       tion, under a particular policy."
    INDEX {
        ipCidrRouteDest,
        ipCidrRouteMask,
        ipCidrRouteTos,
        ipCidrRouteNextHop
        }
    ::= { ipCidrRouteTable 1 }

IpCidrRouteEntry ::=
    SEQUENCE {
        ipCidrRouteDest
            IpAddress,
        ipCidrRouteMask
            IpAddress,
        ipCidrRouteTos
             Integer32,
        ipCidrRouteNextHop
            IpAddress,
        ipCidrRouteIfIndex
            Integer32,
        ipCidrRouteType
            INTEGER,
        ipCidrRouteProto
            INTEGER,
        ipCidrRouteAge
            Integer32,
        ipCidrRouteInfo
            OBJECT IDENTIFIER,
        ipCidrRouteNextHopAS
            Integer32,
        ipCidrRouteMetric1
            Integer32,
        ipCidrRouteMetric2
            Integer32,
        ipCidrRouteMetric3
            Integer32,
        ipCidrRouteMetric4
            Integer32,
        ipCidrRouteMetric5
            Integer32,
        ipCidrRouteStatus
            RowStatus
    }

ipCidrRouteDest OBJECT-TYPE
    SYNTAX   IpAddress
    MAX-ACCESS read-only
    STATUS   current
    DESCRIPTION
       "The destination IP address of this route.

       This object may not take a Multicast (Class  D)
       address value.

       Any assignment (implicit or  otherwise)  of  an
       instance  of  this  object to a value x must be
       rejected if the bitwise logical-AND of  x  with
       the  value of the corresponding instance of the
       ipCidrRouteMask object is not equal to x."
    ::= { ipCidrRouteEntry 1 }

ipCidrRouteMask OBJECT-TYPE
    SYNTAX   IpAddress
    MAX-ACCESS read-only
    STATUS   current
    DESCRIPTION
       "Indicate the mask to be logical-ANDed with the
       destination  address  before  being compared to
       the value  in  the  ipCidrRouteDest  field.   For
       those  systems  that  do  not support arbitrary
       subnet masks, an agent constructs the value  of
       the  ipCidrRouteMask  by  reference to the IP Ad-
       dress Class.

       Any assignment (implicit or  otherwise)  of  an
       instance  of  this  object to a value x must be
       rejected if the bitwise logical-AND of  x  with
       the  value of the corresponding instance of the
       ipCidrRouteDest object is not equal to ipCidrRoute-
       Dest."
    ::= { ipCidrRouteEntry 2 }

-- The following convention is included for specification
-- of TOS Field contents.  At this time, the Host Requirements
-- and the Router Requirements documents disagree on the width
-- of the TOS field.  This mapping describes the Router
-- Requirements mapping, and leaves room to widen the TOS field
-- without impact to fielded systems.

ipCidrRouteTos OBJECT-TYPE
    SYNTAX   Integer32
    MAX-ACCESS read-only
    STATUS   current
    DESCRIPTION
       "The policy specifier is the IP TOS Field.  The encoding
       of IP TOS is as specified  by  the  following convention.
       Zero indicates the default path if no more  specific
       policy applies.

       +-----+-----+-----+-----+-----+-----+-----+-----+
       |                 |                       |     |
       |   PRECEDENCE    |    TYPE OF SERVICE    |  0  |
       |                 |                       |     |
       +-----+-----+-----+-----+-----+-----+-----+-----+

                IP TOS                IP TOS
           Field     Policy      Field     Policy
           Contents    Code      Contents    Code
           0 0 0 0  ==>   0      0 0 0 1  ==>   2
           0 0 1 0  ==>   4      0 0 1 1  ==>   6
           0 1 0 0  ==>   8      0 1 0 1  ==>  10
           0 1 1 0  ==>  12      0 1 1 1  ==>  14
           1 0 0 0  ==>  16      1 0 0 1  ==>  18
           1 0 1 0  ==>  20      1 0 1 1  ==>  22
           1 1 0 0  ==>  24      1 1 0 1  ==>  26
           1 1 1 0  ==>  28      1 1 1 1  ==>  30"
    ::= { ipCidrRouteEntry 3 }

ipCidrRouteNextHop OBJECT-TYPE
    SYNTAX   IpAddress
    MAX-ACCESS read-only
    STATUS   current
    DESCRIPTION
       "On remote routes, the address of the next sys-
       tem en route; Otherwise, 0.0.0.0."
    ::= { ipCidrRouteEntry 4 }

ipCidrRouteIfIndex OBJECT-TYPE
    SYNTAX   Integer32
    MAX-ACCESS read-create
    STATUS   current
    DESCRIPTION
       "The ifIndex value which identifies  the  local
       interface  through  which  the next hop of this
       route should be reached."
    DEFVAL { 0 }
    ::= { ipCidrRouteEntry 5 }

ipCidrRouteType OBJECT-TYPE
    SYNTAX   INTEGER {
                other    (1), -- not specified by this MIB
                reject   (2), -- route which discards traffic
                local    (3), -- local interface
                remote   (4)  -- remote destination
             }
    MAX-ACCESS read-create
    STATUS   current
    DESCRIPTION
       "The type of route.  Note that local(3)  refers
       to  a route for which the next hop is the final
       destination; remote(4) refers to  a  route  for
       which  the  next  hop is not the final destina-
       tion.

       Routes which do not result in traffic forwarding or
       rejection should not be displayed even if the
       implementation keeps them stored internally.


       reject (2) refers to a route which, if matched, discards
       the message as unreachable. This is used in some
       protocols as a means of correctly aggregating routes."
    ::= { ipCidrRouteEntry 6 }

ipCidrRouteProto OBJECT-TYPE
    SYNTAX   INTEGER {
                other     (1),  -- not specified
                local     (2),  -- local interface
                netmgmt   (3),  -- static route
                icmp      (4),  -- result of ICMP Redirect

                        -- the following are all dynamic
                        -- routing protocols
                egp        (5),  -- Exterior Gateway Protocol
                ggp        (6),  -- Gateway-Gateway Protocol
                hello      (7),  -- FuzzBall HelloSpeak
                rip        (8),  -- Berkeley RIP or RIP-II
                isIs       (9),  -- Dual IS-IS
                esIs       (10), -- ISO 9542
                ciscoIgrp  (11), -- Cisco IGRP
                bbnSpfIgp  (12), -- BBN SPF IGP
                ospf       (13), -- Open Shortest Path First
                bgp        (14), -- Border Gateway Protocol
                idpr       (15), -- InterDomain Policy Routing
                ciscoEigrp (16)  -- Cisco EIGRP
             }
    MAX-ACCESS read-only
    STATUS   current
    DESCRIPTION
       "The routing mechanism via which this route was
       learned.  Inclusion of values for gateway rout-
       ing protocols is not  intended  to  imply  that
       hosts should support those protocols."
    ::= { ipCidrRouteEntry 7 }

ipCidrRouteAge OBJECT-TYPE
    SYNTAX   Integer32
    MAX-ACCESS read-only
    STATUS   current
    DESCRIPTION
       "The number of seconds  since  this  route  was
       last  updated  or  otherwise  determined  to be
       correct.  Note that no semantics of  `too  old'
       can  be implied except through knowledge of the
       routing  protocol  by  which  the   route   was
       learned."
    DEFVAL  { 0 }
    ::= { ipCidrRouteEntry 8 }

ipCidrRouteInfo OBJECT-TYPE
    SYNTAX   OBJECT IDENTIFIER
    MAX-ACCESS read-create
    STATUS   current
    DESCRIPTION
       "A reference to MIB definitions specific to the
       particular  routing protocol which is responsi-
       ble for this route, as determined by the  value
       specified  in the route's ipCidrRouteProto value.
       If this information is not present,  its  value
       should be set to the OBJECT IDENTIFIER { 0 0 },
       which is a syntactically valid object  identif-
       ier, and any implementation conforming to ASN.1
       and the Basic Encoding Rules must  be  able  to
       generate and recognize this value."
    ::= { ipCidrRouteEntry 9 }

ipCidrRouteNextHopAS OBJECT-TYPE
    SYNTAX   Integer32
    MAX-ACCESS read-create
    STATUS   current
    DESCRIPTION
       "The Autonomous System Number of the Next  Hop.
       The  semantics of this object are determined by
       the routing-protocol specified in  the  route's
       ipCidrRouteProto  value. When  this object is
       unknown or not relevant its value should be set
       to zero."
    DEFVAL { 0 }
    ::= { ipCidrRouteEntry 10 }

ipCidrRouteMetric1 OBJECT-TYPE
    SYNTAX   Integer32
    MAX-ACCESS read-create
    STATUS   current
    DESCRIPTION
       "The primary routing  metric  for  this  route.
       The  semantics of this metric are determined by
       the routing-protocol specified in  the  route's
       ipCidrRouteProto  value.   If  this metric is not
       used, its value should be set to -1."
    DEFVAL { -1 }
    ::= { ipCidrRouteEntry 11 }

ipCidrRouteMetric2 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { ipCidrRouteEntry 12 }

ipCidrRouteMetric3 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { ipCidrRouteEntry 13 }

ipCidrRouteMetric4 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { ipCidrRouteEntry 14 }

ipCidrRouteMetric5 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { ipCidrRouteEntry 15 }

ipCidrRouteStatus OBJECT-TYPE
    SYNTAX   RowStatus
    MAX-ACCESS read-create
    STATUS   current
    DESCRIPTION
       "The row status variable, used according to
       row installation and removal conventions."
    ::= { ipCidrRouteEntry 16 }

-- conformance information

ipForwardConformance OBJECT IDENTIFIER ::= { ipForward 5 }
ipForwardGroups      OBJECT IDENTIFIER ::= { ipForwardConformance 1 }
ipForwardCompliances OBJECT IDENTIFIER ::= { ipForwardConformance 2 }

-- compliance statements

ipForwardCompliance MODULE-COMPLIANCE
   STATUS  current
   DESCRIPTION
       "The compliance statement for SNMPv2 entities
       which implement the ipForward MIB."

   MODULE  -- this module
   MANDATORY-GROUPS { ipForwardCidrRouteGroup }

   ::= { ipForwardCompliances 1 }

-- units of conformance

ipForwardCidrRouteGroup OBJECT-GROUP
    OBJECTS { ipCidrRouteNumber,
              ipCidrRouteDest, ipCidrRouteMask, ipCidrRouteTos,
              ipCidrRouteNextHop, ipCidrRouteIfIndex, ipCidrRouteType,
              ipCidrRouteProto, ipCidrRouteAge, ipCidrRouteInfo,
              ipCidrRouteNextHopAS, ipCidrRouteMetric1,
              ipCidrRouteMetric2, ipCidrRouteMetric3,
              ipCidrRouteMetric4, ipCidrRouteMetric5, ipCidrRouteStatus
        }
    STATUS  current
    DESCRIPTION
       "The CIDR Route Table."
    ::= { ipForwardGroups 3 }

-- Obsoleted Definitions - Objects

ipForwardNumber OBJECT-TYPE
    SYNTAX   Gauge32
    MAX-ACCESS read-only
    STATUS   obsolete
    DESCRIPTION
       "The number of current  ipForwardTable  entries
       that are not invalid."
    ::= { ipForward 1 }

--  IP Forwarding Table

--  The IP Forwarding Table obsoletes and replaces the ipRoute
--  Table current in MIB-I and MIB-II.  It adds knowledge of
--  the autonomous system of the next hop, multiple next hop
--  support, and policy routing support.

ipForwardTable OBJECT-TYPE
    SYNTAX   SEQUENCE OF IpForwardEntry
    MAX-ACCESS not-accessible
    STATUS   obsolete
    DESCRIPTION
       "This entity's IP Routing table."
    REFERENCE
       "RFC 1213 Section 6.6, The IP Group"
    ::= { ipForward 2 }

ipForwardEntry OBJECT-TYPE
    SYNTAX   IpForwardEntry
    MAX-ACCESS not-accessible
    STATUS   obsolete
    DESCRIPTION
       "A particular route to  a  particular  destina-
       tion, under a particular policy."
    INDEX {
        ipForwardDest,
        ipForwardProto,
        ipForwardPolicy,
        ipForwardNextHop
        }
    ::= { ipForwardTable 1 }

IpForwardEntry ::=
    SEQUENCE {
        ipForwardDest
            IpAddress,
        ipForwardMask
            IpAddress,
        ipForwardPolicy
             Integer32,
        ipForwardNextHop
            IpAddress,
        ipForwardIfIndex
            Integer32,
        ipForwardType
            INTEGER,
        ipForwardProto
            INTEGER,
        ipForwardAge
            Integer32,
        ipForwardInfo
            OBJECT IDENTIFIER,
        ipForwardNextHopAS
            Integer32,
        ipForwardMetric1
            Integer32,
        ipForwardMetric2
            Integer32,
        ipForwardMetric3
            Integer32,
        ipForwardMetric4
            Integer32,
        ipForwardMetric5
            Integer32
    }

ipForwardDest OBJECT-TYPE
    SYNTAX   IpAddress
    MAX-ACCESS read-only
    STATUS   obsolete
    DESCRIPTION
       "The destination IP address of this route.   An
       entry  with  a value of 0.0.0.0 is considered a
       default route.

       This object may not take a Multicast (Class  D)
       address value.

       Any assignment (implicit or  otherwise)  of  an
       instance  of  this  object to a value x must be
       rejected if the bitwise logical-AND of  x  with
       the  value of the corresponding instance of the
       ipForwardMask object is not equal to x."
    ::= { ipForwardEntry 1 }

ipForwardMask OBJECT-TYPE
    SYNTAX   IpAddress
    MAX-ACCESS read-create
    STATUS   obsolete
    DESCRIPTION
       "Indicate the mask to be logical-ANDed with the
       destination  address  before  being compared to
       the value  in  the  ipForwardDest  field.   For
       those  systems  that  do  not support arbitrary
       subnet masks, an agent constructs the value  of
       the  ipForwardMask  by  reference to the IP Ad-
       dress Class.

       Any assignment (implicit or  otherwise)  of  an
       instance  of  this  object to a value x must be
       rejected if the bitwise logical-AND of  x  with
       the  value of the corresponding instance of the
       ipForwardDest object is not equal to ipForward-
       Dest."
    DEFVAL { '00000000'h }      -- 0.0.0.0
    ::= { ipForwardEntry 2 }

-- The following convention is included for specification
-- of TOS Field contents.  At this time, the Host Requirements
-- and the Router Requirements documents disagree on the width
-- of the TOS field.  This mapping describes the Router
-- Requirements mapping, and leaves room to widen the TOS field
-- without impact to fielded systems.

ipForwardPolicy OBJECT-TYPE
    SYNTAX   Integer32
    MAX-ACCESS read-only
    STATUS   obsolete
    DESCRIPTION
       "The general set of conditions that would cause
       the  selection  of  one multipath route (set of
       next hops for a given destination) is  referred
       to as 'policy'.

       Unless the mechanism indicated by ipForwardPro-
       to specifies otherwise, the policy specifier is
       the IP TOS Field.  The encoding of IP TOS is as
        specified  by  the  following convention.  Zero
       indicates the default path if no more  specific
       policy applies.

       +-----+-----+-----+-----+-----+-----+-----+-----+
       |                 |                       |     |
       |   PRECEDENCE    |    TYPE OF SERVICE    |  0  |
       |                 |                       |     |
       +-----+-----+-----+-----+-----+-----+-----+-----+

                IP TOS                IP TOS
           Field     Policy      Field     Policy
           Contents    Code      Contents    Code
           0 0 0 0  ==>   0      0 0 0 1  ==>   2
           0 0 1 0  ==>   4      0 0 1 1  ==>   6
           0 1 0 0  ==>   8      0 1 0 1  ==>  10
           0 1 1 0  ==>  12      0 1 1 1  ==>  14
           1 0 0 0  ==>  16      1 0 0 1  ==>  18
           1 0 1 0  ==>  20      1 0 1 1  ==>  22
           1 1 0 0  ==>  24      1 1 0 1  ==>  26
           1 1 1 0  ==>  28      1 1 1 1  ==>  30

       Protocols defining 'policy' otherwise must  ei-
       ther define a set of values which are valid for
       this  object  or  must  implement  an  integer-
       instanced  policy table for which this object's
       value acts as an index."
    ::= { ipForwardEntry 3 }

ipForwardNextHop OBJECT-TYPE
    SYNTAX   IpAddress
    MAX-ACCESS read-only
    STATUS   obsolete
    DESCRIPTION
       "On remote routes, the address of the next sys-
       tem en route; Otherwise, 0.0.0.0."
    ::= { ipForwardEntry 4 }

ipForwardIfIndex OBJECT-TYPE
    SYNTAX   Integer32
    MAX-ACCESS read-create
    STATUS   obsolete
    DESCRIPTION
       "The ifIndex value which identifies  the  local
       interface  through  which  the next hop of this
       route should be reached."
    DEFVAL { 0 }
    ::= { ipForwardEntry 5 }

ipForwardType OBJECT-TYPE
    SYNTAX   INTEGER {
                other    (1), -- not specified by this MIB
                invalid  (2), -- logically deleted
                local    (3), -- local interface
                remote   (4)  -- remote destination
             }
    MAX-ACCESS read-create
    STATUS   obsolete
    DESCRIPTION
       "The type of route.  Note that local(3)  refers
       to  a route for which the next hop is the final
       destination; remote(4) refers to  a  route  for
       which  the  next  hop is not the final destina-
       tion.

       Setting this object to the value invalid(2) has
       the  effect  of  invalidating the corresponding
       entry in the ipForwardTable object.   That  is,
       it  effectively  disassociates  the destination
       identified with said entry from the route iden-
       tified    with    said   entry.    It   is   an
       implementation-specific matter  as  to  whether
       the agent removes an invalidated entry from the
       table.  Accordingly, management  stations  must
       be prepared to receive tabular information from
       agents that corresponds to entries not current-
       ly  in  use.  Proper interpretation of such en-
       tries requires examination of the relevant  ip-
       ForwardType object."
    DEFVAL { invalid }
    ::= { ipForwardEntry 6 }

ipForwardProto OBJECT-TYPE
    SYNTAX   INTEGER {
                other     (1),  -- not specified
                local     (2),  -- local interface
                netmgmt   (3),  -- static route
                icmp      (4),  -- result of ICMP Redirect

                        -- the following are all dynamic
                        -- routing protocols
                egp       (5),  -- Exterior Gateway Protocol
                ggp       (6),  -- Gateway-Gateway Protocol
                hello     (7),  -- FuzzBall HelloSpeak
                rip       (8),  -- Berkeley RIP or RIP-II
                is-is     (9),  -- Dual IS-IS
                es-is     (10), -- ISO 9542
                ciscoIgrp (11), -- Cisco IGRP
                bbnSpfIgp (12), -- BBN SPF IGP
                ospf      (13), -- Open Shortest Path First
                bgp       (14), -- Border Gateway Protocol
                idpr      (15)  -- InterDomain Policy Routing
             }
    MAX-ACCESS read-only
    STATUS   obsolete
    DESCRIPTION
       "The routing mechanism via which this route was
       learned.  Inclusion of values for gateway rout-
       ing protocols is not  intended  to  imply  that
       hosts should support those protocols."
    ::= { ipForwardEntry 7 }

ipForwardAge OBJECT-TYPE
    SYNTAX   Integer32
    MAX-ACCESS read-only
    STATUS   obsolete
    DESCRIPTION
       "The number of seconds  since  this  route  was
       last  updated  or  otherwise  determined  to be
       correct.  Note that no semantics of  `too  old'
       can  be implied except through knowledge of the
       routing  protocol  by  which  the   route   was
       learned."
    DEFVAL  { 0 }
    ::= { ipForwardEntry 8 }

ipForwardInfo OBJECT-TYPE
    SYNTAX   OBJECT IDENTIFIER
    MAX-ACCESS read-create
    STATUS   obsolete
    DESCRIPTION
       "A reference to MIB definitions specific to the
       particular  routing protocol which is responsi-
       ble for this route, as determined by the  value
       specified  in the route's ipForwardProto value.
       If this information is not present,  its  value
       should be set to the OBJECT IDENTIFIER { 0 0 },
       which is a syntactically valid object  identif-
       ier, and any implementation conforming to ASN.1
       and the Basic Encoding Rules must  be  able  to
       generate and recognize this value."
    ::= { ipForwardEntry 9 }

ipForwardNextHopAS OBJECT-TYPE
    SYNTAX   Integer32
    MAX-ACCESS read-create
    STATUS   obsolete
    DESCRIPTION
       "The Autonomous System Number of the Next  Hop.
       When  this  is  unknown  or not relevant to the
       protocol indicated by ipForwardProto, zero."
    DEFVAL { 0 }
    ::= { ipForwardEntry 10 }

ipForwardMetric1 OBJECT-TYPE
    SYNTAX   Integer32
    MAX-ACCESS read-create
    STATUS   obsolete
    DESCRIPTION
       "The primary routing  metric  for  this  route.
       The  semantics of this metric are determined by
       the routing-protocol specified in  the  route's
       ipForwardProto  value.   If  this metric is not
       used, its value should be set to -1."
    DEFVAL { -1 }
    ::= { ipForwardEntry 11 }
ipForwardMetric2 OBJECT-TYPE
    SYNTAX   Integer32
    MAX-ACCESS read-create
    STATUS   obsolete
    DESCRIPTION
       "An alternate routing metric  for  this  route.
       The  semantics of this metric are determined by
       the routing-protocol specified in  the  route's
       ipForwardProto  value.   If  this metric is not
       used, its value should be set to -1."

    DEFVAL { -1 }
    ::= { ipForwardEntry 12 }

ipForwardMetric3 OBJECT-TYPE
    SYNTAX   Integer32
    MAX-ACCESS read-create
    STATUS   obsolete
    DESCRIPTION
       "An alternate routing metric  for  this  route.
       The  semantics of this metric are determined by
       the routing-protocol specified in  the  route's
       ipForwardProto  value.   If  this metric is not
       used, its value should be set to -1."
    DEFVAL { -1 }
    ::= { ipForwardEntry 13 }

ipForwardMetric4 OBJECT-TYPE
    SYNTAX   Integer32
    MAX-ACCESS read-create
    STATUS   obsolete
    DESCRIPTION
       "An alternate routing metric  for  this  route.
       The  semantics of this metric are determined by
       the routing-protocol specified in  the  route's
       ipForwardProto  value.   If  this metric is not
       used, its value should be set to -1."
    DEFVAL { -1 }
    ::= { ipForwardEntry 14 }

ipForwardMetric5 OBJECT-TYPE
    SYNTAX   Integer32
    MAX-ACCESS read-create
    STATUS   obsolete
    DESCRIPTION
       "An alternate routing metric  for  this  route.
       The  semantics of this metric are determined by
       the routing-protocol specified in  the  route's
       ipForwardProto  value.   If  this metric is not
       used, its value should be set to -1."
    DEFVAL { -1 }
    ::= { ipForwardEntry 15 }

-- Obsoleted Definitions - Groups
-- compliance statements

ipForwardOldCompliance MODULE-COMPLIANCE
   STATUS  obsolete
   DESCRIPTION
       "The compliance statement for SNMP entities
       which implement the ipForward MIB."

   MODULE  -- this module
   MANDATORY-GROUPS { ipForwardMultiPathGroup }

   ::= { ipForwardCompliances 2 }

ipForwardMultiPathGroup OBJECT-GROUP
    OBJECTS { ipForwardNumber,
              ipForwardDest, ipForwardMask, ipForwardPolicy,
              ipForwardNextHop, ipForwardIfIndex, ipForwardType,
              ipForwardProto, ipForwardAge, ipForwardInfo,
              ipForwardNextHopAS,
              ipForwardMetric1, ipForwardMetric2, ipForwardMetric3,
              ipForwardMetric4, ipForwardMetric5
        }
    STATUS  obsolete
    DESCRIPTION
       "IP Multipath Route Table."
    ::= { ipForwardGroups 2 }

END

ATM-TC-MIB DEFINITIONS ::= BEGIN

     IMPORTS
        MODULE-IDENTITY, OBJECT-IDENTITY,
        TimeTicks, mib-2
            FROM SNMPv2-SMI
        TEXTUAL-CONVENTION
            FROM SNMPv2-TC;

     atmMIB OBJECT IDENTIFIER ::= { mib-2 37 }
     
     atmMIBObjects  OBJECT IDENTIFIER ::= {atmMIB 1}
     
     atmTCMIB MODULE-IDENTITY
          LAST-UPDATED "9810190200Z"
          ORGANIZATION "IETF AToMMIB Working Group"
          CONTACT-INFO
            "          Michael Noto
              Postal:  3Com Corporation
                       5400 Bayfront Plaza, M/S 3109
                       Santa Clara, CA 95052
                       USA
              Tel:     +1 408 326 2218
              E-mail:  mike_noto@3com.com

                       Ethan Mickey Spiegel


              Postal:  Cisco Systems
                       170 W. Tasman Dr.
                       San Jose, CA 95134
                       USA
              Tel:     +1 408 526 6408
              E-mail:  mspiegel@cisco.com

                       Kaj Tesink
              Postal:  Bellcore
                       331 Newman Springs Road
                       Red Bank, NJ 07701
                       USA
              Tel:     +1 732 758 5254
              Fax:     +1 732 758 4177
              E-mail:  kaj@bellcore.com"
          DESCRIPTION
           "This MIB Module provides Textual Conventions
           and OBJECT-IDENTITY Objects to be used by
           ATM systems."
          ::= { mib-2 37 3 } -- atmMIB 3 (see [3])

     -- The Textual Conventions defined below are organized
     -- alphabetically

     AtmAddr ::= TEXTUAL-CONVENTION
             DISPLAY-HINT "1x"
             STATUS  current
             DESCRIPTION
                 "An ATM address. The semantics are implied by
                 the length. The address types are: - no
                 address (0 octets) - E.164 (8 octets) - NSAP
                 (20 octets) In addition, when subaddresses
                 are used the AtmAddr may represent the
                 concatenation of address and subaddress. The
                 associated address types are: - E.164, E.164
                 (16 octets) - E.164, NSAP (28 octets) - NSAP,
                 NSAP (40 octets) Address lengths other than
                 defined in this definition imply address
                 types defined elsewhere.  Note: The E.164
                 address is encoded in BCD format."
            SYNTAX   OCTET STRING (SIZE(0..40))

    AtmConnCastType ::= TEXTUAL-CONVENTION
            STATUS  current
            DESCRIPTION
              "The type of topology of a connection (point-


              to-point, point-to-multipoint). In the case
              of point-to-multipoint, the orientation of
              this VPL or VCL in the connection.
              On a host:
              - p2mpRoot indicates that the host
                is the root of the p2mp connection.
              - p2mpLeaf indicates that the host
                is a leaf of the p2mp connection.
              On a switch interface:
              - p2mpRoot indicates that cells received
                by the switching fabric from the interface
                are from the root of the p2mp connection.
              - p2mpLeaf indicates that cells transmitted
                to the interface from the switching fabric
                are to the leaf of the p2mp connection."
            SYNTAX   INTEGER {
               p2p(1),
               p2mpRoot(2),
               p2mpLeaf(3)
               }

    AtmConnKind ::= TEXTUAL-CONVENTION
            STATUS  current
            DESCRIPTION
                "The type of call control used for an ATM
                connection at a particular interface. The use
                is as follows:
                   pvc(1)
                      Virtual link of a PVC. Should not be
                      used for an PVC/SVC (i.e., Soft PVC)
                      crossconnect.
                   svcIncoming(2)
                      Virtual link established after a
                      received signaling request to setup
                      an SVC.
                   svcOutgoing(3)
                      Virtual link established after a
                      transmitted or forwarded signaling
                      request to setup an SVC.
                   spvcInitiator(4)
                      Virtual link at the PVC side of an
                      SVC/PVC crossconnect, where the
                      switch is the initiator of the Soft PVC
                      setup.
                   spvcTarget(5)
                      Virtual link at the PVC side of an
                      SVC/PVC crossconnect, where the
                      switch is the target of the Soft PVC


                      setup.

                For PVCs, a pvc virtual link is always cross-
                connected to a pvc virtual link.

                For SVCs, an svcIncoming virtual link is always cross-
                connected to an svcOutgoing virtual link.

For Soft PVCs, an spvcInitiator is either cross-connected to
an svcOutgoing or an spvcTarget, and an spvcTarget is either
cross-connected to an svcIncoming or an spvcInitiator."
        SYNTAX   INTEGER {
           pvc(1),
           svcIncoming(2),
           svcOutgoing(3),
           spvcInitiator(4),
           spvcTarget(5)
           }

    AtmIlmiNetworkPrefix ::= TEXTUAL-CONVENTION
        STATUS   current
        DESCRIPTION
            "A network prefix used for ILMI address
            registration.  In the case of ATM endsystem
            addresses (AESAs), the network prefix is the first
            13 octets of the address which includes the AFI,
            IDI, and HO-DSP fields.  In the case of native
            E.164 addresses, the network prefix is the entire
            E.164 address encoded in 8 octets, as if it were
            an E.164 IDP in an ATM endsystem address
            structure."
        REFERENCE
            "ATM Forum, Integrated Local Management Interface
               (ILMI) Specification, Version 4.0,
               af-ilmi-0065.000, September 1996, Section 9
             ATM Forum, ATM User-Network Interface Signalling
               Specification, Version 4.0 (UNI 4.0),
               af-sig-0061.000, June 1996, Section 3"
        SYNTAX   OCTET STRING (SIZE(8|13))

AtmInterfaceType ::= TEXTUAL-CONVENTION
        STATUS       current
        DESCRIPTION
            "The connection setup procedures used for the
            identified interface.

            Other: Connection setup procedures other than
               those listed below.


            Auto-configuration:
               Indicates that the connection setup
               procedures are to be determined dynamically,
               or that determination has not yet been
               completed. One such mechanism is via ATM
               Forum ILMI auto-configuration procedures.

            ITU-T DSS2:
            -  ITU-T Recommendation Q.2931, Broadband
               Integrated Service Digital Network (B-ISDN)
               Digital Subscriber Signalling System No.2
               (DSS2) User-Network Interface (UNI) Layer 3
               Specification for Basic Call/Connection
               Control (September 1994)
            -  ITU-T Draft Recommendation Q.2961,
               B-ISDN DSS 2 Support of Additional Traffic
               Parameters (May 1995)

            -  ITU-T Draft Recommendation Q.2971,
               B-ISDN DSS 2 User Network Interface Layer 3
               Specification for Point-to-multipoint
               Call/connection Control (May 1995)

            ATM Forum UNI 3.0:
               ATM Forum, ATM User-Network Interface,
               Version 3.0 (UNI 3.0) Specification,
               (1994).

            ATM Forum UNI 3.1:
               ATM Forum, ATM User-Network Interface,
               Version 3.1 (UNI 3.1) Specification,
               (November 1994).

            ATM Forum UNI Signalling 4.0:
               ATM Forum, ATM User-Network Interface (UNI)
               Signalling Specification Version 4.0,
               af-sig-0061.000 (June 1996).

            ATM Forum IISP (based on UNI 3.0 or UNI 3.1) :
               Interim Inter-switch Signaling Protocol
               (IISP) Specification, Version 1.0,
               af-pnni-0026.000, (December 1994).

            ATM Forum PNNI 1.0 :
               ATM Forum, Private Network-Network Interface
               Specification, Version 1.0, af-pnni-0055.000,
               (March 1996).


            ATM Forum B-ICI:
               ATM Forum, B-ICI Specification, Version 2.0,
               af-bici-0013.002, (November 1995).

            ATM Forum UNI PVC Only:
               An ATM Forum compliant UNI with the
               signalling disabled.
            ATM Forum NNI PVC Only:
               An ATM Forum compliant NNI with the
               signalling disabled."
        SYNTAX  INTEGER  {
                  other(1),
                  autoConfig(2),
                  ituDss2(3),
                  atmfUni3Dot0(4),
                  atmfUni3Dot1(5),
                  atmfUni4Dot0(6),
                  atmfIispUni3Dot0(7),
                  atmfIispUni3Dot1(8),
                  atmfIispUni4Dot0(9),
        atmfPnni1Dot0(10),
        atmfBici2Dot0(11),
        atmfUniPvcOnly(12),
        atmfNniPvcOnly(13)  }

AtmServiceCategory ::= TEXTUAL-CONVENTION
        STATUS  current
        DESCRIPTION
            "The service category for a connection."
        REFERENCE
            "ATM Forum Traffic Management Specification,
            Version 4.0, af-tm-0056.000, June 1996."
        SYNTAX   INTEGER {
           other(1),   -- none of the following
           cbr(2),     -- constant bit rate
           rtVbr(3),   -- real-time variable bit rate
           nrtVbr(4),  -- non real-time variable bit rate
           abr(5),     -- available bit rate
           ubr(6)      -- unspecified bit rate
           }

AtmSigDescrParamIndex ::= TEXTUAL-CONVENTION
        STATUS  current
        DESCRIPTION
            "The value of this object identifies a row in the
            atmSigDescrParamTable. The value 0 signifies that
            none of the signalling parameters defined in the
            atmSigDescrParamTable are applicable."


        SYNTAX  INTEGER (0..2147483647)

AtmTrafficDescrParamIndex ::= TEXTUAL-CONVENTION
        STATUS  current
        DESCRIPTION
            "The value of this object identifies a row in the
            atmTrafficDescrParamTable.  The value 0 signifies
            that no row has been identified."
        SYNTAX  INTEGER (0..2147483647)

AtmVcIdentifier ::= TEXTUAL-CONVENTION
        STATUS  current
        DESCRIPTION
            "The VCI value for a VCL. The maximum VCI value
            cannot exceed the value allowable by
            atmInterfaceMaxVciBits defined in ATM-MIB."
        SYNTAX   INTEGER (0..65535)

AtmVpIdentifier ::= TEXTUAL-CONVENTION
        STATUS  current
        DESCRIPTION
            "The VPI value for a VPL or VCL. The value VPI=0
            is only allowed for a VCL. For ATM UNIs supporting
            VPCs the VPI value ranges from 0 to 255.  The VPI
            value 0 is supported for ATM UNIs conforming to
            the ATM Forum UNI 4.0 Annex 8 (Virtual UNIs)
            specification. For ATM UNIs supporting VCCs the
            VPI value ranges from 0 to 255.  For ATM NNIs the
            VPI value ranges from 0 to 4095.  The maximum VPI
            value cannot exceed the value allowable by
            atmInterfaceMaxVpiBits defined in ATM-MIB."
        SYNTAX    INTEGER (0..4095)

AtmVorXAdminStatus ::= TEXTUAL-CONVENTION
        STATUS  current
        DESCRIPTION
            "The value determines the desired administrative
            status of a virtual link or cross-connect. The up
            and down states indicate that the traffic flow is
            enabled or disabled respectively on the virtual
            link or cross-connect."
        SYNTAX   INTEGER {
           up(1),
           down(2)
            }

AtmVorXLastChange ::= TEXTUAL-CONVENTION
        STATUS  current


        DESCRIPTION
            "The value of MIB II's sysUpTime at the time a
            virtual link or cross-connect entered its current
            operational state. If the current state was
            entered prior to the last re-initialization of the
            agent then this object contains a zero value."
        SYNTAX   TimeTicks

AtmVorXOperStatus ::= TEXTUAL-CONVENTION
        STATUS  current
        DESCRIPTION
            "The value determines the operational status of a
            virtual link or cross-connect. The up and down
            states indicate that the traffic flow is enabled
            or disabled respectively on the virtual link or
            cross-connect. The unknown state indicates that
            the state of it cannot be determined. The state
            will be down or unknown if the supporting ATM
            interface(s) is down or unknown respectively."
        SYNTAX   INTEGER {
           up(1),
           down(2),
           unknown(3)
           }

-- OBJECT-IDENTITIES:

-- The following atmTrafficDescriptorTypes has been moved
-- from RFC1695 and no longer appear in the revision of
-- RFC1695[3].

atmTrafficDescriptorTypes OBJECT IDENTIFIER ::= {mib-2 37 1 1}
                                            -- atmMIBObjects
                                            -- See [3].

-- All other and new OBJECT IDENTITIES
-- are defined under the following subtree:

    atmObjectIdentities OBJECT IDENTIFIER ::= {atmTCMIB 1}

-- The following values are defined for use as
-- possible values of the ATM traffic descriptor type.

atmNoTrafficDescriptor  OBJECT-IDENTITY
    STATUS  deprecated


    DESCRIPTION
        "This identifies the no ATM traffic
        descriptor type.  Parameters 1, 2, 3, 4,
        and 5 are not used.  This traffic descriptor
        type can be used for best effort traffic."
    ::= {atmTrafficDescriptorTypes 1}

atmNoClpNoScr  OBJECT-IDENTITY
    STATUS  current
    DESCRIPTION
        "This traffic descriptor type is for no CLP
        and no Sustained Cell Rate.  The use of the
        parameter vector for this type:
        Parameter 1: peak cell rate in cells/second
                     for CLP=0+1 traffic
        Parameter 2: not used
        Parameter 3: not used
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 2}

atmClpNoTaggingNoScr  OBJECT-IDENTITY
    STATUS  deprecated
    DESCRIPTION
        "This traffic descriptor is for CLP without
        tagging and no Sustained Cell Rate.  The use
        of the parameter vector for this type:
        Parameter 1: peak cell rate in cells/second
                     for CLP=0+1 traffic
        Parameter 2: peak cell rate in cells/second
                     for CLP=0 traffic
        Parameter 3: not used
        Parameter 4: not used
        Parameter 5: not used."
    ::= {atmTrafficDescriptorTypes 3}

atmClpTaggingNoScr  OBJECT-IDENTITY
    STATUS  deprecated
    DESCRIPTION
        "This traffic descriptor is for CLP with
        tagging and no Sustained Cell Rate.  The use
        of the parameter vector for this type:


        Parameter 1: peak cell rate in cells/second
                     for CLP=0+1 traffic
        Parameter 2: peak cell rate in cells/second
                     for CLP=0 traffic, excess
                     tagged as CLP=1
        Parameter 3: not used
        Parameter 4: not used
        Parameter 5: not used."
    ::= {atmTrafficDescriptorTypes 4}

atmNoClpScr  OBJECT-IDENTITY
    STATUS  current
    DESCRIPTION
        "This traffic descriptor type is for no CLP
        with Sustained Cell Rate.  The use of the
        parameter vector for this type:
        Parameter 1: peak cell rate in cells/second
                     for CLP=0+1 traffic
        Parameter 2: sustainable cell rate in cells/second
                     for CLP=0+1 traffic
        Parameter 3: maximum burst size in cells
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 5}

atmClpNoTaggingScr  OBJECT-IDENTITY
    STATUS  current
    DESCRIPTION
        "This traffic descriptor type is for CLP with
        Sustained Cell Rate and no tagging.  The use
        of the parameter vector for this type:
        Parameter 1: peak cell rate in cells/second
                     for CLP=0+1 traffic
        Parameter 2: sustainable cell rate in cells/second
                     for CLP=0 traffic
        Parameter 3: maximum burst size in cells
        Parameter 4: not used
        Parameter 5: not used."
    REFERENCE
        "ATM Forum,ATM User-Network Interface,
           Version 3.0 (UNI 3.0) Specification, 1994.
         ATM Forum, ATM User-Network Interface,


           Version 3.1 (UNI 3.1) Specification,
           November 1994."
    ::= {atmTrafficDescriptorTypes 6}

atmClpTaggingScr  OBJECT-IDENTITY
    STATUS  current
    DESCRIPTION
        "This traffic descriptor type is for CLP with
        tagging and Sustained Cell Rate.  The use of
        the parameter vector for this type:
        Parameter 1: peak cell rate in cells/second
                     for CLP=0+1 traffic
        Parameter 2: sustainable cell rate in cells/second
                     for CLP=0 traffic, excess tagged as
                     CLP=1
        Parameter 3: maximum burst size in cells
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 7}

atmClpNoTaggingMcr  OBJECT-IDENTITY
    STATUS  current
    DESCRIPTION
        "This traffic descriptor type is for CLP with
        Minimum Cell Rate and no tagging.  The use of
        the parameter vector for this type:
        Parameter 1: peak cell rate in cells/second
                     for CLP=0+1 traffic
        Parameter 2: CDVT in tenths of microseconds
        Parameter 3: minimum cell rate in cells/second
        Parameter 4: unused
        Parameter 5: unused."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 8}

atmClpTransparentNoScr  OBJECT-IDENTITY
    STATUS  current


    DESCRIPTION
        "This traffic descriptor type is for the CLP-
        transparent model and no Sustained Cell Rate.
        The use of the parameter vector for this type:
        Parameter 1: peak cell rate in cells/second
                     for CLP=0+1 traffic
        Parameter 2: CDVT in tenths of microseconds
        Parameter 3: not used
        Parameter 4: not used
        Parameter 5: not used.

        This traffic descriptor type is applicable to
        connections following the CBR.1 conformance
        definition.

        Connections specifying this traffic descriptor
        type will be rejected at UNI 3.0 or UNI 3.1
        interfaces.  For a similar traffic descriptor
        type that can be accepted at UNI 3.0 and
        UNI 3.1 interfaces, see atmNoClpNoScr."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 9}

atmClpTransparentScr  OBJECT-IDENTITY
    STATUS  current
    DESCRIPTION
        "This traffic descriptor type is for the CLP-
        transparent model with Sustained Cell Rate.
        The use of the parameter vector for this type:
        Parameter 1: peak cell rate in cells/second
                     for CLP=0+1 traffic
        Parameter 2: sustainable cell rate in cells/second
                     for CLP=0+1 traffic
        Parameter 3: maximum burst size in cells
        Parameter 4: CDVT in tenths of microseconds
        Parameter 5: not used.

        This traffic descriptor type is applicable to
        connections following the VBR.1 conformance
        definition.


        Connections specifying this traffic descriptor
        type will be rejected at UNI 3.0 or UNI 3.1
        interfaces.  For a similar traffic descriptor
        type that can be accepted at UNI 3.0 and
        UNI 3.1 interfaces, see atmNoClpScr."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 10}

atmNoClpTaggingNoScr  OBJECT-IDENTITY
    STATUS  current
    DESCRIPTION
        "This traffic descriptor type is for no CLP
        with tagging and no Sustained Cell Rate.  The
        use of the parameter vector for this type:
        Parameter 1: peak cell rate in cells/second
                     for CLP=0+1 traffic
        Parameter 2: CDVT in tenths of microseconds
        Parameter 3: not used
        Parameter 4: not used
        Parameter 5: not used.

        This traffic descriptor type is applicable to
        connections following the UBR.2 conformance
        definition ."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 11}

atmNoClpNoScrCdvt  OBJECT-IDENTITY
    STATUS  current
    DESCRIPTION
        "This traffic descriptor type is for no CLP
        and no Sustained Cell Rate.  The use of the
        parameter vector for this type:
        Parameter 1: peak cell rate in cells/second


                     for CLP=0+1 traffic
        Parameter 2: CDVT in tenths of microseconds
        Parameter 3: not used
        Parameter 4: not used
        Parameter 5: not used.

        This traffic descriptor type is applicable to
        CBR connections following the UNI 3.0/3.1
        conformance definition for PCR CLP=0+1.
        These CBR connections differ from CBR.1
        connections in that the CLR objective
        applies only to the CLP=0 cell flow.

        This traffic descriptor type is also
        applicable to connections following the UBR.1
        conformance definition."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 12}

atmNoClpScrCdvt  OBJECT-IDENTITY
    STATUS  current
    DESCRIPTION
        "This traffic descriptor type is for no CLP
        with Sustained Cell Rate.  The use of the
        parameter vector for this type:
        Parameter 1: peak cell rate in cells/second
                     for CLP=0+1 traffic
        Parameter 2: sustainable cell rate in cells/second
                     for CLP=0+1 traffic
        Parameter 3: maximum burst size in cells
        Parameter 4: CDVT in tenths of microseconds
        Parameter 5: not used.

        This traffic descriptor type is applicable
        to VBR connections following the UNI 3.0/3.1
        conformance definition for PCR CLP=0+1 and
        SCR CLP=0+1.  These VBR connections
        differ from VBR.1 connections in that
        the CLR objective applies only to the CLP=0
        cell flow."
    REFERENCE


        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 13}

atmClpNoTaggingScrCdvt  OBJECT-IDENTITY
    STATUS  current
    DESCRIPTION
        "This traffic descriptor type is for CLP with
        Sustained Cell Rate and no tagging.  The use
        of the parameter vector for this type:
        Parameter 1: peak cell rate in cells/second
                     for CLP=0+1 traffic
        Parameter 2: sustainable cell rate in cells/second
                     for CLP=0 traffic
        Parameter 3: maximum burst size in cells
        Parameter 4: CDVT in tenths of microseconds
        Parameter 5: not used.

        This traffic descriptor type is applicable to
        connections following the VBR.2 conformance
        definition."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 14}

atmClpTaggingScrCdvt  OBJECT-IDENTITY
    STATUS  current
    DESCRIPTION
        "This traffic descriptor type is for CLP with
        tagging and Sustained Cell Rate.  The use of
        the parameter vector for this type:
        Parameter 1: peak cell rate in cells/second
                     for CLP=0+1 traffic
        Parameter 2: sustainable cell rate in cells/second
                     for CLP=0 traffic, excess tagged as
                     CLP=1
        Parameter 3: maximum burst size in cells


        Parameter 4: CDVT in tenths of microseconds
        Parameter 5: not used.

        This traffic descriptor type is applicable to
        connections following the VBR.3 conformance
        definition."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 15}

END

ATM-MIB DEFINITIONS ::= BEGIN

     IMPORTS
        MODULE-IDENTITY, OBJECT-TYPE,
        Counter32, Integer32, IpAddress, mib-2
            FROM SNMPv2-SMI
        DisplayString, RowStatus, TruthValue
            FROM SNMPv2-TC
        MODULE-COMPLIANCE, OBJECT-GROUP
            FROM SNMPv2-CONF
        InterfaceIndex, ifIndex
            FROM IF-MIB
        AtmAddr, AtmConnKind, AtmConnCastType,
        AtmServiceCategory, AtmTrafficDescrParamIndex,
        AtmVpIdentifier, AtmVcIdentifier,
        AtmVorXAdminStatus, AtmVorXLastChange,
        AtmVorXOperStatus, atmNoClpNoScr
            FROM ATM-TC-MIB;

     atmMIB MODULE-IDENTITY
          LAST-UPDATED "9810191200Z"
          ORGANIZATION "IETF AToM MIB Working Group"
          CONTACT-INFO
            "          Kaj Tesink
              Postal:  Bellcore
                       331 Newman Springs Road
                       Red Bank, NJ 07701
              Tel:     732-758-5254
              Fax:     732-758-2269
              E-mail:  kaj@bellcore.com"
          DESCRIPTION
           "This is the MIB Module for ATM and AAL5-related
            objects for managing ATM interfaces, ATM virtual


            links, ATM cross-connects, AAL5 entities, and
            and AAL5 connections."
          REVISION      "9810191200Z"
          DESCRIPTION
           "The initial revision of this module was published
            as RFC 1695. Key revisions include:
            o  Textual Conventions and OBJECT IDENTITIES have
               been moved to a separate MIB module.
            o  Applicability of objects to PVCs, SVCs and Soft
               PVCs has been clarified.
            o  DEFVAL clauses have been added.
            o  The relationship of ifIndex values with different
               layers and sublayers related to ATM has been
               clarified.
            o  atmTrafficQosClass has been deprecated
               and replaced with atmServiceCategory.
            o  atmInterfaceCurrentMaxVpiBits and
               atmInterfaceCurrentMaxVciBits have been added with
               a description on their relationship with other
               objects.
            o  atmInterfaceAddressType and atmInterfaceAdminAddress
               have been deprecated and replaced by
               atmInterfaceSubscrAddress.
            o  atmInterfaceTCAlarmState has been clarified.
            o  atmTrafficDescrParamIndexNext has been introduced
               in order to provide a manager a free
               atmTrafficDescrParamIndex value.
            o  The atmTrafficFrameDiscard capability has been added.
            o  A connection topology type (atmVpl/VclCastType) and
               a call control type (atmVpl/VclConnKind) have been
               added.
            o  aal2 has been added to atmVccAalType."
          REVISION      "9406072245Z"
          DESCRIPTION
           "The RFC1695 version of this MIB module."
          ::= { mib-2 37 }

     atmMIBObjects  OBJECT IDENTIFIER ::= {atmMIB 1}

     -- {atmMIBObjects 1} has been moved to a separate
     -- specification [19].

     -- This ATM MIB Module consists of the following tables:
     -- (1) ATM Interface configuration table
     -- (2) ATM Interface DS3 PLCP table
     -- (3) ATM Interface TC Sublayer table


     -- (4) Atm Traffic Descriptor table
     -- (5) ATM Interface VPL configuration table
     -- (6) ATM Interface VCL configuration table
     -- (7) ATM VP Cross Connect table (for PVCs)
     -- (8) ATM VC Cross Connect table (for PVCs)
     -- (9) ATM Interface AAL5 VCC performance statistics
     --     table

     --    ATM Interface Configuration Parameters Table

     -- This table contains ATM specific
     -- configuration information associated with
     -- an ATM interface beyond those
     -- supported using the ifTable.

     atmInterfaceConfTable  OBJECT-TYPE
          SYNTAX         SEQUENCE OF AtmInterfaceConfEntry
          MAX-ACCESS     not-accessible
          STATUS         current
          DESCRIPTION
           "This table contains ATM local interface
            configuration parameters, one entry per ATM
            interface port."
          ::= { atmMIBObjects 2 }

     atmInterfaceConfEntry    OBJECT-TYPE
          SYNTAX         AtmInterfaceConfEntry
          MAX-ACCESS     not-accessible
          STATUS         current
          DESCRIPTION
           "This list contains ATM interface configuration
            parameters and state variables and is indexed
            by ifIndex values of ATM interfaces."
          INDEX { ifIndex }
          ::= { atmInterfaceConfTable  1}

     AtmInterfaceConfEntry    ::= SEQUENCE  {
          atmInterfaceMaxVpcs             INTEGER,
          atmInterfaceMaxVccs             INTEGER,
          atmInterfaceConfVpcs            INTEGER,
          atmInterfaceConfVccs            INTEGER,
          atmInterfaceMaxActiveVpiBits    INTEGER,
          atmInterfaceMaxActiveVciBits    INTEGER,
          atmInterfaceIlmiVpi             AtmVpIdentifier,
          atmInterfaceIlmiVci             AtmVcIdentifier,


          atmInterfaceAddressType         INTEGER,
          atmInterfaceAdminAddress        AtmAddr,
          atmInterfaceMyNeighborIpAddress IpAddress,
          atmInterfaceMyNeighborIfName    DisplayString,
          atmInterfaceCurrentMaxVpiBits   INTEGER,
          atmInterfaceCurrentMaxVciBits   INTEGER,
          atmInterfaceSubscrAddress       AtmAddr
               }

     atmInterfaceMaxVpcs OBJECT-TYPE
          SYNTAX         INTEGER  (0..4096)
          MAX-ACCESS     read-write
          STATUS         current
          DESCRIPTION
           "The maximum number of VPCs (PVPCs and SVPCs)
            supported at this ATM interface. At the ATM UNI,
            the maximum number of VPCs (PVPCs and SVPCs)
            ranges from 0 to 256 only."
          ::= { atmInterfaceConfEntry 1}

     atmInterfaceMaxVccs OBJECT-TYPE
          SYNTAX         INTEGER  (0..65536)
          MAX-ACCESS     read-write
          STATUS         current
          DESCRIPTION
           "The maximum number of VCCs (PVCCs and SVCCs)
            supported at this ATM interface."
          ::= { atmInterfaceConfEntry 2}

     atmInterfaceConfVpcs  OBJECT-TYPE
          SYNTAX         INTEGER  (0..4096)
          MAX-ACCESS     read-only
          STATUS         current
          DESCRIPTION
           "The number of VPCs (PVPC, Soft PVPC and SVPC)
            currently in use at this ATM interface.  It includes
            the number of PVPCs and Soft PVPCs that are configured
            at the interface, plus the number of SVPCs
            that are currently  established at the
            interface.

            At the ATM UNI, the configured number of
            VPCs (PVPCs and SVPCs) can range from
            0 to 256 only."
          ::= { atmInterfaceConfEntry 3}

     atmInterfaceConfVccs  OBJECT-TYPE


          SYNTAX         INTEGER  (0..65536)
          MAX-ACCESS     read-only
          STATUS         current
          DESCRIPTION
           "The number of VCCs (PVCC, Soft PVCC and SVCC)
            currently in use at this ATM interface.  It includes
            the number of PVCCs and Soft PVCCs that are configured
            at the interface, plus the number of SVCCs
            that are currently  established at the
            interface."
          ::= { atmInterfaceConfEntry 4}

     atmInterfaceMaxActiveVpiBits  OBJECT-TYPE
          SYNTAX         INTEGER (0..12)
          MAX-ACCESS     read-write
          STATUS         current
          DESCRIPTION
           "The  maximum number of active VPI bits
            configured for use at the ATM interface.
            At the ATM UNI, the maximum number of active
            VPI bits configured for use ranges from
            0 to 8 only."
          ::= { atmInterfaceConfEntry 5}

     atmInterfaceMaxActiveVciBits  OBJECT-TYPE
          SYNTAX         INTEGER (0..16)
          MAX-ACCESS     read-write
          STATUS         current
          DESCRIPTION
           "The maximum number of active VCI bits
            configured for use at this ATM interface."
          ::= { atmInterfaceConfEntry 6}

     atmInterfaceIlmiVpi OBJECT-TYPE
          SYNTAX         AtmVpIdentifier
          MAX-ACCESS     read-write
          STATUS         current
          DESCRIPTION
           "The VPI value of the VCC supporting
            the ILMI at this ATM interface.  If the values of
            atmInterfaceIlmiVpi and atmInterfaceIlmiVci are
            both equal to zero then the ILMI is not
            supported at this ATM interface."
          DEFVAL { 0 }
          ::= { atmInterfaceConfEntry 7}

     atmInterfaceIlmiVci OBJECT-TYPE
          SYNTAX         AtmVcIdentifier


          MAX-ACCESS     read-write
          STATUS         current
          DESCRIPTION
           "The VCI value of the VCC supporting
            the ILMI at this ATM interface.  If the values of
            atmInterfaceIlmiVpi and atmInterfaceIlmiVci are
            both equal to zero then the ILMI is not
            supported at this ATM interface."
          DEFVAL { 16 }
          ::= { atmInterfaceConfEntry 8}

     atmInterfaceAddressType  OBJECT-TYPE
          SYNTAX         INTEGER {
                            private(1),
                            nsapE164(2),
                            nativeE164(3),
                            other(4)
                              }
          MAX-ACCESS     read-only
          STATUS         deprecated
          DESCRIPTION
           "The type of primary ATM address configured
            for use at this ATM interface."
          ::= { atmInterfaceConfEntry 9 }

     --  The atmInterfaceAdminAddress object has been replaced by
     --  atmInterfaceSubscrAddress.

     atmInterfaceAdminAddress OBJECT-TYPE
          SYNTAX         AtmAddr
          MAX-ACCESS     read-only
          STATUS         deprecated
          DESCRIPTION
           "The primary address assigned for administrative purposes,
            for example, an address associated with the
            service provider side of a public network UNI
            (thus, the value of this address corresponds
            with the value of ifPhysAddress at the host side).
            If this interface has no assigned administrative
            address, or when the address used for
            administrative purposes is the same as that used
            for ifPhysAddress, then this is an octet string of
            zero length."
          ::= { atmInterfaceConfEntry 10 }

     atmInterfaceMyNeighborIpAddress OBJECT-TYPE
          SYNTAX         IpAddress
          MAX-ACCESS     read-write


          STATUS         current
          DESCRIPTION
           "The IP address of the neighbor system connected to
            the  far end of this interface, to which a Network
            Management Station can send SNMP messages, as IP
            datagrams sent to UDP port 161, in order to access
            network management information concerning the
            operation of that system.  Note that the value
            of this object may be obtained in different ways,
            e.g., by manual configuration, or through ILMI
            interaction with the neighbor system."
          ::= { atmInterfaceConfEntry 11 }

     atmInterfaceMyNeighborIfName OBJECT-TYPE
          SYNTAX         DisplayString
          MAX-ACCESS     read-write
          STATUS         current
          DESCRIPTION
           "The textual name of the interface on the neighbor
            system on the far end of this interface, and to
            which this interface connects.  If the neighbor
            system is manageable through SNMP and supports
            the object ifName, the value of this object must
            be identical with that of ifName for the ifEntry
            of the lowest level physical interface
            for this port.  If this interface does not have a
            textual name, the value of this object is a zero
            length string.  Note that the value of this object
            may be obtained in different ways, e.g., by manual
            configuration, or through ILMI interaction with
            the neighbor system."
          ::= { atmInterfaceConfEntry 12 }

     atmInterfaceCurrentMaxVpiBits    OBJECT-TYPE
          SYNTAX         INTEGER  (0..12)
          MAX-ACCESS     read-only
          STATUS         current
          DESCRIPTION
           "The maximum number of VPI Bits that may
            currently be used at this ATM interface.
            The value is the minimum of
            atmInterfaceMaxActiveVpiBits, and the
            atmInterfaceMaxActiveVpiBits of the interface's
            UNI/NNI peer.

            If the interface does not negotiate with
            its peer to determine the number of VPI Bits
            that can be used on the interface, then the


            value of this object must equal
            atmInterfaceMaxActiveVpiBits."
          ::= { atmInterfaceConfEntry 13 }

     atmInterfaceCurrentMaxVciBits    OBJECT-TYPE
          SYNTAX         INTEGER  (0..16)
          MAX-ACCESS     read-only
          STATUS         current
          DESCRIPTION
           "The maximum number of VCI Bits that may
            currently be used at this ATM interface.
            The value is the minimum of
            atmInterfaceMaxActiveVciBits, and the
            atmInterfaceMaxActiveVciBits of the interface's
            UNI/NNI peer.

            If the interface does not negotiate with
            its peer to determine the number of VCI Bits
            that can be used on the interface, then the
            value of this object must equal
            atmInterfaceMaxActiveVciBits."
          ::= { atmInterfaceConfEntry 14 }

     atmInterfaceSubscrAddress OBJECT-TYPE
          SYNTAX         AtmAddr
          MAX-ACCESS     read-write
          STATUS         current
          DESCRIPTION
           "The identifier assigned by a service provider
            to the network side of a public network UNI.
            If this interface has no assigned service provider
            address, or for other interfaces this is an octet string
            of zero length."
          ::= { atmInterfaceConfEntry 15 }

     -- The ATM Interface DS3 PLCP Table

     -- This table contains the DS3 PLCP configuration and
     -- state parameters of those ATM interfaces
     -- which use DS3 PLCP for carrying ATM cells over DS3.

     atmInterfaceDs3PlcpTable  OBJECT-TYPE
          SYNTAX       SEQUENCE OF AtmInterfaceDs3PlcpEntry
          MAX-ACCESS   not-accessible
          STATUS       current
          DESCRIPTION
           "This table contains ATM interface DS3 PLCP
            parameters and state variables, one entry per


            ATM interface port."
          ::= { atmMIBObjects 3}

     atmInterfaceDs3PlcpEntry OBJECT-TYPE
          SYNTAX         AtmInterfaceDs3PlcpEntry
          MAX-ACCESS     not-accessible
          STATUS         current
          DESCRIPTION
           "This list contains DS3 PLCP parameters and
            state variables at the ATM interface and is
            indexed by the ifIndex value of the ATM interface."
          INDEX    { ifIndex }
          ::= { atmInterfaceDs3PlcpTable 1}

     AtmInterfaceDs3PlcpEntry    ::= SEQUENCE  {
          atmInterfaceDs3PlcpSEFSs       Counter32,
          atmInterfaceDs3PlcpAlarmState  INTEGER,
          atmInterfaceDs3PlcpUASs        Counter32
            }

     atmInterfaceDs3PlcpSEFSs  OBJECT-TYPE
          SYNTAX         Counter32
          MAX-ACCESS     read-only
          STATUS         current
          DESCRIPTION
           "The number of DS3 PLCP Severely Errored Framing
            Seconds (SEFS). Each SEFS represents a
            one-second interval which contains
            one or more SEF events."
          ::= { atmInterfaceDs3PlcpEntry 1}

     atmInterfaceDs3PlcpAlarmState    OBJECT-TYPE
          SYNTAX         INTEGER {
                            noAlarm(1),
                            receivedFarEndAlarm(2),
                            incomingLOF(3)
                                 }
          MAX-ACCESS     read-only
          STATUS         current
          DESCRIPTION
           "This variable indicates if there is an
            alarm present for the DS3 PLCP.  The value
            receivedFarEndAlarm means that the DS3 PLCP
            has received an incoming Yellow
            Signal, the value incomingLOF means that
            the DS3 PLCP has declared a loss of frame (LOF)
            failure condition, and the value noAlarm


            means that there are no alarms present.
            Transition from the failure to the no alarm state
            occurs when no defects (e.g., LOF) are received
            for more than 10 seconds."
          ::= { atmInterfaceDs3PlcpEntry 2}

     atmInterfaceDs3PlcpUASs  OBJECT-TYPE
          SYNTAX         Counter32
          MAX-ACCESS     read-only
          STATUS         current
          DESCRIPTION
           "The counter associated with the number of
            Unavailable Seconds encountered by the PLCP."
          ::= { atmInterfaceDs3PlcpEntry 3}

     -- The ATM Interface TC Sublayer Table

     -- This table contains TC sublayer configuration and
     -- state parameters of those ATM interfaces
     -- which use TC sublayer for carrying ATM cells over
     -- SONET/SDH or DS3.

     atmInterfaceTCTable  OBJECT-TYPE
          SYNTAX         SEQUENCE OF AtmInterfaceTCEntry
          MAX-ACCESS     not-accessible
          STATUS         current
          DESCRIPTION
           "This table contains ATM interface TC
            Sublayer parameters and state variables,
            one entry per ATM interface port."
          ::= { atmMIBObjects 4}

     atmInterfaceTCEntry OBJECT-TYPE
          SYNTAX         AtmInterfaceTCEntry
          MAX-ACCESS     not-accessible
          STATUS         current
          DESCRIPTION
           "This list contains TC Sublayer parameters
            and state variables at the ATM interface and is
            indexed by the ifIndex value of the ATM interface."
          INDEX  {ifIndex }
          ::= { atmInterfaceTCTable 1}

     AtmInterfaceTCEntry    ::= SEQUENCE  {
          atmInterfaceOCDEvents      Counter32,
          atmInterfaceTCAlarmState   INTEGER


            }

     atmInterfaceOCDEvents  OBJECT-TYPE
          SYNTAX         Counter32
          MAX-ACCESS     read-only
          STATUS         current
          DESCRIPTION
           "The number of times the Out of Cell
            Delineation (OCD) events occur.  If seven
            consecutive ATM cells have Header Error
            Control (HEC) violations, an OCD event occurs.
            A high number of OCD events may indicate a
            problem with the TC Sublayer."
          ::= { atmInterfaceTCEntry 1}

     atmInterfaceTCAlarmState    OBJECT-TYPE
          SYNTAX         INTEGER {
                            noAlarm(1),
                            lcdFailure(2)
                                  }
          MAX-ACCESS     read-only
          STATUS         current
          DESCRIPTION
           "This variable indicates if there is an
            alarm present for the TC Sublayer.  The value
            lcdFailure(2) indicates that the TC Sublayer
            is currently in the Loss of Cell Delineation
            (LCD) defect maintenance state.  The value
            noAlarm(1) indicates that the TC Sublayer
            is currently not in the LCD defect
            maintenance state."
           ::= { atmInterfaceTCEntry 2}

     --  ATM Traffic Descriptor Parameter Table

     -- This table contains a set of self-consistent
     -- ATM traffic parameters including the
     -- ATM traffic service category.

     -- The ATM virtual link tables (i.e., VPL and VCL tables)
     -- will use this ATM Traffic Descriptor table
     -- to assign traffic parameters and service category
     -- to the receive and transmit directions of
     -- the ATM virtual links (i.e., VPLs and VCLs).
     -- The ATM VPL or VCL table will indicate a row
     -- in the atmTrafficDescrParamTable
     -- using its atmTrafficDescrParamIndex value.


     -- The management application can then compare a set of
     -- ATM traffic parameters with a single value.

     -- If no suitable row(s) in the atmTrafficDescrParamTable
     -- exists, the manager must create a new row(s) in this
     -- table. If such a row is created, agent checks the
     -- sanity of that set of ATM traffic parameter values.

     -- The manager may use atmTrafficDescrParamIndexNext
     -- in order to obtain a free atmTrafficDescrParamIndex
     -- value.

     -- When creating a new row, the parameter values
     -- will be checked for self-consistency.
     -- Predefined/template rows may be supported.

     -- A row in the atmTrafficDescrParamTable is deleted
     -- by setting the atmTrafficDescrRowStatus to destroy(6).
     -- The agent will check whether this row is still in use
     -- by any entry of the atmVplTable or atmVclTable.
     -- The agent denies the request if the row is still in
     -- use.

     --  The ATM Traffic Descriptor Parameter Table

     atmTrafficDescrParamTable    OBJECT-TYPE
          SYNTAX       SEQUENCE OF AtmTrafficDescrParamEntry
          MAX-ACCESS   not-accessible
          STATUS       current
          DESCRIPTION
           "This table contains information on ATM traffic
            descriptor type and the associated parameters."
          ::= { atmMIBObjects 5}

     atmTrafficDescrParamEntry    OBJECT-TYPE
          SYNTAX         AtmTrafficDescrParamEntry
          MAX-ACCESS     not-accessible
          STATUS         current
          DESCRIPTION
           "This list contains ATM traffic descriptor
            type and the associated parameters."
          INDEX  {atmTrafficDescrParamIndex}
          ::= { atmTrafficDescrParamTable 1}

     AtmTrafficDescrParamEntry   ::= SEQUENCE  {
       atmTrafficDescrParamIndex  AtmTrafficDescrParamIndex,
       atmTrafficDescrType        OBJECT IDENTIFIER,


       atmTrafficDescrParam1      Integer32,
       atmTrafficDescrParam2      Integer32,
       atmTrafficDescrParam3      Integer32,
       atmTrafficDescrParam4      Integer32,
       atmTrafficDescrParam5      Integer32,
       atmTrafficQoSClass         INTEGER,
       atmTrafficDescrRowStatus   RowStatus,
       atmServiceCategory         AtmServiceCategory,
       atmTrafficFrameDiscard     TruthValue
                    }

     atmTrafficDescrParamIndex OBJECT-TYPE
          SYNTAX  AtmTrafficDescrParamIndex (1..2147483647)
          MAX-ACCESS     not-accessible
          STATUS         current
          DESCRIPTION
           "This object is used by the virtual link
            table (i.e., VPL or VCL table)
            to identify the row of this table.
            When creating a new row in the table
            the value of this index may be obtained
            by retrieving the value of
            atmTrafficDescrParamIndexNext."
          ::= { atmTrafficDescrParamEntry  1}

     atmTrafficDescrType OBJECT-TYPE
          SYNTAX         OBJECT IDENTIFIER
          MAX-ACCESS     read-create
          STATUS         current
          DESCRIPTION
           "The value of this object identifies the type
            of ATM traffic descriptor.
            The type may indicate no traffic descriptor or
            traffic descriptor with one or more parameters.
            These parameters are specified as a parameter
            vector, in the corresponding instances of the
            objects:
                atmTrafficDescrParam1
                atmTrafficDescrParam2
                atmTrafficDescrParam3
                atmTrafficDescrParam4
                atmTrafficDescrParam5."
           DEFVAL  { atmNoClpNoScr }
           ::= { atmTrafficDescrParamEntry 2}

     atmTrafficDescrParam1 OBJECT-TYPE
          SYNTAX         Integer32
          MAX-ACCESS     read-create


          STATUS         current
          DESCRIPTION
           "The first parameter of the ATM traffic descriptor
            used according to the value of
            atmTrafficDescrType."
          DEFVAL  { 0 }
          ::= { atmTrafficDescrParamEntry 3}

     atmTrafficDescrParam2 OBJECT-TYPE
          SYNTAX         Integer32
          MAX-ACCESS     read-create
          STATUS         current
          DESCRIPTION
           "The second parameter of the ATM traffic descriptor
            used according to the value of
            atmTrafficDescrType."
          DEFVAL  { 0 }
          ::= { atmTrafficDescrParamEntry 4}

     atmTrafficDescrParam3 OBJECT-TYPE
          SYNTAX         Integer32
          MAX-ACCESS     read-create
          STATUS         current
          DESCRIPTION
           "The third parameter of the ATM traffic descriptor
            used according to the value of
            atmTrafficDescrType."
          DEFVAL  { 0 }
          ::= { atmTrafficDescrParamEntry 5}

     atmTrafficDescrParam4 OBJECT-TYPE
          SYNTAX         Integer32
          MAX-ACCESS     read-create
          STATUS         current
          DESCRIPTION
           "The fourth parameter of the ATM traffic descriptor
            used according to the value of
            atmTrafficDescrType."
          DEFVAL  { 0 }
          ::= { atmTrafficDescrParamEntry 6}

     atmTrafficDescrParam5 OBJECT-TYPE
          SYNTAX         Integer32
          MAX-ACCESS     read-create
          STATUS         current
          DESCRIPTION
           "The fifth parameter of the ATM traffic descriptor
            used according to the value of


            atmTrafficDescrType."
          DEFVAL  { 0 }
          ::= { atmTrafficDescrParamEntry 7}

     atmTrafficQoSClass  OBJECT-TYPE
          SYNTAX         INTEGER (0..255)
          MAX-ACCESS     read-create
          STATUS         deprecated
          DESCRIPTION
           "The value of this object identifies the QoS Class.
            Four Service classes have been
            specified in the ATM Forum UNI Specification:
            Service Class A: Constant bit rate video and
                             Circuit emulation
            Service Class B: Variable bit rate video/audio
            Service Class C: Connection-oriented data
            Service Class D: Connectionless data
            Four QoS classes numbered 1, 2, 3, and 4 have
            been specified with the aim to support service
            classes A, B, C, and D respectively.
            An unspecified QoS Class numbered `0' is used
            for best effort traffic."
          DEFVAL  { 0 }
          ::= { atmTrafficDescrParamEntry 8}

     atmTrafficDescrRowStatus  OBJECT-TYPE
          SYNTAX         RowStatus
          MAX-ACCESS     read-create
          STATUS         current
          DESCRIPTION
           "This object is used to create
            a new row or modify or delete an
            existing row in this table."
          DEFVAL  { active }
          ::= {atmTrafficDescrParamEntry 9}

     atmServiceCategory  OBJECT-TYPE
          SYNTAX         AtmServiceCategory
          MAX-ACCESS     read-create
          STATUS         current
          DESCRIPTION
           "The ATM service category."
          DEFVAL  { ubr }
          ::= { atmTrafficDescrParamEntry 10}

     atmTrafficFrameDiscard    OBJECT-TYPE
          SYNTAX       TruthValue


          MAX-ACCESS   read-create
          STATUS       current
          DESCRIPTION
           "If set to 'true', this object indicates that the network
            is requested to treat data for this connection, in the
            given direction, as frames (e.g. AAL5 CPCS_PDU's) rather
            than as individual cells.  While the precise
            implementation is network-specific, this treatment may
            for example involve discarding entire frames during
            congestion, rather than a few cells from many frames."
          DEFVAL { true }
          ::= { atmTrafficDescrParamEntry 11 }

     --  ATM Interface Virtual Path Link (VPL) Table

     -- This table contains configuration and state
     -- information of a bi-directional Virtual Path Link
     -- (VPL)

     -- This table can be used to create, delete or modify
     -- a VPL that is terminated in an ATM host or switch.
     -- This table can also be used to create, delete or
     -- modify a VPL which is cross-connected to another
     -- VPL.

     -- In the example below, the traffic flows on the receive
     -- and transmit directions of the VPLs are characterized
     -- by atmVplReceiveTrafficDescrIndex and
     -- atmVplTransmitTrafficDescrIndex respectively.
     -- The cross-connected VPLs are identified by
     -- atmVplCrossConnectIdentifier.

     --           ________________________________
     --           |                              |
     --  VPL      | ATM Host, Switch, or Network |   VPL
     -- receive   |                              |  receive
     -- ========> X                              X <=======
     -- <======== X                              X ========>
     -- transmit  |                              |  transmit
     --           |______________________________|

     --  The ATM Interface VPL Table


     atmVplTable         OBJECT-TYPE
          SYNTAX         SEQUENCE OF AtmVplEntry
          MAX-ACCESS     not-accessible
          STATUS         current
          DESCRIPTION
           "The Virtual Path Link (VPL) table.  A
            bi-directional VPL is modeled as one entry
            in this table. This table can be used for
            PVCs, SVCs and Soft PVCs.
            Entries are not present in this table for
            the VPIs used by entries in the atmVclTable."
          ::= { atmMIBObjects 6}

     atmVplEntry         OBJECT-TYPE
          SYNTAX         AtmVplEntry
          MAX-ACCESS     not-accessible
          STATUS         current
          DESCRIPTION
           "An entry in the VPL table.  This entry is
            used to model a bi-directional VPL.
            To create a VPL at an ATM interface,
            either of the following procedures are used:

            Negotiated VPL establishment

          (1) The management application creates
              a VPL entry in the atmVplTable
              by setting atmVplRowStatus to createAndWait(5).
              This may fail for the following reasons:
              - The selected VPI value is unavailable,
              - The selected VPI value is in use.
              Otherwise, the agent creates a row and
              reserves the VPI value on that port.

          (2) The manager selects an existing row(s) in the
              atmTrafficDescrParamTable,
              thereby, selecting a set of self-consistent
              ATM traffic parameters and the service category
              for receive and transmit directions of the VPL.

         (2a) If no suitable row(s) in the
              atmTrafficDescrParamTable exists,
              the manager must create a new row(s)
              in that table.

         (2b) The manager characterizes the VPL's traffic
              parameters through setting the
              atmVplReceiveTrafficDescrIndex and the


              atmVplTransmitTrafficDescrIndex values
              in the VPL table, which point to the rows
              containing desired ATM traffic parameter values
              in the atmTrafficDescrParamTable.  The agent
              will check the availability of resources and
              may refuse the request.
              If the transmit and receive service categories
              are inconsistent, the agent should refuse the
              request.

          (3) The manager activates the VPL by setting the
              the atmVplRowStatus to active(1).
              If this set is successful, the agent has
              reserved the resources to satisfy the requested
              traffic parameter values and the service category
              for that VPL.

          (4) If the VPL terminates a VPC in the ATM host
              or switch, the manager turns on the
              atmVplAdminStatus to up(1) to turn the VPL
              traffic flow on.  Otherwise, the
              atmVpCrossConnectTable  must be used
              to cross-connect the VPL to another VPL(s)
              in an ATM switch or network.

            One-Shot VPL Establishment

            A VPL may also be established in one step by a
            set-request with all necessary VPL parameter
            values and atmVplRowStatus set to createAndGo(4).

            In contrast to the negotiated VPL establishment
            which allows for detailed error checking
            (i.e., set errors are explicitly linked to
            particular resource acquisition failures),
            the one-shot VPL establishment
            performs the setup on one operation but
            does not have the advantage of step-wise
            error checking.

            VPL Retirement

            A VPL is released by setting atmVplRowStatus to
            destroy(6), and the agent may release all
            associated resources."
          INDEX  {ifIndex, atmVplVpi }
          ::= { atmVplTable  1}


     AtmVplEntry    ::= SEQUENCE  {
          atmVplVpi          AtmVpIdentifier,
          atmVplAdminStatus  AtmVorXAdminStatus,
          atmVplOperStatus   AtmVorXOperStatus,
          atmVplLastChange   AtmVorXLastChange,
          atmVplReceiveTrafficDescrIndex
                         AtmTrafficDescrParamIndex,
          atmVplTransmitTrafficDescrIndex
                         AtmTrafficDescrParamIndex,
          atmVplCrossConnectIdentifier INTEGER,
          atmVplRowStatus    RowStatus,
          atmVplCastType     AtmConnCastType,
          atmVplConnKind     AtmConnKind
             }

     atmVplVpi           OBJECT-TYPE
          SYNTAX         AtmVpIdentifier
          MAX-ACCESS     not-accessible
          STATUS         current
          DESCRIPTION
           "The VPI value of the VPL."
          ::= { atmVplEntry 1}

     atmVplAdminStatus   OBJECT-TYPE
          SYNTAX         AtmVorXAdminStatus
          MAX-ACCESS     read-create
          STATUS         current
          DESCRIPTION
           "This object is instanciated only for a VPL
            which terminates a VPC (i.e., one which is
            NOT cross-connected to other VPLs).
            Its value specifies the desired
            administrative state of the VPL."
          DEFVAL { down }
          ::= { atmVplEntry 2}

     atmVplOperStatus    OBJECT-TYPE
          SYNTAX         AtmVorXOperStatus
          MAX-ACCESS     read-only
          STATUS         current
          DESCRIPTION
           "The current operational status of the VPL."
          ::= { atmVplEntry 3}

     atmVplLastChange    OBJECT-TYPE
          SYNTAX         AtmVorXLastChange
          MAX-ACCESS     read-only


          STATUS         current
          DESCRIPTION
           "The value of sysUpTime at the time this
            VPL entered its current operational state."
          ::= { atmVplEntry 4 }

     atmVplReceiveTrafficDescrIndex  OBJECT-TYPE
          SYNTAX         AtmTrafficDescrParamIndex
          MAX-ACCESS     read-create
          STATUS         current
          DESCRIPTION
           "The value of this object identifies the row
            in the atmTrafficDescrParamTable which
            applies to the receive direction of the VPL."
          DEFVAL { 0 }
           ::= { atmVplEntry 5}

     atmVplTransmitTrafficDescrIndex  OBJECT-TYPE
          SYNTAX         AtmTrafficDescrParamIndex
          MAX-ACCESS     read-create
          STATUS         current
          DESCRIPTION
           "The value of this object identifies the row
            in the atmTrafficDescrParamTable which
            applies to the transmit direction of the VPL."
          DEFVAL { 0 }
           ::= { atmVplEntry 6}

     atmVplCrossConnectIdentifier   OBJECT-TYPE
          SYNTAX         INTEGER (0..2147483647)
          MAX-ACCESS     read-only
          STATUS         current
          DESCRIPTION
           "This object is instantiated only for a VPL
            which is cross-connected to other VPLs
            that belong to the same VPC.  All such
            associated VPLs have the same value of this
            object, and all their cross-connections are
            identified either by entries that are indexed
            by the same value of atmVpCrossConnectIndex in
            the atmVpCrossConnectTable of this MIB module or by
            the same value of the cross-connect index in
            the cross-connect table for SVCs and Soft PVCs
            (defined in a separate MIB module).
            At no time should entries in these respective
            cross-connect tables exist simultaneously
            with the same cross-connect index value.


            The value of this object is initialized by the
            agent after the associated entries in the
            atmVpCrossConnectTable have been created."
          ::= {atmVplEntry 7}

     atmVplRowStatus     OBJECT-TYPE
          SYNTAX         RowStatus
          MAX-ACCESS     read-create
          STATUS         current
          DESCRIPTION
           "This object is used to create, delete
            or modify a row in this table.
            To create a new VCL, this object is
            initially set to 'createAndWait' or
            'createAndGo'.  This object should not be
            set to 'active' unless the following columnar
            objects have been set to their desired value
            in this row:
            atmVplReceiveTrafficDescrIndex and
            atmVplTransmitTrafficDescrIndex.
            The DESCRIPTION of atmVplEntry provides
            further guidance to row treatment in this table."
          DEFVAL { createAndWait }
          ::= {atmVplEntry 8}

     atmVplCastType      OBJECT-TYPE
          SYNTAX         AtmConnCastType
          MAX-ACCESS     read-create
          STATUS         current
          DESCRIPTION
           "The connection topology type."
          DEFVAL { p2p }
          ::= {atmVplEntry 9}

     atmVplConnKind      OBJECT-TYPE
          SYNTAX         AtmConnKind
          MAX-ACCESS     read-create
          STATUS         current
          DESCRIPTION
           "The use of call control."
          DEFVAL { pvc }
          ::= {atmVplEntry 10}

     --  ATM Interface Virtual Channel Link (VCL) Table

     -- This table contains configuration and state
     -- information of a bi-directional Virtual Channel
     -- Link (VCL) at an ATM interface.


     -- This table can be used to create, delete or modify
     -- a VCL that is terminated in an ATM host or switch.
     -- This table can also be
     -- used to create, delete or modify a VCL that is
     -- cross-connected to another VCL.

     --  The ATM Interface VCL Table

     atmVclTable         OBJECT-TYPE
          SYNTAX         SEQUENCE OF AtmVclEntry
          MAX-ACCESS     not-accessible
          STATUS         current
          DESCRIPTION
           "The Virtual Channel Link (VCL) table.  A
            bi-directional VCL is modeled as one entry
            in this table. This table can be used for
            PVCs, SVCs and Soft PVCs."
          ::= { atmMIBObjects 7}

     atmVclEntry         OBJECT-TYPE
          SYNTAX         AtmVclEntry
          MAX-ACCESS     not-accessible
          STATUS         current
          DESCRIPTION
           "An entry in the VCL table. This entry is
            used to model a bi-directional VCL.
            To create a VCL at an ATM interface,
            either of the following procedures are used:

            Negotiated VCL establishment

          (1) The management application creates
              a VCL entry in the atmVclTable
              by setting atmVclRowStatus to createAndWait(5).
              This may fail for the following reasons:
              - The selected VPI/VCI values are unavailable,
              - The selected VPI/VCI values are in use.
              Otherwise, the agent creates a row and
              reserves the VPI/VCI values on that port.

          (2) The manager selects an existing row(s) in the
              atmTrafficDescrParamTable,
              thereby, selecting a set of self-consistent
              ATM traffic parameters and the service category
              for receive and transmit directions of the VCL.


         (2a) If no suitable row(s) in the
              atmTrafficDescrParamTable exists,
              the manager must create a new row(s)
              in that table.

         (2b) The manager characterizes the VCL's traffic
              parameters through setting the
              atmVclReceiveTrafficDescrIndex and the
              atmVclTransmitTrafficDescrIndex values
              in the VCL table, which point to the rows
              containing desired ATM traffic parameter values
              in the atmTrafficDescrParamTable.  The agent
              will check the availability of resources and
              may refuse the request.
              If the transmit and receive service categories
              are inconsistent, the agent should refuse the
              request.

          (3) The manager activates the VCL by setting the
              the atmVclRowStatus to active(1) (for
              requirements on this activation see the
              description of atmVclRowStatus).
              If this set is successful, the agent has
              reserved the resources to satisfy the requested
              traffic parameter values and the service category
              for that VCL.
          (4) If the VCL terminates a VCC in the ATM host
              or switch, the manager turns on the
              atmVclAdminStatus to up(1) to turn the VCL
              traffic flow on.  Otherwise, the
              atmVcCrossConnectTable  must be used
              to cross-connect the VCL to another VCL(s)
              in an ATM switch or network.

           One-Shot VCL Establishment

           A VCL may also be established in one step by a
           set-request with all necessary VCL parameter
           values and atmVclRowStatus set to createAndGo(4).

           In contrast to the negotiated VCL establishment
           which allows for detailed error checking
           (i.e., set errors are explicitly linked to
           particular resource acquisition failures),
           the one-shot VCL establishment
           performs the setup on one operation but
           does not have the advantage of step-wise
           error checking.


           VCL Retirement

           A VCL is released by setting atmVclRowStatus to
           destroy(6), and the agent may release all
           associated resources."
          INDEX  {ifIndex, atmVclVpi, atmVclVci }
          ::= { atmVclTable  1}

     AtmVclEntry    ::= SEQUENCE  {
          atmVclVpi                     AtmVpIdentifier,
          atmVclVci                     AtmVcIdentifier,
          atmVclAdminStatus             AtmVorXAdminStatus,
          atmVclOperStatus              AtmVorXOperStatus,
          atmVclLastChange              AtmVorXLastChange,
          atmVclReceiveTrafficDescrIndex
                                AtmTrafficDescrParamIndex,
          atmVclTransmitTrafficDescrIndex
                                AtmTrafficDescrParamIndex,
          atmVccAalType                 INTEGER,
          atmVccAal5CpcsTransmitSduSize INTEGER,
          atmVccAal5CpcsReceiveSduSize  INTEGER,
          atmVccAal5EncapsType          INTEGER,
          atmVclCrossConnectIdentifier  INTEGER,
          atmVclRowStatus               RowStatus,
          atmVclCastType                AtmConnCastType,
          atmVclConnKind                AtmConnKind
                 }

     atmVclVpi           OBJECT-TYPE
          SYNTAX         AtmVpIdentifier
          MAX-ACCESS     not-accessible
          STATUS         current
          DESCRIPTION
           "The VPI value of the VCL."
          ::= { atmVclEntry 1}

     atmVclVci           OBJECT-TYPE
          SYNTAX         AtmVcIdentifier
          MAX-ACCESS     not-accessible
          STATUS         current
          DESCRIPTION
           "The VCI value of the VCL."
          ::= { atmVclEntry 2}

     atmVclAdminStatus   OBJECT-TYPE
          SYNTAX         AtmVorXAdminStatus
          MAX-ACCESS     read-create
          STATUS         current


          DESCRIPTION
           "This object is instanciated only for a VCL which
            terminates a VCC (i.e., one which is NOT
            cross-connected to other VCLs). Its value
            specifies the desired administrative state of
            the VCL."
          DEFVAL { down }
          ::= { atmVclEntry 3}

     atmVclOperStatus    OBJECT-TYPE
          SYNTAX         AtmVorXOperStatus
          MAX-ACCESS     read-only
          STATUS         current
          DESCRIPTION
           "The current operational status of the VCL."
          ::= { atmVclEntry 4}

     atmVclLastChange    OBJECT-TYPE
          SYNTAX         AtmVorXLastChange
          MAX-ACCESS     read-only
          STATUS         current
          DESCRIPTION
           "The value of sysUpTime at the time this VCL
            entered its current operational state."
          ::= { atmVclEntry 5 }

     atmVclReceiveTrafficDescrIndex  OBJECT-TYPE
          SYNTAX         AtmTrafficDescrParamIndex
          MAX-ACCESS     read-create
          STATUS         current
          DESCRIPTION
           "The value of this object identifies the row
            in the ATM Traffic Descriptor Table which
            applies to the receive direction of this VCL."
          DEFVAL { 0 }
           ::= { atmVclEntry 6}

     atmVclTransmitTrafficDescrIndex  OBJECT-TYPE
          SYNTAX         AtmTrafficDescrParamIndex
          MAX-ACCESS     read-create
          STATUS         current
          DESCRIPTION
           "The value of this object identifies the row
            of the ATM Traffic Descriptor Table which applies
            to the transmit direction of this VCL."
          DEFVAL { 0 }
           ::= { atmVclEntry 7}


     atmVccAalType       OBJECT-TYPE
          SYNTAX         INTEGER {
                            aal1(1),
                            aal34(2),
                            aal5(3),
                            other(4),
                            unknown(5),
                            aal2(6)
                              }
          MAX-ACCESS    read-create
          STATUS        current
          DESCRIPTION
           "An instance of this object only exists when the
            local VCL end-point is also the VCC end-point,
            and AAL is in use.
            The type of AAL used on this VCC.
            The AAL type includes AAL1, AAL2, AAL3/4,
            and AAL5. The other(4) may be user-defined
            AAL type.  The unknown type indicates that
            the AAL type cannot be determined."
          DEFVAL { aal5 }
          ::= { atmVclEntry 8 }

     atmVccAal5CpcsTransmitSduSize OBJECT-TYPE
          SYNTAX         INTEGER (1..65535)
          MAX-ACCESS     read-create
          STATUS         current
          DESCRIPTION
           "An instance of this object only exists when the
            local VCL end-point is also the VCC end-point,
            and AAL5 is in use.
            The maximum AAL5 CPCS SDU size in octets that is
            supported on the transmit direction of this VCC."
          DEFVAL { 9188 }
                ::= { atmVclEntry 9 }

     atmVccAal5CpcsReceiveSduSize OBJECT-TYPE
          SYNTAX         INTEGER (1..65535)
          MAX-ACCESS     read-create
          STATUS         current
          DESCRIPTION
           "An instance of this object only exists when the
            local VCL end-point is also the VCC end-point,
            and AAL5 is in use.
            The maximum AAL5 CPCS SDU size in octets that is
            supported on the receive direction of this VCC."
          DEFVAL { 9188 }
                ::= { atmVclEntry 10 }


     atmVccAal5EncapsType  OBJECT-TYPE
          SYNTAX         INTEGER {
                         vcMultiplexRoutedProtocol(1),
                         vcMultiplexBridgedProtocol8023(2),
                         vcMultiplexBridgedProtocol8025(3),
                         vcMultiplexBridgedProtocol8026(4),
                         vcMultiplexLANemulation8023(5),
                         vcMultiplexLANemulation8025(6),
                         llcEncapsulation(7),
                         multiprotocolFrameRelaySscs(8),
                         other(9),
                         unknown(10)
                            }
          MAX-ACCESS     read-create
          STATUS         current
          DESCRIPTION
           "An instance of this object only exists when the
            local VCL end-point is also the VCC end-point,
            and AAL5 is in use.
            The type of data encapsulation used over
            the AAL5 SSCS layer. The definitions reference
            RFC 1483 Multiprotocol Encapsulation
            over ATM AAL5 and to the ATM Forum
            LAN Emulation specification."
          DEFVAL { llcEncapsulation }
                ::= { atmVclEntry 11 }

     atmVclCrossConnectIdentifier   OBJECT-TYPE
          SYNTAX         INTEGER (0..2147483647)
          MAX-ACCESS     read-only
          STATUS         current
          DESCRIPTION
           "This object is instantiated only for a VCL
            which is cross-connected to other VCLs
            that belong to the same VCC.  All such
            associated VCLs have the same value of this
            object, and all their cross-connections are
            identified either by entries that are indexed
            by the same value of atmVcCrossConnectIndex in
            the atmVcCrossConnectTable of this MIB module or by
            the same value of the cross-connect index in
            the cross-connect table for SVCs and Soft PVCs
            (defined in a separate MIB module).

            At no time should entries in these respective
            cross-connect tables exist simultaneously
            with the same cross-connect index value.


            The value of this object is initialized by the
            agent after the associated entries in the
            atmVcCrossConnectTable have been created."
          ::= {atmVclEntry 12}

     atmVclRowStatus     OBJECT-TYPE
          SYNTAX         RowStatus
          MAX-ACCESS     read-create
          STATUS         current
          DESCRIPTION
           "This object is used to create, delete or
            modify a row in this table.  To create
            a new VCL, this object is initially set
            to 'createAndWait' or 'createAndGo'.
            This object should not be
            set to 'active' unless the following columnar
            objects have been set to their desired value
            in this row:
            atmVclReceiveTrafficDescrIndex,
            atmVclTransmitTrafficDescrIndex.
            In addition, if the local VCL end-point
            is also the VCC end-point:
            atmVccAalType.
            In addition, for AAL5 connections only:
            atmVccAal5CpcsTransmitSduSize,
            atmVccAal5CpcsReceiveSduSize, and
            atmVccAal5EncapsType. (The existence
            of these objects imply the AAL connection type.).
            The DESCRIPTION of atmVclEntry provides
            further guidance to row treatment in this table."
          DEFVAL { createAndWait }
                ::= {atmVclEntry 13}

     atmVclCastType      OBJECT-TYPE
          SYNTAX         AtmConnCastType
          MAX-ACCESS     read-create
          STATUS         current
          DESCRIPTION
           "The connection topology type."
          DEFVAL { p2p }
                ::= {atmVclEntry 14}

     atmVclConnKind      OBJECT-TYPE
          SYNTAX         AtmConnKind
          MAX-ACCESS     read-create
          STATUS         current
          DESCRIPTION


           "The use of call control."
          DEFVAL { pvc }
          ::= {atmVclEntry 15}

     --     ATM Virtual Path (VP) Cross Connect Table

     -- This table contains configuration and state
     -- information of point-to-point,
     -- point-to-multipoint, or multipoint-to-multipoint
     -- VP cross-connects for PVCs.

     -- This table has read-create access and can be used
     -- to cross-connect the VPLs together in an ATM switch
     -- or network. The atmVpCrossConnectIndex
     -- is used to associate the related
     -- VPLs that are cross-connected together.

     -- The ATM VP Cross Connect Table
     -- models each bi-directional VPC
     -- cross-connect as a set of entries in
     -- the atmVpCrossConnectTable. A
     -- point-to-point VPC cross-connect is modeled
     -- as one entry; a point-to-multipoint (N leafs) VPC
     -- cross-connect as N entries in this table; and
     -- a multipoint-to-multipoint (N parties) VPC cross-
     -- connect as N(N-1)/2 entries in this table.
     -- In the latter cases, all the N (or N(N-1)/2) entries
     -- are associated with a single VPC cross-connect by
     -- having the same value of atmVpCrossConnectIndex.

     --      _________________________________________
     --      |                                       |
     --  Low |         ATM Switch or Network         | High
     --  port|                                       | port
     -- _____|>> from low to high VPC traffic flow >>|______
     --      |<< from high to low VPC traffic flow <<|
     --      |                                       |
     --      |_______________________________________|
     --

     -- The terms low and high are chosen to represent
     -- numerical ordering of the two interfaces associated
     -- with a VPC cross-connect. That is, the ATM interface
     -- with the lower value of ifIndex is termed 'low',
     -- while the other ATM interface associated with the
     -- VPC cross-connect is termed 'high'. This terminology


     -- is used to provide directional information; for
     -- example, the atmVpCrossConnectL2HOperStatus applies
     -- to the low->high direction, and
     -- atmVpCrossConnectH2LOperStatus applies to the
     -- high->low  direction, as illustrated above.

     atmVpCrossConnectIndexNext  OBJECT-TYPE
          SYNTAX         INTEGER (0..2147483647)
          MAX-ACCESS     read-only
          STATUS         current
          DESCRIPTION
           "This object contains an appropriate value to
            be used for atmVpCrossConnectIndex when creating
            entries in the atmVpCrossConnectTable.  The value
            0 indicates that no unassigned entries are
            available. To obtain the atmVpCrossConnectIndex
            value for a new entry, the manager issues a
            management protocol retrieval operation to obtain
            the current value of this object.  After each
            retrieval, the agent should modify the value to
            the next unassigned index.
            After a manager retrieves a value the agent will
            determine through its local policy when this index
            value will be made available for reuse."
          ::= { atmMIBObjects 8 }

     --  The ATM VP Cross Connect Table

     atmVpCrossConnectTable OBJECT-TYPE
          SYNTAX         SEQUENCE OF AtmVpCrossConnectEntry
          MAX-ACCESS     not-accessible
          STATUS         current
          DESCRIPTION
           "The ATM VP Cross Connect table for PVCs.
            An entry in this table models two
            cross-connected VPLs.
            Each VPL must have its atmConnKind set
            to pvc(1)."
          ::= { atmMIBObjects 9 }

     atmVpCrossConnectEntry OBJECT-TYPE
          SYNTAX         AtmVpCrossConnectEntry


          MAX-ACCESS     not-accessible
          STATUS         current
          DESCRIPTION
           "An entry in the ATM VP Cross Connect table.
            This entry is used to model a bi-directional
            ATM VP cross-connect which cross-connects
            two VPLs.

            Step-wise Procedures to set up a VP Cross-connect

            Once the entries in the atmVplTable are created,
            the following procedures are used
            to cross-connect the VPLs together.

           (1) The manager obtains a unique
               atmVpCrossConnectIndex by reading the
               atmVpCrossConnectIndexNext object.

           (2) Next, the manager creates a set of one
               or more rows in the ATM VP Cross Connect
               Table, one for each cross-connection between
               two VPLs.  Each row is indexed by the ATM
               interface port numbers and VPI values of the
               two ends of that cross-connection.
               This set of rows specifies the topology of the
               VPC cross-connect and is identified by a single
               value of atmVpCrossConnectIndex.

            Negotiated VP Cross-Connect Establishment

          (2a) The manager creates a row in this table by
               setting atmVpCrossConnectRowStatus to
               createAndWait(5).  The agent checks the
               requested topology and the mutual sanity of
               the ATM traffic parameters and
               service categories, i.e., the row creation
               fails if:
               - the requested topology is incompatible with
                 associated values of atmVplCastType,
               - the requested topology is not supported
                 by the agent,
               - the traffic/service category parameter values
                 associated with the requested row are
                 incompatible with those of already existing
                 rows for this VP cross-connect.
               [For example, for setting up
               a point-to-point VP cross-connect, the
               ATM traffic parameters in the receive direction


               of a VPL at the low end of the cross-connect
               must equal to the traffic parameters in the
               transmit direction of the other VPL at the
               high end of the cross-connect,
               otherwise, the row creation fails.]
               The agent also checks for internal errors
               in building the cross-connect.

               The atmVpCrossConnectIndex values in the
               corresponding atmVplTable rows are filled
               in by the agent at this point.

          (2b) The manager promotes the row in the
               atmVpCrossConnectTable by setting
               atmVpCrossConnectRowStatus to active(1).  If
               this set is successful, the agent has reserved
               the resources specified by the ATM traffic
               parameter and Service category values
               for each direction of the VP cross-connect
               in an ATM switch or network.

           (3) The manager sets the
               atmVpCrossConnectAdminStatus to up(1) in all
               rows of this VP cross-connect to turn the
               traffic flow on.

            One-Shot VP Cross-Connect Establishment

            A VP cross-connect may also be established in
            one step by a set-request with all necessary
            parameter values and atmVpCrossConnectRowStatus
            set to createAndGo(4).

            In contrast to the negotiated VP cross-connect
            establishment which allows for detailed error
            checking (i.e., set errors are explicitly linked
            to particular resource acquisition failures),
            the one-shot VP cross-connect establishment
            performs the setup on one operation but does not
            have the advantage of step-wise error checking.

            VP Cross-Connect Retirement

            A VP cross-connect identified by a particular
            value of atmVpCrossConnectIndex is released by:

           (1) Setting atmVpCrossConnectRowStatus of all


               rows identified by this value of
               atmVpCrossConnectIndex to destroy(6).
               The agent may release all
               associated resources, and the
               atmVpCrossConnectIndex values in the
               corresponding atmVplTable row are removed.
               Note that a situation when only a subset of
               the associated rows are deleted corresponds
               to a VP topology change.

           (2) After deletion of the appropriate
               atmVpCrossConnectEntries, the manager may
               set atmVplRowStatus to destroy(6) the
               associated VPLs.  The agent releases
               the resources and removes the associated
               rows in the atmVplTable.

            VP Cross-connect Reconfiguration

            At the discretion of the agent, a VP
            cross-connect may be reconfigured by
            adding and/or deleting leafs to/from
            the VP topology as per the VP cross-connect
            establishment/retirement procedures.
            Reconfiguration of traffic/service category parameter
            values requires release of the VP cross-connect
            before those parameter values may by changed
            for individual VPLs."
          INDEX { atmVpCrossConnectIndex,
                atmVpCrossConnectLowIfIndex,
                atmVpCrossConnectLowVpi,
                atmVpCrossConnectHighIfIndex,
                atmVpCrossConnectHighVpi }
          ::= { atmVpCrossConnectTable 1 }

     AtmVpCrossConnectEntry ::= SEQUENCE {
          atmVpCrossConnectIndex          INTEGER,
          atmVpCrossConnectLowIfIndex     InterfaceIndex,
          atmVpCrossConnectLowVpi         AtmVpIdentifier,
          atmVpCrossConnectHighIfIndex    InterfaceIndex,
          atmVpCrossConnectHighVpi        AtmVpIdentifier,
          atmVpCrossConnectAdminStatus    AtmVorXAdminStatus,
          atmVpCrossConnectL2HOperStatus  AtmVorXOperStatus,
          atmVpCrossConnectH2LOperStatus  AtmVorXOperStatus,
          atmVpCrossConnectL2HLastChange  AtmVorXLastChange,
          atmVpCrossConnectH2LLastChange  AtmVorXLastChange,
          atmVpCrossConnectRowStatus      RowStatus
                  }


     atmVpCrossConnectIndex OBJECT-TYPE
          SYNTAX         INTEGER (1..2147483647)
          MAX-ACCESS     not-accessible
          STATUS         current
          DESCRIPTION
           "A unique value to identify this VP cross-connect.
            For each VPL associated with this cross-connect,
            the agent reports this cross-connect index value
            in the atmVplCrossConnectIdentifier attribute of
            the corresponding atmVplTable entries."
          ::= { atmVpCrossConnectEntry 1 }

     atmVpCrossConnectLowIfIndex OBJECT-TYPE
          SYNTAX         InterfaceIndex
          MAX-ACCESS     not-accessible
          STATUS         current
          DESCRIPTION
           "The ifIndex value of the ATM interface for
            this VP cross-connect. The term low implies
            that this ATM interface has the numerically lower
            ifIndex value than the other ATM interface
            identified in the same atmVpCrossConnectEntry."
          ::= { atmVpCrossConnectEntry 2 }

     atmVpCrossConnectLowVpi OBJECT-TYPE
          SYNTAX         AtmVpIdentifier
          MAX-ACCESS     not-accessible
          STATUS         current
          DESCRIPTION
           "The VPI value at the ATM interface
            associated with the VP cross-connect that is
            identified by atmVpCrossConnectLowIfIndex."
          ::= { atmVpCrossConnectEntry 3 }

     atmVpCrossConnectHighIfIndex OBJECT-TYPE
          SYNTAX         InterfaceIndex
          MAX-ACCESS     not-accessible
          STATUS  current
          DESCRIPTION
           "The ifIndex value of the ATM interface for
            this VP cross-connect. The term high implies that
            this ATM interface has the numerically higher
            ifIndex value than the  other ATM interface
            identified in the same atmVpCrossConnectEntry."
          ::= { atmVpCrossConnectEntry 4 }

     atmVpCrossConnectHighVpi OBJECT-TYPE
          SYNTAX         AtmVpIdentifier


          MAX-ACCESS     not-accessible
          STATUS         current
          DESCRIPTION
           "The VPI value at the ATM interface
            associated with the VP cross-connect that is
            identified by atmVpCrossConnectHighIfIndex."
          ::= { atmVpCrossConnectEntry 5 }

     atmVpCrossConnectAdminStatus OBJECT-TYPE
          SYNTAX         AtmVorXAdminStatus
          MAX-ACCESS     read-create
          STATUS         current
          DESCRIPTION
           "The desired administrative status of this
            bi-directional VP cross-connect."
          DEFVAL { down }
          ::= { atmVpCrossConnectEntry 6 }

     atmVpCrossConnectL2HOperStatus OBJECT-TYPE
          SYNTAX         AtmVorXOperStatus
          MAX-ACCESS     read-only
          STATUS         current
          DESCRIPTION
           "The operational status of the VP cross-connect
            in one direction; (i.e., from the low to
            high direction)."
          ::= { atmVpCrossConnectEntry 7 }

     atmVpCrossConnectH2LOperStatus OBJECT-TYPE
          SYNTAX         AtmVorXOperStatus
          MAX-ACCESS     read-only
          STATUS         current
          DESCRIPTION
           "The operational status of the VP cross-connect
            in one direction; (i.e., from the high to
            low direction)."
          ::= { atmVpCrossConnectEntry 8 }

     atmVpCrossConnectL2HLastChange OBJECT-TYPE
          SYNTAX         AtmVorXLastChange
          MAX-ACCESS     read-only
          STATUS         current
          DESCRIPTION
           "The value of sysUpTime at the time this
            VP cross-connect entered its current operational
            state in the low to high direction."
          ::= { atmVpCrossConnectEntry 9 }


     atmVpCrossConnectH2LLastChange OBJECT-TYPE
          SYNTAX         AtmVorXLastChange
          MAX-ACCESS     read-only
          STATUS         current
          DESCRIPTION
            "The value of sysUpTime at the time this
            VP cross-connect entered its current operational
            in the high to low direction."
          ::= { atmVpCrossConnectEntry 10 }

     atmVpCrossConnectRowStatus OBJECT-TYPE
          SYNTAX         RowStatus
          MAX-ACCESS     read-create
          STATUS         current
          DESCRIPTION
           "The status of this entry in the
            atmVpCrossConnectTable.  This object is used to
            create a cross-connect for cross-connecting
            VPLs which are created using the atmVplTable
            or to change or delete an existing cross-connect.
            This object must be initially set
            to `createAndWait' or 'createAndGo'.
            To turn on a VP cross-connect,
            the atmVpCrossConnectAdminStatus
            is set to `up'."
          DEFVAL { createAndWait }
          ::= { atmVpCrossConnectEntry 11 }

     --     ATM Virtual Channel (VC) Cross Connect Table

     -- This table contains configuration and state
     -- information of point-to-point,
     -- point-to-multipoint or multipoint-to-multipoint
     -- VC cross-connects for PVCs.

     -- This table has read-create access and is used
     -- to cross-connect the VCLs together in an ATM switch
     -- or network that belong to a VC connection.
     -- The atmVcCrossConnectIndex is used to associate
     -- the related VCLs that are cross-connected together.

     -- The model using step-wise procedures described for setting
     -- up a VP cross-connect is also used for setting up
     -- a VC cross-connect.


     atmVcCrossConnectIndexNext  OBJECT-TYPE
          SYNTAX         INTEGER (0..2147483647)
          MAX-ACCESS     read-only
          STATUS         current
          DESCRIPTION
           "This object contains an appropriate value to
            be used for atmVcCrossConnectIndex when creating
            entries in the atmVcCrossConnectTable.  The value
            0 indicates that no unassigned entries are
            available. To obtain the atmVcCrossConnectIndex
            value for a new entry, the manager issues a
            management protocol retrieval operation to obtain
            the current value of this object.  After each
            retrieval, the agent should modify the value to
            the next unassigned index.
            After a manager retrieves a value the agent will
            determine through its local policy when this index
            value will be made available for reuse."
          ::= { atmMIBObjects 10 }

     --  The ATM VC Cross Connect Table

     atmVcCrossConnectTable OBJECT-TYPE
          SYNTAX         SEQUENCE OF AtmVcCrossConnectEntry
          MAX-ACCESS     not-accessible
          STATUS         current
          DESCRIPTION
           "The ATM VC Cross Connect table for PVCs.
            An entry in this table models two
            cross-connected VCLs.
            Each VCL must have its atmConnKind set
            to pvc(1)."
          ::= { atmMIBObjects 11 }

     atmVcCrossConnectEntry OBJECT-TYPE
          SYNTAX       AtmVcCrossConnectEntry
          MAX-ACCESS   not-accessible
          STATUS       current
          DESCRIPTION
           "An entry in the ATM VC Cross Connect table.
            This entry is used to model a bi-directional ATM
            VC cross-connect cross-connecting two end points.

            Step-wise Procedures to set up a VC Cross-connect


            Once the entries in the atmVclTable are created,
            the following procedures are used
            to cross-connect the VCLs together to
            form a VCC segment.

           (1) The manager obtains a unique
               atmVcCrossConnectIndex by reading the
               atmVcCrossConnectIndexNext object.

           (2) Next, the manager creates a set of one
               or more rows in the ATM VC Cross Connect
               Table, one for each cross-connection between
               two VCLs.  Each row is indexed by the ATM
               interface port numbers and VPI/VCI values of
               the two ends of that cross-connection.
               This set of rows specifies the topology of the
               VCC cross-connect and is identified by a single
               value of atmVcCrossConnectIndex.

            Negotiated VC Cross-Connect Establishment

          (2a) The manager creates a row in this table by
               setting atmVcCrossConnectRowStatus to
               createAndWait(5).  The agent checks the
               requested topology and the mutual sanity of
               the ATM traffic parameters and
               service categories, i.e., the row creation
               fails if:
               - the requested topology is incompatible with
                 associated values of atmVclCastType,
               - the requested topology is not supported
                 by the agent,
               - the traffic/service category parameter values
                 associated with the requested row are
                 incompatible with those of already existing
                 rows for this VC cross-connect.
               [For example, for setting up
               a point-to-point VC cross-connect, the
               ATM traffic parameters in the receive direction
               of a VCL at the low end of the cross-connect
               must equal to the traffic parameters in the
               transmit direction of the other VCL at the
               high end of the cross-connect,
               otherwise, the row creation fails.]
               The agent also checks for internal errors
               in building the cross-connect.

               The atmVcCrossConnectIndex values in the


               corresponding atmVclTable rows are filled
               in by the agent at this point.

          (2b) The manager promotes the row in the
               atmVcCrossConnectTable by setting
               atmVcCrossConnectRowStatus to active(1).  If
               this set is successful, the agent has reserved
               the resources specified by the ATM traffic
               parameter and Service category values
               for each direction of the VC cross-connect
               in an ATM switch or network.

           (3) The manager sets the
               atmVcCrossConnectAdminStatus to up(1)
               in all rows of this VC cross-connect to
               turn the traffic flow on.

            One-Shot VC Cross-Connect Establishment

            A VC cross-connect may also be established in
            one step by a set-request with all necessary
            parameter values and atmVcCrossConnectRowStatus
            set to createAndGo(4).

            In contrast to the negotiated VC cross-connect
            establishment which allows for detailed error
            checking i.e., set errors are explicitly linked to
            particular resource acquisition failures), the
            one-shot VC cross-connect establishment
            performs the setup on one operation but does
            not have the advantage of step-wise error
            checking.

            VC Cross-Connect Retirement

            A VC cross-connect identified by a particular
            value of atmVcCrossConnectIndex is released by:

           (1) Setting atmVcCrossConnectRowStatus of all rows
               identified by this value of
               atmVcCrossConnectIndex to destroy(6).
               The agent may release all
               associated resources, and the
               atmVcCrossConnectIndex values in the
               corresponding atmVclTable row are removed.
               Note that a situation when only a subset of
               the associated rows are deleted corresponds


               to a VC topology change.

           (2) After deletion of the appropriate
               atmVcCrossConnectEntries, the manager may
               set atmVclRowStatus to destroy(6) the
               associated VCLs.  The agent releases
               the resources and removes the associated
               rows in the atmVclTable.

            VC Cross-Connect Reconfiguration

            At the discretion of the agent, a VC
            cross-connect may be reconfigured by
            adding and/or deleting leafs to/from
            the VC topology as per the VC cross-connect
            establishment/retirement procedures.
            Reconfiguration of traffic/service category parameter
            values requires release of the VC cross-connect
            before those parameter values may by changed
            for individual VCLs."
          INDEX { atmVcCrossConnectIndex,
                atmVcCrossConnectLowIfIndex,
                atmVcCrossConnectLowVpi,
                atmVcCrossConnectLowVci,
                atmVcCrossConnectHighIfIndex,
                atmVcCrossConnectHighVpi,
                atmVcCrossConnectHighVci }
          ::= { atmVcCrossConnectTable 1 }

     AtmVcCrossConnectEntry ::= SEQUENCE {
          atmVcCrossConnectIndex          INTEGER,
          atmVcCrossConnectLowIfIndex     InterfaceIndex,
          atmVcCrossConnectLowVpi         AtmVpIdentifier,
          atmVcCrossConnectLowVci         AtmVcIdentifier,
          atmVcCrossConnectHighIfIndex    InterfaceIndex,
          atmVcCrossConnectHighVpi        AtmVpIdentifier,
          atmVcCrossConnectHighVci        AtmVcIdentifier,
          atmVcCrossConnectAdminStatus    AtmVorXAdminStatus,
          atmVcCrossConnectL2HOperStatus  AtmVorXOperStatus,
          atmVcCrossConnectH2LOperStatus  AtmVorXOperStatus,
          atmVcCrossConnectL2HLastChange  AtmVorXLastChange,
          atmVcCrossConnectH2LLastChange  AtmVorXLastChange,
          atmVcCrossConnectRowStatus      RowStatus
                  }

     atmVcCrossConnectIndex OBJECT-TYPE
          SYNTAX         INTEGER (1..2147483647)
          MAX-ACCESS     not-accessible


          STATUS         current
          DESCRIPTION
           "A unique value to identify this VC cross-connect.
            For each VCL associated with this cross-connect,
            the agent reports this cross-connect index value
            in the atmVclCrossConnectIdentifier attribute of
            the corresponding atmVclTable entries."
          ::= { atmVcCrossConnectEntry 1 }

     atmVcCrossConnectLowIfIndex OBJECT-TYPE
          SYNTAX         InterfaceIndex
          MAX-ACCESS     not-accessible
          STATUS         current
          DESCRIPTION
           "The ifIndex value of the ATM interface for this
            VC cross-connect. The term low implies
            that this ATM interface has the numerically lower
            ifIndex value than the other ATM interface
            identified in the same atmVcCrossConnectEntry."
          ::= { atmVcCrossConnectEntry 2 }

     atmVcCrossConnectLowVpi OBJECT-TYPE
          SYNTAX         AtmVpIdentifier
          MAX-ACCESS     not-accessible
          STATUS         current
          DESCRIPTION
           "The VPI value at the ATM interface
            associated with the VC cross-connect that is
            identified by atmVcCrossConnectLowIfIndex."
          ::= { atmVcCrossConnectEntry 3 }

     atmVcCrossConnectLowVci OBJECT-TYPE
          SYNTAX         AtmVcIdentifier
          MAX-ACCESS     not-accessible
          STATUS         current
          DESCRIPTION
           "The VCI value at the ATM interface
            associated with this VC cross-connect that is
            identified by atmVcCrossConnectLowIfIndex."
          ::= { atmVcCrossConnectEntry 4 }

     atmVcCrossConnectHighIfIndex OBJECT-TYPE
          SYNTAX         InterfaceIndex
          MAX-ACCESS     not-accessible
          STATUS         current
          DESCRIPTION
           "The ifIndex value for the ATM interface for
            this VC cross-connect. The term high implies


            that this ATM interface has the numerically higher
            ifIndex value than the other ATM interface
            identified in the same atmVcCrossConnectEntry."
          ::= { atmVcCrossConnectEntry 5 }

     atmVcCrossConnectHighVpi OBJECT-TYPE
          SYNTAX         AtmVpIdentifier
          MAX-ACCESS     not-accessible
          STATUS         current
          DESCRIPTION
           "The VPI value at the ATM interface
            associated with the VC cross-connect that is
            identified by atmVcCrossConnectHighIfIndex."
          ::= { atmVcCrossConnectEntry 6 }

     atmVcCrossConnectHighVci OBJECT-TYPE
          SYNTAX         AtmVcIdentifier
          MAX-ACCESS     not-accessible
          STATUS         current
          DESCRIPTION
           "The VCI value at the ATM interface
            associated with the VC cross-connect that is
            identified by atmVcCrossConnectHighIfIndex."
          ::= { atmVcCrossConnectEntry 7 }

     atmVcCrossConnectAdminStatus OBJECT-TYPE
          SYNTAX         AtmVorXAdminStatus
          MAX-ACCESS     read-create
          STATUS         current
          DESCRIPTION
           "The desired administrative status of this
            bi-directional VC cross-connect."
          DEFVAL { down }
          ::= { atmVcCrossConnectEntry 8 }

     atmVcCrossConnectL2HOperStatus OBJECT-TYPE
          SYNTAX         AtmVorXOperStatus
          MAX-ACCESS     read-only
          STATUS         current
          DESCRIPTION
           "The current operational status of the
            VC cross-connect in one direction; (i.e.,
            from the low to high direction)."
          ::= { atmVcCrossConnectEntry 9 }

     atmVcCrossConnectH2LOperStatus OBJECT-TYPE
          SYNTAX         AtmVorXOperStatus


          MAX-ACCESS     read-only
          STATUS         current
          DESCRIPTION
           "The current operational status of the
            VC cross-connect in one direction; (i.e.,
            from the high to low direction)."
          ::= { atmVcCrossConnectEntry 10 }

     atmVcCrossConnectL2HLastChange OBJECT-TYPE
          SYNTAX         AtmVorXLastChange
          MAX-ACCESS     read-only
          STATUS         current
          DESCRIPTION
           "The value of sysUpTime at the time this
            VC cross-connect entered its current
            operational state in low to high direction."
          ::= { atmVcCrossConnectEntry 11 }

     atmVcCrossConnectH2LLastChange OBJECT-TYPE
          SYNTAX         AtmVorXLastChange
          MAX-ACCESS     read-only
          STATUS         current
          DESCRIPTION
           "The value of sysUpTime at the time this
            VC cross-connect entered its current
            operational state in high to low direction."
          ::= { atmVcCrossConnectEntry 12 }

     atmVcCrossConnectRowStatus OBJECT-TYPE
          SYNTAX         RowStatus
          MAX-ACCESS     read-create
          STATUS         current
          DESCRIPTION
           "The status of this entry in the
            atmVcCrossConnectTable.  This object is used to
            create a new cross-connect for cross-connecting
            VCLs which are created using the atmVclTable
            or to change or delete existing cross-connect.
            This object must be initially set to
            `createAndWait' or 'createAndGo'.
            To turn on a VC cross-connect,
            the atmVcCrossConnectAdminStatus
            is set to `up'."
          DEFVAL { createAndWait }
          ::= { atmVcCrossConnectEntry 13 }

     -- AAL5 Virtual Channel Connection Performance Statistics


     -- Table

     -- This table contains the AAL5
     -- performance statistics of a VCC at the
     -- interface associated with an AAL5 entity in an ATM
     -- host or ATM switch.

     aal5VccTable        OBJECT-TYPE
          SYNTAX         SEQUENCE OF Aal5VccEntry
          MAX-ACCESS     not-accessible
          STATUS         current
          DESCRIPTION
           "This table contains AAL5 VCC performance
            parameters."
          ::= { atmMIBObjects 12 }

     aal5VccEntry        OBJECT-TYPE
          SYNTAX         Aal5VccEntry
          MAX-ACCESS     not-accessible
          STATUS         current
          DESCRIPTION
           "This list contains the AAL5 VCC
            performance parameters and is indexed
            by ifIndex values of AAL5 interfaces
            and the associated VPI/VCI values."
          INDEX { ifIndex, aal5VccVpi, aal5VccVci }
          ::= { aal5VccTable 1 }

     Aal5VccEntry    ::= SEQUENCE  {
          aal5VccVpi             AtmVpIdentifier,
          aal5VccVci             AtmVcIdentifier,
          aal5VccCrcErrors       Counter32,
          aal5VccSarTimeOuts     Counter32,
          aal5VccOverSizedSDUs   Counter32
               }

     aal5VccVpi          OBJECT-TYPE
          SYNTAX         AtmVpIdentifier
          MAX-ACCESS     not-accessible
          STATUS         current
          DESCRIPTION
           "The VPI value of the AAL5 VCC at the
            interface identified by the ifIndex."
          ::= { aal5VccEntry 1 }

     aal5VccVci          OBJECT-TYPE


          SYNTAX         AtmVcIdentifier
          MAX-ACCESS     not-accessible
          STATUS         current
          DESCRIPTION
           "The VCI value of the AAL5 VCC at the
            interface identified by the ifIndex."
          ::= { aal5VccEntry 2 }

     aal5VccCrcErrors    OBJECT-TYPE
          SYNTAX         Counter32
          MAX-ACCESS     read-only
          STATUS         current
          DESCRIPTION
           "The number of AAL5 CPCS PDUs received with
            CRC-32 errors on this AAL5 VCC at the
            interface associated with an AAL5 entity."
          ::= { aal5VccEntry 3 }

     aal5VccSarTimeOuts  OBJECT-TYPE
          SYNTAX         Counter32
          MAX-ACCESS     read-only
          STATUS         current
          DESCRIPTION
           "The number of partially re-assembled AAL5
            CPCS PDUs which were discarded
            on this AAL5 VCC at the interface associated
            with an AAL5 entity because they
            were not fully re-assembled within the
            required time period.  If the re-assembly
            timer is not supported, then this object
            contains a zero value."
          ::= { aal5VccEntry 4 }

     aal5VccOverSizedSDUs OBJECT-TYPE
          SYNTAX         Counter32
          MAX-ACCESS     read-only
          STATUS         current
          DESCRIPTION
           "The number of AAL5 CPCS PDUs discarded
            on this AAL5 VCC at the interface
            associated with an AAL5 entity because the
            AAL5 SDUs were too large."
          ::= { aal5VccEntry 5 }

     --
     -- The following object may be used in conjunction with
     -- the atmTrafficDescrParamTable for the creation of


     -- new table entries.
     --

     atmTrafficDescrParamIndexNext  OBJECT-TYPE
          SYNTAX         INTEGER (0..2147483647)
          MAX-ACCESS     read-only
          STATUS         current
          DESCRIPTION
           "This object contains an appropriate value to
            be used for atmTrafficDescrParamIndex when
            creating entries in the
            atmTrafficDescrParamTable.
            The value 0 indicates that no unassigned
            entries are available. To obtain the
            atmTrafficDescrParamIndex value for a new
            entry, the manager issues a management
            protocol retrieval operation to obtain the
            current value of this object.  After each
            retrieval, the agent should modify the value
            to the next unassigned index.
            After a manager retrieves a value the agent will
            determine through its local policy when this index
            value will be made available for reuse."
          ::= { atmMIBObjects 13 }

     -- Conformance Information

     atmMIBConformance   OBJECT IDENTIFIER ::= { atmMIB 2 }

     atmMIBGroups        OBJECT IDENTIFIER
                                ::= { atmMIBConformance 1 }
     atmMIBCompliances   OBJECT IDENTIFIER
                                ::= { atmMIBConformance 2 }

     -- Compliance Statements

     atmMIBCompliance2    MODULE-COMPLIANCE
          STATUS         current
          DESCRIPTION
            "The compliance statement for SNMP entities
             including networks which have ATM and
             AAL5 interfaces."

          MODULE -- this module
     --
     -- ****** Interface and Traffic Descriptor Support ***


     --
            MANDATORY-GROUPS  {atmInterfaceConfGroup2,
                               atmTrafficDescrGroup2 }

            OBJECT         atmInterfaceMaxVpcs
            MIN-ACCESS     read-only
            DESCRIPTION
              "Write access is not required."

            OBJECT         atmInterfaceMaxVccs
            MIN-ACCESS     read-only
            DESCRIPTION
              "Write access is not required."

            OBJECT         atmInterfaceMaxActiveVpiBits
            MIN-ACCESS     read-only
            DESCRIPTION
              "Write access is not required.
               At the ATM UNI the maximum number of
               active VPI bits configured for use ranges
               from 0 to 8 only.
               Implementations may support smaller ranges."
            OBJECT         atmInterfaceMaxActiveVciBits
            MIN-ACCESS     read-only
            DESCRIPTION
              "Write access is not required.
               Implementations may support smaller ranges."

            OBJECT         atmInterfaceIlmiVpi
            MIN-ACCESS     read-only
            DESCRIPTION
              "Write access is not required."

            OBJECT         atmInterfaceIlmiVci
            MIN-ACCESS     read-only
            DESCRIPTION
              "Write access is not required."

            OBJECT         atmInterfaceMyNeighborIpAddress
            MIN-ACCESS     read-only
            DESCRIPTION
              "Write access is not required."

            OBJECT         atmInterfaceMyNeighborIfName
            MIN-ACCESS     read-only
            DESCRIPTION
              "Write access is not required."


            OBJECT         atmInterfaceSubscrAddress
            MIN-ACCESS     read-only
            DESCRIPTION
              "Write access is not required."

            OBJECT         atmTrafficDescrParamIndexNext
            DESCRIPTION
              "This object is only required for systems
               that support the creation of entries in
               the atmTrafficDescrParamTable."

            OBJECT         atmTrafficDescrType
            MIN-ACCESS     read-only
            DESCRIPTION
              "Write access is not required."

            OBJECT         atmTrafficDescrParam1
            MIN-ACCESS     read-only
            DESCRIPTION
              "Write access is not required."

            OBJECT         atmTrafficDescrParam2
            MIN-ACCESS     read-only
            DESCRIPTION
              "Write access is not required."

            OBJECT         atmTrafficDescrParam3
            MIN-ACCESS     read-only
            DESCRIPTION
              "Write access is not required."

            OBJECT         atmTrafficDescrParam4
            MIN-ACCESS     read-only
            DESCRIPTION
              "Write access is not required."

            OBJECT         atmTrafficDescrParam5
            MIN-ACCESS     read-only
            DESCRIPTION
              "Write access is not required."

            OBJECT         atmServiceCategory
            MIN-ACCESS     read-only
            DESCRIPTION
              "Write access is not required."

            OBJECT         atmTrafficDescrRowStatus
            SYNTAX         INTEGER {active(1)}


                             -- subset of RowStatus
            MIN-ACCESS     read-only
            DESCRIPTION
              "Write access is not required, and only one
               of the six enumerated values for the
               RowStatus textual convention need be
               supported, specifically: active(1)."

            OBJECT         atmTrafficFrameDiscard
            MIN-ACCESS     read-only
            DESCRIPTION
              "Write access is not required."

     --
     -- ****** DS3 PLCP Support **************************
     --
            GROUP          atmInterfaceDs3PlcpGroup
            DESCRIPTION
              "This group is mandatory only for those
               ATM interfaces which implement the
               DS3 PLCP layer."
     --
     -- ****** TC Sublayer Support ********************************
     --
            GROUP          atmInterfaceTCGroup
            DESCRIPTION
              "This group is mandatory only for those
               ATM interfaces which implement the
               TC Sublayer."

     --
     -- ****** VPC Support *******************************
     --
            GROUP          atmVpcTerminationGroup2
            DESCRIPTION
              "This group is mandatory only for those
               ATM interfaces which implement ATM
               VPLs that terminate VPCs (i.e., ones which
               are NOT cross-connected to other VPLs)."

            GROUP          atmVplCrossConnectGroup
            DESCRIPTION
              "This group is mandatory only for those
               ATM interfaces which implement ATM
               VPLs that are not associated with VCLs
               and are cross-connected to other VPLs
               for VPCs."


            GROUP          atmVpPvcCrossConnectGroup
            DESCRIPTION
              "This group is mandatory only for those
               ATM interfaces which implement ATM
               VPLs that are not associated with VCLs
               and are cross-connected to other VPLs
               for permanent VPCs (i.e., PVCs).
               This group is not used to crossconnect
               a PVC with an SVC to form a Soft PVC."

            OBJECT         atmVplAdminStatus
            MIN-ACCESS     read-only
            DESCRIPTION
              "Write access is not required."

            OBJECT         atmVplReceiveTrafficDescrIndex
            MIN-ACCESS     read-only
            DESCRIPTION
              "Write access is not required."

            OBJECT         atmVplTransmitTrafficDescrIndex
            MIN-ACCESS     read-only
            DESCRIPTION
              "Write access is not required."

            OBJECT         atmVplRowStatus
            SYNTAX         INTEGER {active(1)}
                             -- subset of RowStatus
            MIN-ACCESS      read-only
            DESCRIPTION
              "Write access is not required, and only one
               of the six enumerated values for the
               RowStatus textual convention need be
               supported, specifically: active(1)."

            OBJECT         atmVplCastType
            MIN-ACCESS     read-only
            DESCRIPTION
              "Write access is not required."

            OBJECT         atmVplConnKind
            MIN-ACCESS     read-only
            DESCRIPTION
              "Write access is not required."

            OBJECT         atmVpCrossConnectAdminStatus
            MIN-ACCESS     read-only
            DESCRIPTION


              "Write access is not required."

            OBJECT         atmVpCrossConnectRowStatus
            SYNTAX         INTEGER {active(1)}
                             -- subset of RowStatus
            MIN-ACCESS     read-only
            DESCRIPTION
              "Write access is not required, and only one
               of the six enumerated values for the
               RowStatus textual convention need be
               supported, specifically: active(1)."

     --
     -- ****** VCC Support *******************************
     --
            GROUP          atmVccTerminationGroup2
            DESCRIPTION
              "This group is mandatory only for those
               ATM interfaces which implement ATM
               VCLs that terminate VCCs (i.e., ones which
               are NOT cross-connected to other VCLs)."

            GROUP          atmVclCrossConnectGroup
            DESCRIPTION
              "This group is mandatory only for those
               ATM interfaces which implement ATM
               VCLs that are cross-connected to other VCLs
               for VCCs."

            GROUP          atmVcPvcCrossConnectGroup
            DESCRIPTION
              "This group is mandatory only for those
               ATM interfaces which implement ATM
               VCLs that are cross-connected to other
               VCLs for permanent VCCs (i.e., PVCs).
               This group is not used to crossconnect
               a PVC with an SVC to form a Soft PVC."

            OBJECT         atmVclAdminStatus
            MIN-ACCESS     read-only
            DESCRIPTION
              "Write access is not required."

            OBJECT         atmVclReceiveTrafficDescrIndex
            MIN-ACCESS     read-only
            DESCRIPTION
              "Write access is not required."


            OBJECT         atmVclTransmitTrafficDescrIndex
            MIN-ACCESS     read-only
            DESCRIPTION
              "Write access is not required."

            OBJECT         atmVccAalType
            MIN-ACCESS     read-only
            DESCRIPTION
              "Write access is not required."

            OBJECT         atmVclRowStatus
            SYNTAX         INTEGER {active(1)}
                             -- subset of RowStatus
            MIN-ACCESS     read-only
            DESCRIPTION
              "Write access is not required, and only one
               of the six enumerated values for the
               RowStatus textual convention need be
               supported, specifically: active(1)."

            OBJECT         atmVclCastType
            MIN-ACCESS     read-only
            DESCRIPTION
              "Write access is not required."

            OBJECT         atmVclConnKind
            MIN-ACCESS     read-only
            DESCRIPTION
              "Write access is not required."

            OBJECT         atmVcCrossConnectAdminStatus
            MIN-ACCESS     read-only
            DESCRIPTION
              "Write access is not required."

            OBJECT         atmVcCrossConnectRowStatus
            SYNTAX         INTEGER { active(1)}
                             -- subset of RowStatus
            MIN-ACCESS     read-only
            DESCRIPTION
              "Write access is not required, and only one
               of the six enumerated values for the
               RowStatus textual convention need be
               supported, specifically: active(1)."
     --
     -- ****** AAL5 Support ******************************
     --
            GROUP          aal5VccGroup


            DESCRIPTION
              "This group is mandatory for the
               AAL5 virtual connections only."
            OBJECT         atmVccAal5CpcsTransmitSduSize
            MIN-ACCESS     read-only
            DESCRIPTION
              "Write access is not required."

            OBJECT         atmVccAal5CpcsReceiveSduSize
            MIN-ACCESS     read-only
            DESCRIPTION
              "Write access is not required."

            OBJECT         atmVccAal5EncapsType
            MIN-ACCESS     read-only
            DESCRIPTION
              "Write access is not required."
             ::= { atmMIBCompliances 2 }

     -- Units of Conformance

     atmInterfaceDs3PlcpGroup    OBJECT-GROUP
            OBJECTS {atmInterfaceDs3PlcpSEFSs,
                atmInterfaceDs3PlcpAlarmState,
                atmInterfaceDs3PlcpUASs}
            STATUS     current
            DESCRIPTION
               "A collection of objects providing information
                about DS3 PLCP layer at an ATM interface."
            ::= { atmMIBGroups 3 }

     atmInterfaceTCGroup    OBJECT-GROUP
            OBJECTS { atmInterfaceOCDEvents,
                atmInterfaceTCAlarmState }
            STATUS     current
            DESCRIPTION
               "A collection of objects providing information
                about TC sublayer at an ATM interface."
            ::= { atmMIBGroups 4 }

     aal5VccGroup    OBJECT-GROUP
            OBJECTS {atmVccAal5CpcsTransmitSduSize,
                atmVccAal5CpcsReceiveSduSize,
                atmVccAal5EncapsType,
                aal5VccCrcErrors, aal5VccSarTimeOuts,
                aal5VccOverSizedSDUs }
            STATUS     current


            DESCRIPTION
               "A collection of objects providing
                AAL5 configuration and performance statistics
                of a VCC."
            ::= { atmMIBGroups 9 }

     atmInterfaceConfGroup2    OBJECT-GROUP
            OBJECTS {
                  atmInterfaceMaxVpcs, atmInterfaceMaxVccs,
                  atmInterfaceConfVpcs, atmInterfaceConfVccs,
                  atmInterfaceMaxActiveVpiBits,
                  atmInterfaceMaxActiveVciBits,
                  atmInterfaceIlmiVpi,
                  atmInterfaceIlmiVci,
                  atmInterfaceMyNeighborIpAddress,
                  atmInterfaceMyNeighborIfName,
                  atmInterfaceCurrentMaxVpiBits,
                  atmInterfaceCurrentMaxVciBits,
                  atmInterfaceSubscrAddress }
            STATUS     current
            DESCRIPTION
              "A collection of objects providing configuration
               information about an ATM interface."
            ::= { atmMIBGroups 10 }

     atmTrafficDescrGroup2    OBJECT-GROUP
            OBJECTS {
                atmTrafficDescrType, atmTrafficDescrParam1,
                atmTrafficDescrParam2, atmTrafficDescrParam3,
                atmTrafficDescrParam4, atmTrafficDescrParam5,
                atmTrafficDescrRowStatus, atmServiceCategory,
                atmTrafficFrameDiscard,
                atmTrafficDescrParamIndexNext }
            STATUS     current
            DESCRIPTION
               "A collection of objects providing information
                about ATM traffic descriptor type and
                the associated parameters."
            ::= { atmMIBGroups 11 }

     atmVpcTerminationGroup2    OBJECT-GROUP
            OBJECTS  {atmVplOperStatus, atmVplAdminStatus,
                atmVplLastChange,
                atmVplReceiveTrafficDescrIndex,
                atmVplTransmitTrafficDescrIndex,
                atmVplRowStatus, atmVplCastType,
                atmVplConnKind }
            STATUS     current


            DESCRIPTION
               "A collection of objects providing information
                about a VPL at an ATM interface which
                terminates a VPC (i.e., one which is NOT
                cross-connected to other VPLs)."
            ::= { atmMIBGroups 12 }

     atmVccTerminationGroup2    OBJECT-GROUP
            OBJECTS {atmVclOperStatus, atmVclAdminStatus,
                 atmVclLastChange,
                 atmVclReceiveTrafficDescrIndex,
                 atmVclTransmitTrafficDescrIndex,
                 atmVccAalType, atmVclRowStatus,
                 atmVclCastType, atmVclConnKind }
            STATUS     current
            DESCRIPTION
               "A collection of objects providing information
                about a VCL at an ATM interface
                which terminates a VCC (i.e., one which is
                NOT cross-connected to other VCLs)."
            ::= { atmMIBGroups 13 }

     atmVplCrossConnectGroup    OBJECT-GROUP
            OBJECTS { atmVplReceiveTrafficDescrIndex,
                atmVplTransmitTrafficDescrIndex,
                atmVplOperStatus, atmVplLastChange,
                atmVplRowStatus,
                atmVplCastType, atmVplConnKind }
            STATUS     current
            DESCRIPTION
               "A collection of objects providing
                information about the VPLs that
                are cross-connected together."
            ::= { atmMIBGroups 14 }

     atmVpPvcCrossConnectGroup    OBJECT-GROUP
            OBJECTS { atmVpCrossConnectAdminStatus,
                atmVpCrossConnectL2HOperStatus,
                atmVpCrossConnectH2LOperStatus,
                atmVpCrossConnectL2HLastChange,
                atmVpCrossConnectH2LLastChange,
                atmVpCrossConnectRowStatus,
                atmVplCrossConnectIdentifier,
                atmVpCrossConnectIndexNext }
            STATUS     current
            DESCRIPTION
               "A collection of objects providing
                information about a VP cross-connect


                for PVCs. These objects are not used
                for Soft PVCs or SVCs."
            ::= { atmMIBGroups 15 }

     atmVclCrossConnectGroup    OBJECT-GROUP
            OBJECTS { atmVclReceiveTrafficDescrIndex,
                atmVclTransmitTrafficDescrIndex,
                atmVclOperStatus, atmVclLastChange,
                atmVclRowStatus,
                atmVclCastType, atmVclConnKind }
            STATUS     current
            DESCRIPTION
               "A collection of objects providing
                information about the VCLs that
                are cross-connected together."
            ::= { atmMIBGroups 16 }

     atmVcPvcCrossConnectGroup    OBJECT-GROUP
            OBJECTS { atmVcCrossConnectAdminStatus,
                atmVcCrossConnectL2HOperStatus,
                atmVcCrossConnectH2LOperStatus,
                atmVcCrossConnectL2HLastChange,
                atmVcCrossConnectH2LLastChange,
                atmVcCrossConnectRowStatus,
                atmVclCrossConnectIdentifier,
                atmVcCrossConnectIndexNext }
            STATUS     current
            DESCRIPTION
               "A collection of objects providing
                information about a VC cross-connect
                for PVCs. These objects are not used
                for Soft PVCs or SVCs."
            ::= { atmMIBGroups 17 }

     -- Deprecated Definitions - Objects

     -- atmInterfaceAddressType
     -- atmTrafficQoSClass

     -- Deprecated Definitions - Compliance

     atmMIBCompliance    MODULE-COMPLIANCE
          STATUS         deprecated
          DESCRIPTION
            "The compliance statement for SNMP entities
             including networks which have ATM and


             AAL5 interfaces."

          MODULE -- this module
            MANDATORY-GROUPS  {atmInterfaceConfGroup,
                               atmTrafficDescrGroup}

            OBJECT         atmInterfaceMaxVpcs
            MIN-ACCESS     read-only
            DESCRIPTION
              "Write access is not required."

            OBJECT         atmInterfaceMaxVccs
            MIN-ACCESS     read-only
            DESCRIPTION
              "Write access is not required."

            OBJECT         atmInterfaceMaxActiveVpiBits
            MIN-ACCESS     read-only
            DESCRIPTION
              "Write access is not required."

            OBJECT         atmInterfaceMaxActiveVciBits
            MIN-ACCESS     read-only
            DESCRIPTION
              "Write access is not required."

            OBJECT         atmInterfaceIlmiVpi
            MIN-ACCESS     read-only
            DESCRIPTION
              "Write access is not required."

            OBJECT         atmInterfaceIlmiVci
            MIN-ACCESS     read-only
            DESCRIPTION
              "Write access is not required."

            OBJECT         atmInterfaceMyNeighborIpAddress
            MIN-ACCESS     read-only
            DESCRIPTION
              "Write access is not required."

            OBJECT         atmInterfaceMyNeighborIfName
            MIN-ACCESS     read-only
            DESCRIPTION
              "Write access is not required."

            OBJECT         atmTrafficDescrType
            MIN-ACCESS     read-only


            DESCRIPTION
              "Write access is not required."

            OBJECT         atmTrafficDescrParam1
            MIN-ACCESS     read-only
            DESCRIPTION
              "Write access is not required."

            OBJECT         atmTrafficDescrParam2
            MIN-ACCESS     read-only
            DESCRIPTION
              "Write access is not required."

            OBJECT         atmTrafficDescrParam3
            MIN-ACCESS     read-only
            DESCRIPTION
              "Write access is not required."

            OBJECT         atmTrafficDescrParam4
            MIN-ACCESS     read-only
            DESCRIPTION
              "Write access is not required."

            OBJECT         atmTrafficDescrParam5
            MIN-ACCESS     read-only
            DESCRIPTION
              "Write access is not required."

            OBJECT         atmTrafficQoSClass
            MIN-ACCESS     read-only
            DESCRIPTION
              "Write access is not required."

            OBJECT         atmTrafficDescrRowStatus
            SYNTAX         INTEGER {active(1)}
                             -- subset of RowStatus
            MIN-ACCESS     read-only
            DESCRIPTION
              "Write access is not required, and only one
               of the six enumerated values for the
               RowStatus textual convention need be
               supported, specifically: active(1)."

            GROUP          atmInterfaceDs3PlcpGroup
            DESCRIPTION
              "This group is mandatory only for those
               ATM interfaces which implement the
               DS3 PLCP layer."


            GROUP          atmInterfaceTCGroup
            DESCRIPTION
              "This group is mandatory only for those
               ATM interfaces which implement the
               TC Sublayer."

            GROUP          atmVpcTerminationGroup
            DESCRIPTION
              "This group is mandatory only for those
               ATM interfaces which implement ATM
               VPLs that terminate VPCs (i.e., ones which
               are NOT cross-connected to other VPLs)."

            GROUP          atmVpCrossConnectGroup
            DESCRIPTION
              "This group is mandatory only for those
               ATM interfaces which implement ATM
               VPLs that are not associated with VCLs
               and are cross-connected to other VPLs."

            OBJECT         atmVplAdminStatus
            MIN-ACCESS     read-only
            DESCRIPTION
              "Write access is not required."

            OBJECT         atmVplReceiveTrafficDescrIndex
            MIN-ACCESS     read-only
            DESCRIPTION
              "Write access is not required."

            OBJECT         atmVplTransmitTrafficDescrIndex
            MIN-ACCESS     read-only
            DESCRIPTION
              "Write access is not required."

            OBJECT         atmVplRowStatus
            SYNTAX         INTEGER {active(1)}
                             -- subset of RowStatus
            MIN-ACCESS      read-only
            DESCRIPTION
              "Write access is not required, and only one
               of the six enumerated values for the
               RowStatus textual convention need be
               supported, specifically: active(1)."

            OBJECT         atmVpCrossConnectAdminStatus
            MIN-ACCESS     read-only
            DESCRIPTION


              "Write access is not required."

            OBJECT         atmVpCrossConnectRowStatus
            SYNTAX         INTEGER {active(1)}
                             -- subset of RowStatus
            MIN-ACCESS     read-only
            DESCRIPTION
              "Write access is not required, and only one
               of the six enumerated values for the
               RowStatus textual convention need be
               supported, specifically: active(1)."

            GROUP          atmVccTerminationGroup
            DESCRIPTION
              "This group is mandatory only for those
               ATM interfaces which implement ATM
               VCLs that terminate VCCs (i.e., ones which
               are NOT cross-connected to other VCLs)."

            GROUP          atmVcCrossConnectGroup
            DESCRIPTION
              "This group is mandatory only for those
               ATM interfaces which implement ATM
               VCLs that are cross-connected to
               other VCLs."

            OBJECT         atmVclAdminStatus
            MIN-ACCESS     read-only
            DESCRIPTION
              "Write access is not required."

            OBJECT         atmVclReceiveTrafficDescrIndex
            MIN-ACCESS     read-only
            DESCRIPTION
              "Write access is not required."

            OBJECT         atmVclTransmitTrafficDescrIndex
            MIN-ACCESS     read-only
            DESCRIPTION
              "Write access is not required."

            OBJECT         atmVccAalType
            MIN-ACCESS     read-only
            DESCRIPTION
              "Write access is not required."

            OBJECT         atmVclRowStatus
            SYNTAX         INTEGER {active(1)}


                             -- subset of RowStatus
            MIN-ACCESS     read-only
            DESCRIPTION
              "Write access is not required, and only one
               of the six enumerated values for the
               RowStatus textual convention need be
               supported, specifically: active(1)."

            OBJECT         atmVcCrossConnectAdminStatus
            MIN-ACCESS     read-only
            DESCRIPTION
              "Write access is not required."

            OBJECT         atmVcCrossConnectRowStatus
            SYNTAX         INTEGER { active(1)}
                             -- subset of RowStatus
            MIN-ACCESS     read-only
            DESCRIPTION
              "Write access is not required, and only one
               of the six enumerated values for the
               RowStatus textual convention need be
               supported, specifically: active(1)."

            GROUP          aal5VccGroup
            DESCRIPTION
              "This group is mandatory for the
               AAL5 virtual connections only."

            OBJECT         atmVccAal5CpcsTransmitSduSize
            MIN-ACCESS     read-only
            DESCRIPTION
              "Write access is not required."

            OBJECT         atmVccAal5CpcsReceiveSduSize
            MIN-ACCESS     read-only
            DESCRIPTION
              "Write access is not required."

            OBJECT         atmVccAal5EncapsType
            MIN-ACCESS     read-only
            DESCRIPTION
              "Write access is not required."
             ::= { atmMIBCompliances 1 }

     -- Deprecated Definitions - Groups


     atmInterfaceConfGroup    OBJECT-GROUP
            OBJECTS {
                  atmInterfaceMaxVpcs, atmInterfaceMaxVccs,
                  atmInterfaceConfVpcs, atmInterfaceConfVccs,
                  atmInterfaceMaxActiveVpiBits,
                  atmInterfaceMaxActiveVciBits,
                  atmInterfaceIlmiVpi,
                  atmInterfaceIlmiVci,
                  atmInterfaceAddressType,
                  atmInterfaceAdminAddress,
                  atmInterfaceMyNeighborIpAddress,
                  atmInterfaceMyNeighborIfName }
            STATUS     deprecated
            DESCRIPTION
              "A collection of objects providing configuration
               information about an ATM interface."
            ::= { atmMIBGroups 1 }

     atmTrafficDescrGroup    OBJECT-GROUP
            OBJECTS {
                atmTrafficDescrType, atmTrafficDescrParam1,
                atmTrafficDescrParam2, atmTrafficDescrParam3,
                atmTrafficDescrParam4, atmTrafficDescrParam5,
                atmTrafficQoSClass, atmTrafficDescrRowStatus}
            STATUS     deprecated
            DESCRIPTION
               "A collection of objects providing information
                about ATM traffic descriptor type and
                the associated parameters."
            ::= { atmMIBGroups 2 }

     atmVpcTerminationGroup    OBJECT-GROUP
            OBJECTS  {atmVplOperStatus, atmVplAdminStatus,
                atmVplLastChange,
                atmVplReceiveTrafficDescrIndex,
                atmVplTransmitTrafficDescrIndex,
                atmVplRowStatus }
            STATUS     deprecated
            DESCRIPTION
               "A collection of objects providing
                information about a VPL at an ATM interface
                which terminates a VPC
                (i.e., one which is NOT cross-connected
                to other VPLs)."
            ::= { atmMIBGroups 5 }

     atmVccTerminationGroup    OBJECT-GROUP
            OBJECTS {atmVclOperStatus, atmVclAdminStatus,


                atmVclLastChange,
                 atmVclReceiveTrafficDescrIndex,
                 atmVclTransmitTrafficDescrIndex,
                 atmVccAalType, atmVclRowStatus }
            STATUS     deprecated
            DESCRIPTION
               "A collection of objects providing information
                about a VCL at an ATM interface
                which terminates a VCC (i.e., one which is
                NOT cross-connected to other VCLs)."
            ::= { atmMIBGroups 6 }

     atmVpCrossConnectGroup    OBJECT-GROUP
            OBJECTS { atmVplReceiveTrafficDescrIndex,
                atmVplTransmitTrafficDescrIndex,
                atmVplOperStatus, atmVplRowStatus,
                atmVpCrossConnectAdminStatus,
                atmVpCrossConnectL2HOperStatus,
                atmVpCrossConnectH2LOperStatus,
                atmVpCrossConnectL2HLastChange,
                atmVpCrossConnectH2LLastChange,
                atmVpCrossConnectRowStatus,
                atmVplCrossConnectIdentifier,
                atmVpCrossConnectIndexNext }
            STATUS     deprecated
            DESCRIPTION
               "A collection of objects providing
                information about a VP cross-connect
                and the associated VPLs that are
                cross-connected together."
            ::= { atmMIBGroups 7 }

     atmVcCrossConnectGroup    OBJECT-GROUP
            OBJECTS { atmVclReceiveTrafficDescrIndex,
                atmVclTransmitTrafficDescrIndex,
                atmVclOperStatus, atmVclRowStatus,
                atmVcCrossConnectAdminStatus,
                atmVcCrossConnectL2HOperStatus,
                atmVcCrossConnectH2LOperStatus,
                atmVcCrossConnectL2HLastChange,
                atmVcCrossConnectH2LLastChange,
                atmVcCrossConnectRowStatus,
                atmVclCrossConnectIdentifier,
                atmVcCrossConnectIndexNext }
            STATUS     deprecated
            DESCRIPTION
               "A collection of objects providing
                information about a VC cross-connect


                and the associated VCLs that are
                cross-connected together."
            ::= { atmMIBGroups 8 }

     -- {atmMIB 3} has been used by [19].

END

HOST-RESOURCES-MIB DEFINITIONS ::= BEGIN

   IMPORTS
   MODULE-IDENTITY, OBJECT-TYPE, mib-2,
   Integer32, Counter32, Gauge32, TimeTicks  FROM SNMPv2-SMI

   TEXTUAL-CONVENTION, DisplayString,
   TruthValue, DateAndTime, AutonomousType   FROM SNMPv2-TC

   MODULE-COMPLIANCE, OBJECT-GROUP           FROM SNMPv2-CONF

   InterfaceIndexOrZero                      FROM IF-MIB;

   hostResourcesMibModule MODULE-IDENTITY
      LAST-UPDATED "200003060000Z"    -- 6 March 2000
      ORGANIZATION "IETF Host Resources MIB Working Group"
      CONTACT-INFO
          "Steve Waldbusser
          Postal: Lucent Technologies, Inc.
                  1213 Innsbruck Dr.
                  Sunnyvale, CA 94089
                  USA
          Phone:  650-318-1251
          Fax:    650-318-1633
          Email:  waldbusser@lucent.com


          In addition, the Host Resources MIB mailing list is
          dedicated to discussion of this MIB. To join the
          mailing list, send a request message to
          hostmib-request@andrew.cmu.edu. The mailing list
          address is hostmib@andrew.cmu.edu."

      DESCRIPTION
          "This MIB is for use in managing host systems. The term
          `host' is construed to mean any computer that communicates
          with other similar computers attached to the internet and
          that is directly used by one or more human beings. Although
          this MIB does not necessarily apply to devices whose primary
          function is communications services (e.g., terminal servers,
          routers, bridges, monitoring equipment), such relevance is
          not explicitly precluded.  This MIB instruments attributes
          common to all internet hosts including, for example, both
          personal computers and systems that run variants of Unix."

      REVISION "200003060000Z"        -- 6 March 2000
      DESCRIPTION
          "Clarifications and bug fixes based on implementation
          experience.  This revision was also reformatted in the SMIv2
          format. The revisions made were:

          New RFC document standards:
             Added Copyright notice, updated introduction to SNMP
             Framework, updated references section, added reference to
             RFC 2119, and added a meaningful Security Considerations
             section.

          New IANA considerations section for registration of new types

          Conversion to new SMIv2 syntax for the following types and
          macros:
              Counter32, Integer32, Gauge32, MODULE-IDENTITY,
              OBJECT-TYPE, TEXTUAL-CONVENTION, OBJECT-IDENTITY,
              MODULE-COMPLIANCE, OBJECT-GROUP

          Used new Textual Conventions:
              TruthValue, DateAndTime, AutonomousType,
              InterfaceIndexOrZero

          Fixed typo in hrPrinterStatus.

          Added missing error bits to hrPrinterDetectedErrorState and
          clarified confusion resulting from suggested mappings to
          hrPrinterStatus.


          Clarified that size of objects of type
          InternationalDisplayString is number of octets, not number
          of encoded symbols.

          Clarified the use of the following objects based on
          implementation experience:
              hrSystemInitialLoadDevice, hrSystemInitialLoadParameters,
              hrMemorySize, hrStorageSize, hrStorageAllocationFailures,
              hrDeviceErrors, hrProcessorLoad, hrNetworkIfIndex,
              hrDiskStorageCapacity, hrSWRunStatus, hrSWRunPerfCPU,
              and hrSWInstalledDate.

          Clarified implementation technique for hrSWInstalledTable.

          Used new AUGMENTS clause for hrSWRunPerfTable.

          Added Internationalization Considerations section.

   This revision published as RFC2790."

      REVISION "9910202200Z"    -- 20 October, 1999
      DESCRIPTION
          "The original version of this MIB, published as
          RFC1514."
      ::= { hrMIBAdminInfo 1 }

   host     OBJECT IDENTIFIER ::= { mib-2 25 }

   hrSystem        OBJECT IDENTIFIER ::= { host 1 }
   hrStorage       OBJECT IDENTIFIER ::= { host 2 }
   hrDevice        OBJECT IDENTIFIER ::= { host 3 }
   hrSWRun         OBJECT IDENTIFIER ::= { host 4 }
   hrSWRunPerf     OBJECT IDENTIFIER ::= { host 5 }
   hrSWInstalled   OBJECT IDENTIFIER ::= { host 6 }
   hrMIBAdminInfo  OBJECT IDENTIFIER ::= { host 7 }

   -- textual conventions

   KBytes ::= TEXTUAL-CONVENTION
       STATUS current
       DESCRIPTION
           "Storage size, expressed in units of 1024 bytes."
       SYNTAX Integer32 (0..2147483647)

   ProductID ::= TEXTUAL-CONVENTION
       STATUS current
       DESCRIPTION
           "This textual convention is intended to identify the


           manufacturer, model, and version of a specific
           hardware or software product.  It is suggested that
           these OBJECT IDENTIFIERs are allocated such that all
           products from a particular manufacturer are registered
           under a subtree distinct to that manufacturer.  In
           addition, all versions of a product should be
           registered under a subtree distinct to that product.
           With this strategy, a management station may uniquely
           determine the manufacturer and/or model of a product
           whose productID is unknown to the management station.
           Objects of this type may be useful for inventory
           purposes or for automatically detecting
           incompatibilities or version mismatches between
           various hardware and software components on a system.

           For example, the product ID for the ACME 4860 66MHz
           clock doubled processor might be:
           enterprises.acme.acmeProcessors.a4860DX2.MHz66

           A software product might be registered as:
           enterprises.acme.acmeOperatingSystems.acmeDOS.six(6).one(1)
           "
       SYNTAX OBJECT IDENTIFIER

   -- unknownProduct will be used for any unknown ProductID
   -- unknownProduct OBJECT IDENTIFIER ::= { 0 0 }

   InternationalDisplayString ::= TEXTUAL-CONVENTION
       STATUS current
       DESCRIPTION
           "This data type is used to model textual information
           in some character set.  A network management station
           should use a local algorithm to determine which
           character set is in use and how it should be
           displayed.  Note that this character set may be
           encoded with more than one octet per symbol, but will
           most often be NVT ASCII. When a size clause is
           specified for an object of this type, the size refers
           to the length in octets, not the number of symbols."
       SYNTAX OCTET STRING

   -- The Host Resources System Group

   hrSystemUptime OBJECT-TYPE
       SYNTAX     TimeTicks
       MAX-ACCESS read-only
       STATUS     current
       DESCRIPTION


           "The amount of time since this host was last
           initialized.  Note that this is different from
           sysUpTime in the SNMPv2-MIB [RFC1907] because
           sysUpTime is the uptime of the network management
           portion of the system."
       ::= { hrSystem 1 }

   hrSystemDate OBJECT-TYPE
       SYNTAX     DateAndTime
       MAX-ACCESS read-write
       STATUS     current
       DESCRIPTION
           "The host's notion of the local date and time of day."
       ::= { hrSystem 2 }

   hrSystemInitialLoadDevice OBJECT-TYPE
       SYNTAX     Integer32 (1..2147483647)
       MAX-ACCESS read-write
       STATUS     current
       DESCRIPTION
           "The index of the hrDeviceEntry for the device from
           which this host is configured to load its initial
           operating system configuration (i.e., which operating
           system code and/or boot parameters).

           Note that writing to this object just changes the
           configuration that will be used the next time the
           operating system is loaded and does not actually cause
           the reload to occur."
       ::= { hrSystem 3 }

   hrSystemInitialLoadParameters OBJECT-TYPE
       SYNTAX     InternationalDisplayString (SIZE (0..128))
       MAX-ACCESS read-write
       STATUS     current
       DESCRIPTION
           "This object contains the parameters (e.g. a pathname
           and parameter) supplied to the load device when
           requesting the initial operating system configuration
           from that device.

        Note that writing to this object just changes the
        configuration that will be used the next time the
        operating system is loaded and does not actually cause
        the reload to occur."
       ::= { hrSystem 4 }

   hrSystemNumUsers OBJECT-TYPE


       SYNTAX     Gauge32
       MAX-ACCESS read-only
       STATUS     current
       DESCRIPTION
           "The number of user sessions for which this host is
           storing state information.  A session is a collection
           of processes requiring a single act of user
           authentication and possibly subject to collective job
           control."
       ::= { hrSystem 5 }

   hrSystemProcesses OBJECT-TYPE
       SYNTAX     Gauge32
       MAX-ACCESS read-only
       STATUS     current
       DESCRIPTION
           "The number of process contexts currently loaded or
           running on this system."
       ::= { hrSystem 6 }

   hrSystemMaxProcesses OBJECT-TYPE
       SYNTAX     Integer32 (0..2147483647)
       MAX-ACCESS read-only
       STATUS     current
       DESCRIPTION
           "The maximum number of process contexts this system
           can support.  If there is no fixed maximum, the value
           should be zero.  On systems that have a fixed maximum,
           this object can help diagnose failures that occur when
           this maximum is reached."
       ::= { hrSystem 7 }

   -- The Host Resources Storage Group

   -- Registration point for storage types, for use with hrStorageType.
   -- These are defined in the HOST-RESOURCES-TYPES module.
   hrStorageTypes          OBJECT IDENTIFIER ::= { hrStorage 1 }

   hrMemorySize OBJECT-TYPE
       SYNTAX     KBytes
       UNITS      "KBytes"
       MAX-ACCESS read-only
       STATUS     current
       DESCRIPTION
           "The amount of physical read-write main memory,
           typically RAM, contained by the host."
       ::= { hrStorage 2 }


   hrStorageTable OBJECT-TYPE
       SYNTAX     SEQUENCE OF HrStorageEntry
       MAX-ACCESS not-accessible
       STATUS     current
       DESCRIPTION
           "The (conceptual) table of logical storage areas on
           the host.

           An entry shall be placed in the storage table for each
           logical area of storage that is allocated and has
           fixed resource limits.  The amount of storage
           represented in an entity is the amount actually usable
           by the requesting entity, and excludes loss due to
           formatting or file system reference information.

           These entries are associated with logical storage
           areas, as might be seen by an application, rather than
           physical storage entities which are typically seen by
           an operating system.  Storage such as tapes and
           floppies without file systems on them are typically
           not allocated in chunks by the operating system to
           requesting applications, and therefore shouldn't
           appear in this table.  Examples of valid storage for
           this table include disk partitions, file systems, ram
           (for some architectures this is further segmented into
           regular memory, extended memory, and so on), backing
           store for virtual memory (`swap space').

           This table is intended to be a useful diagnostic for
           `out of memory' and `out of buffers' types of
           failures.  In addition, it can be a useful performance
           monitoring tool for tracking memory, disk, or buffer
           usage."
       ::= { hrStorage 3 }

   hrStorageEntry OBJECT-TYPE
       SYNTAX     HrStorageEntry
       MAX-ACCESS not-accessible
       STATUS     current
       DESCRIPTION
           "A (conceptual) entry for one logical storage area on
           the host.  As an example, an instance of the
           hrStorageType object might be named hrStorageType.3"
       INDEX { hrStorageIndex }
       ::= { hrStorageTable 1 }

   HrStorageEntry ::= SEQUENCE {
           hrStorageIndex               Integer32,


           hrStorageType                AutonomousType,
           hrStorageDescr               DisplayString,
           hrStorageAllocationUnits     Integer32,
           hrStorageSize                Integer32,
           hrStorageUsed                Integer32,
           hrStorageAllocationFailures  Counter32
       }

   hrStorageIndex OBJECT-TYPE
       SYNTAX     Integer32 (1..2147483647)
       MAX-ACCESS read-only
       STATUS     current
       DESCRIPTION
           "A unique value for each logical storage area
           contained by the host."
       ::= { hrStorageEntry 1 }

   hrStorageType OBJECT-TYPE
       SYNTAX     AutonomousType
       MAX-ACCESS read-only
       STATUS     current
       DESCRIPTION
           "The type of storage represented by this entry."
       ::= { hrStorageEntry 2 }

   hrStorageDescr OBJECT-TYPE
       SYNTAX     DisplayString
       MAX-ACCESS read-only
       STATUS     current
       DESCRIPTION
           "A description of the type and instance of the storage
           described by this entry."
       ::= { hrStorageEntry 3 }

   hrStorageAllocationUnits OBJECT-TYPE
       SYNTAX     Integer32 (1..2147483647)
       UNITS      "Bytes"
       MAX-ACCESS read-only
       STATUS     current
       DESCRIPTION
           "The size, in bytes, of the data objects allocated
           from this pool.  If this entry is monitoring sectors,
           blocks, buffers, or packets, for example, this number
           will commonly be greater than one.  Otherwise this
           number will typically be one."
       ::= { hrStorageEntry 4 }

   hrStorageSize OBJECT-TYPE


       SYNTAX     Integer32 (0..2147483647)
       MAX-ACCESS read-write
       STATUS     current
       DESCRIPTION
           "The size of the storage represented by this entry, in
           units of hrStorageAllocationUnits. This object is
           writable to allow remote configuration of the size of
           the storage area in those cases where such an
           operation makes sense and is possible on the
           underlying system. For example, the amount of main
           memory allocated to a buffer pool might be modified or
           the amount of disk space allocated to virtual memory
           might be modified."
       ::= { hrStorageEntry 5 }

   hrStorageUsed OBJECT-TYPE
       SYNTAX     Integer32 (0..2147483647)
       MAX-ACCESS read-only
       STATUS     current
       DESCRIPTION
           "The amount of the storage represented by this entry
           that is allocated, in units of
           hrStorageAllocationUnits."
       ::= { hrStorageEntry 6 }

   hrStorageAllocationFailures OBJECT-TYPE
       SYNTAX     Counter32
       MAX-ACCESS read-only
       STATUS     current
       DESCRIPTION
           "The number of requests for storage represented by
           this entry that could not be honored due to not enough
           storage.  It should be noted that as this object has a
           SYNTAX of Counter32, that it does not have a defined
           initial value.  However, it is recommended that this
           object be initialized to zero, even though management
           stations must not depend on such an initialization."
       ::= { hrStorageEntry 7 }

   -- The Host Resources Device Group
   --
   -- The device group is useful for identifying and diagnosing the
   -- devices on a system.  The hrDeviceTable contains common
   -- information for any type of device.  In addition, some devices
   -- have device-specific tables for more detailed information.  More
   -- such tables may be defined in the future for other device types.

   -- Registration point for device types, for use with hrDeviceType.


   -- These are defined in the HOST-RESOURCES-TYPES module.
   hrDeviceTypes             OBJECT IDENTIFIER ::= { hrDevice 1 }

   hrDeviceTable OBJECT-TYPE
       SYNTAX     SEQUENCE OF HrDeviceEntry
       MAX-ACCESS not-accessible
       STATUS     current
       DESCRIPTION
           "The (conceptual) table of devices contained by the
           host."
       ::= { hrDevice 2 }

   hrDeviceEntry OBJECT-TYPE
       SYNTAX     HrDeviceEntry
       MAX-ACCESS not-accessible
       STATUS     current
       DESCRIPTION
           "A (conceptual) entry for one device contained by the
           host.  As an example, an instance of the hrDeviceType
           object might be named hrDeviceType.3"
       INDEX { hrDeviceIndex }
       ::= { hrDeviceTable 1 }

   HrDeviceEntry ::= SEQUENCE {
           hrDeviceIndex           Integer32,
           hrDeviceType            AutonomousType,
           hrDeviceDescr           DisplayString,
           hrDeviceID              ProductID,
           hrDeviceStatus          INTEGER,
           hrDeviceErrors          Counter32
       }

   hrDeviceIndex OBJECT-TYPE
       SYNTAX     Integer32 (1..2147483647)
       MAX-ACCESS read-only
       STATUS     current
       DESCRIPTION
           "A unique value for each device contained by the host.
           The value for each device must remain constant at
           least from one re-initialization of the agent to the
           next re-initialization."
       ::= { hrDeviceEntry 1 }

   hrDeviceType OBJECT-TYPE
       SYNTAX     AutonomousType
       MAX-ACCESS read-only
       STATUS     current
       DESCRIPTION


           "An indication of the type of device.

           If this value is
           `hrDeviceProcessor { hrDeviceTypes 3 }' then an entry
           exists in the hrProcessorTable which corresponds to
           this device.

           If this value is
           `hrDeviceNetwork { hrDeviceTypes 4 }', then an entry
           exists in the hrNetworkTable which corresponds to this
           device.

           If this value is
           `hrDevicePrinter { hrDeviceTypes 5 }', then an entry
           exists in the hrPrinterTable which corresponds to this
           device.

           If this value is
           `hrDeviceDiskStorage { hrDeviceTypes 6 }', then an
           entry exists in the hrDiskStorageTable which
           corresponds to this device."
       ::= { hrDeviceEntry 2 }

   hrDeviceDescr OBJECT-TYPE
       SYNTAX     DisplayString (SIZE (0..64))
       MAX-ACCESS read-only
       STATUS     current
       DESCRIPTION
           "A textual description of this device, including the
           device's manufacturer and revision, and optionally,
           its serial number."
       ::= { hrDeviceEntry 3 }

   hrDeviceID OBJECT-TYPE
       SYNTAX     ProductID
       MAX-ACCESS read-only
       STATUS     current
       DESCRIPTION
           "The product ID for this device."
       ::= { hrDeviceEntry 4 }

   hrDeviceStatus OBJECT-TYPE
       SYNTAX     INTEGER {
                      unknown(1),
                      running(2),
                      warning(3),
                      testing(4),
                      down(5)


                  }
       MAX-ACCESS read-only
       STATUS     current
       DESCRIPTION
           "The current operational state of the device described
           by this row of the table.  A value unknown(1)
           indicates that the current state of the device is
           unknown.  running(2) indicates that the device is up
           and running and that no unusual error conditions are
           known.  The warning(3) state indicates that agent has
           been informed of an unusual error condition by the
           operational software (e.g., a disk device driver) but
           that the device is still 'operational'.  An example
           would be a high number of soft errors on a disk.  A
           value of testing(4), indicates that the device is not
           available for use because it is in the testing state.
           The state of down(5) is used only when the agent has
           been informed that the device is not available for any
           use."
       ::= { hrDeviceEntry 5 }

   hrDeviceErrors OBJECT-TYPE
       SYNTAX     Counter32
       MAX-ACCESS read-only
       STATUS     current
       DESCRIPTION
           "The number of errors detected on this device.  It
           should be noted that as this object has a SYNTAX of
           Counter32, that it does not have a defined initial
           value.  However, it is recommended that this object be
           initialized to zero, even though management stations
           must not depend on such an initialization."
       ::= { hrDeviceEntry 6 }

   hrProcessorTable OBJECT-TYPE
       SYNTAX     SEQUENCE OF HrProcessorEntry
       MAX-ACCESS not-accessible
       STATUS     current
       DESCRIPTION
           "The (conceptual) table of processors contained by the
           host.

           Note that this table is potentially sparse: a
           (conceptual) entry exists only if the correspondent
           value of the hrDeviceType object is
           `hrDeviceProcessor'."
       ::= { hrDevice 3 }


   hrProcessorEntry OBJECT-TYPE
       SYNTAX     HrProcessorEntry
       MAX-ACCESS not-accessible
       STATUS     current
       DESCRIPTION
           "A (conceptual) entry for one processor contained by
           the host.  The hrDeviceIndex in the index represents
           the entry in the hrDeviceTable that corresponds to the
           hrProcessorEntry.

           As an example of how objects in this table are named,
           an instance of the hrProcessorFrwID object might be
           named hrProcessorFrwID.3"
       INDEX { hrDeviceIndex }
       ::= { hrProcessorTable 1 }

   HrProcessorEntry ::= SEQUENCE {
           hrProcessorFrwID            ProductID,
           hrProcessorLoad             Integer32
       }

   hrProcessorFrwID OBJECT-TYPE
       SYNTAX     ProductID
       MAX-ACCESS read-only
       STATUS     current
       DESCRIPTION
           "The product ID of the firmware associated with the
           processor."
       ::= { hrProcessorEntry 1 }

   hrProcessorLoad OBJECT-TYPE
       SYNTAX     Integer32 (0..100)
       MAX-ACCESS read-only
       STATUS     current
       DESCRIPTION
           "The average, over the last minute, of the percentage
           of time that this processor was not idle.
           Implementations may approximate this one minute
           smoothing period if necessary."
       ::= { hrProcessorEntry 2 }

   hrNetworkTable OBJECT-TYPE
       SYNTAX     SEQUENCE OF HrNetworkEntry
       MAX-ACCESS not-accessible
       STATUS     current
       DESCRIPTION
           "The (conceptual) table of network devices contained
           by the host.


           Note that this table is potentially sparse: a
           (conceptual) entry exists only if the correspondent
           value of the hrDeviceType object is
           `hrDeviceNetwork'."
       ::= { hrDevice 4 }

   hrNetworkEntry OBJECT-TYPE
       SYNTAX     HrNetworkEntry
       MAX-ACCESS not-accessible
       STATUS     current
       DESCRIPTION
           "A (conceptual) entry for one network device contained
           by the host.  The hrDeviceIndex in the index
           represents the entry in the hrDeviceTable that
           corresponds to the hrNetworkEntry.

           As an example of how objects in this table are named,
           an instance of the hrNetworkIfIndex object might be
           named hrNetworkIfIndex.3"
       INDEX { hrDeviceIndex }
       ::= { hrNetworkTable 1 }

   HrNetworkEntry ::= SEQUENCE {
           hrNetworkIfIndex    InterfaceIndexOrZero
       }

   hrNetworkIfIndex OBJECT-TYPE
       SYNTAX     InterfaceIndexOrZero
       MAX-ACCESS read-only
       STATUS     current
       DESCRIPTION
           "The value of ifIndex which corresponds to this
           network device. If this device is not represented in
           the ifTable, then this value shall be zero."
       ::= { hrNetworkEntry 1 }

   hrPrinterTable OBJECT-TYPE
       SYNTAX     SEQUENCE OF HrPrinterEntry
       MAX-ACCESS not-accessible
       STATUS     current
       DESCRIPTION
           "The (conceptual) table of printers local to the host.

           Note that this table is potentially sparse: a
           (conceptual) entry exists only if the correspondent
           value of the hrDeviceType object is
           `hrDevicePrinter'."
       ::= { hrDevice 5 }


   hrPrinterEntry OBJECT-TYPE
       SYNTAX     HrPrinterEntry
       MAX-ACCESS not-accessible
       STATUS     current
       DESCRIPTION
           "A (conceptual) entry for one printer local to the
           host.  The hrDeviceIndex in the index represents the
           entry in the hrDeviceTable that corresponds to the
           hrPrinterEntry.

           As an example of how objects in this table are named,
           an instance of the hrPrinterStatus object might be
           named hrPrinterStatus.3"
       INDEX { hrDeviceIndex }
       ::= { hrPrinterTable 1 }

   HrPrinterEntry ::= SEQUENCE {
           hrPrinterStatus             INTEGER,
           hrPrinterDetectedErrorState OCTET STRING
       }

   hrPrinterStatus OBJECT-TYPE
       SYNTAX     INTEGER {
                      other(1),
                      unknown(2),
                      idle(3),
                      printing(4),
                      warmup(5)
                  }
       MAX-ACCESS read-only
       STATUS     current
       DESCRIPTION
           "The current status of this printer device."
       ::= { hrPrinterEntry 1 }

   hrPrinterDetectedErrorState OBJECT-TYPE
       SYNTAX     OCTET STRING
       MAX-ACCESS read-only
       STATUS     current
       DESCRIPTION
           "This object represents any error conditions detected
           by the printer.  The error conditions are encoded as
           bits in an octet string, with the following
           definitions:

                Condition         Bit #

                lowPaper              0


                noPaper               1
                lowToner              2
                noToner               3
                doorOpen              4
                jammed                5
                offline               6
                serviceRequested      7
                inputTrayMissing      8
                outputTrayMissing     9
                markerSupplyMissing  10
                outputNearFull       11
                outputFull           12
                inputTrayEmpty       13
                overduePreventMaint  14

           Bits are numbered starting with the most significant
           bit of the first byte being bit 0, the least
           significant bit of the first byte being bit 7, the
           most significant bit of the second byte being bit 8,
           and so on.  A one bit encodes that the condition was
           detected, while a zero bit encodes that the condition
           was not detected.

           This object is useful for alerting an operator to
           specific warning or error conditions that may occur,
           especially those requiring human intervention."
       ::= { hrPrinterEntry 2 }

   hrDiskStorageTable OBJECT-TYPE
       SYNTAX     SEQUENCE OF HrDiskStorageEntry
       MAX-ACCESS not-accessible
       STATUS     current
       DESCRIPTION
           "The (conceptual) table of long-term storage devices
           contained by the host.  In particular, disk devices
           accessed remotely over a network are not included
           here.

           Note that this table is potentially sparse: a
           (conceptual) entry exists only if the correspondent
           value of the hrDeviceType object is
           `hrDeviceDiskStorage'."
       ::= { hrDevice 6 }

   hrDiskStorageEntry OBJECT-TYPE
       SYNTAX     HrDiskStorageEntry
       MAX-ACCESS not-accessible
       STATUS     current


       DESCRIPTION
           "A (conceptual) entry for one long-term storage device
           contained by the host.  The hrDeviceIndex in the index
           represents the entry in the hrDeviceTable that
           corresponds to the hrDiskStorageEntry. As an example,
           an instance of the hrDiskStorageCapacity object might
           be named hrDiskStorageCapacity.3"
       INDEX { hrDeviceIndex }
       ::= { hrDiskStorageTable 1 }

   HrDiskStorageEntry ::= SEQUENCE {
           hrDiskStorageAccess         INTEGER,
           hrDiskStorageMedia          INTEGER,
           hrDiskStorageRemoveble      TruthValue,
           hrDiskStorageCapacity       KBytes
       }

   hrDiskStorageAccess OBJECT-TYPE
       SYNTAX     INTEGER {
                      readWrite(1),
                      readOnly(2)
                  }
       MAX-ACCESS read-only
       STATUS     current
       DESCRIPTION
           "An indication if this long-term storage device is
           readable and writable or only readable.  This should
           reflect the media type, any write-protect mechanism,
           and any device configuration that affects the entire
           device."
       ::= { hrDiskStorageEntry 1 }

   hrDiskStorageMedia OBJECT-TYPE
       SYNTAX     INTEGER {
                      other(1),
                      unknown(2),
                      hardDisk(3),
                      floppyDisk(4),
                      opticalDiskROM(5),
                      opticalDiskWORM(6),     -- Write Once Read Many
                      opticalDiskRW(7),
                      ramDisk(8)
                  }
       MAX-ACCESS read-only
       STATUS     current
       DESCRIPTION
           "An indication of the type of media used in this long-
           term storage device."


       ::= { hrDiskStorageEntry 2 }

   hrDiskStorageRemoveble OBJECT-TYPE
       SYNTAX     TruthValue
       MAX-ACCESS read-only
       STATUS     current
       DESCRIPTION
           "Denotes whether or not the disk media may be removed
           from the drive."
       ::= { hrDiskStorageEntry 3 }

   hrDiskStorageCapacity OBJECT-TYPE
       SYNTAX     KBytes
       UNITS      "KBytes"
       MAX-ACCESS read-only
       STATUS     current
       DESCRIPTION
           "The total size for this long-term storage device. If
           the media is removable and is currently removed, this
           value should be zero."
       ::= { hrDiskStorageEntry 4 }

   hrPartitionTable OBJECT-TYPE
       SYNTAX     SEQUENCE OF HrPartitionEntry
       MAX-ACCESS not-accessible
       STATUS     current
       DESCRIPTION
           "The (conceptual) table of partitions for long-term
           storage devices contained by the host.  In particular,
           partitions accessed remotely over a network are not
           included here."
       ::= { hrDevice 7 }

   hrPartitionEntry OBJECT-TYPE
       SYNTAX     HrPartitionEntry
       MAX-ACCESS not-accessible
       STATUS     current
       DESCRIPTION
           "A (conceptual) entry for one partition.  The
           hrDeviceIndex in the index represents the entry in the
           hrDeviceTable that corresponds to the
           hrPartitionEntry.

           As an example of how objects in this table are named,
           an instance of the hrPartitionSize object might be
           named hrPartitionSize.3.1"
       INDEX { hrDeviceIndex, hrPartitionIndex }
       ::= { hrPartitionTable 1 }


   HrPartitionEntry ::= SEQUENCE {
           hrPartitionIndex                Integer32,
           hrPartitionLabel                InternationalDisplayString,
           hrPartitionID                   OCTET STRING,
           hrPartitionSize                 KBytes,
           hrPartitionFSIndex              Integer32
       }

   hrPartitionIndex OBJECT-TYPE
       SYNTAX     Integer32 (1..2147483647)
       MAX-ACCESS read-only
       STATUS     current
       DESCRIPTION
           "A unique value for each partition on this long-term
           storage device.  The value for each long-term storage
           device must remain constant at least from one re-
           initialization of the agent to the next re-
           initialization."
       ::= { hrPartitionEntry 1 }

   hrPartitionLabel OBJECT-TYPE
       SYNTAX     InternationalDisplayString (SIZE (0..128))
       MAX-ACCESS read-only
       STATUS     current
       DESCRIPTION
           "A textual description of this partition."
       ::= { hrPartitionEntry 2 }

   hrPartitionID OBJECT-TYPE
       SYNTAX     OCTET STRING
       MAX-ACCESS read-only
       STATUS     current
       DESCRIPTION
           "A descriptor which uniquely represents this partition
           to the responsible operating system.  On some systems,
           this might take on a binary representation."
       ::= { hrPartitionEntry 3 }

   hrPartitionSize OBJECT-TYPE
       SYNTAX     KBytes
       UNITS      "KBytes"
       MAX-ACCESS read-only
       STATUS     current
       DESCRIPTION
           "The size of this partition."
       ::= { hrPartitionEntry 4 }

   hrPartitionFSIndex OBJECT-TYPE


       SYNTAX     Integer32 (0..2147483647)
       MAX-ACCESS read-only
       STATUS     current
       DESCRIPTION
           "The index of the file system mounted on this
           partition.  If no file system is mounted on this
           partition, then this value shall be zero.  Note that
           multiple partitions may point to one file system,
           denoting that that file system resides on those
           partitions.  Multiple file systems may not reside on
           one partition."
       ::= { hrPartitionEntry 5 }

   -- The File System Table

   -- Registration point for popular File System types,
   -- for use with hrFSType. These are defined in the
   -- HOST-RESOURCES-TYPES module.
   hrFSTypes               OBJECT IDENTIFIER ::= { hrDevice 9 }

   hrFSTable OBJECT-TYPE
       SYNTAX     SEQUENCE OF HrFSEntry
       MAX-ACCESS not-accessible
       STATUS     current
       DESCRIPTION
           "The (conceptual) table of file systems local to this
           host or remotely mounted from a file server.  File
           systems that are in only one user's environment on a
           multi-user system will not be included in this table."
       ::= { hrDevice 8 }

   hrFSEntry OBJECT-TYPE
       SYNTAX     HrFSEntry
       MAX-ACCESS not-accessible
       STATUS     current
       DESCRIPTION
           "A (conceptual) entry for one file system local to
           this host or remotely mounted from a file server.
           File systems that are in only one user's environment
           on a multi-user system will not be included in this
           table.

           As an example of how objects in this table are named,
           an instance of the hrFSMountPoint object might be
           named hrFSMountPoint.3"
       INDEX { hrFSIndex }
       ::= { hrFSTable 1 }


   HrFSEntry ::= SEQUENCE {
           hrFSIndex                   Integer32,
           hrFSMountPoint              InternationalDisplayString,
           hrFSRemoteMountPoint        InternationalDisplayString,
           hrFSType                    AutonomousType,
           hrFSAccess                  INTEGER,
           hrFSBootable                TruthValue,
           hrFSStorageIndex            Integer32,
           hrFSLastFullBackupDate      DateAndTime,
           hrFSLastPartialBackupDate   DateAndTime
       }

   hrFSIndex OBJECT-TYPE
       SYNTAX     Integer32 (1..2147483647)
       MAX-ACCESS read-only
       STATUS     current
       DESCRIPTION
           "A unique value for each file system local to this
           host.  The value for each file system must remain
           constant at least from one re-initialization of the
           agent to the next re-initialization."
       ::= { hrFSEntry 1 }

   hrFSMountPoint OBJECT-TYPE
       SYNTAX     InternationalDisplayString (SIZE(0..128))
       MAX-ACCESS read-only
       STATUS     current
       DESCRIPTION
           "The path name of the root of this file system."
       ::= { hrFSEntry 2 }

   hrFSRemoteMountPoint OBJECT-TYPE
       SYNTAX     InternationalDisplayString (SIZE(0..128))
       MAX-ACCESS read-only
       STATUS     current
       DESCRIPTION
           "A description of the name and/or address of the
           server that this file system is mounted from.  This
           may also include parameters such as the mount point on
           the remote file system.  If this is not a remote file
           system, this string should have a length of zero."
       ::= { hrFSEntry 3 }

   hrFSType OBJECT-TYPE
       SYNTAX     AutonomousType
       MAX-ACCESS read-only
       STATUS     current
       DESCRIPTION


           "The value of this object identifies the type of this
           file system."
       ::= { hrFSEntry 4 }

   hrFSAccess OBJECT-TYPE
       SYNTAX     INTEGER {
                      readWrite(1),
                      readOnly(2)
                  }
       MAX-ACCESS read-only
       STATUS     current
       DESCRIPTION
           "An indication if this file system is logically
           configured by the operating system to be readable and
           writable or only readable.  This does not represent
           any local access-control policy, except one that is
           applied to the file system as a whole."
       ::= { hrFSEntry 5 }

   hrFSBootable OBJECT-TYPE
       SYNTAX     TruthValue
       MAX-ACCESS read-only
       STATUS     current
       DESCRIPTION
           "A flag indicating whether this file system is
           bootable."
       ::= { hrFSEntry 6 }

   hrFSStorageIndex OBJECT-TYPE
       SYNTAX     Integer32 (0..2147483647)
       MAX-ACCESS read-only
       STATUS     current
       DESCRIPTION
           "The index of the hrStorageEntry that represents
           information about this file system.  If there is no
           such information available, then this value shall be
           zero.  The relevant storage entry will be useful in
           tracking the percent usage of this file system and
           diagnosing errors that may occur when it runs out of
           space."
       ::= { hrFSEntry 7 }

   hrFSLastFullBackupDate OBJECT-TYPE
       SYNTAX     DateAndTime
       MAX-ACCESS read-write
       STATUS     current
       DESCRIPTION
           "The last date at which this complete file system was


           copied to another storage device for backup.  This
           information is useful for ensuring that backups are
           being performed regularly.

           If this information is not known, then this variable
           shall have the value corresponding to January 1, year
           0000, 00:00:00.0, which is encoded as
           (hex)'00 00 01 01 00 00 00 00'."
       ::= { hrFSEntry 8 }

   hrFSLastPartialBackupDate OBJECT-TYPE
       SYNTAX     DateAndTime
       MAX-ACCESS read-write
       STATUS     current
       DESCRIPTION
           "The last date at which a portion of this file system
           was copied to another storage device for backup.  This
           information is useful for ensuring that backups are
           being performed regularly.

           If this information is not known, then this variable
           shall have the value corresponding to January 1, year
           0000, 00:00:00.0, which is encoded as
           (hex)'00 00 01 01 00 00 00 00'."
       ::= { hrFSEntry 9 }

   -- The Host Resources Running Software Group
   --
   -- The hrSWRunTable contains an entry for each distinct piece of
   -- software that is running or loaded into physical or virtual
   -- memory in preparation for running.  This includes the host's
   -- operating system, device drivers, and applications.

   hrSWOSIndex OBJECT-TYPE
       SYNTAX     Integer32 (1..2147483647)
       MAX-ACCESS read-only
       STATUS     current
       DESCRIPTION
           "The value of the hrSWRunIndex for the hrSWRunEntry
           that represents the primary operating system running
           on this host.  This object is useful for quickly and
           uniquely identifying that primary operating system."
       ::= { hrSWRun 1 }

   hrSWRunTable OBJECT-TYPE
       SYNTAX     SEQUENCE OF HrSWRunEntry
       MAX-ACCESS not-accessible
       STATUS     current


       DESCRIPTION
           "The (conceptual) table of software running on the
           host."
       ::= { hrSWRun 2 }

   hrSWRunEntry OBJECT-TYPE
       SYNTAX     HrSWRunEntry
       MAX-ACCESS not-accessible
       STATUS     current
       DESCRIPTION
           "A (conceptual) entry for one piece of software
           running on the host Note that because the installed
           software table only contains information for software
           stored locally on this host, not every piece of
           running software will be found in the installed
           software table.  This is true of software that was
           loaded and run from a non-local source, such as a
           network-mounted file system.

           As an example of how objects in this table are named,
           an instance of the hrSWRunName object might be named
           hrSWRunName.1287"
       INDEX { hrSWRunIndex }
       ::= { hrSWRunTable 1 }

   HrSWRunEntry ::= SEQUENCE {
           hrSWRunIndex       Integer32,
           hrSWRunName        InternationalDisplayString,
           hrSWRunID          ProductID,
           hrSWRunPath        InternationalDisplayString,
           hrSWRunParameters  InternationalDisplayString,
           hrSWRunType        INTEGER,
           hrSWRunStatus      INTEGER
       }

   hrSWRunIndex OBJECT-TYPE
       SYNTAX     Integer32 (1..2147483647)
       MAX-ACCESS read-only
       STATUS     current
       DESCRIPTION
           "A unique value for each piece of software running on
           the host.  Wherever possible, this should be the
           system's native, unique identification number."
       ::= { hrSWRunEntry 1 }

   hrSWRunName OBJECT-TYPE
       SYNTAX     InternationalDisplayString (SIZE (0..64))
       MAX-ACCESS read-only


       STATUS     current
       DESCRIPTION
           "A textual description of this running piece of
           software, including the manufacturer, revision,  and
           the name by which it is commonly known.  If this
           software was installed locally, this should be the
           same string as used in the corresponding
           hrSWInstalledName."
       ::= { hrSWRunEntry 2 }

   hrSWRunID OBJECT-TYPE
       SYNTAX     ProductID
       MAX-ACCESS read-only
       STATUS     current
       DESCRIPTION
           "The product ID of this running piece of software."
       ::= { hrSWRunEntry 3 }

   hrSWRunPath OBJECT-TYPE
       SYNTAX     InternationalDisplayString (SIZE(0..128))
       MAX-ACCESS read-only
       STATUS     current
       DESCRIPTION
           "A description of the location on long-term storage
           (e.g. a disk drive) from which this software was
           loaded."
       ::= { hrSWRunEntry 4 }

   hrSWRunParameters OBJECT-TYPE
       SYNTAX     InternationalDisplayString (SIZE(0..128))
       MAX-ACCESS read-only
       STATUS     current
       DESCRIPTION
           "A description of the parameters supplied to this
           software when it was initially loaded."
       ::= { hrSWRunEntry 5 }

   hrSWRunType OBJECT-TYPE
       SYNTAX     INTEGER {
                      unknown(1),
                      operatingSystem(2),
                      deviceDriver(3),
                      application(4)
                  }
       MAX-ACCESS read-only
       STATUS     current
       DESCRIPTION
           "The type of this software."


       ::= { hrSWRunEntry 6 }

   hrSWRunStatus OBJECT-TYPE
       SYNTAX     INTEGER {
                      running(1),
                      runnable(2),    -- waiting for resource
                                      -- (i.e., CPU, memory, IO)
                      notRunnable(3), -- loaded but waiting for event
                      invalid(4)      -- not loaded
                  }
       MAX-ACCESS read-write
       STATUS     current
       DESCRIPTION
           "The status of this running piece of software.
           Setting this value to invalid(4) shall cause this
           software to stop running and to be unloaded. Sets to
           other values are not valid."
       ::= { hrSWRunEntry 7 }

   -- The Host Resources Running Software Performance Group
   --
   -- The hrSWRunPerfTable contains an entry corresponding to
   -- each entry in the hrSWRunTable.

   hrSWRunPerfTable OBJECT-TYPE
       SYNTAX     SEQUENCE OF HrSWRunPerfEntry
       MAX-ACCESS not-accessible
       STATUS     current
       DESCRIPTION
           "The (conceptual) table of running software
           performance metrics."
       ::= { hrSWRunPerf 1 }

   hrSWRunPerfEntry OBJECT-TYPE
       SYNTAX     HrSWRunPerfEntry
       MAX-ACCESS not-accessible
       STATUS     current
       DESCRIPTION
           "A (conceptual) entry containing software performance
           metrics.  As an example, an instance of the
           hrSWRunPerfCPU object might be named
           hrSWRunPerfCPU.1287"
       AUGMENTS { hrSWRunEntry }  -- This table augments information in
                                  -- the hrSWRunTable.
       ::= { hrSWRunPerfTable 1 }

   HrSWRunPerfEntry ::= SEQUENCE {
           hrSWRunPerfCPU          Integer32,


           hrSWRunPerfMem          KBytes
   }

   hrSWRunPerfCPU OBJECT-TYPE
       SYNTAX     Integer32 (0..2147483647)
       MAX-ACCESS read-only
       STATUS     current
       DESCRIPTION
           "The number of centi-seconds of the total system's CPU
           resources consumed by this process.  Note that on a
           multi-processor system, this value may increment by
           more than one centi-second in one centi-second of real
           (wall clock) time."
       ::= { hrSWRunPerfEntry 1 }

   hrSWRunPerfMem OBJECT-TYPE
       SYNTAX     KBytes
       UNITS      "KBytes"
       MAX-ACCESS read-only
       STATUS     current
       DESCRIPTION
           "The total amount of real system memory allocated to
           this process."
       ::= { hrSWRunPerfEntry 2 }

   -- The Host Resources Installed Software Group
   --
   -- The hrSWInstalledTable contains an entry for each piece
   -- of software installed in long-term storage (e.g. a disk
   -- drive) locally on this host.  Note that this does not
   -- include software loadable remotely from a network
   -- server.
   --
   -- Different implementations may track software in varying
   -- ways. For example, while some implementations may track
   -- executable files as distinct pieces of software, other
   -- implementations may use other strategies such as keeping
   -- track of software "packages" (e.g., related groups of files)
   -- or keeping track of system or application "patches".
   --
   -- This table is useful for identifying and inventorying
   -- software on a host and for diagnosing incompatibility
   -- and version mismatch problems between various pieces
   -- of hardware and software.

   hrSWInstalledLastChange OBJECT-TYPE
       SYNTAX     TimeTicks
       MAX-ACCESS read-only


       STATUS     current
       DESCRIPTION
           "The value of sysUpTime when an entry in the
           hrSWInstalledTable was last added, renamed, or
           deleted.  Because this table is likely to contain many
           entries, polling of this object allows a management
           station to determine when re-downloading of the table
           might be useful."
       ::= { hrSWInstalled 1 }

   hrSWInstalledLastUpdateTime OBJECT-TYPE
       SYNTAX     TimeTicks
       MAX-ACCESS read-only
       STATUS     current
       DESCRIPTION
           "The value of sysUpTime when the hrSWInstalledTable
           was last completely updated.  Because caching of this
           data will be a popular implementation strategy,
           retrieval of this object allows a management station
           to obtain a guarantee that no data in this table is
           older than the indicated time."
       ::= { hrSWInstalled 2 }

   hrSWInstalledTable OBJECT-TYPE
       SYNTAX     SEQUENCE OF HrSWInstalledEntry
       MAX-ACCESS not-accessible
       STATUS     current
       DESCRIPTION
           "The (conceptual) table of software installed on this
           host."
       ::= { hrSWInstalled 3 }

   hrSWInstalledEntry OBJECT-TYPE
       SYNTAX     HrSWInstalledEntry
       MAX-ACCESS not-accessible
       STATUS     current
       DESCRIPTION
           "A (conceptual) entry for a piece of software
           installed on this host.

           As an example of how objects in this table are named,
           an instance of the hrSWInstalledName object might be
           named hrSWInstalledName.96"
       INDEX { hrSWInstalledIndex }
       ::= { hrSWInstalledTable 1 }

   HrSWInstalledEntry ::= SEQUENCE {
           hrSWInstalledIndex       Integer32,


           hrSWInstalledName        InternationalDisplayString,
           hrSWInstalledID          ProductID,
           hrSWInstalledType        INTEGER,
           hrSWInstalledDate        DateAndTime
   }

   hrSWInstalledIndex OBJECT-TYPE
       SYNTAX     Integer32 (1..2147483647)
       MAX-ACCESS read-only
       STATUS     current
       DESCRIPTION
           "A unique value for each piece of software installed
           on the host.  This value shall be in the range from 1
           to the number of pieces of software installed on the
           host."
       ::= { hrSWInstalledEntry 1 }

   hrSWInstalledName OBJECT-TYPE
       SYNTAX     InternationalDisplayString (SIZE (0..64))
       MAX-ACCESS read-only
       STATUS     current
       DESCRIPTION
           "A textual description of this installed piece of
           software, including the manufacturer, revision, the
           name by which it is commonly known, and optionally,
           its serial number."
       ::= { hrSWInstalledEntry 2 }

   hrSWInstalledID OBJECT-TYPE
       SYNTAX     ProductID
       MAX-ACCESS read-only
       STATUS     current
       DESCRIPTION
           "The product ID of this installed piece of software."
       ::= { hrSWInstalledEntry 3 }

   hrSWInstalledType OBJECT-TYPE
       SYNTAX     INTEGER {
                      unknown(1),
                      operatingSystem(2),
                      deviceDriver(3),
                      application(4)
                  }
       MAX-ACCESS read-only
       STATUS     current
       DESCRIPTION
           "The type of this software."
       ::= { hrSWInstalledEntry 4 }


   hrSWInstalledDate OBJECT-TYPE
       SYNTAX     DateAndTime
       MAX-ACCESS read-only
       STATUS     current
       DESCRIPTION
           "The last-modification date of this application as it
           would appear in a directory listing.

           If this information is not known, then this variable
           shall have the value corresponding to January 1, year
           0000, 00:00:00.0, which is encoded as
           (hex)'00 00 01 01 00 00 00 00'."
       ::= { hrSWInstalledEntry 5 }

   -- Conformance information

   hrMIBCompliances OBJECT IDENTIFIER ::= { hrMIBAdminInfo 2 }
   hrMIBGroups      OBJECT IDENTIFIER ::= { hrMIBAdminInfo 3 }

   -- Compliance Statements
   hrMIBCompliance MODULE-COMPLIANCE
       STATUS current
       DESCRIPTION
           "The requirements for conformance to the Host Resources MIB."
       MODULE -- this module
         MANDATORY-GROUPS { hrSystemGroup, hrStorageGroup,
                            hrDeviceGroup }

         OBJECT hrSystemDate
             MIN-ACCESS read-only
             DESCRIPTION
                 "Write access is not required."

         OBJECT hrSystemInitialLoadDevice
             MIN-ACCESS read-only
             DESCRIPTION
                 "Write access is not required."

         OBJECT hrSystemInitialLoadParameters
             MIN-ACCESS read-only
             DESCRIPTION
                 "Write access is not required."

         OBJECT hrStorageSize
             MIN-ACCESS read-only
             DESCRIPTION
                 "Write access is not required."


         OBJECT hrFSLastFullBackupDate
             MIN-ACCESS read-only
             DESCRIPTION
                 "Write access is not required."

         OBJECT hrFSLastPartialBackupDate
             MIN-ACCESS read-only
             DESCRIPTION
                 "Write access is not required."

         GROUP hrSWRunGroup
             DESCRIPTION
                 "The Running Software Group. Implementation
                 of this group is mandatory only when the
                 hrSWRunPerfGroup is implemented."

         OBJECT hrSWRunStatus
             MIN-ACCESS read-only
             DESCRIPTION
                 "Write access is not required."

         GROUP hrSWRunPerfGroup
             DESCRIPTION
                 "The Running Software Performance Group.
                 Implementation of this group is at the discretion
                 of the implementor."

         GROUP hrSWInstalledGroup
             DESCRIPTION
                 "The Installed Software Group.
                 Implementation of this group is at the discretion
                 of the implementor."

       ::= { hrMIBCompliances 1 }

       hrSystemGroup OBJECT-GROUP
           OBJECTS {
               hrSystemUptime, hrSystemDate,
               hrSystemInitialLoadDevice,
               hrSystemInitialLoadParameters,
               hrSystemNumUsers, hrSystemProcesses,
               hrSystemMaxProcesses
           }
           STATUS current
           DESCRIPTION
               "The Host Resources System Group."
           ::= { hrMIBGroups 1 }


       hrStorageGroup OBJECT-GROUP
           OBJECTS {
               hrMemorySize, hrStorageIndex, hrStorageType,
               hrStorageDescr, hrStorageAllocationUnits,
               hrStorageSize, hrStorageUsed,
               hrStorageAllocationFailures
           }
           STATUS current
           DESCRIPTION
               "The Host Resources Storage Group."
           ::= { hrMIBGroups 2 }

       hrDeviceGroup OBJECT-GROUP
           OBJECTS {
               hrDeviceIndex, hrDeviceType, hrDeviceDescr,
               hrDeviceID, hrDeviceStatus, hrDeviceErrors,
               hrProcessorFrwID, hrProcessorLoad,
               hrNetworkIfIndex, hrPrinterStatus,
               hrPrinterDetectedErrorState,
               hrDiskStorageAccess, hrDiskStorageMedia,
               hrDiskStorageRemoveble, hrDiskStorageCapacity,
               hrPartitionIndex, hrPartitionLabel,
               hrPartitionID, hrPartitionSize,
               hrPartitionFSIndex, hrFSIndex, hrFSMountPoint,
               hrFSRemoteMountPoint, hrFSType, hrFSAccess,
               hrFSBootable, hrFSStorageIndex,
               hrFSLastFullBackupDate,
               hrFSLastPartialBackupDate
           }
           STATUS current
           DESCRIPTION
               "The Host Resources Device Group."
           ::= { hrMIBGroups 3 }

       hrSWRunGroup OBJECT-GROUP
           OBJECTS {
               hrSWOSIndex, hrSWRunIndex, hrSWRunName,
               hrSWRunID, hrSWRunPath, hrSWRunParameters,
               hrSWRunType, hrSWRunStatus
           }
           STATUS current
           DESCRIPTION
               "The Host Resources Running Software Group."
           ::= { hrMIBGroups 4 }

       hrSWRunPerfGroup OBJECT-GROUP
           OBJECTS { hrSWRunPerfCPU, hrSWRunPerfMem }
           STATUS current


           DESCRIPTION
               "The Host Resources Running Software
               Performance Group."
           ::= { hrMIBGroups 5 }

       hrSWInstalledGroup OBJECT-GROUP
           OBJECTS {
               hrSWInstalledLastChange,
               hrSWInstalledLastUpdateTime,
               hrSWInstalledIndex, hrSWInstalledName,
               hrSWInstalledID, hrSWInstalledType,
               hrSWInstalledDate
           }
           STATUS current
           DESCRIPTION
               "The Host Resources Installed Software Group."
           ::= { hrMIBGroups 6 }

END

ATM-FORUM-SNMP-M4-MIB DEFINITIONS ::= BEGIN

IMPORTS
     MODULE-IDENTITY, OBJECT-TYPE,
     NOTIFICATION-TYPE, OBJECT-IDENTITY,
     Integer32, IpAddress, Gauge32,
     Unsigned32, enterprises            FROM SNMPv2-SMI
     TEXTUAL-CONVENTION, DisplayString,
     AutonomousType, RowStatus,
     TestAndIncr, RowPointer,
     TruthValue, TimeStamp,
     DateAndTime, TimeInterval          FROM SNMPv2-TC
     MODULE-COMPLIANCE, OBJECT-GROUP,
     NOTIFICATION-GROUP                 FROM SNMPv2-CONF
     ifIndex, ifOperStatus, OwnerString FROM IF-MIB
     atmVplEntry, atmVplVpi,
     atmVplOperStatus,
     atmVclEntry, atmVclVpi, atmVclVci,
     atmVclOperStatus,
     atmVpCrossConnectEntry,
     atmVpCrossConnectL2HOperStatus,
     atmVpCrossConnectH2LOperStatus,
     atmVcCrossConnectEntry,
     atmVcCrossConnectL2HOperStatus,
     atmVcCrossConnectH2LOperStatus     FROM ATM-MIB
     entPhysicalIndex, entPhysicalClass,
     entPhysicalContainedIn,
     entPhysicalParentRelPos
                                        FROM ENTITY-MIB
     hrSWInstalledIndex,
     hrSWInstalledName                  FROM HOST-RESOURCES-MIB;


atmfM4MIB MODULE-IDENTITY
     LAST-UPDATED   "9805140000Z"
     ORGANIZATION   "The ATM Forum"
     CONTACT-INFO
           "The ATM Forum
            2570 West El Camino Real, Suite 304
            Mountain View, CA 94040-1313 USA
            Phone: +1 415-949-6700
            Fax:   +1 415-949-6705
            info@atmforum.com"
     DESCRIPTION
           "This MIB module is the SNMP version of the ATM Forum's
            M4 interface (network element view)."
     REVISION   "9805140000Z"
     DESCRIPTION
           "Initial version of MIB module ATM-FORUM-SNMP-M4-MIB."
    ::= { atmfM4SnmpNEView 1 }

atmForum                OBJECT IDENTIFIER ::= { enterprises 353 }
atmForumNetworkManagement    OBJECT IDENTIFIER ::= { atmForum 5 }
atmfM4      OBJECT IDENTIFIER ::= { atmForumNetworkManagement 1 }
atmfM4SnmpNEView               OBJECT IDENTIFIER ::= { atmfM4 3 }

atmfM4MIBObjects    OBJECT IDENTIFIER ::= { atmfM4MIB 1 }
atmfM4MIBTraps      OBJECT IDENTIFIER ::= { atmfM4MIB 2 }
atmfM4MIBTrapPrefix OBJECT IDENTIFIER ::= { atmfM4MIBTraps 0 }
atmfM4MIBConformance OBJECT IDENTIFIER ::= { atmfM4MIB 3 }

--   This MIB module consists of the following groups:
--        (1)   ATM NE High-Level Objects
--        (2)   Interfaces: Physical Path Termination Point Table
--        (3)   TC Adapter Table
--        (4)   ATM Cell Layer Interface Table
--        (5)   VPL Termination Point Table Extensions
--        (6)   VCL Termination Point Table Extensions
--        (7)   VP Cross-Connect Table Extensions
--        (8)   VC Cross-Connect Table Extensions
--        (9)   VP 'next VPI' Table
--        (10)  VC 'next VCI' Table
--        (11)  ATM Cell Protocol Monitoring Current Data Table
--        (12)  ATM Cell Protocol Monitoring History Data Table
--        (13)  ATM Cell Protocol Monitoring Error Log Table
--        (14)  TC Adapter Protocol Monitoring Current Data Table
--        (15)  TC Adapter Protocol Monitoring History Data Table
--        (16)  VPL UPC/NPC Disagreement Monitoring Current Data Table
--        (17)  VPL UPC/NPC Disagreement Monitoring History Data Table
--        (18)  VCL UPC/NPC Disagreement Monitoring Current Data Table
--        (19)  VCL UPC/NPC Disagreement Monitoring History Data Table
--        (20)  OAM Loopback Test Definitions
--        (21)  VPL/VPC Termination Point Test Table
--        (22)  VCL/VCC Termination Point Test Table
--        (23)  Equipment Table extension
--        (24)  Equipment Holder Table extension
--        (25)  Plug-In Unit Table extension
--        (26)  Hardware Unit/Running Software Relationship Table
--        (27)  Hardware Unit/Installed Software Relationship Table
--        (28)  Alarm Forwarding Discriminator Table
--        (29)  Trap Log Table
--        (30)  Trap Log Entry Table
--        (31)  Alarm Trap Log Entry Table extension
--        (32)  Notifications (traps)
--        (33)  Conformance statements


-- ATM Forum M4 ATM network element (NE) high-level objects

atmfM4NeVendor OBJECT-TYPE
     SYNTAX    DisplayString
     MAX-ACCESS     read-only
     STATUS    current
     DESCRIPTION
          "The vendor of the ATM network element."
     ::= { atmfM4MIBObjects 1 }

atmfM4NeVersion OBJECT-TYPE
     SYNTAX    AutonomousType
     MAX-ACCESS     read-only
     STATUS    current
     DESCRIPTION
          "The version of the ATM network element."
     ::= { atmfM4MIBObjects 2 }

atmfM4NeStartTime OBJECT-TYPE
     SYNTAX    DateAndTime
     MAX-ACCESS     read-only
     STATUS    current
     DESCRIPTION
          "The time at which the agent was last started; in other
          words, the time at which sysUpTime was zero."
     ::= { atmfM4MIBObjects 3 }

atmfM4NeAlarmSeverityIndex OBJECT-TYPE
     SYNTAX    Integer32
     MAX-ACCESS     read-write
     STATUS    current
     DESCRIPTION
          "An index into the alarm severity profile table, specifying
          the severity assignments for M4 alarms reported for the
          ATM network element.  The default value for this object is
          zero."
     ::= { atmfM4MIBObjects 4 }

atmfM4NeSuppressZeroStats OBJECT-TYPE
     SYNTAX    TruthValue
     MAX-ACCESS     read-write
     STATUS    current
     DESCRIPTION
          "When the value of this object is true, no entry will be
          created in any of the historical statistics tables for
          intervals in which all counts are zero.  The default value for
          this object is true(1)."
     ::= { atmfM4MIBObjects 5 }


-- ATM Forum M4 Interface Configuration Table Extensions
-- Physical Path Termination Point Layer

atmfM4PhysPathTpTable OBJECT-TYPE
     SYNTAX    SEQUENCE OF    AtmfM4PhysPathTpEntry
     MAX-ACCESS     not-accessible
     STATUS    current
     DESCRIPTION
          "The ATM Forum M4 interface Configuration table extensions
          for the physical path termination point."
     ::= { atmfM4MIBObjects 6 }

atmfM4PhysPathTpEntry OBJECT-TYPE
     SYNTAX    AtmfM4PhysPathTpEntry
     MAX-ACCESS     not-accessible
     STATUS    current
     DESCRIPTION
          "Columns conceptually added to the interface table
          entry for an ATM interface to model the physical path
          termination point.

          The row of the interface table modeling this object should
          also include columns for the TC Adapter object and the ATM
          interface table defined in RFC 1695.

          The interface table entry for the physical path TP
          fields of an ATM interface are set up without management
          system control (or else that setup is outside the
          scope of M4)."
     INDEX          { ifIndex }
     ::= { atmfM4PhysPathTpTable 1 }

AtmfM4PhysPathTpEntry ::= SEQUENCE {
     atmfM4PhysPathTpHwUnitIndex         Integer32,
     atmfM4PhysPathTpPortID              Integer32,
     atmfM4PhysPathTpAlarmSeverityIndex  Integer32
          }

atmfM4PhysPathTpHwUnitIndex OBJECT-TYPE
     SYNTAX    Integer32 (1..2147483647)
     MAX-ACCESS     read-only
     STATUS    current
     DESCRIPTION
          "Specifies the index of the entry in the entPhysicalTable
          that represents the device (i.e., card) on which the
          physical path terminates."
     ::= { atmfM4PhysPathTpEntry 1 }

atmfM4PhysPathTpPortID OBJECT-TYPE
     SYNTAX    Integer32 (1..2147483647)
     MAX-ACCESS     read-only
     STATUS    current
     DESCRIPTION
          "Identifies the port (within the card identified by the
          hardware unit index) on which the physical path terminates."
     ::= { atmfM4PhysPathTpEntry 2 }

atmfM4PhysPathTpAlarmSeverityIndex OBJECT-TYPE
     SYNTAX    Integer32
     MAX-ACCESS     read-write
     STATUS    current
     DESCRIPTION
          "Specifies the index of the entry in the communications
          alarm severity profile table that should be used.  The default
          value of this object is zero."
     ::= { atmfM4PhysPathTpEntry 3 }


-- ATM Forum M4 Interface Configuration Table Extensions
-- TC Adapter Layer

atmfM4TcAdapterTable OBJECT-TYPE
     SYNTAX    SEQUENCE OF    AtmfM4TcAdapterEntry
     MAX-ACCESS     not-accessible
     STATUS    current
     DESCRIPTION
          "The ATM Forum M4 interface Configuration table extensions
          for the TC Adapter."
     ::= { atmfM4MIBObjects 7 }

atmfM4TcAdapterEntry OBJECT-TYPE
     SYNTAX    AtmfM4TcAdapterEntry
     MAX-ACCESS     not-accessible
     STATUS    current
     DESCRIPTION
          "Columns conceptually added to the interface table
          entry for an ATM interface to model the TC Adapter.

          The row of the interface table modeling this object should
          also include columns for the physical path TP and the ATM
          interface table defined in RFC 1695.

          The interface table entry for the TC Adapter
          fields of an ATM interface are set up without management
          system control (or else that setup is outside the
          scope of M4)."
     INDEX          { ifIndex }
     ::= { atmfM4TcAdapterTable 1 }

AtmfM4TcAdapterEntry ::= SEQUENCE {
     atmfM4TcACellScrambling       TruthValue,
     atmfM4TcAlarmSeverityIndex    Integer32
          }

atmfM4TcACellScrambling OBJECT-TYPE
     SYNTAX    TruthValue
     MAX-ACCESS     read-write
     STATUS    current
     DESCRIPTION
          "This attribute is used by the management system to
          activate and deactivate the ATM cell scrambling function.
          When the value of this attribute is TRUE, cell scrambling
          on the interface is activated.

          This attribute shall be present only for interfaces that
          support the deactivation of cell scrambling.  The ATM Forum
          UNI specification requires cell scrambling for ATM/SONET
          interfaces but allows cell scrambling to be controlled
          (i.e., turned on and off) for ATM/DS3 interfaces.

          The default value of this object is true(1)."
     ::= { atmfM4TcAdapterEntry 1 }

atmfM4TcAlarmSeverityIndex OBJECT-TYPE
     SYNTAX    Integer32
     MAX-ACCESS     read-write
     STATUS    current
     DESCRIPTION
          "Specifies the index of the entry in the communications
          alarm severity profile table that should be used.  The
          default value of this object is zero."
     ::= { atmfM4TcAdapterEntry 2 }


-- ATM Forum M4 Interface Configuration Table Extensions
-- ATM Cell Layer

atmfM4AtmLayerTable OBJECT-TYPE
     SYNTAX    SEQUENCE OF    AtmfM4AtmLayerEntry
     MAX-ACCESS     not-accessible
     STATUS    current
     DESCRIPTION
          "The ATM Forum M4 interface Configuration table extensions
          for the ATM cell layer."
     ::= { atmfM4MIBObjects 8 }

atmfM4AtmLayerEntry OBJECT-TYPE
     SYNTAX    AtmfM4AtmLayerEntry
     MAX-ACCESS     not-accessible
     STATUS    current
     DESCRIPTION
          "Columns conceptually added to the interface table
          entry for an ATM interface to model the ATM cell layer.
          The row of the interface table modeling this object should
          also include columns for the physical path TP and TC Adapter
          object, as well as the ATM interface table defined in
          RFC 1695.

          The default configuration of an entry in this table is
          used whenever the entries for the physical path TP, etc.,
          are created.  The management system configures a UNI,
          B-ICI, or B-ISSI on the interface by first modifying the
          atmfM4IfType column (this can be done in the same SNMP
          set-request that sets up the other necessary variables."
     INDEX          { ifIndex }
     ::= { atmfM4AtmLayerTable 1 }

AtmfM4AtmLayerEntry ::= SEQUENCE {
     atmfM4IfType                  INTEGER,
     atmfM4IfLoopbackLocationCode  Integer32,
     atmfM4IfSubscriberAddress     DisplayString,
     atmfM4IfPreferredCarrier      DisplayString,
     atmfM4IfFarEndCarrierNetwork  DisplayString
          }

atmfM4IfType OBJECT-TYPE
     SYNTAX    INTEGER {
                    none(0),
                    uni(1),
                    bici(2),
                    bissi(3)
                         }
     MAX-ACCESS     read-write
     STATUS    current
     DESCRIPTION
          "Specifies the type of ATM cell layer interface defined
          on the physical path termination point modeled by this
          entry in the interface table.  The default value of this
          object is none(0)."
     ::= { atmfM4AtmLayerEntry 1 }

atmfM4IfLoopbackLocationCode OBJECT-TYPE
     SYNTAX    Integer32
     MAX-ACCESS     read-write
     STATUS    current
     DESCRIPTION
          "Specifies the code that shall exist in incoming OAM
          Loopback cells that are to be looped back at this
          interface.

          A value of zero shall indicate that the management system
          has not set any loopback location code for this interface.
          Therefore, zero should not be used as the actual loopback
          location code for any interface.

          This object shall be present only for table entries that
          represent an actual ATM cell layer interface (i.e., the
          atmfM4IfType is not none(0)).

          The default value of this object is zero."
     ::= { atmfM4AtmLayerEntry 2 }

atmfM4IfSubscriberAddress OBJECT-TYPE
     SYNTAX    DisplayString
     MAX-ACCESS     read-write
     STATUS    current
     DESCRIPTION
          "Specifies the address or newline-delimited list of
          addresses assigned to the UNI.

          This object shall be present only for table entries that
          represent a UNI interface.

          The default value of this object is the null string."
     ::= { atmfM4AtmLayerEntry 3 }

atmfM4IfPreferredCarrier OBJECT-TYPE
     SYNTAX    DisplayString
     MAX-ACCESS     read-write
     STATUS    current
     DESCRIPTION
          "Specifies the name of the default carrier to use when one
          is not explicitly identified in the call set-up message.

          This object shall be present only for table entries that
          represent a UNI interface and only when SVC services are
          supported.

          The default value of this object is the null string."
     ::= { atmfM4AtmLayerEntry 4 }

atmfM4IfFarEndCarrierNetwork OBJECT-TYPE
     SYNTAX    DisplayString
     MAX-ACCESS     read-write
     STATUS    current
     DESCRIPTION
          "Specifies the adjacent carrier to which the B-ICI
          transmission path is connected.

          This object shall be present only for table entries that
          represent a B-ICI interface and only when SVC services are
          supported.

          The default value of this object is the null string."
     ::= { atmfM4AtmLayerEntry 5 }




-- ATM Forum M4 VPL Termination Point Configuration Table Extensions

atmfM4VplTable OBJECT-TYPE
     SYNTAX    SEQUENCE OF    AtmfM4VplEntry
     MAX-ACCESS     not-accessible
     STATUS    current
     DESCRIPTION
          "The ATM Forum M4 VPL Termination Point Configuration
          table extensions.  This table augments the VPL
          configuration table in RFC 1695."
     ::= { atmfM4MIBObjects 9 }

atmfM4VplEntry OBJECT-TYPE
     SYNTAX    AtmfM4VplEntry
     MAX-ACCESS     not-accessible
     STATUS    current
     DESCRIPTION
          "Additional columns for the VPL configuration table entry."
     AUGMENTS { atmVplEntry }
     ::= { atmfM4VplTable 1 }

AtmfM4VplEntry ::= SEQUENCE {
     atmfM4VplSegEndPt        TruthValue
          }

atmfM4VplSegEndPt OBJECT-TYPE
     SYNTAX    TruthValue
     MAX-ACCESS     read-create
     STATUS    current
     DESCRIPTION
          "Specifies whether the VPL termination point is a segment
          end-point."
     DEFVAL    { false }
     ::= { atmfM4VplEntry 1 }


-- ATM Forum M4 VCL Termination Point Configuration Table Extensions

atmfM4VclTable OBJECT-TYPE
     SYNTAX    SEQUENCE OF    AtmfM4VclEntry
     MAX-ACCESS     not-accessible
     STATUS    current
     DESCRIPTION
          "The ATM Forum M4 VCL Termination Point Configuration
          table extensions.  This table augments the VCL
          configuration table in RFC 1695."
     ::= { atmfM4MIBObjects 10 }

atmfM4VclEntry OBJECT-TYPE
     SYNTAX    AtmfM4VclEntry
     MAX-ACCESS     not-accessible
     STATUS    current
     DESCRIPTION
          "Additional columns for the VCL configuration table entry."
     AUGMENTS { atmVclEntry }
     ::= { atmfM4VclTable 1 }

AtmfM4VclEntry ::= SEQUENCE {
     atmfM4VclSegEndPt        TruthValue
          }

atmfM4VclSegEndPt OBJECT-TYPE
     SYNTAX    TruthValue
     MAX-ACCESS     read-create
     STATUS    current
     DESCRIPTION
          "Specifies whether the VCL termination point is a segment
          end-point."
     DEFVAL    { false }
     ::= { atmfM4VclEntry 1 }


-- ATM Forum M4 VP Cross-Connect Table Extensions

atmfM4VpXConnTable OBJECT-TYPE
     SYNTAX    SEQUENCE OF    AtmfM4VpXConnEntry
     MAX-ACCESS     not-accessible
     STATUS    current
     DESCRIPTION
          "The ATM Forum M4 VP Cross-Connect Configuration
          table extensions.  This table augments the VP Cross-Connect
          configuration table in RFC 1695."
     ::= { atmfM4MIBObjects 11 }

atmfM4VpXConnEntry OBJECT-TYPE
     SYNTAX    AtmfM4VpXConnEntry
     MAX-ACCESS     not-accessible
     STATUS    current
     DESCRIPTION
          "Additional columns for the VP Cross-Connect table entry."
     AUGMENTS { atmVpCrossConnectEntry }
     ::= { atmfM4VpXConnTable 1 }

AtmfM4VpXConnEntry ::= SEQUENCE {
     atmfM4VpXConnRecover     TruthValue
          }

atmfM4VpXConnRecover OBJECT-TYPE
     SYNTAX    TruthValue
     MAX-ACCESS     read-create
     STATUS    current
     DESCRIPTION
          "If FALSE, this cross-connection will be removed on
          failure."
     DEFVAL    { true }
     ::= { atmfM4VpXConnEntry 1 }


-- ATM Forum M4 VC Cross-Connect Table Extensions

atmfM4VcXConnTable OBJECT-TYPE
     SYNTAX    SEQUENCE OF    AtmfM4VcXConnEntry
     MAX-ACCESS     not-accessible
     STATUS    current
     DESCRIPTION
          "The ATM Forum M4 VC Cross-Connect Configuration
          table extensions.  This table augments the VC Cross-Connect
          configuration table in RFC 1695."
     ::= { atmfM4MIBObjects 12 }

atmfM4VcXConnEntry OBJECT-TYPE
     SYNTAX    AtmfM4VcXConnEntry
     MAX-ACCESS     not-accessible
     STATUS    current
     DESCRIPTION
          "Additional columns for the VC Cross-Connect table entry."
     AUGMENTS { atmVcCrossConnectEntry }
     ::= { atmfM4VcXConnTable 1 }

AtmfM4VcXConnEntry ::= SEQUENCE {
     atmfM4VcXConnRecover     TruthValue
          }

atmfM4VcXConnRecover OBJECT-TYPE
     SYNTAX    TruthValue
     MAX-ACCESS     read-create
     STATUS    current
     DESCRIPTION
          "If FALSE, this cross-connection will be removed on
          failure."
     DEFVAL    { true }
     ::= { atmfM4VcXConnEntry 1 }


-- ATM Forum M4 VP "Next VPI" Table

atmfM4VpNextVpiTable OBJECT-TYPE
     SYNTAX    SEQUENCE OF    AtmfM4VpNextVpiEntry
     MAX-ACCESS     not-accessible
     STATUS    current
     DESCRIPTION
          "The ATM Forum M4 VP Next VPI value table.  This optional
          table supplies unused VPI values for use in creating
          entries in the atmVplTable."
     ::= { atmfM4MIBObjects 13 }

atmfM4VpNextVpiEntry OBJECT-TYPE
     SYNTAX    AtmfM4VpNextVpiEntry
     MAX-ACCESS     not-accessible
     STATUS    current
     DESCRIPTION
          "Each entry in this table represents the 'next' VPI
          value available for a given ATM interface.

          Each ATM interface (UNI, BICI, BISSI) automatically has
          an entry in this table associated with it."
     INDEX          { ifIndex }
     ::= { atmfM4VpNextVpiTable 1 }

AtmfM4VpNextVpiEntry ::= SEQUENCE {
     atmfM4VpNextVpiValue     INTEGER
          }

atmfM4VpNextVpiValue OBJECT-TYPE
     SYNTAX    INTEGER (-1..4095)
     MAX-ACCESS     read-only
     STATUS    current
     DESCRIPTION
          "This object contains an appropriate value to be used for
          atmVplVpi when creating entries in the atmVplTable.  The
          value -1 indicates that no unassigned entries are available.
          To obtain the atmVplVpi value for a new entry, the manager
          issues a management protocol retrieval operation to obtain
          the current value of this object.  After each retrieval, the
          agent should modify the value to the next unassigned index
          (or -1)."
     ::= { atmfM4VpNextVpiEntry 1 }


-- ATM Forum M4 VC "Next VCI" Table

atmfM4VcNextVciTable OBJECT-TYPE
     SYNTAX    SEQUENCE OF    AtmfM4VcNextVciEntry
     MAX-ACCESS     not-accessible
     STATUS    current
     DESCRIPTION
          "The ATM Forum M4 VC Next VCI value table.  This optional
          table supplies unused VCI values for use in creating
          entries in the atmVclTable."
     ::= { atmfM4MIBObjects 14 }

atmfM4VcNextVciEntry OBJECT-TYPE
     SYNTAX    AtmfM4VcNextVciEntry
     MAX-ACCESS     not-accessible
     STATUS    current
     DESCRIPTION
          "Each entry in this table represents the 'next' VCI
          value available for a given ATM interface.

          Each VPL Termination Point automatically has
          an entry in this table associated with it."
     INDEX          { ifIndex,
                    atmVplVpi }
     ::= { atmfM4VcNextVciTable 1 }

AtmfM4VcNextVciEntry ::= SEQUENCE {
     atmfM4VcNextVciValue     INTEGER
          }

atmfM4VcNextVciValue OBJECT-TYPE
     SYNTAX    INTEGER (-1..65535)
     MAX-ACCESS     read-only
     STATUS    current
     DESCRIPTION
          "This object contains an appropriate value to be used for
          atmVclVci when creating entries in the atmVclTable.  The
          value -1 indicates that no unassigned entries are available.
          To obtain the atmVclVci value for a new entry, the manager
          issues a management protocol retrieval operation to obtain
          the current value of this object.  After each retrieval, the
          agent should modify the value to the next unassigned index
          (or -1)."
     ::= { atmfM4VcNextVciEntry 1 }


-- ATM Cell Protocol Monitoring Current Data (per interface)

atmfM4CellProtoCurrTable OBJECT-TYPE
     SYNTAX    SEQUENCE OF    AtmfM4CellProtoCurrEntry
     MAX-ACCESS     not-accessible
     STATUS    current
     DESCRIPTION
          "The ATM Forum M4 Cell Protocol Monitoring Current Data
          table.

          This table maintains per-interface statistics for the
          fifteen-minute interval currently being collected."
     ::= { atmfM4MIBObjects 15 }

atmfM4CellProtoCurrEntry OBJECT-TYPE
     SYNTAX    AtmfM4CellProtoCurrEntry
     MAX-ACCESS     not-accessible
     STATUS    current
     DESCRIPTION
          "An entry in the ATM Forum M4 Cell Protocol Monitoring
          Current Data table.

          Each ATM interface (UNI, BICI, BISSI) automatically has
          an entry in this table associated with it."
     INDEX          { ifIndex }
     ::= { atmfM4CellProtoCurrTable 1 }

AtmfM4CellProtoCurrEntry ::= SEQUENCE {
     atmfM4CellProtoCurrSuspect         TruthValue,
     atmfM4CellProtoCurrElapsedTime     TimeInterval,
     atmfM4CellProtoCurrSupprIntvls     Gauge32,
     atmfM4CellProtoCurrProtoErrors     Gauge32,
     atmfM4CellProtoCurrInOAMCells      Gauge32
          }

atmfM4CellProtoCurrSuspect OBJECT-TYPE
     SYNTAX    TruthValue
     MAX-ACCESS     read-only
     STATUS    current
     DESCRIPTION
          "If true, the statistics in this entry may be unreliable."
     ::= { atmfM4CellProtoCurrEntry 1 }

atmfM4CellProtoCurrElapsedTime OBJECT-TYPE
     SYNTAX    TimeInterval
     MAX-ACCESS     read-only
     STATUS    current
     DESCRIPTION
          "Amount of time, measured in units of 0.01 second, that
          statistics for this entry (the current interval) have been
          counted."
     ::= { atmfM4CellProtoCurrEntry 2 }

atmfM4CellProtoCurrSupprIntvls OBJECT-TYPE
     SYNTAX    Gauge32
     MAX-ACCESS     read-only
     STATUS    current
     DESCRIPTION
          "This attribute is non-zero only if the ATM NE is
          suppressing ATM Cell Protocol Monitoring History Data
          entry creation when the current interval terminates with
          'all-zeroes' performance measurements.

          When non-zero, this attribute represents the number of
          'all-zeroes' intervals that were suppressed immediately
          prior to the current interval.

          Note that the suppression of 'all-zeroes' intervals is
          controlled by the atmfM4NeSuppressZeroStats object."
     ::= { atmfM4CellProtoCurrEntry 3 }

atmfM4CellProtoCurrProtoErrors OBJECT-TYPE
     SYNTAX    Gauge32
     MAX-ACCESS     read-only
     STATUS    current
     DESCRIPTION
          "The number of ATM cells dropped on this interface, due to
          an unrecognized field or set of fields in the ATM cell
          header, since the start of this interval."
     ::= { atmfM4CellProtoCurrEntry 4 }

atmfM4CellProtoCurrInOAMCells OBJECT-TYPE
     SYNTAX    Gauge32
     MAX-ACCESS     read-only
     STATUS    current
     DESCRIPTION
          "The number of OAM cells received at this interface since
          the start of this interval."
     ::= { atmfM4CellProtoCurrEntry 5 }


-- ATM Cell Protocol Monitoring History Data (per interface and time
-- interval)

atmfM4CellProtoHistTable OBJECT-TYPE
     SYNTAX    SEQUENCE OF    AtmfM4CellProtoHistEntry
     MAX-ACCESS     not-accessible
     STATUS    current
     DESCRIPTION
          "The ATM Forum M4 Cell Protocol Monitoring History Data
          table.

          This table maintains per-interface statistics for previous
          fifteen-minute intervals."
     ::= { atmfM4MIBObjects 16 }

atmfM4CellProtoHistEntry OBJECT-TYPE
     SYNTAX    AtmfM4CellProtoHistEntry
     MAX-ACCESS     not-accessible
     STATUS    current
     DESCRIPTION
          "An entry in the ATM Forum M4 Cell Protocol Monitoring
          History Data table.

          Each ATM interface (UNI, BICI, BISSI) automatically has
          an entry in this table associated with it for each fifteen-
          minute interval in which statistics are collected for it."
     INDEX          { ifIndex,
                    atmfM4CellProtoHistIndex }
     ::= { atmfM4CellProtoHistTable 1 }


AtmfM4CellProtoHistEntry ::= SEQUENCE {
     atmfM4CellProtoHistIndex           INTEGER,
     atmfM4CellProtoHistSuspect         TruthValue,
     atmfM4CellProtoHistElapsedTime     TimeInterval,
     atmfM4CellProtoHistSupprIntvls     Gauge32,
     atmfM4CellProtoHistProtoErrors     Gauge32,
     atmfM4CellProtoHistInOAMCells      Gauge32
          }

atmfM4CellProtoHistIndex OBJECT-TYPE
     SYNTAX    INTEGER (1..96)
     MAX-ACCESS     not-accessible
     STATUS    current
     DESCRIPTION
          "A number between 1 and 96, which identifies the interval
          for which the set of statistics in this entry was
          collected.

          The interval identified by 1 is the most recently completed
          15 minute interval, and the interval identified by N is the
          interval immediately preceding the one identified by N-1."
     ::= { atmfM4CellProtoHistEntry 1 }

atmfM4CellProtoHistSuspect OBJECT-TYPE
     SYNTAX    TruthValue
     MAX-ACCESS     read-only
     STATUS    current
     DESCRIPTION
          "If true, the statistics in this entry may be unreliable."
     ::= { atmfM4CellProtoHistEntry 2 }

atmfM4CellProtoHistElapsedTime OBJECT-TYPE
     SYNTAX    TimeInterval
     MAX-ACCESS     read-only
     STATUS    current
     DESCRIPTION
          "Amount of time, measured in units of 0.01 second, that
          statistics for this entry (the current interval) have been
          counted."
     ::= { atmfM4CellProtoHistEntry 3 }

atmfM4CellProtoHistSupprIntvls OBJECT-TYPE
     SYNTAX    Gauge32
     MAX-ACCESS     read-only
     STATUS    current
     DESCRIPTION
          "This attribute is non-zero only if the ATM NE is
          suppressing ATM Cell Protocol Monitoring History Data
          entry creation when the current interval terminates with
          'all-zeroes' performance measurements.

          When non-zero, this attribute represents the number of
          'all-zeroes' intervals that were suppressed immediately
          prior to this 'non-all-zeroes' history interval.

          Note that the suppression of 'all-zeroes' intervals is
          controlled by the atmfM4NeSuppressZeroStats object."
     ::= { atmfM4CellProtoHistEntry 4 }

atmfM4CellProtoHistProtoErrors OBJECT-TYPE
     SYNTAX    Gauge32
     MAX-ACCESS     read-only
     STATUS    current
     DESCRIPTION
          "The number of ATM cells dropped on this interface, due to
          an unrecognized field or set of fields in the ATM cell
          header, during this interval."
     ::= { atmfM4CellProtoHistEntry 5 }

atmfM4CellProtoHistInOAMCells OBJECT-TYPE
     SYNTAX    Gauge32
     MAX-ACCESS     read-only
     STATUS    current
     DESCRIPTION
          "The number of OAM cells received at this interface during
          this interval."
     ::= { atmfM4CellProtoHistEntry 6 }


-- ATM Cell Protocol Monitoring Error Log (per interface, error code)

atmfM4CellProtoErrorTable OBJECT-TYPE
     SYNTAX    SEQUENCE OF    AtmfM4CellProtoErrorEntry
     MAX-ACCESS     not-accessible
     STATUS    current
     DESCRIPTION
          "The ATM Forum M4 Cell Protocol Monitoring Error Log
          table.

          This table maintains a record of the last error of each
          type encountered on each interface, as a result of ATM
          Cell Protocol Monitoring."
     ::= { atmfM4MIBObjects 17 }

atmfM4CellProtoErrorEntry OBJECT-TYPE
     SYNTAX    AtmfM4CellProtoErrorEntry
     MAX-ACCESS     not-accessible
     STATUS    current
     DESCRIPTION
          "An entry in the ATM Forum M4 Cell Protocol Monitoring
          Error Log table.

          Each ATM interface (UNI, BICI, BISSI) automatically has
          an entry in this table associated with it for each error
          that has occurred since agent start-up."
     INDEX          { ifIndex,
                    atmfM4CellProtoErrorCode }
     ::= { atmfM4CellProtoErrorTable 1 }

AtmfM4CellProtoErrorEntry ::= SEQUENCE {
     atmfM4CellProtoErrorCode      Integer32,
     atmfM4CellProtoErrorTime      TimeStamp,
     atmfM4CellProtoErrorReason    INTEGER,
     atmfM4CellProtoErrorVpi       INTEGER,
     atmfM4CellProtoErrorVci       INTEGER
          }

atmfM4CellProtoErrorCode OBJECT-TYPE
     SYNTAX    Integer32 (0..2147483647)
     MAX-ACCESS     not-accessible
     STATUS    current
     DESCRIPTION
          "Indicates the type of error for which this entry contains
          information.  The range and interpretation of this error
          code value is left up to the individual agent implementor."
     ::= { atmfM4CellProtoErrorEntry 1 }

atmfM4CellProtoErrorTime OBJECT-TYPE
     SYNTAX    TimeStamp
     MAX-ACCESS     read-only
     STATUS    current
     DESCRIPTION
          "Value of sysUpTime when the error occurred."
     ::= { atmfM4CellProtoErrorEntry 2 }

atmfM4CellProtoErrorReason OBJECT-TYPE
     SYNTAX    INTEGER {
                    unassignedVpiVciValue(1),
                    outOfRangeVpiVciValue(2)
                         }
     MAX-ACCESS     read-only
     STATUS    current
     DESCRIPTION
          "The cell header abnormality type: the reason for discarding
          the ATM cell (i.e., unassigned VPI/VCI value or VPI/VCI
          value out of range)."
     ::= { atmfM4CellProtoErrorEntry 3 }

atmfM4CellProtoErrorVpi OBJECT-TYPE
     SYNTAX    INTEGER (0..4095)
     MAX-ACCESS     read-only
     STATUS    current
     DESCRIPTION
          "The VPI value of the discarded cell."
     ::= { atmfM4CellProtoErrorEntry 4 }

atmfM4CellProtoErrorVci OBJECT-TYPE
     SYNTAX    INTEGER (0..65535)
     MAX-ACCESS     read-only
     STATUS    current
     DESCRIPTION
          "The VCI value of the discarded cell."
     ::= { atmfM4CellProtoErrorEntry 5 }


-- TC Adapter Protocol Monitoring Current Data (per interface)

atmfM4TcProtoCurrTable OBJECT-TYPE
     SYNTAX    SEQUENCE OF    AtmfM4TcProtoCurrEntry
     MAX-ACCESS     not-accessible
     STATUS    current
     DESCRIPTION
          "The ATM Forum M4 TC Adapter Protocol Monitoring Current
          Data table.

          This table maintains per-interface statistics for the
          fifteen-minute interval currently being collected."
     ::= { atmfM4MIBObjects 18 }

atmfM4TcProtoCurrEntry OBJECT-TYPE
     SYNTAX    AtmfM4TcProtoCurrEntry
     MAX-ACCESS     not-accessible
     STATUS    current
     DESCRIPTION
          "An entry in the ATM Forum M4 TC Adapter Protocol Monitoring
          Current Data table.

          Each ATM interface (UNI, BICI, BISSI) automatically has
          an entry in this table associated with it."
     INDEX          { ifIndex }
     ::= { atmfM4TcProtoCurrTable 1 }

AtmfM4TcProtoCurrEntry ::= SEQUENCE {
     atmfM4TcProtoCurrSuspect           TruthValue,
     atmfM4TcProtoCurrElapsedTime       TimeInterval,
     atmfM4TcProtoCurrSupprIntvls       Gauge32,
     atmfM4TcProtoCurrDiscardHECViol    Gauge32
          }

atmfM4TcProtoCurrSuspect OBJECT-TYPE
     SYNTAX    TruthValue
     MAX-ACCESS     read-only
     STATUS    current
     DESCRIPTION
          "If true, the statistics in this entry may be unreliable."
     ::= { atmfM4TcProtoCurrEntry 1 }

atmfM4TcProtoCurrElapsedTime OBJECT-TYPE
     SYNTAX    TimeInterval
     MAX-ACCESS     read-only
     STATUS    current
     DESCRIPTION
          "Amount of time, measured in units of 0.01 second, that
          statistics for this entry (the current interval) have been
          counted."
     ::= { atmfM4TcProtoCurrEntry 2 }

atmfM4TcProtoCurrSupprIntvls OBJECT-TYPE
     SYNTAX    Gauge32
     MAX-ACCESS     read-only
     STATUS    current
     DESCRIPTION
          "This attribute is non-zero only if the ATM NE is
          suppressing ATM TC Adapter Protocol Monitoring History Data
          entry creation when the current interval terminates with
          'all-zeroes' performance measurements.

          When non-zero, this attribute represents the number of
          'all-zeroes' intervals that were suppressed immediately
          prior to the current interval.

          Note that the suppression of 'all-zeroes' intervals is
          controlled by the atmfM4NeSuppressZeroStats object."
     ::= { atmfM4TcProtoCurrEntry 3 }

atmfM4TcProtoCurrDiscardHECViol OBJECT-TYPE
     SYNTAX    Gauge32
     MAX-ACCESS     read-only
     STATUS    current
     DESCRIPTION
          "The number of ATM cells discarded on this interface, due to
          a HEC violation, since the start of this interval."
     ::= { atmfM4TcProtoCurrEntry 4 }


-- ATM TC Adapter Protocol Monitoring History Data (per interface and
-- time interval)

atmfM4TcProtoHistTable OBJECT-TYPE
     SYNTAX    SEQUENCE OF    AtmfM4TcProtoHistEntry
     MAX-ACCESS     not-accessible
     STATUS    current
     DESCRIPTION
          "The ATM Forum M4 TC Adapter Protocol Monitoring History
          Data table.

          This table maintains per-interface statistics for previous
          fifteen-minute intervals."
     ::= { atmfM4MIBObjects 19 }

atmfM4TcProtoHistEntry OBJECT-TYPE
     SYNTAX    AtmfM4TcProtoHistEntry
     MAX-ACCESS     not-accessible
     STATUS    current
     DESCRIPTION
          "An entry in the ATM Forum M4 TC Adapter Protocol Monitoring
          History Data table.

          Each ATM interface (UNI, BICI, BISSI) automatically has
          an entry in this table associated with it for each fifteen-
          minute interval in which statistics are collected for it."
     INDEX          { ifIndex,
                    atmfM4TcProtoHistIndex }
     ::= { atmfM4TcProtoHistTable 1 }

AtmfM4TcProtoHistEntry ::= SEQUENCE {
     atmfM4TcProtoHistIndex             INTEGER,
     atmfM4TcProtoHistSuspect           TruthValue,
     atmfM4TcProtoHistElapsedTime       TimeInterval,
     atmfM4TcProtoHistSupprIntvls       Gauge32,
     atmfM4TcProtoHistDiscardHECViol    Gauge32
          }

atmfM4TcProtoHistIndex OBJECT-TYPE
     SYNTAX    INTEGER (1..96)
     MAX-ACCESS     not-accessible
     STATUS    current
     DESCRIPTION
          "A number between 1 and 96, which identifies the interval
          for which the set of statistics in this entry was
          collected.

          The interval identified by 1 is the most recently completed
          15 minute interval, and the interval identified by N is the
          interval immediately preceding the one identified by N-1."
     ::= { atmfM4TcProtoHistEntry 1 }

atmfM4TcProtoHistSuspect OBJECT-TYPE
     SYNTAX    TruthValue
     MAX-ACCESS     read-only
     STATUS    current
     DESCRIPTION
          "If true, the statistics in this entry may be unreliable."
     ::= { atmfM4TcProtoHistEntry 2 }

atmfM4TcProtoHistElapsedTime OBJECT-TYPE
     SYNTAX    TimeInterval
     MAX-ACCESS     read-only
     STATUS    current
     DESCRIPTION
          "Amount of time, measured in units of 0.01 second, that
          statistics for this entry (the current interval) have been
          counted."
     ::= { atmfM4TcProtoHistEntry 3 }

atmfM4TcProtoHistSupprIntvls OBJECT-TYPE
     SYNTAX    Gauge32
     MAX-ACCESS     read-only
     STATUS    current
     DESCRIPTION
          "This attribute is non-zero only if the ATM NE is
          suppressing ATM Cell Protocol Monitoring History Data
          entry creation when the current interval terminates with
          'all-zeroes' performance measurements.

          When non-zero, this attribute represents the number of
          'all-zeroes' intervals that were suppressed immediately
          prior to this 'non-all-zeroes' history interval.

          Note that the suppression of 'all-zeroes' intervals is
          controlled by the atmfM4NeSuppressZeroStats object."
     ::= { atmfM4TcProtoHistEntry 4 }

atmfM4TcProtoHistDiscardHECViol OBJECT-TYPE
     SYNTAX    Gauge32
     MAX-ACCESS     read-only
     STATUS    current
     DESCRIPTION
          "The number of ATM cells discarded on this interface, due to
          a HEC violation, during this interval."
     ::= { atmfM4TcProtoHistEntry 5 }


-- UPC/NPC Disagreement Monitoring Current Data (per VPL
-- termination point)

atmfM4VpUpcNpcCurrTable OBJECT-TYPE
     SYNTAX    SEQUENCE OF    AtmfM4VpUpcNpcCurrEntry
     MAX-ACCESS     not-accessible
     STATUS    current
     DESCRIPTION
          "The ATM Forum M4 UPC/NPC Disagreement Monitoring Current
          Data table for VPL termination points.

          This table maintains per-TP statistics for the
          fifteen-minute interval currently being collected."
     ::= { atmfM4MIBObjects 20 }

atmfM4VpUpcNpcCurrEntry OBJECT-TYPE
     SYNTAX    AtmfM4VpUpcNpcCurrEntry
     MAX-ACCESS     not-accessible
     STATUS    current
     DESCRIPTION
          "An entry in the ATM Forum M4 UPC/NPC Disagreement
          Monitoring Current Data table for VPL termination points.

          Each VPL Termination Point automatically has
          an entry in this table associated with it."
     INDEX          { ifIndex,
                    atmVplVpi }
     ::= { atmfM4VpUpcNpcCurrTable 1 }

AtmfM4VpUpcNpcCurrEntry ::= SEQUENCE {
     atmfM4VpUpcNpcCurrSuspect          TruthValue,
     atmfM4VpUpcNpcCurrElapsedTime      TimeInterval,
     atmfM4VpUpcNpcCurrSupprIntvls      Gauge32,
     atmfM4VpUpcNpcCurrDiscardedCells   Gauge32,
     atmfM4VpUpcNpcCurrDiscardedClp0    Gauge32,
     atmfM4VpUpcNpcCurrPassedCells      Gauge32,
     atmfM4VpUpcNpcCurrPassedClp0       Gauge32
          }

atmfM4VpUpcNpcCurrSuspect OBJECT-TYPE
     SYNTAX    TruthValue
     MAX-ACCESS     read-only
     STATUS    current
     DESCRIPTION
          "If true, the statistics in this entry may be unreliable."
     ::= { atmfM4VpUpcNpcCurrEntry 1 }

atmfM4VpUpcNpcCurrElapsedTime OBJECT-TYPE
     SYNTAX    TimeInterval
     MAX-ACCESS     read-only
     STATUS    current
     DESCRIPTION
          "Amount of time, measured in units of 0.01 second, that
          statistics for this entry (the current interval) have been
          counted."
     ::= { atmfM4VpUpcNpcCurrEntry 2 }

atmfM4VpUpcNpcCurrSupprIntvls OBJECT-TYPE
     SYNTAX    Gauge32
     MAX-ACCESS     read-only
     STATUS    current
     DESCRIPTION
          "This attribute is non-zero only if the ATM NE is
          suppressing UPC/NPC Disagreement Monitoring History Data
          entry creation when the current interval terminates with
          'all-zeroes' performance measurements.

          When non-zero, this attribute represents the number of
          'all-zeroes' intervals that were suppressed immediately
          prior to the current interval.

          Note that the suppression of 'all-zeroes' intervals is
          controlled by the atmfM4NeSuppressZeroStats object."
     ::= { atmfM4VpUpcNpcCurrEntry 3 }

atmfM4VpUpcNpcCurrDiscardedCells OBJECT-TYPE
     SYNTAX    Gauge32
     MAX-ACCESS     read-only
     STATUS    current
     DESCRIPTION
          "The number of discarded cells due to combined CLP=0 and
          CLP=1 UPC/NPC policing."
     ::= { atmfM4VpUpcNpcCurrEntry 4 }

atmfM4VpUpcNpcCurrDiscardedClp0 OBJECT-TYPE
     SYNTAX    Gauge32
     MAX-ACCESS     read-only
     STATUS    current
     DESCRIPTION
          "The number of discarded CLP=0 cells due to CLP=0 only
          UPC/NPC policing.

          This object shall be present only if CLP=0 traffic is
          separately policed."
     ::= { atmfM4VpUpcNpcCurrEntry 5 }

atmfM4VpUpcNpcCurrPassedCells OBJECT-TYPE
     SYNTAX    Gauge32
     MAX-ACCESS     read-only
     STATUS    current
     DESCRIPTION
          "The number of cells that have been successfully passed by
          the combined CLP=0 and CLP=1 UPC/NPC policing."
     ::= { atmfM4VpUpcNpcCurrEntry 6 }

atmfM4VpUpcNpcCurrPassedClp0 OBJECT-TYPE
     SYNTAX    Gauge32
     MAX-ACCESS     read-only
     STATUS    current
     DESCRIPTION
          "The number of CLP=0 cells that have been successfully
          passed by the CLP=0 UPC/NPC policing.

          This object shall be present only if CLP=0 traffic is
          separately policed."
     ::= { atmfM4VpUpcNpcCurrEntry 7 }


-- UPC/NPC Disagreement Monitoring History (per VPL termination
-- point and time interval)

atmfM4VpUpcNpcHistTable OBJECT-TYPE
     SYNTAX    SEQUENCE OF    AtmfM4VpUpcNpcHistEntry
     MAX-ACCESS     not-accessible
     STATUS    current
     DESCRIPTION
          "The ATM Forum M4 UPC/NPC Disagreement Monitoring History
          Data table for VPL termination points.

          This table maintains per-interface statistics for previous
          fifteen-minute intervals."
     ::= { atmfM4MIBObjects 21 }

atmfM4VpUpcNpcHistEntry OBJECT-TYPE
     SYNTAX    AtmfM4VpUpcNpcHistEntry
     MAX-ACCESS     not-accessible
     STATUS    current
     DESCRIPTION
          "An entry in the ATM Forum M4 UPC/NPC Disagreement
          Monitoring History Data table for VPL termination points.

          Each VPL Termination Point automatically has
          an entry in this table associated with it."
     INDEX          { ifIndex,
                    atmVplVpi,
                    atmfM4VpUpcNpcHistIndex }
     ::= { atmfM4VpUpcNpcHistTable 1 }

AtmfM4VpUpcNpcHistEntry ::= SEQUENCE {
     atmfM4VpUpcNpcHistIndex            INTEGER,
     atmfM4VpUpcNpcHistSuspect          TruthValue,
     atmfM4VpUpcNpcHistElapsedTime      TimeInterval,
     atmfM4VpUpcNpcHistSupprIntvls      Gauge32,
     atmfM4VpUpcNpcHistDiscardedCells   Gauge32,
     atmfM4VpUpcNpcHistDiscardedClp0    Gauge32,
     atmfM4VpUpcNpcHistPassedCells      Gauge32,
     atmfM4VpUpcNpcHistPassedClp0       Gauge32
          }

atmfM4VpUpcNpcHistIndex OBJECT-TYPE
     SYNTAX    INTEGER (1..96)
     MAX-ACCESS     not-accessible
     STATUS    current
     DESCRIPTION
          "A number between 1 and 96, which identifies the interval
          for which the set of statistics in this entry was
          collected.

          The interval identified by 1 is the most recently completed
          15 minute interval, and the interval identified by N is the
          interval immediately preceding the one identified by N-1."
     ::= { atmfM4VpUpcNpcHistEntry 1 }

atmfM4VpUpcNpcHistSuspect OBJECT-TYPE
     SYNTAX    TruthValue
     MAX-ACCESS     read-only
     STATUS    current
     DESCRIPTION
          "If true, the statistics in this entry may be unreliable."
     ::= { atmfM4VpUpcNpcHistEntry 2 }

atmfM4VpUpcNpcHistElapsedTime OBJECT-TYPE
     SYNTAX    TimeInterval
     MAX-ACCESS     read-only
     STATUS    current
     DESCRIPTION
          "Amount of time, measured in units of 0.01 second, that
          statistics for this entry (the current interval) have been
          counted."
     ::= { atmfM4VpUpcNpcHistEntry 3 }

atmfM4VpUpcNpcHistSupprIntvls OBJECT-TYPE
     SYNTAX    Gauge32
     MAX-ACCESS     read-only
     STATUS    current
     DESCRIPTION
          "This attribute is non-zero only if the ATM NE is
          suppressing UPC/NPC Disagreement Monitoring History Data
          entry creation when the current interval terminates with
          'all-zeroes' performance measurements.

          When non-zero, this attribute represents the number of
          'all-zeroes' intervals that were suppressed immediately
          prior to this 'non-all-zeroes' history interval.

          Note that the suppression of 'all-zeroes' intervals is
          controlled by the atmfM4NeSuppressZeroStats object."
     ::= { atmfM4VpUpcNpcHistEntry 4 }

atmfM4VpUpcNpcHistDiscardedCells OBJECT-TYPE
     SYNTAX    Gauge32
     MAX-ACCESS     read-only
     STATUS    current
     DESCRIPTION
          "The number of discarded cells due to combined CLP=0 and
          CLP=1 UPC/NPC policing."
     ::= { atmfM4VpUpcNpcHistEntry 5 }

atmfM4VpUpcNpcHistDiscardedClp0 OBJECT-TYPE
     SYNTAX    Gauge32
     MAX-ACCESS     read-only
     STATUS    current
     DESCRIPTION
          "The number of discarded CLP=0 cells due to CLP=0 only
          UPC/NPC policing.

          This object shall be present only if CLP=0 traffic is
          separately policed."
     ::= { atmfM4VpUpcNpcHistEntry 6 }

atmfM4VpUpcNpcHistPassedCells OBJECT-TYPE
     SYNTAX    Gauge32
     MAX-ACCESS     read-only
     STATUS    current
     DESCRIPTION
          "The number of cells that have been successfully passed by
          the combined CLP=0 and CLP=1 UPC/NPC policing."
     ::= { atmfM4VpUpcNpcHistEntry 7 }

atmfM4VpUpcNpcHistPassedClp0 OBJECT-TYPE
     SYNTAX    Gauge32
     MAX-ACCESS     read-only
     STATUS    current
     DESCRIPTION
          "The number of CLP=0 cells that have been successfully
          passed by the CLP=0 UPC/NPC policing.

          This object shall be present only if CLP=0 traffic is
          separately policed."
     ::= { atmfM4VpUpcNpcHistEntry 8 }



-- UPC/NPC Disagreement Monitoring Current Data (per VCL
-- termination point)

atmfM4VcUpcNpcCurrTable OBJECT-TYPE
     SYNTAX    SEQUENCE OF    AtmfM4VcUpcNpcCurrEntry
     MAX-ACCESS     not-accessible
     STATUS    current
     DESCRIPTION
          "The ATM Forum M4 UPC/NPC Disagreement Monitoring Current
          Data table for VCL termination points.

          This table maintains per-TP statistics for the
          fifteen-minute interval currently being collected."
     ::= { atmfM4MIBObjects 22 }

atmfM4VcUpcNpcCurrEntry OBJECT-TYPE
     SYNTAX    AtmfM4VcUpcNpcCurrEntry
     MAX-ACCESS     not-accessible
     STATUS    current
     DESCRIPTION
          "An entry in the ATM Forum M4 UPC/NPC Disagreement
          Monitoring Current Data table for VCL termination points.

          Each VCL Termination Point automatically has
          an entry in this table associated with it."
     INDEX          { ifIndex,
                    atmVclVpi,
                    atmVclVci }
     ::= { atmfM4VcUpcNpcCurrTable 1 }

AtmfM4VcUpcNpcCurrEntry ::= SEQUENCE {
     atmfM4VcUpcNpcCurrSuspect          TruthValue,
     atmfM4VcUpcNpcCurrElapsedTime      TimeInterval,
     atmfM4VcUpcNpcCurrSupprIntvls      Gauge32,
     atmfM4VcUpcNpcCurrDiscardedCells   Gauge32,
     atmfM4VcUpcNpcCurrDiscardedClp0    Gauge32,
     atmfM4VcUpcNpcCurrPassedCells      Gauge32,
     atmfM4VcUpcNpcCurrPassedClp0       Gauge32
          }

atmfM4VcUpcNpcCurrSuspect OBJECT-TYPE
     SYNTAX    TruthValue
     MAX-ACCESS     read-only
     STATUS    current
     DESCRIPTION
          "If true, the statistics in this entry may be unreliable."
     ::= { atmfM4VcUpcNpcCurrEntry 1 }

atmfM4VcUpcNpcCurrElapsedTime OBJECT-TYPE
     SYNTAX    TimeInterval
     MAX-ACCESS     read-only
     STATUS    current
     DESCRIPTION
          "Amount of time, measured in units of 0.01 second, that
          statistics for this entry (the current interval) have been
          counted."
     ::= { atmfM4VcUpcNpcCurrEntry 2 }

atmfM4VcUpcNpcCurrSupprIntvls OBJECT-TYPE
     SYNTAX    Gauge32
     MAX-ACCESS     read-only
     STATUS    current
     DESCRIPTION
          "This attribute is non-zero only if the ATM NE is
          suppressing UPC/NPC Disagreement Monitoring History Data
          entry creation when the current interval terminates with
          'all-zeroes' performance measurements.

          When non-zero, this attribute represents the number of
          'all-zeroes' intervals that were suppressed immediately
          prior to the current interval.

          Note that the suppression of 'all-zeroes' intervals is
          controlled by the atmfM4NeSuppressZeroStats object."
     ::= { atmfM4VcUpcNpcCurrEntry 3 }

atmfM4VcUpcNpcCurrDiscardedCells OBJECT-TYPE
     SYNTAX    Gauge32
     MAX-ACCESS     read-only
     STATUS    current
     DESCRIPTION
          "The number of discarded cells due to combined CLP=0 and
          CLP=1 UPC/NPC policing."
     ::= { atmfM4VcUpcNpcCurrEntry 4 }

atmfM4VcUpcNpcCurrDiscardedClp0 OBJECT-TYPE
     SYNTAX    Gauge32
     MAX-ACCESS     read-only
     STATUS    current
     DESCRIPTION
          "The number of discarded CLP=0 cells due to CLP=0 only
          UPC/NPC policing.

          This object shall be present only if CLP=0 traffic is
          separately policed."
     ::= { atmfM4VcUpcNpcCurrEntry 5 }

atmfM4VcUpcNpcCurrPassedCells OBJECT-TYPE
     SYNTAX    Gauge32
     MAX-ACCESS     read-only
     STATUS    current
     DESCRIPTION
          "The number of cells that have been successfully passed by
          the combined CLP=0 and CLP=1 UPC/NPC policing."
     ::= { atmfM4VcUpcNpcCurrEntry 6 }

atmfM4VcUpcNpcCurrPassedClp0 OBJECT-TYPE
     SYNTAX    Gauge32
     MAX-ACCESS     read-only
     STATUS    current
     DESCRIPTION
          "The number of CLP=0 cells that have been successfully
          passed by the CLP=0 UPC/NPC policing.

          This object shall be present only if CLP=0 traffic is
          separately policed."
     ::= { atmfM4VcUpcNpcCurrEntry 7 }


-- UPC/NPC Disagreement Monitoring History (per VCL termination
-- point and time interval)

atmfM4VcUpcNpcHistTable OBJECT-TYPE
     SYNTAX    SEQUENCE OF    AtmfM4VcUpcNpcHistEntry
     MAX-ACCESS     not-accessible
     STATUS    current
     DESCRIPTION
          "The ATM Forum M4 UPC/NPC Disagreement Monitoring History
          Data table for VCL termination points.

          This table maintains per-interface statistics for previous
          fifteen-minute intervals."
     ::= { atmfM4MIBObjects 23 }

atmfM4VcUpcNpcHistEntry OBJECT-TYPE
     SYNTAX    AtmfM4VcUpcNpcHistEntry
     MAX-ACCESS     not-accessible
     STATUS    current
     DESCRIPTION
          "An entry in the ATM Forum M4 UPC/NPC Disagreement
          Monitoring History Data table for VCL termination points.

          Each VCL Termination Point automatically has
          an entry in this table associated with it."
     INDEX          { ifIndex,
                    atmVclVpi,
                    atmVclVci,
                    atmfM4VcUpcNpcHistIndex }
     ::= { atmfM4VcUpcNpcHistTable 1 }

AtmfM4VcUpcNpcHistEntry ::= SEQUENCE {
     atmfM4VcUpcNpcHistIndex            INTEGER,
     atmfM4VcUpcNpcHistSuspect          TruthValue,
     atmfM4VcUpcNpcHistElapsedTime      TimeInterval,
     atmfM4VcUpcNpcHistSupprIntvls      Gauge32,
     atmfM4VcUpcNpcHistDiscardedCells   Gauge32,
     atmfM4VcUpcNpcHistDiscardedClp0    Gauge32,
     atmfM4VcUpcNpcHistPassedCells      Gauge32,
     atmfM4VcUpcNpcHistPassedClp0       Gauge32
          }

atmfM4VcUpcNpcHistIndex OBJECT-TYPE
     SYNTAX    INTEGER (1..96)
     MAX-ACCESS     not-accessible
     STATUS    current
     DESCRIPTION
          "A number between 1 and 96, which identifies the interval
          for which the set of statistics in this entry was
          collected.

          The interval identified by 1 is the most recently completed
          15 minute interval, and the interval identified by N is the
          interval immediately preceding the one identified by N-1."
     ::= { atmfM4VcUpcNpcHistEntry 1 }

atmfM4VcUpcNpcHistSuspect OBJECT-TYPE
     SYNTAX    TruthValue
     MAX-ACCESS     read-only
     STATUS    current
     DESCRIPTION
          "If true, the statistics in this entry may be unreliable."
     ::= { atmfM4VcUpcNpcHistEntry 2 }

atmfM4VcUpcNpcHistElapsedTime OBJECT-TYPE
     SYNTAX    TimeInterval
     MAX-ACCESS     read-only
     STATUS    current
     DESCRIPTION
          "Amount of time, measured in units of 0.01 second, that
          statistics for this entry (the current interval) have been
          counted."
     ::= { atmfM4VcUpcNpcHistEntry 3 }

atmfM4VcUpcNpcHistSupprIntvls OBJECT-TYPE
     SYNTAX    Gauge32
     MAX-ACCESS     read-only
     STATUS    current
     DESCRIPTION
          "This attribute is non-zero only if the ATM NE is
          suppressing UPC/NPC Disagreement Monitoring History Data
          entry creation when the current interval terminates with
          'all-zeroes' performance measurements.

          When non-zero, this attribute represents the number of
          'all-zeroes' intervals that were suppressed immediately
          prior to this 'non-all-zeroes' history interval.

          Note that the suppression of 'all-zeroes' intervals is
          controlled by the atmfM4NeSuppressZeroStats object."
     ::= { atmfM4VcUpcNpcHistEntry 4 }

atmfM4VcUpcNpcHistDiscardedCells OBJECT-TYPE
     SYNTAX    Gauge32
     MAX-ACCESS     read-only
     STATUS    current
     DESCRIPTION
          "The number of discarded cells due to combined CLP=0 and
          CLP=1 UPC/NPC policing."
     ::= { atmfM4VcUpcNpcHistEntry 5 }

atmfM4VcUpcNpcHistDiscardedClp0 OBJECT-TYPE
     SYNTAX    Gauge32
     MAX-ACCESS     read-only
     STATUS    current
     DESCRIPTION
          "The number of discarded CLP=0 cells due to CLP=0 only
          UPC/NPC policing.

          This object shall be present only if CLP=0 traffic is
          separately policed."
     ::= { atmfM4VcUpcNpcHistEntry 6 }

atmfM4VcUpcNpcHistPassedCells OBJECT-TYPE
     SYNTAX    Gauge32
     MAX-ACCESS     read-only
     STATUS    current
     DESCRIPTION
          "The number of cells that have been successfully passed by
          the combined CLP=0 and CLP=1 UPC/NPC policing."
     ::= { atmfM4VcUpcNpcHistEntry 7 }

atmfM4VcUpcNpcHistPassedClp0 OBJECT-TYPE
     SYNTAX    Gauge32
     MAX-ACCESS     read-only
     STATUS    current
     DESCRIPTION
          "The number of CLP=0 cells that have been successfully
          passed by the CLP=0 UPC/NPC policing.

          This object shall be present only if CLP=0 traffic is
          separately policed."
     ::= { atmfM4VcUpcNpcHistEntry 8 }


-- ATM Forum M4 Test Types

atmfM4TestTypes     OBJECT IDENTIFIER
     ::= { atmfM4MIBObjects 24 }


-- OAM Loopback Tests (VPL, VPC, VCL, and VCC termination points):

atmfM4TestOAMLoopbackSeg OBJECT-IDENTITY
     STATUS    current
     DESCRIPTION
          "This identifies an OAM Loopback Test on a VPL, VPC,
          VCL, or VCC termination point, using a segment OAM
          cell.

          The test type must have appended to it a code that uniquely
          identifies an intermediate point responsible for looping
          back the cell.  If this is absent, the loopback is performed
          at the end of the segment or connection.

          E.g., the OID { atmfM4TestOAMLoopbackSeg 5 } identifies
          that the loopback should be performed at the intermediate
          point labeled 5."
     ::= { atmfM4TestTypes 1 }

atmfM4TestOAMLoopbackE2E OBJECT-IDENTITY
     STATUS    current
     DESCRIPTION
          "This identifies an OAM Loopback Test on a VPL, VPC,
          VCL, or VCC termination point, using an end-to-end OAM
          cell."
     ::= { atmfM4TestTypes 2 }


-- ATM Forum M4 VP Termination Point Test Table

atmfM4VpTestTable OBJECT-TYPE
     SYNTAX    SEQUENCE OF    AtmfM4VpTestEntry
     MAX-ACCESS     not-accessible
     STATUS    current
     DESCRIPTION
          "The ATM Forum M4 VP Termination Point Test table.
          This table allows tests to be run on VPL and VPC
          termination points.

          The operation of this table is entirely analogous to
          that of the ifTestTable in RFC 1573 (which was later
          deprecated in RFC 2233), except that the indexes into
          this table are different."
     ::= { atmfM4MIBObjects 25 }

atmfM4VpTestEntry OBJECT-TYPE
     SYNTAX    AtmfM4VpTestEntry
     MAX-ACCESS     not-accessible
     STATUS    current
     DESCRIPTION
          "An entry containing objects for invoking tests on a
          VPL or VPC termination point."
     INDEX          { ifIndex,
                    atmVplVpi,
                    atmfM4VpTestObject }
     ::= { atmfM4VpTestTable 1 }

AtmfM4VpTestEntry ::= SEQUENCE {
     atmfM4VpTestObject  INTEGER,
     atmfM4VpTestId      TestAndIncr,
     atmfM4VpTestStatus  INTEGER,
     atmfM4VpTestType    AutonomousType,
     atmfM4VpTestResult  INTEGER,
     atmfM4VpTestCode    OBJECT IDENTIFIER,
     atmfM4VpTestOwner   OwnerString
          }

atmfM4VpTestObject OBJECT-TYPE
     SYNTAX    INTEGER {
                    vplTp(1),
                    vpcTp(2)
                         }
     MAX-ACCESS     not-accessible
     STATUS    current
     DESCRIPTION
          "Specifies whether the test applies to the VPL termination
          point with the specified VPI, or the VPC termination point."
     ::= { atmfM4VpTestEntry 1 }

atmfM4VpTestId         OBJECT-TYPE
     SYNTAX       TestAndIncr
     MAX-ACCESS   read-write
     STATUS       current
     DESCRIPTION
           "This object identifies the current invocation of the
           interface's test."
     ::= { atmfM4VpTestEntry 2 }

atmfM4VpTestStatus     OBJECT-TYPE
     SYNTAX       INTEGER { notInUse(1), inUse(2) }
     MAX-ACCESS   read-write
     STATUS       current
     DESCRIPTION
           "This object indicates whether or not some manager
           currently has the necessary 'ownership' required to
           invoke a test on this interface.  A write to this
           object is only successful when it changes its value
           from 'notInUse(1)' to 'inUse(2)'.  After completion of
           a test, the agent resets the value back to
           'notInUse(1)'."
     ::= { atmfM4VpTestEntry 3 }

atmfM4VpTestType       OBJECT-TYPE
     SYNTAX       AutonomousType
     MAX-ACCESS   read-write
     STATUS       current
     DESCRIPTION
           "A control variable used to start and stop operator-
           initiated interface tests.  Most OBJECT IDENTIFIER
           values assigned to tests are defined elsewhere, in
           association with specific types of interface.
           However, this document assigns a value for a full-
           duplex loopback test, and defines the special meanings
           of the subject identifier:

               noTest  OBJECT IDENTIFIER ::= { 0 0 }

           When the value noTest is written to this object, no
           action is taken unless a test is in progress, in which
           case the test is aborted.  Writing any other value to
           this object is only valid when no test is currently in
           progress, in which case the indicated test is
           initiated.

           When read, this object always returns the most recent
           value that atmfM4VpTestType was set to.  If it has not been
           set since the last initialization of the network
           management subsystem on the agent, a value of noTest
           is returned."
     ::= { atmfM4VpTestEntry 4 }

atmfM4VpTestResult  OBJECT-TYPE
     SYNTAX       INTEGER {
                      none(1),          -- no test yet requested
                      success(2),
                      inProgress(3),
                      notSupported(4),
                      unAbleToRun(5),   -- due to state of system
                      aborted(6),
                      failed(7)
                  }
     MAX-ACCESS   read-only
     STATUS       current
     DESCRIPTION
           "This object contains the result of the most recently
           requested test, or the value none(1) if no tests have
           been requested since the last reset.  Note that this
           facility provides no provision for saving the results
           of one test when starting another, as could be
           required if used by multiple managers concurrently."
     ::= { atmfM4VpTestEntry 5 }

atmfM4VpTestCode  OBJECT-TYPE
     SYNTAX       OBJECT IDENTIFIER
     MAX-ACCESS   read-only
     STATUS       current
     DESCRIPTION
           "This object contains a code which contains more
           specific information on the test result, for example
           an error-code after a failed test.  Error codes and
           other values this object may take are specific to the
           type of interface and/or test.  The value may have the
           semantics of either the AutonomousType or
           RowPointer textual conventions as defined in RFC
           1903 [15].  The identifier:

               testCodeUnknown  OBJECT IDENTIFIER ::= { 0 0 }

           is defined for use if no additional result code is
           available."
     ::= { atmfM4VpTestEntry 6 }

atmfM4VpTestOwner      OBJECT-TYPE
     SYNTAX       OwnerString
     MAX-ACCESS   read-write
     STATUS       current
     DESCRIPTION
           "The entity which currently has the 'ownership'
           required to invoke a test on this interface."
     ::= { atmfM4VpTestEntry 7 }



-- ATM Forum M4 VC Termination Point Test Table

atmfM4VcTestTable OBJECT-TYPE
     SYNTAX    SEQUENCE OF    AtmfM4VcTestEntry
     MAX-ACCESS     not-accessible
     STATUS    current
     DESCRIPTION
          "The ATM Forum M4 VC Termination Point Test table.
          This table allows tests to be run on VCL and VCC
          termination points.

          The operation of this table is entirely analogous to
          that of the ifTestTable in RFC 1573 (which was later
          deprecated in RFC 2233), except that the indexes into
          this table are different."
     ::= { atmfM4MIBObjects 26 }

atmfM4VcTestEntry OBJECT-TYPE
     SYNTAX    AtmfM4VcTestEntry
     MAX-ACCESS     not-accessible
     STATUS    current
     DESCRIPTION
          "An entry containing objects for invoking tests on a
          VCL or VCC termination point."
     INDEX          { ifIndex,
                    atmVclVpi,
                    atmVclVci,
                    atmfM4VcTestObject }
     ::= { atmfM4VcTestTable 1 }

AtmfM4VcTestEntry ::= SEQUENCE {
     atmfM4VcTestObject  INTEGER,
     atmfM4VcTestId      TestAndIncr,
     atmfM4VcTestStatus  INTEGER,
     atmfM4VcTestType    AutonomousType,
     atmfM4VcTestResult  INTEGER,
     atmfM4VcTestCode    OBJECT IDENTIFIER,
     atmfM4VcTestOwner   OwnerString
          }

atmfM4VcTestObject OBJECT-TYPE
     SYNTAX    INTEGER {
                    vclTp(1),
                    vccTp(2)
                         }
     MAX-ACCESS     not-accessible
     STATUS    current
     DESCRIPTION
          "Specifies whether the test applies to the VCL termination
          point with the specified VPI and VCI values, or to the VCC
          termination point."
     ::= { atmfM4VcTestEntry 1 }

atmfM4VcTestId         OBJECT-TYPE
     SYNTAX       TestAndIncr
     MAX-ACCESS   read-write
     STATUS       current
     DESCRIPTION
          "This object identifies the current invocation of the
          interface's test."
     ::= { atmfM4VcTestEntry 2 }

atmfM4VcTestStatus     OBJECT-TYPE
     SYNTAX       INTEGER { notInUse(1), inUse(2) }
     MAX-ACCESS   read-write
     STATUS       current
     DESCRIPTION
          "This object indicates whether or not some manager
          currently has the necessary 'ownership' required to
          invoke a test on this interface.  A write to this
          object is only successful when it changes its value
          from 'notInUse(1)' to 'inUse(2)'.  After completion of
          a test, the agent resets the value back to
          'notInUse(1)'."
     ::= { atmfM4VcTestEntry 3 }

atmfM4VcTestType       OBJECT-TYPE
     SYNTAX       AutonomousType
     MAX-ACCESS   read-write
     STATUS       current
     DESCRIPTION
          "A control variable used to start and stop operator-
          initiated interface tests.  Most OBJECT IDENTIFIER
          values assigned to tests are defined elsewhere, in
          association with specific types of interface.
          However, this document assigns a value for a full-
          duplex loopback test, and defines the special meanings
          of the subject identifier:

              noTest  OBJECT IDENTIFIER ::= { 0 0 }

          When the value noTest is written to this object, no
          action is taken unless a test is in progress, in which
          case the test is aborted.  Writing any other value to
          this object is only valid when no test is currently in
          progress, in which case the indicated test is
          initiated.

          When read, this object always returns the most recent
          value that atmfM4VcTestType was set to.  If it has not been
          set since the last initialization of the network
          management subsystem on the agent, a value of noTest
          is returned."
     ::= { atmfM4VcTestEntry 4 }

atmfM4VcTestResult  OBJECT-TYPE
     SYNTAX       INTEGER {
                      none(1),          -- no test yet requested
                      success(2),
                      inProgress(3),
                      notSupported(4),
                      unAbleToRun(5),   -- due to state of system
                      aborted(6),
                      failed(7)
                  }
     MAX-ACCESS   read-only
     STATUS       current
     DESCRIPTION
          "This object contains the result of the most recently
          requested test, or the value none(1) if no tests have
          been requested since the last reset.  Note that this
          facility provides no provision for saving the results
          of one test when starting another, as could be
          required if used by multiple managers concurrently."
     ::= { atmfM4VcTestEntry 5 }

atmfM4VcTestCode  OBJECT-TYPE
     SYNTAX       OBJECT IDENTIFIER
     MAX-ACCESS   read-only
     STATUS       current
     DESCRIPTION
          "This object contains a code which contains more
          specific information on the test result, for example
          an error-code after a failed test.  Error codes and
          other values this object may take are specific to the
          type of interface and/or test.  The value may have the
          semantics of either the AutonomousType or
          RowPointer textual conventions as defined in RFC
          1903 [15].  The identifier:

              testCodeUnknown  OBJECT IDENTIFIER ::= { 0 0 }

          is defined for use if no additional result code is
          available."
     ::= { atmfM4VcTestEntry 6 }

atmfM4VcTestOwner      OBJECT-TYPE
     SYNTAX       OwnerString
     MAX-ACCESS   read-write
     STATUS       current
     DESCRIPTION
          "The entity which currently has the 'ownership'
          required to invoke a test on this termination point."
     ::= { atmfM4VcTestEntry 7 }


-- ATM Forum M4 Equipment Table

atmfM4EquipTable OBJECT-TYPE
     SYNTAX    SEQUENCE OF    AtmfM4EquipEntry
     MAX-ACCESS     not-accessible
     STATUS    current
     DESCRIPTION
          "The ATM Forum M4 Equipment table.  This table augments the
          entPhysicalTable."
     ::= { atmfM4MIBObjects 28 }

atmfM4EquipEntry OBJECT-TYPE
     SYNTAX    AtmfM4EquipEntry
     MAX-ACCESS     not-accessible
     STATUS    current
     DESCRIPTION
          "An entry in the ATM Forum M4 Equipment table.  Each entry
          of this table represents a piece of equipment within the ATM
          NE that neither is nor accepts a replaceable plug-in unit."
     INDEX          { entPhysicalIndex }
     ::= { atmfM4EquipTable 1 }

AtmfM4EquipEntry ::= SEQUENCE {
     atmfM4EquipAdminStatus   INTEGER,
     atmfM4EquipLocation      DisplayString,
     atmfM4EquipOperStatus    INTEGER,
     atmfM4EquipVendor        DisplayString,
     atmfM4EquipVersion       AutonomousType,
     atmfM4EquipUserLabel     DisplayString,
     atmfM4EquipAlarmSeverityIndex Integer32
          }

atmfM4EquipAdminStatus OBJECT-TYPE
     SYNTAX    INTEGER {
                    up(1),
                    down(2)
                         }
     MAX-ACCESS     read-write
     STATUS    current
     DESCRIPTION
          "Used by the administrator to lock and unlock the object."
     ::= { atmfM4EquipEntry 1 }

atmfM4EquipLocation OBJECT-TYPE
     SYNTAX    DisplayString
     MAX-ACCESS     read-write
     STATUS    current
     DESCRIPTION
          "The specific or general location of the component."
     ::= { atmfM4EquipEntry 2 }

atmfM4EquipOperStatus OBJECT-TYPE
     SYNTAX    INTEGER {
                    up(1),
                    down(2),
                    unknown(3)
                         }
     MAX-ACCESS     read-only
     STATUS    current
     DESCRIPTION
          "This attributes identifies whether or not the component is
          capable of performing its normal functions."
     ::= { atmfM4EquipEntry 3 }

atmfM4EquipVendor OBJECT-TYPE
     SYNTAX    DisplayString
     MAX-ACCESS     read-only
     STATUS    current
     DESCRIPTION
          "The vendor of the component."
     ::= { atmfM4EquipEntry 4 }

atmfM4EquipVersion OBJECT-TYPE
     SYNTAX    AutonomousType
     MAX-ACCESS     read-only
     STATUS    current
     DESCRIPTION
          "The version of the component."
     ::= { atmfM4EquipEntry 5 }

atmfM4EquipUserLabel OBJECT-TYPE
     SYNTAX    DisplayString
     MAX-ACCESS     read-write
     STATUS    current
     DESCRIPTION
          "A user-friendly name for the piece of equipment.  The
          default value of this object is the null string."
     ::= { atmfM4EquipEntry 6 }

atmfM4EquipAlarmSeverityIndex OBJECT-TYPE
     SYNTAX    Integer32
     MAX-ACCESS     read-write
     STATUS    current
     DESCRIPTION
          "An index into the alarm severity profile table, specifying
          the severity assignments for M4 alarms reported for this
          component.  The default value of this object is zero."
     ::= { atmfM4EquipEntry 7 }


-- ATM Forum M4 Equipment Holder Table

atmfM4EquipHolderTable OBJECT-TYPE
     SYNTAX    SEQUENCE OF    AtmfM4EquipHolderEntry
     MAX-ACCESS     not-accessible
     STATUS    current
     DESCRIPTION
          "The ATM Forum M4 Equipment Holder table.  This table
          augments the entPhysicalTable."
     ::= { atmfM4MIBObjects 29 }

atmfM4EquipHolderEntry OBJECT-TYPE
     SYNTAX    AtmfM4EquipHolderEntry
     MAX-ACCESS     not-accessible
     STATUS    current
     DESCRIPTION
          "An entry in the ATM Forum M4 Equipment Holder table.  Each
          entry of this table represents a component within the ATM NE
          that accepts a replaceable plug-in unit."
     INDEX          { entPhysicalIndex }
     ::= { atmfM4EquipHolderTable 1 }

AtmfM4EquipHolderEntry ::= SEQUENCE {
     atmfM4EquipHolderType              INTEGER,
     atmfM4EquipHolderAcceptableTypes   DisplayString,
     atmfM4EquipHolderSlotStatus        INTEGER,
     atmfM4EquipHolderSwLoad            INTEGER
          }

atmfM4EquipHolderType OBJECT-TYPE
     SYNTAX    INTEGER {
                    rack(1),
                    shelf(2),
                    drawer(3),
                    slot(4)
                         }
     MAX-ACCESS     read-only
     STATUS    current
     DESCRIPTION
          "The type of the component."
     ::= { atmfM4EquipHolderEntry 1 }

atmfM4EquipHolderAcceptableTypes OBJECT-TYPE
     SYNTAX    DisplayString
     MAX-ACCESS     read-only
     STATUS    current
     DESCRIPTION
          "The types of plug-in units that can be supported by the
          slot, separated by newline characters.

          This attribute shall be present only when the Equipment
          Holder represents a slot."
     ::= { atmfM4EquipHolderEntry 2 }

atmfM4EquipHolderSlotStatus OBJECT-TYPE
     SYNTAX    INTEGER {
                    empty(1),
                    full(2)
                         }
     MAX-ACCESS     read-only
     STATUS    current
     DESCRIPTION
          "This attributes identifies whether or not a plug-in unit is
          present in the slot.

          This attribute shall be present only when the Equipment
          Holder represents a slot."
     ::= { atmfM4EquipHolderEntry 3 }

atmfM4EquipHolderSwLoad OBJECT-TYPE
     SYNTAX    INTEGER (1..2147483647)
     MAX-ACCESS     read-write
     STATUS    current
     DESCRIPTION
          "An index into the installed software table, specifying
          the software that is to be loaded into the plug-in unit
          whenever an automatic reload of software is needed.

          This attribute shall be present only when the Equipment
          Holder represents a slot."
     ::= { atmfM4EquipHolderEntry 4 }


-- ATM Forum M4 Plug-In Unit Table

atmfM4PlugInUnitTable OBJECT-TYPE
     SYNTAX    SEQUENCE OF    AtmfM4PlugInUnitEntry
     MAX-ACCESS     not-accessible
     STATUS    current
     DESCRIPTION
          "The ATM Forum M4 Plug-In Unit table.  This table augments
          the entPhysicalTable."
     ::= { atmfM4MIBObjects 30 }

atmfM4PlugInUnitEntry OBJECT-TYPE
     SYNTAX    AtmfM4PlugInUnitEntry
     MAX-ACCESS     not-accessible
     STATUS    current
     DESCRIPTION
          "An entry in the ATM Forum M4 Plug-In Unit table.  Each
          entry of this table represents a piece of equipment within
          the ATM NE that is inserted into and removed from an
          Equipment Holder."
     INDEX          { entPhysicalIndex }
     ::= { atmfM4PlugInUnitTable 1 }

AtmfM4PlugInUnitEntry ::= SEQUENCE {
     atmfM4PlugInUnitAdminStatus   INTEGER,
     atmfM4PlugInUnitAvailStatus   INTEGER,
     atmfM4PlugInUnitOperStatus    INTEGER,
     atmfM4PlugInUnitVendor        DisplayString,
     atmfM4PlugInUnitVersion       AutonomousType,
     atmfM4PlugInUnitAlarmSeverityIndex Integer32
          }

atmfM4PlugInUnitAdminStatus OBJECT-TYPE
     SYNTAX    INTEGER {
                    up(1),
                    down(2)
                         }
     MAX-ACCESS     read-write
     STATUS    current
     DESCRIPTION
          "Used by the administrator to lock and unlock the object."
     ::= { atmfM4PlugInUnitEntry 1 }

atmfM4PlugInUnitAvailStatus OBJECT-TYPE
     SYNTAX    INTEGER {
                    available(1),
                    inTest(2),
                    failed(3),
                    powerOff(4),
                    notInstalled(5),
                    offLine(6),
                    dependency(7)
                         }
     MAX-ACCESS     read-only
     STATUS    current
     DESCRIPTION
          "Provides further information regarding the state of the
          component."
     ::= { atmfM4PlugInUnitEntry 2 }

atmfM4PlugInUnitOperStatus OBJECT-TYPE
     SYNTAX    INTEGER {
                    up(1),
                    down(2),
                    unknown(3)
                         }
     MAX-ACCESS     read-only
     STATUS    current
     DESCRIPTION
          "This attributes identifies whether or not the component is
          capable of performing its normal functions."
     ::= { atmfM4PlugInUnitEntry 3 }

atmfM4PlugInUnitVendor OBJECT-TYPE
     SYNTAX    DisplayString
     MAX-ACCESS     read-only
     STATUS    current
     DESCRIPTION
          "The vendor of the component."
     ::= { atmfM4PlugInUnitEntry 4 }

atmfM4PlugInUnitVersion OBJECT-TYPE
     SYNTAX    AutonomousType
     MAX-ACCESS     read-only
     STATUS    current
     DESCRIPTION
          "The version of the component."
     ::= { atmfM4PlugInUnitEntry 5 }

atmfM4PlugInUnitAlarmSeverityIndex OBJECT-TYPE
     SYNTAX    Integer32
     MAX-ACCESS     read-write
     STATUS    current
     DESCRIPTION
          "An index into the alarm severity profile table, specifying
          the severity assignments for M4 alarms reported for this
          component.  The default value of this object is zero."
     ::= { atmfM4PlugInUnitEntry 6 }

-- ATM Forum M4 Hardware Unit/Running Software Relationship Table

atmfM4HwRunningSwTable OBJECT-TYPE
     SYNTAX    SEQUENCE OF    AtmfM4HwRunningSwEntry
     MAX-ACCESS     not-accessible
     STATUS    current
     DESCRIPTION
          "The ATM Forum M4 Hardware Unit/Running Software
          relationship table.  This table describes the software that
          is running on each hardware unit in the ATM NE."
     ::= { atmfM4MIBObjects 32 }

atmfM4HwRunningSwEntry OBJECT-TYPE
     SYNTAX    AtmfM4HwRunningSwEntry
     MAX-ACCESS     not-accessible
     STATUS    current
     DESCRIPTION
          "An entry in the ATM Forum M4 Hardware Unit/Running Software
          relationship table.  Each entry of this table identifies an
          entry in the entPhysicalTable and one in the hrSWRunTable."
     INDEX          { atmfM4HwRunningSwHwIndex,
                    atmfM4HwRunningSwIndex }
     ::= { atmfM4HwRunningSwTable 1 }

AtmfM4HwRunningSwEntry ::= SEQUENCE {
     atmfM4HwRunningSwHwIndex INTEGER,
     atmfM4HwRunningSwIndex        INTEGER,
     atmfM4HwRunningSwSwIndex INTEGER
          }

atmfM4HwRunningSwHwIndex OBJECT-TYPE
     SYNTAX    INTEGER (1..2147483647)
     MAX-ACCESS     not-accessible
     STATUS    current
     DESCRIPTION
          "The index, in the entPhysicalTable, of the containing
          hardware unit in this pair."
     ::= { atmfM4HwRunningSwEntry 1 }

atmfM4HwRunningSwIndex OBJECT-TYPE
     SYNTAX    INTEGER (1..2147483647)
     MAX-ACCESS     not-accessible
     STATUS    current
     DESCRIPTION
          "A unique number within the context of the containing
          hardware unit."
     ::= { atmfM4HwRunningSwEntry 2 }

atmfM4HwRunningSwSwIndex OBJECT-TYPE
     SYNTAX    INTEGER (1..2147483647)
     MAX-ACCESS     read-only
     STATUS    current
     DESCRIPTION
          "The index, in the hrSWRunTable, of the software product
          represented by this entry."
     ::= { atmfM4HwRunningSwEntry 3 }


-- ATM Forum M4 Hardware Unit/Installed Software Relationship Table

atmfM4HwInstalledSwTable OBJECT-TYPE
     SYNTAX    SEQUENCE OF    AtmfM4HwInstalledSwEntry
     MAX-ACCESS     not-accessible
     STATUS    current
     DESCRIPTION
          "The ATM Forum M4 Hardware Unit/Installed Software
          relationship table.  This table describes the software that
          is installed on each hardware unit in the ATM NE."
     ::= { atmfM4MIBObjects 33 }

atmfM4HwInstalledSwEntry OBJECT-TYPE
     SYNTAX    AtmfM4HwInstalledSwEntry
     MAX-ACCESS     not-accessible
     STATUS    current
     DESCRIPTION
          "An entry in the ATM Forum M4 Hardware Unit/Installed
          Software relationship table.  Each entry of this table
          identifies an entry in the entPhysicalTable and one in
          the hrSWInstalledTable."
     INDEX          { atmfM4HwInstalledSwHwIndex,
                    atmfM4HwInstalledSwIndex }
     ::= { atmfM4HwInstalledSwTable 1 }

AtmfM4HwInstalledSwEntry ::= SEQUENCE {
     atmfM4HwInstalledSwHwIndex    INTEGER,
     atmfM4HwInstalledSwIndex      INTEGER,
     atmfM4HwInstalledSwSwIndex    INTEGER,
     atmfM4HwSwAlarmSeverityIndex  Integer32
          }

atmfM4HwInstalledSwHwIndex OBJECT-TYPE
     SYNTAX    INTEGER (1..2147483647)
     MAX-ACCESS     not-accessible
     STATUS    current
     DESCRIPTION
          "The index, in the entPhysicalTable, of the containing
          physical entity in this pair."
     ::= { atmfM4HwInstalledSwEntry 1 }

atmfM4HwInstalledSwIndex OBJECT-TYPE
     SYNTAX    INTEGER (1..2147483647)
     MAX-ACCESS     not-accessible
     STATUS    current
     DESCRIPTION
          "A unique number within the context of the containing
          hardware unit."
     ::= { atmfM4HwInstalledSwEntry 2 }

atmfM4HwInstalledSwSwIndex OBJECT-TYPE
     SYNTAX    INTEGER (1..2147483647)
     MAX-ACCESS     read-only
     STATUS    current
     DESCRIPTION
          "The index, in the hrSWInstalledTable, of the software
          product represented by this entry."
     ::= { atmfM4HwInstalledSwEntry 3 }

atmfM4HwSwAlarmSeverityIndex OBJECT-TYPE
     SYNTAX    Integer32
     MAX-ACCESS     read-write
     STATUS    current
     DESCRIPTION
          "An index into the alarm severity profile table, specifying
          the severity assignments for M4 alarms reported for this
          piece of software installed on the hardware unit.  The
          default value of this object is zero."
     ::= { atmfM4HwInstalledSwEntry 4 }



-- ATM Forum M4 Alarm Severity Identifier Textual Convention

AtmfM4AlarmLogSeverity ::= TEXTUAL-CONVENTION
     STATUS    current
     DESCRIPTION
          "The value of this object identifies the severity of
          an alarm in the log, including 'cleared'."
     SYNTAX    INTEGER {
                    cleared(-1),
                    indeterminate(0),
                    critical(1),
                    major(2),
                    minor(3),
                    warning(4)
                         }

AtmfM4AlarmSeverity ::= TEXTUAL-CONVENTION
     STATUS    current
     DESCRIPTION
          "The value of this object identifies the severity of
          an alarm that has occurred.  (Note that there is no
          value corresponding to 'cleared'.)"
     SYNTAX    INTEGER {
                    indeterminate(0),
                    critical(1),
                    major(2),
                    minor(3),
                    warning(4)
                         }

-- ATM Forum M4 Alarm Severity Profile Table

atmfM4AlarmSevDefault OBJECT-TYPE
     SYNTAX    AtmfM4AlarmSeverity
     MAX-ACCESS     read-write
     STATUS    current
     DESCRIPTION
          "The default severity value used for new profile
          index/trap ID pairs that have not yet been modified.
          This value is also used whenever an object's alarm
          severity profile index is set to 0.  The default value
          of this object is minor(3)."
     ::= { atmfM4MIBObjects 34 }

atmfM4AlarmSevProfileIndexNext OBJECT-TYPE
     SYNTAX    Integer32
     MAX-ACCESS     read-only
     STATUS    current
     DESCRIPTION
          "This object contains an appropriate value to be used for
          atmfM4AlarmSevProfileIndex when creating entries in the
          atmfM4AlarmSevProfileTable.

          The value -1 indicates that no unassigned entries are
          available.

          To obtain the index value for a new entry, the manager
          issues a management protocol retrieval operation to obtain
          the current value of this object.  After each retrieval, the
          agent should modify the value to the next unassigned index
          (or -1)."
     ::= { atmfM4MIBObjects 35 }

atmfM4AlarmSevProfileTable OBJECT-TYPE
     SYNTAX    SEQUENCE OF    AtmfM4AlarmSevProfileEntry
     MAX-ACCESS     not-accessible
     STATUS    current
     DESCRIPTION
          "The ATM Forum M4 alarm severity profile table.
          This table specifies which profiles exist. Creating
          or deleting an entry in this table automatically
          creates or deletes the corresponding entries in the
          atmfM4AlarmSeverityTable."
     ::= { atmfM4MIBObjects 36 }

atmfM4AlarmSevProfileEntry OBJECT-TYPE
     SYNTAX    AtmfM4AlarmSevProfileEntry
     MAX-ACCESS     not-accessible
     STATUS    current
     DESCRIPTION
          "A group of severities, one for each alarm type in
          the communications alarm group."
     INDEX          { atmfM4AlarmSevProfileIndex }
     ::= { atmfM4AlarmSevProfileTable 1 }

AtmfM4AlarmSevProfileEntry ::= SEQUENCE {
     atmfM4AlarmSevProfileIndex         Integer32,
     atmfM4AlarmSevProfileRowStatus     RowStatus
          }

atmfM4AlarmSevProfileIndex OBJECT-TYPE
     SYNTAX    Integer32 (1..2147483647)
     MAX-ACCESS     not-accessible
     STATUS    current
     DESCRIPTION
          "A number identifying this alarm severity profile."
     ::= { atmfM4AlarmSevProfileEntry 1 }

atmfM4AlarmSevProfileRowStatus OBJECT-TYPE
     SYNTAX    RowStatus
     MAX-ACCESS     read-create
     STATUS    current
     DESCRIPTION
          "This object is used to create a new row or to delete
          an existing row in the table."
     ::= { atmfM4AlarmSevProfileEntry 2 }


-- ATM Forum M4 Alarm Severity Table

atmfM4AlarmSevTable OBJECT-TYPE
     SYNTAX    SEQUENCE OF    AtmfM4AlarmSevEntry
     MAX-ACCESS     not-accessible
     STATUS    current
     DESCRIPTION
          "The ATM Forum M4 alarm severity table.
          This table associates profile index and trap
          ID pairs with severities to be used for
          M4 alarm traps that have occurred.
          (Note that this table does not apply to cleared alarms.)"
     ::= { atmfM4MIBObjects 37 }

atmfM4AlarmSevEntry OBJECT-TYPE
     SYNTAX    AtmfM4AlarmSevEntry
     MAX-ACCESS     not-accessible
     STATUS    current
     DESCRIPTION
          "An entry in this table associates an alarm severity
          profile index/trap ID pair with a severity.
          Deleting a particular profile's row in the alarm severity
          profile table deletes all rows in this table with the
          same profile index.
          Conceptually, rows corresponding to all possible trap ID's
          are created in this table when a new alarm severity profile
          is created, but the agent will return a default value
          except for those few traps for which values have been set."
     INDEX          { atmfM4AlarmSevProfileIndex,
                    atmfM4AlarmSevTrapId }
     ::= { atmfM4AlarmSevTable 1 }

AtmfM4AlarmSevEntry ::= SEQUENCE {
     atmfM4AlarmSevTrapId     OBJECT IDENTIFIER,
     atmfM4AlarmSeverity      AtmfM4AlarmSeverity
          }

atmfM4AlarmSevTrapId OBJECT-TYPE
     SYNTAX    OBJECT IDENTIFIER
     MAX-ACCESS     not-accessible
     STATUS    current
     DESCRIPTION
          "The ID of the trap type to which this entry applies."
     ::= { atmfM4AlarmSevEntry 1 }

atmfM4AlarmSeverity OBJECT-TYPE
     SYNTAX    AtmfM4AlarmSeverity
     MAX-ACCESS     read-create
     STATUS    current
     DESCRIPTION
          "The severity to be used for this trap type when the TrapId
          is selected.
          If no value for this object has ever been set since
          the corresponding profile was created, the agent should
          return the value of the object atmfM4AlarmSevDefault."
     ::= { atmfM4AlarmSevEntry 2 }


-- ATM Forum M4 Alarm Forwarding Discriminator Table

atmfM4ForwardAllTraps OBJECT-IDENTITY
     STATUS    current
     DESCRIPTION
          "This is used as the value of the object
          atmfM4ForwardedTrapObject when traps from all objects
          are to be forwarded, or when there is only one
          object of the type that forwards the specified
          trap type."
     ::= { atmfM4MIBObjects 38 }


atmfM4TrapForwardingTable OBJECT-TYPE
     SYNTAX    SEQUENCE OF    AtmfM4TrapForwardingEntry
     MAX-ACCESS     not-accessible
     STATUS    current
     DESCRIPTION
          "The ATM Forum M4 Trap forwarding discriminator
          table.
          This table specifies which traps will be sent to
          which management system."
     ::= { atmfM4MIBObjects 39 }

atmfM4TrapForwardingEntry OBJECT-TYPE
     SYNTAX    AtmfM4TrapForwardingEntry
     MAX-ACCESS     not-accessible
     STATUS    current
     DESCRIPTION
          "Information about a group of traps to be sent to
          a particular IP address.

          A new entry must have values for all attributes that
          do not have default values before its RowStatus column
          can be set to active(1)."
     INDEX          { atmfM4TrapForwardingIndex }
     ::= { atmfM4TrapForwardingTable 1 }

AtmfM4TrapForwardingEntry ::= SEQUENCE {
     atmfM4TrapForwardingIndex     Integer32,
     atmfM4TrapForwardingDest      IpAddress,
     atmfM4ForwardedTrapId         OBJECT IDENTIFIER,
     atmfM4ForwardedTrapObject     RowPointer,
     atmfM4TrapForwardingPort      Integer32,
     atmfM4LowestForwardedSeverity AtmfM4AlarmSeverity,
     atmfM4ForwardedIndeterminate  TruthValue,
     atmfM4TrapForwardingRowStatus RowStatus
          }

atmfM4TrapForwardingIndex OBJECT-TYPE
     SYNTAX    Integer32 (1..2147483647)
     MAX-ACCESS     not-accessible
     STATUS    current
     DESCRIPTION
          "A unique number identifying the table entry."
     ::= { atmfM4TrapForwardingEntry 1 }

atmfM4TrapForwardingDest OBJECT-TYPE
     SYNTAX    IpAddress
     MAX-ACCESS     read-create
     STATUS    current
     DESCRIPTION
          "The IP address to which traps identified by this
          table entry should be sent."
     ::= { atmfM4TrapForwardingEntry 2 }

atmfM4ForwardedTrapId OBJECT-TYPE
     SYNTAX    OBJECT IDENTIFIER
     MAX-ACCESS     read-create
     STATUS    current
     DESCRIPTION
          "The ID of the trap type to which this entry applies."
     ::= { atmfM4TrapForwardingEntry 3 }

atmfM4ForwardedTrapObject OBJECT-TYPE
     SYNTAX    RowPointer
     MAX-ACCESS     read-create
     STATUS    current
     DESCRIPTION
          "The object to which this entry applies.
          By convention, this is the name of the first object in
          the row in the table referenced.

          The special value { 0 0 } indicates that
          traps of this type from all objects of the type that can
          generate it.  It should also be used when traps from the
          ATM NE are to be specified."
     ::= { atmfM4TrapForwardingEntry 4 }

atmfM4TrapForwardingPort OBJECT-TYPE
     SYNTAX    Integer32
     MAX-ACCESS     read-create
     STATUS    current
     DESCRIPTION
          "The UDP port on the specified management system to
          which traps identified by this entry should be sent."
     DEFVAL    { 162 }
     ::= { atmfM4TrapForwardingEntry 5 }

atmfM4LowestForwardedSeverity OBJECT-TYPE
     SYNTAX    AtmfM4AlarmSeverity
     MAX-ACCESS     read-create
     STATUS    current
     DESCRIPTION
          "The lowest severity of traps of this type from
          the specified object that should be sent to this
          address.
          This object has significance only if the trap type
          specified has a severity associated with it."
     DEFVAL    { minor }
     ::= { atmfM4TrapForwardingEntry 6 }

atmfM4ForwardedIndeterminate OBJECT-TYPE
     SYNTAX    TruthValue
     MAX-ACCESS     read-create
     STATUS    current
     DESCRIPTION
          "When this object has the value TRUE, traps with
          indeterminate severity will be forwarded to the
          specified event.
          This object has significance only if the trap type
          specified has a severity associated with it."
     DEFVAL    { false }
     ::= { atmfM4TrapForwardingEntry 7 }

atmfM4TrapForwardingRowStatus OBJECT-TYPE
     SYNTAX    RowStatus
     MAX-ACCESS     read-create
     STATUS    current
     DESCRIPTION
          "This object is used to create a new row or to delete
          an existing row in the table."
     ::= { atmfM4TrapForwardingEntry 8 }


-- ATM Forum M4 Trap Agent MIB Log Table

atmfM4TrapLogTable OBJECT-TYPE
     SYNTAX    SEQUENCE OF    AtmfM4TrapLogEntry
     MAX-ACCESS     not-accessible
     STATUS    current
     DESCRIPTION
          "The ATM Forum M4 Trap Agent log table.
          This table defines the trap logs currently maintained
          by the agent.
          The management system creates entries in this table to
          specify which types of traps, from which ATM network
          elements, should be logged.
          Deleting an entry in this table deletes all entries in
          the corresponding log."
     ::= { atmfM4MIBObjects 40 }

atmfM4TrapLogEntry OBJECT-TYPE
     SYNTAX    AtmfM4TrapLogEntry
     MAX-ACCESS     not-accessible
     STATUS    current
     DESCRIPTION
          "Information about a single trap log."
     INDEX          { atmfM4TrapLogSrc,
                    atmfM4TrapLogType }
     ::= { atmfM4TrapLogTable 1 }

AtmfM4TrapLogEntry ::= SEQUENCE {
     atmfM4TrapLogSrc              IpAddress,
     atmfM4TrapLogType             INTEGER,
     atmfM4TrapLogAdminStatus      INTEGER,
     atmfM4TrapLogOperStatus       INTEGER,
     atmfM4TrapLogFullAction       INTEGER,
     atmfM4TrapLogRowStatus        RowStatus
          }

atmfM4TrapLogSrc OBJECT-TYPE
     SYNTAX    IpAddress
     MAX-ACCESS     not-accessible
     STATUS    current
     DESCRIPTION
          "The IP address of the SNMP agent whose traps are
          stored in this log."
     ::= { atmfM4TrapLogEntry 1 }

atmfM4TrapLogType OBJECT-TYPE
     SYNTAX    INTEGER {
                    objectCreated(1),
                    objectDeleted(2),
                    configChange(3),
                    stateChange(4),
                    alarm(5)
                         }
     MAX-ACCESS     not-accessible
     STATUS    current
     DESCRIPTION
          "The type of traps stored in this log."
     ::= { atmfM4TrapLogEntry 2 }

atmfM4TrapLogAdminStatus OBJECT-TYPE
     SYNTAX    INTEGER {
                    up(1),
                    down(2)
                         }
     MAX-ACCESS     read-create
     STATUS    current
     DESCRIPTION
          "The management system uses this object to stop and
          start the operations of this object."
     DEFVAL    { up }
     ::= { atmfM4TrapLogEntry 3 }

atmfM4TrapLogOperStatus OBJECT-TYPE
     SYNTAX    INTEGER {
                    up(1),
                    down(2),
                    logFull(3)
                         }
     MAX-ACCESS     read-only
     STATUS    current
     DESCRIPTION
          "Indicates whether or not the log is capable of
          performing its normal operations."
     ::= { atmfM4TrapLogEntry 4 }

atmfM4TrapLogFullAction OBJECT-TYPE
     SYNTAX    INTEGER {
                    halt(1),
                    wrap(2)
                         }
     MAX-ACCESS     read-create
     STATUS    current
     DESCRIPTION
          "Indicates the action that should be performed when no
          more log entries can be created due to a log-full
          condition.  If the value of this object is wrap(2),
          each new log entry will cause the deletion of the oldest
          entry still in the log, for as long as the log is still
          full."
     DEFVAL    { wrap }
     ::= { atmfM4TrapLogEntry 5 }

atmfM4TrapLogRowStatus OBJECT-TYPE
     SYNTAX    RowStatus
     MAX-ACCESS     read-create
     STATUS    current
     DESCRIPTION
          "This object is used to create a new row or to delete
          an existing row in the table."
     ::= { atmfM4TrapLogEntry 6 }


-- ATM Forum M4 Trap Agent MIB Logged Trap Table

atmfM4LoggedTrapTable OBJECT-TYPE
     SYNTAX    SEQUENCE OF    AtmfM4LoggedTrapEntry
     MAX-ACCESS     not-accessible
     STATUS    current
     DESCRIPTION
          "The ATM Forum M4 Trap Agent logged trap table.
          This table is used to maintain the traps logged."
     ::= { atmfM4MIBObjects 41 }

atmfM4LoggedTrapEntry OBJECT-TYPE
     SYNTAX    AtmfM4LoggedTrapEntry
     MAX-ACCESS     not-accessible
     STATUS    current
     DESCRIPTION
          "Information about a single trap in the log.
          Entries in this table are created automatically but
          can be deleted by the management system.
          Entries that represent 'alarm' log types are augmented
          by the atmfM4LoggedAlarmEntry table."
     INDEX          { atmfM4TrapLogSrc,
                    atmfM4TrapLogType,
                    atmfM4LoggedTrapIndex }
     ::= { atmfM4LoggedTrapTable 1 }

AtmfM4LoggedTrapEntry ::= SEQUENCE {
     atmfM4LoggedTrapIndex         Unsigned32,
     atmfM4LoggedTrapTime          DateAndTime,
     atmfM4LoggedTrapID            Integer32,
     atmfM4LoggedTrapObject        RowPointer,
     atmfM4LoggedTrapRowStatus     RowStatus
          }

atmfM4LoggedTrapIndex OBJECT-TYPE
     SYNTAX    Unsigned32
     MAX-ACCESS     not-accessible
     STATUS    current
     DESCRIPTION
          "A unique number identifying this entry in the log.
          When the maximum value for this object has been reached,
          it will wrap around to 0."
     ::= { atmfM4LoggedTrapEntry 1 }

atmfM4LoggedTrapTime OBJECT-TYPE
     SYNTAX    DateAndTime
     MAX-ACCESS     read-only
     STATUS    current
     DESCRIPTION
          "The time at which this trap was logged."
     ::= { atmfM4LoggedTrapEntry 2 }

atmfM4LoggedTrapID OBJECT-TYPE
     SYNTAX    Integer32
     MAX-ACCESS     read-only
     STATUS    current
     DESCRIPTION
          "The type of trap to which this entry applies.
          Together with the logged trap ID object, this object
          specifies the entity to which this logged trap referred."
     ::= { atmfM4LoggedTrapEntry 3 }

atmfM4LoggedTrapObject OBJECT-TYPE
     SYNTAX    RowPointer
     MAX-ACCESS     read-only
     STATUS    current
     DESCRIPTION
          "The object to which this entry applies.
          By convention, this is the name of the first object in
          the row in the table referenced.
          Together with the logged trap ID object, this object
          specifies the entity to which this logged trap referred.

          The special value { 0 0 } indicates that the trap refers
          to the ATM NE entity itself."
     ::= { atmfM4LoggedTrapEntry 4 }

atmfM4LoggedTrapRowStatus OBJECT-TYPE
     SYNTAX    RowStatus
     MAX-ACCESS     read-write
     STATUS    current
     DESCRIPTION
          "This object is used to delete an existing row in the
          table.  Note that the only value to which a management
          system can set this object is destroy(6)."
     ::= { atmfM4LoggedTrapEntry 5 }


-- ATM Forum M4 Trap Agent MIB Logged Alarm Table

atmfM4LoggedAlarmTable OBJECT-TYPE
     SYNTAX    SEQUENCE OF    AtmfM4LoggedAlarmEntry
     MAX-ACCESS     not-accessible
     STATUS    current
     DESCRIPTION
          "The ATM Forum M4 Trap Agent logged alarm trap table.
          This table is used to maintain extra information for
          logged traps that represent alarm types."
     ::= { atmfM4MIBObjects 42 }

atmfM4LoggedAlarmEntry OBJECT-TYPE
     SYNTAX    AtmfM4LoggedAlarmEntry
     MAX-ACCESS     not-accessible
     STATUS    current
     DESCRIPTION
          "Information about the alarm-specific attributes of
          a single trap in the log."
     INDEX          { atmfM4TrapLogSrc,
                    atmfM4TrapLogType,
                    atmfM4LoggedTrapIndex }
     ::= { atmfM4LoggedAlarmTable 1 }

AtmfM4LoggedAlarmEntry ::= SEQUENCE {
     atmfM4LoggedAlarmSeverity     AtmfM4AlarmLogSeverity,
     atmfM4LoggedAlarmBackedUp     TruthValue,
     atmfM4LoggedAlarmBUObject     RowPointer,
     atmfM4LoggedAlarmSpecificProb DisplayString,
     atmfM4LoggedAlarmRepairAct    DisplayString
          }

atmfM4LoggedAlarmSeverity OBJECT-TYPE
     SYNTAX    AtmfM4AlarmLogSeverity
     MAX-ACCESS     read-only
     STATUS    current
     DESCRIPTION
          "The perceived severity of the alarm, as specified by
          the agent that generated it."
     ::= { atmfM4LoggedAlarmEntry 1 }

atmfM4LoggedAlarmBackedUp OBJECT-TYPE
     SYNTAX    TruthValue
     MAX-ACCESS     read-only
     STATUS    current
     DESCRIPTION
          "If the value of this object is true, the agent reported
          in this trap that the failed object had been backed up.

          This object is only present if it was included in the
          alarm trap corresponding to this log entry."
     ::= { atmfM4LoggedAlarmEntry 2 }

atmfM4LoggedAlarmBUObject OBJECT-TYPE
     SYNTAX    RowPointer
     MAX-ACCESS     read-only
     STATUS    current
     DESCRIPTION
          "Indicates the object that provided back-up services to
          the failed object.

          This object is only present if it was included in the
          alarm trap corresponding to this log entry."
     ::= { atmfM4LoggedAlarmEntry 3 }

atmfM4LoggedAlarmSpecificProb OBJECT-TYPE
     SYNTAX    DisplayString
     MAX-ACCESS     read-only
     STATUS    current
     DESCRIPTION
          "Indicates further refinements to the problem identified
          by the alarm type.  If more than one specific problem
          is described in this object, the problem descriptions are
          separated by newline characters.

          This object is only present if it was included in the
          alarm trap corresponding to this log entry."
     ::= { atmfM4LoggedAlarmEntry 4 }

atmfM4LoggedAlarmRepairAct OBJECT-TYPE
     SYNTAX    DisplayString
     MAX-ACCESS     read-only
     STATUS    current
     DESCRIPTION
          "Indicates proposed repair actions reported by the agent
          for the problem identified by the alarm.  If more than
          one action is described in this object, the problem
          descriptions are separated by newline characters.

          This object is only present if it was included in the
          alarm trap corresponding to this log entry."
     ::= { atmfM4LoggedAlarmEntry 5 }


-- ATM M4 MIB Notification types

-- Auxiliary definitions for alarms

-- Except for perceived severity, the following objects may be
-- optionally appended to any alarm notification.

atmfM4TrapAlarmSeverity OBJECT-TYPE
     SYNTAX    AtmfM4AlarmLogSeverity
     MAX-ACCESS     accessible-for-notify
     STATUS    current
     DESCRIPTION
          "The perceived severity of the alarm, as specified by
          the agent that generated it."
     ::= { atmfM4MIBObjects 43 }

atmfM4TrapAlarmBackedUp OBJECT-TYPE
     SYNTAX    TruthValue
     MAX-ACCESS     accessible-for-notify
     STATUS    current
     DESCRIPTION
          "If the value of this object is true, the failed object
          has been backed up."
     ::= { atmfM4MIBObjects 44 }

atmfM4TrapAlarmBUObject OBJECT-TYPE
     SYNTAX    RowPointer
     MAX-ACCESS     accessible-for-notify
     STATUS    current
     DESCRIPTION
          "Indicates the object that provided back-up services to
          the failed object."
     ::= { atmfM4MIBObjects 45 }

atmfM4TrapAlarmSpecificProb OBJECT-TYPE
     SYNTAX    DisplayString
     MAX-ACCESS     accessible-for-notify
     STATUS    current
     DESCRIPTION
          "Indicates further refinements to the problem identified
          by the alarm type.  If more than one specific problem
          is described in this object, the problem descriptions are
          separated by newline characters."
     ::= { atmfM4MIBObjects 46 }

atmfM4TrapAlarmRepairAct OBJECT-TYPE
     SYNTAX    DisplayString
     MAX-ACCESS     accessible-for-notify
     STATUS    current
     DESCRIPTION
          "Indicates proposed repair actions reported by the agent
          for the problem identified by the alarm.  If more than
          one action is described in this object, the problem
          descriptions are separated by newline characters."
     ::= { atmfM4MIBObjects 47 }


-- ATM M4 MIB Notifications

-- Note that index values for interfaces, hardware units, VPL TPs,
-- VCL TPs, etc. can be derived from the instance values of the
-- objects included in the notifications.  As examples, the ifIndex
-- value for an interface can be derived from the ifOperStatus
-- instance value, whereas the entPhysicalIndex value can be derived
-- from any of the entPhysicalContainedIn, entPhysicalParentRelPos,
-- and entPhysicalClass instance values.


-- Communications Alarms (interface)

atmfM4IfAisAlarm NOTIFICATION-TYPE
     OBJECTS   { ifOperStatus, atmfM4TrapAlarmSeverity }
     STATUS    current
     DESCRIPTION
          "Indicates that an AIS alarm condition has occurred
          on the physical path TP associated with the specified
          interface."
     ::= { atmfM4MIBTrapPrefix 1 }

atmfM4IfLcdAlarm NOTIFICATION-TYPE
     OBJECTS   { ifOperStatus, atmfM4TrapAlarmSeverity }
     STATUS    current
     DESCRIPTION
          "Indicates that an LCD (Loss of Cell Delineation)
          condition has occurred on the TC Adapter associated
          with the specified interface."
     ::= { atmfM4MIBTrapPrefix 2 }

atmfM4IfLofAlarm NOTIFICATION-TYPE
     OBJECTS   { ifOperStatus, atmfM4TrapAlarmSeverity }
     STATUS    current
     DESCRIPTION
          "Indicates that an LOF (Loss of Frame)
          condition has occurred on the physical path TP associated
          with the specified interface."
     ::= { atmfM4MIBTrapPrefix 3 }

atmfM4IfLopAlarm NOTIFICATION-TYPE
     OBJECTS   { ifOperStatus, atmfM4TrapAlarmSeverity }
     STATUS    current
     DESCRIPTION
          "Indicates that an LOP (Loss of Pointer)
          condition has occurred on the physical path TP associated
          with the specified interface."
     ::= { atmfM4MIBTrapPrefix 4 }

atmfM4IfLosAlarm NOTIFICATION-TYPE
     OBJECTS   { ifOperStatus, atmfM4TrapAlarmSeverity }
     STATUS    current
     DESCRIPTION
          "Indicates that an LOS (Loss of Signal)
          condition has occurred on the physical path TP associated
          with the specified interface."
     ::= { atmfM4MIBTrapPrefix 5 }

atmfM4IfPayloadMismatchAlarm NOTIFICATION-TYPE
     OBJECTS   { ifOperStatus, atmfM4TrapAlarmSeverity }
     STATUS    current
     DESCRIPTION
          "Indicates that a payload type mismatch condition has
          occurred on the physical path TP associated with the specified
          interface."
     ::= { atmfM4MIBTrapPrefix 6 }

atmfM4IfXmissionErrAlarm NOTIFICATION-TYPE
     OBJECTS   { ifOperStatus, atmfM4TrapAlarmSeverity }
     STATUS    current
     DESCRIPTION
          "Indicates that an transmission error condition has occurred
          on the physical path TP associated with the specified
          interface."
     ::= { atmfM4MIBTrapPrefix 7 }

atmfM4IfPathTraceMismatchAlarm NOTIFICATION-TYPE
     OBJECTS   { ifOperStatus, atmfM4TrapAlarmSeverity }
     STATUS    current
     DESCRIPTION
          "Indicates that path trace mismatch condition has occurred
          on the physical path TP associated with the specified
          interface."
     ::= { atmfM4MIBTrapPrefix 8 }

atmfM4IfRdiAlarm NOTIFICATION-TYPE
     OBJECTS   { ifOperStatus, atmfM4TrapAlarmSeverity }
     STATUS    current
     DESCRIPTION
          "Indicates that an RDI (Remote Defect Indication)
          condition has occurred on the physical path TP associated
          with the specified interface."
     ::= { atmfM4MIBTrapPrefix 9 }

atmfM4IfSignalLabelMismatchAlarm NOTIFICATION-TYPE
     OBJECTS   { ifOperStatus, atmfM4TrapAlarmSeverity }
     STATUS    current
     DESCRIPTION
          "Indicates that a signal label mismatch has occurred
          on the physical path TP associated with the specified
          interface."
     ::= { atmfM4MIBTrapPrefix 10 }


-- Communications alarms (VPL termination point)

atmfM4VplTpAisAlarm NOTIFICATION-TYPE
     OBJECTS   { ifOperStatus,
                 atmVplOperStatus,
                 atmfM4TrapAlarmSeverity
                 }
     STATUS    current
     DESCRIPTION
          "Indicates that an AIS alarm condition has occurred
          on the VPL TP associated with the specified
          interface and VPI."
     ::= { atmfM4MIBTrapPrefix 11 }

atmfM4VplTpRdiAlarm NOTIFICATION-TYPE
     OBJECTS   { ifOperStatus,
                 atmVplOperStatus,
                 atmfM4TrapAlarmSeverity
                 }
     STATUS    current
     DESCRIPTION
          "Indicates that an RDI (Remote Defect Indication)
          condition has occurred on the VPL TP associated
          with the specified interface and VPI."
     ::= { atmfM4MIBTrapPrefix 12 }


-- Communications alarms (VPC termination point)

atmfM4VpcTpAisAlarm NOTIFICATION-TYPE
     OBJECTS   { ifOperStatus,
                 atmVplOperStatus,
                 atmfM4TrapAlarmSeverity
                 }
     STATUS    current
     DESCRIPTION
          "Indicates that an AIS alarm condition has occurred
          on the VPC TP associated with the specified
          interface and VPI."
     ::= { atmfM4MIBTrapPrefix 13 }

atmfM4VpcTpRdiAlarm NOTIFICATION-TYPE
     OBJECTS   { ifOperStatus,
                 atmVplOperStatus,
                 atmfM4TrapAlarmSeverity
                 }
     STATUS    current
     DESCRIPTION
          "Indicates that an RDI (Remote Defect Indication)
          condition has occurred on the VPC TP associated
          with the specified interface and VPI."
     ::= { atmfM4MIBTrapPrefix 14 }


-- Communications alarms (VCL termination point)

atmfM4VclTpAisAlarm NOTIFICATION-TYPE
     OBJECTS   { ifOperStatus,
                 atmVclOperStatus,
                 atmfM4TrapAlarmSeverity
                 }
     STATUS    current
     DESCRIPTION
          "Indicates that an AIS alarm condition has occurred
          on the VCL TP associated with the specified
          interface, VPI, and VCI."
     ::= { atmfM4MIBTrapPrefix 15 }

atmfM4VclTpRdiAlarm NOTIFICATION-TYPE
     OBJECTS   { ifOperStatus,
                 atmVclOperStatus,
                 atmfM4TrapAlarmSeverity
                 }
     STATUS    current
     DESCRIPTION
          "Indicates that an RDI (Remote Defect Indication)
          condition has occurred on the VCL TP associated
          with the specified interface, VPI, and VCI."
     ::= { atmfM4MIBTrapPrefix 16 }


-- Communications alarms (VCC termination point)

atmfM4VccTpAisAlarm NOTIFICATION-TYPE
     OBJECTS   { ifOperStatus,
                 atmVclOperStatus,
                 atmfM4TrapAlarmSeverity
                 }
     STATUS    current
     DESCRIPTION
          "Indicates that an AIS alarm condition has occurred
          on the VCC TP associated with the specified
          interface, VPI, and VCI."
     ::= { atmfM4MIBTrapPrefix 17 }

atmfM4VccTpRdiAlarm NOTIFICATION-TYPE
     OBJECTS   { ifOperStatus,
                 atmVclOperStatus,
                 atmfM4TrapAlarmSeverity
                 }
     STATUS    current
     DESCRIPTION
          "Indicates that an RDI (Remote Defect Indication)
          condition has occurred on the VCC TP associated
          with the specified interface, VPI, and VCI."
     ::= { atmfM4MIBTrapPrefix 18 }


-- ATM NE and Hardware Unit Alarms

atmfM4HwBackPlaneAlarm NOTIFICATION-TYPE
     OBJECTS   { entPhysicalContainedIn,
                 entPhysicalParentRelPos,
                 entPhysicalClass,
                 atmfM4TrapAlarmSeverity
                 }
     STATUS    current
     DESCRIPTION
          "Indicates that a back-plane failure condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 19 }

atmfM4HwCallEstErrAlarm NOTIFICATION-TYPE
     OBJECTS   { entPhysicalContainedIn,
                 entPhysicalParentRelPos,
                 entPhysicalClass,
                 atmfM4TrapAlarmSeverity
                 }
     STATUS    current
     DESCRIPTION
          "Indicates that a call establishment error condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 20 }

atmfM4HwCongestionAlarm NOTIFICATION-TYPE
     OBJECTS   { entPhysicalContainedIn,
                 entPhysicalParentRelPos,
                 entPhysicalClass,
                 atmfM4TrapAlarmSeverity
                 }
     STATUS    current
     DESCRIPTION
          "Indicates that a congestion condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 21 }

atmfM4HwExtIfDevProbAlarm NOTIFICATION-TYPE
     OBJECTS   { entPhysicalContainedIn,
                 entPhysicalParentRelPos,
                 entPhysicalClass,
                 atmfM4TrapAlarmSeverity
                 }
     STATUS    current
     DESCRIPTION
          "Indicates that an external interface device problem
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 22 }

atmfM4HwLineCardAlarm NOTIFICATION-TYPE
     OBJECTS   { entPhysicalContainedIn,
                 entPhysicalParentRelPos,
                 entPhysicalClass,
                 atmfM4TrapAlarmSeverity
                 }
     STATUS    current
     DESCRIPTION
          "Indicates that a line-card problem condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 23 }

atmfM4HwMultiplexerAlarm NOTIFICATION-TYPE
     OBJECTS   { entPhysicalContainedIn,
                 entPhysicalParentRelPos,
                 entPhysicalClass,
                 atmfM4TrapAlarmSeverity
                 }
     STATUS    current
     DESCRIPTION
          "Indicates that a multiplexer problem condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 24 }

atmfM4HwPowerAlarm NOTIFICATION-TYPE
     OBJECTS   { entPhysicalContainedIn,
                 entPhysicalParentRelPos,
                 entPhysicalClass,
                 atmfM4TrapAlarmSeverity
                 }
     STATUS    current
     DESCRIPTION
          "Indicates that a power problem alarm condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 25 }

atmfM4HwProcessorAlarm NOTIFICATION-TYPE
     OBJECTS   { entPhysicalContainedIn,
                 entPhysicalParentRelPos,
                 entPhysicalClass,
                 atmfM4TrapAlarmSeverity
                 }
     STATUS    current
     DESCRIPTION
          "Indicates that a processor problem alarm condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 26 }

atmfM4HwProtectionPathAlarm NOTIFICATION-TYPE
     OBJECTS   { entPhysicalContainedIn,
                 entPhysicalParentRelPos,
                 entPhysicalClass,
                 atmfM4TrapAlarmSeverity
                 }
     STATUS    current
     DESCRIPTION
          "Indicates that a protection path problem condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 27 }

atmfM4HwReceiverFailAlarm NOTIFICATION-TYPE
     OBJECTS   { entPhysicalContainedIn,
                 entPhysicalParentRelPos,
                 entPhysicalClass,
                 atmfM4TrapAlarmSeverity
                 }
     STATUS    current
     DESCRIPTION
          "Indicates that a receiver failure condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 28 }

atmfM4HwPIUnitMissingAlarm NOTIFICATION-TYPE
     OBJECTS   { entPhysicalContainedIn,
                 entPhysicalParentRelPos,
                 entPhysicalClass,
                 atmfM4TrapAlarmSeverity
                 }
     STATUS    current
     DESCRIPTION
          "Indicates that a plug-in unit missing condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 29 }

atmfM4HwPIUnitProbAlarm NOTIFICATION-TYPE
     OBJECTS   { entPhysicalContainedIn,
                 entPhysicalParentRelPos,
                 entPhysicalClass,
                 atmfM4TrapAlarmSeverity
                 }
     STATUS    current
     DESCRIPTION
          "Indicates that a plug-in unit problem condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 30 }

atmfM4HwPIUnitMismatchAlarm NOTIFICATION-TYPE
     OBJECTS   { entPhysicalContainedIn,
                 entPhysicalParentRelPos,
                 entPhysicalClass,
                 atmfM4TrapAlarmSeverity
                 }
     STATUS    current
     DESCRIPTION
          "Indicates that a plug-in unit type mismatch condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 31 }

atmfM4HwTimingProbAlarm NOTIFICATION-TYPE
     OBJECTS   { entPhysicalContainedIn,
                 entPhysicalParentRelPos,
                 entPhysicalClass,
                 atmfM4TrapAlarmSeverity
                 }
     STATUS    current
     DESCRIPTION
          "Indicates that a timing problem alarm condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 32 }

atmfM4HwXmitterFailAlarm NOTIFICATION-TYPE
     OBJECTS   { entPhysicalContainedIn,
                 entPhysicalParentRelPos,
                 entPhysicalClass,
                 atmfM4TrapAlarmSeverity
                 }
     STATUS    current
     DESCRIPTION
          "Indicates that a transmitter failure condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 33 }

atmfM4HwTrunkCardAlarm NOTIFICATION-TYPE
     OBJECTS   { entPhysicalContainedIn,
                 entPhysicalParentRelPos,
                 entPhysicalClass,
                 atmfM4TrapAlarmSeverity
                 }
     STATUS    current
     DESCRIPTION
          "Indicates that a trunk-card problem condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 34 }

atmfM4HwStorageCapacityAlarm NOTIFICATION-TYPE
     OBJECTS   { entPhysicalContainedIn,
                 entPhysicalParentRelPos,
                 entPhysicalClass,
                 atmfM4TrapAlarmSeverity
                 }
     STATUS    current
     DESCRIPTION
          "Indicates that a storage capacity problem condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 35 }

atmfM4HwMemoryMismatchAlarm NOTIFICATION-TYPE
     OBJECTS   { entPhysicalContainedIn,
                 entPhysicalParentRelPos,
                 entPhysicalClass,
                 atmfM4TrapAlarmSeverity
                 }
     STATUS    current
     DESCRIPTION
          "Indicates that a memory mismatch alarm condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 36 }

atmfM4HwCorruptDataAlarm NOTIFICATION-TYPE
     OBJECTS   { entPhysicalContainedIn,
                 entPhysicalParentRelPos,
                 entPhysicalClass,
                 atmfM4TrapAlarmSeverity
                 }
     STATUS    current
     DESCRIPTION
          "Indicates that a corrupt data alarm condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 37 }

atmfM4HwSwEnvironAlarm NOTIFICATION-TYPE
     OBJECTS   { entPhysicalContainedIn,
                 entPhysicalParentRelPos,
                 entPhysicalClass,
                 atmfM4TrapAlarmSeverity
                 }
     STATUS    current
     DESCRIPTION
          "Indicates that a software environment problem
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 38 }

atmfM4HwSwDownloadFailAlarm NOTIFICATION-TYPE
     OBJECTS   { entPhysicalContainedIn,
                 entPhysicalParentRelPos,
                 entPhysicalClass,
                 atmfM4TrapAlarmSeverity
                 }
     STATUS    current
     DESCRIPTION
          "Indicates that a software download failure
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 39 }

atmfM4HwVersionMismatchAlarm NOTIFICATION-TYPE
     OBJECTS   { entPhysicalContainedIn,
                 entPhysicalParentRelPos,
                 entPhysicalClass,
                 atmfM4TrapAlarmSeverity
                 }
     STATUS    current
     DESCRIPTION
          "Indicates that a version mismatch condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 40 }

atmfM4HwFanFailAlarm NOTIFICATION-TYPE
     OBJECTS   { entPhysicalContainedIn,
                 entPhysicalParentRelPos,
                 entPhysicalClass,
                 atmfM4TrapAlarmSeverity
                 }
     STATUS    current
     DESCRIPTION
          "Indicates that a cooling fan failure condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 41 }

atmfM4HwDoorOpenAlarm NOTIFICATION-TYPE
     OBJECTS   { entPhysicalContainedIn,
                 entPhysicalParentRelPos,
                 entPhysicalClass,
                 atmfM4TrapAlarmSeverity
                 }
     STATUS    current
     DESCRIPTION
          "Indicates that an enclosure door open condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 42 }

atmfM4HwFuseFailAlarm NOTIFICATION-TYPE
     OBJECTS   { entPhysicalContainedIn,
                 entPhysicalParentRelPos,
                 entPhysicalClass,
                 atmfM4TrapAlarmSeverity
                 }
     STATUS    current
     DESCRIPTION
          "Indicates that a fuse failure alarm condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 43 }

atmfM4HwHighTempAlarm NOTIFICATION-TYPE
     OBJECTS   { entPhysicalContainedIn,
                 entPhysicalParentRelPos,
                 entPhysicalClass,
                 atmfM4TrapAlarmSeverity
                 }
     STATUS    current
     DESCRIPTION
          "Indicates that a high temperature condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 44 }


-- Software alarms

atmfM4SwVersionMismatchAlarm NOTIFICATION-TYPE
     OBJECTS   { entPhysicalContainedIn,
                 entPhysicalParentRelPos,
                 entPhysicalClass,
                 atmfM4HwInstalledSwSwIndex,
                 atmfM4TrapAlarmSeverity
                 }
     STATUS    current
     DESCRIPTION
          "Indicates that a version mismatch condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 45 }


--  State change notification traps

atmfM4VplTpUp NOTIFICATION-TYPE
     OBJECTS   { ifOperStatus, atmVplOperStatus }
     STATUS    current
     DESCRIPTION
          "Indicates that the operational state of the specified
          VPL termination point has transitioned to 'up'."
     ::= { atmfM4MIBTrapPrefix 46 }

atmfM4VplTpDown NOTIFICATION-TYPE
     OBJECTS   { ifOperStatus, atmVplOperStatus }
     STATUS    current
     DESCRIPTION
          "Indicates that the operational state of the specified
          VPL termination point has transitioned to 'down'."
     ::= { atmfM4MIBTrapPrefix 47 }

atmfM4VclTpUp NOTIFICATION-TYPE
     OBJECTS   { ifOperStatus, atmVclOperStatus }
     STATUS    current
     DESCRIPTION
          "Indicates that the operational state of the specified
          VCL termination point has transitioned to 'up'."
     ::= { atmfM4MIBTrapPrefix 48 }

atmfM4VclTpDown NOTIFICATION-TYPE
     OBJECTS   { ifOperStatus, atmVclOperStatus }
     STATUS    current
     DESCRIPTION
          "Indicates that the operational state of the specified
          VCL termination point has transitioned to 'down'."
     ::= { atmfM4MIBTrapPrefix 49 }

atmfM4VplXConnUp NOTIFICATION-TYPE
     OBJECTS   { atmVpCrossConnectL2HOperStatus,
                 atmVpCrossConnectH2LOperStatus
                 }
     STATUS    current
     DESCRIPTION
          "Indicates that the operational state of the specified
          VPL cross-connection has transitioned to 'up'."
     ::= { atmfM4MIBTrapPrefix 50 }

atmfM4VplXConnDown NOTIFICATION-TYPE
     OBJECTS   { atmVpCrossConnectL2HOperStatus,
                 atmVpCrossConnectH2LOperStatus
                 }
     STATUS    current
     DESCRIPTION
          "Indicates that the operational state of the specified
          VPL cross-connection has transitioned to 'down'."
     ::= { atmfM4MIBTrapPrefix 51 }

atmfM4VclXConnUp NOTIFICATION-TYPE
     OBJECTS   { atmVcCrossConnectL2HOperStatus,
                 atmVcCrossConnectH2LOperStatus
                 }
     STATUS    current
     DESCRIPTION
          "Indicates that the operational state of the specified
          VCL cross-connection has transitioned to 'up'."
     ::= { atmfM4MIBTrapPrefix 52 }

atmfM4VclXConnDown NOTIFICATION-TYPE
     OBJECTS   { atmVcCrossConnectL2HOperStatus,
                 atmVcCrossConnectH2LOperStatus
                 }
     STATUS    current
     DESCRIPTION
          "Indicates that the operational state of the specified
          VCL cross-connection has transitioned to 'down'."
     ::= { atmfM4MIBTrapPrefix 53 }

atmfM4HwUnitUp NOTIFICATION-TYPE
     OBJECTS   { entPhysicalContainedIn,
                 entPhysicalParentRelPos,
                 entPhysicalClass
                 }
     STATUS    current
     DESCRIPTION
          "Indicates that the operational state of the specified
          hardware unit has transitioned to 'up'."
     ::= { atmfM4MIBTrapPrefix 54 }

atmfM4HwUnitDown NOTIFICATION-TYPE
     OBJECTS   { entPhysicalContainedIn,
                 entPhysicalParentRelPos,
                 entPhysicalClass
                 }
     STATUS    current
     DESCRIPTION
          "Indicates that the operational state of the specified
          hardware unit has transitioned to 'down'."
     ::= { atmfM4MIBTrapPrefix 55 }


-- Object creation and deletion notification traps

atmfM4AtmCellIfCreated NOTIFICATION-TYPE
     OBJECTS   { ifOperStatus, atmfM4IfType }
     STATUS    current
     DESCRIPTION
          "Indicates that an ATM cell layer interface has just
          been created on the interface."
     ::= { atmfM4MIBTrapPrefix 56 }

atmfM4AtmCellIfDeleted NOTIFICATION-TYPE
     OBJECTS   { ifOperStatus }
     STATUS    current
     DESCRIPTION
          "Indicates that the ATM cell layer interface has just
          been deleted."
     ::= { atmfM4MIBTrapPrefix 57 }

atmfM4VpcTpCreated NOTIFICATION-TYPE
     OBJECTS   { ifOperStatus, atmVplOperStatus }
     STATUS    current
     DESCRIPTION
          "Indicates that the VPC termination point has just
          been created."
     ::= { atmfM4MIBTrapPrefix 58 }

atmfM4VpcTpDeleted NOTIFICATION-TYPE
     OBJECTS   { ifOperStatus, atmVplOperStatus }
     STATUS    current
     DESCRIPTION
          "Indicates that the VPC termination point has just
          been deleted."
     ::= { atmfM4MIBTrapPrefix 59 }

atmfM4VccTpCreated NOTIFICATION-TYPE
     OBJECTS   { ifOperStatus, atmVclOperStatus }
     STATUS    current
     DESCRIPTION
          "Indicates that the VCC termination point has just
          been created."
     ::= { atmfM4MIBTrapPrefix 60 }

atmfM4VccTpDeleted NOTIFICATION-TYPE
     OBJECTS   { ifOperStatus, atmVclOperStatus }
     STATUS    current
     DESCRIPTION
          "Indicates that the VCC termination point has just
          been deleted."
     ::= { atmfM4MIBTrapPrefix 61 }

atmfM4VplXConnCreated NOTIFICATION-TYPE
     OBJECTS   { atmVpCrossConnectL2HOperStatus,
                 atmVpCrossConnectH2LOperStatus
                 }
     STATUS    current
     DESCRIPTION
          "Indicates that the VPL cross-connection has just
          been created.  When a cross-connection is created along
          with its VPL endpoints, this trap should be emitted
          to indicate the creation of the entire group of objects."
     ::= { atmfM4MIBTrapPrefix 62 }

atmfM4VplXConnDeleted NOTIFICATION-TYPE
     OBJECTS   { atmVpCrossConnectL2HOperStatus,
                 atmVpCrossConnectH2LOperStatus
                 }
     STATUS    current
     DESCRIPTION
          "Indicates that the VPL cross-connection has just
          been deleted.  When a cross-connection is deleted along
          with its VPL endpoints, this trap should be emitted
          to indicate the deletion of the entire group of objects."
     ::= { atmfM4MIBTrapPrefix 63 }

atmfM4VclXConnCreated NOTIFICATION-TYPE
     OBJECTS   { atmVcCrossConnectL2HOperStatus,
                 atmVcCrossConnectH2LOperStatus
                 }
     STATUS    current
     DESCRIPTION
          "Indicates that the VCL cross-connection has just
          been created.  When a cross-connection is created along
          with its VCL endpoints, this trap should be emitted
          to indicate the creation of the entire group of objects."
     ::= { atmfM4MIBTrapPrefix 64 }

atmfM4VclXConnDeleted NOTIFICATION-TYPE
     OBJECTS   { atmVcCrossConnectL2HOperStatus,
                 atmVcCrossConnectH2LOperStatus
                 }
     STATUS    current
     DESCRIPTION
          "Indicates that the VCL cross-connection has just
          been deleted.  When a cross-connection is deleted along
          with its VCL endpoints, this trap should be emitted
          to indicate the deletion of the entire group of objects."
     ::= { atmfM4MIBTrapPrefix 65 }

atmfM4HwUnitCreated NOTIFICATION-TYPE
     OBJECTS   { entPhysicalContainedIn,
                 entPhysicalParentRelPos,
                 entPhysicalClass
                 }
     STATUS    current
     DESCRIPTION
          "Indicates that the specified hardware unit has been
          installed at the specified location."
     ::= { atmfM4MIBTrapPrefix 66 }

atmfM4HwUnitDeleted NOTIFICATION-TYPE
     OBJECTS   { entPhysicalContainedIn,
                 entPhysicalParentRelPos,
                 entPhysicalClass
                 }
     STATUS    current
     DESCRIPTION
          "Indicates that the specified hardware unit has been
          removed or de-installed from the specified location."
     ::= { atmfM4MIBTrapPrefix 67 }

atmfM4InstalledSwCreated NOTIFICATION-TYPE
     OBJECTS   { atmfM4HwInstalledSwSwIndex,
                 hrSWInstalledIndex,
                 hrSWInstalledName
                 }
     STATUS    current
     DESCRIPTION
          "Indicates that the specified software package has been
          installed."
     ::= { atmfM4MIBTrapPrefix 68 }

atmfM4InstalledSwDeleted NOTIFICATION-TYPE
     OBJECTS   { atmfM4HwInstalledSwSwIndex,
                 hrSWInstalledIndex,
                 hrSWInstalledName
                 }
     STATUS    current
     DESCRIPTION
          "Indicates that the specified software package has been
          removed."
     ::= { atmfM4MIBTrapPrefix 69 }


--  Configuration change notification traps

atmfM4IfChanged NOTIFICATION-TYPE
     OBJECTS   { ifOperStatus }
     STATUS    current
     DESCRIPTION
          "Indicates that the configuration of the interface has
          been changed."
     ::= { atmfM4MIBTrapPrefix 70 }

atmfM4VplTpChanged NOTIFICATION-TYPE
     OBJECTS   { ifOperStatus, atmVplOperStatus }
     STATUS    current
     DESCRIPTION
          "Indicates that the VPL termination point configuration
          has been changed."
     ::= { atmfM4MIBTrapPrefix 71 }

atmfM4VclTpChanged NOTIFICATION-TYPE
     OBJECTS   { ifOperStatus, atmVclOperStatus }
     STATUS    current
     DESCRIPTION
          "Indicates that the VCL termination point configuration
          has been changed."
     ::= { atmfM4MIBTrapPrefix 72 }

atmfM4VplXConnChanged NOTIFICATION-TYPE
     OBJECTS   { atmVpCrossConnectL2HOperStatus,
                 atmVpCrossConnectH2LOperStatus
                 }
     STATUS    current
     DESCRIPTION
          "Indicates that the VPL cross-connection configuration
          has been changed."
     ::= { atmfM4MIBTrapPrefix 73 }

atmfM4VclXConnChanged NOTIFICATION-TYPE
     OBJECTS   { atmVcCrossConnectL2HOperStatus,
                 atmVcCrossConnectH2LOperStatus
                 }
     STATUS    current
     DESCRIPTION
          "Indicates that the VCL cross-connection configuration
          has been changed."
     ::= { atmfM4MIBTrapPrefix 74 }

atmfM4HwUnitChanged NOTIFICATION-TYPE
     OBJECTS   { entPhysicalContainedIn,
                 entPhysicalParentRelPos,
                 entPhysicalClass
                 }
     STATUS    current
     DESCRIPTION
          "Indicates that the specified hardware unit configuration
          has changed."
     ::= { atmfM4MIBTrapPrefix 75 }

atmfM4InstalledSwChanged NOTIFICATION-TYPE
     OBJECTS   { hrSWInstalledIndex }
     STATUS    current
     DESCRIPTION
          "Indicates that the specified software package configuration
          has changed."
     ::= { atmfM4MIBTrapPrefix 76 }


-- Conformance statements


atmfM4Groups      OBJECT IDENTIFIER ::= { atmfM4MIBConformance 1 }
atmfM4Compliances OBJECT IDENTIFIER ::= { atmfM4MIBConformance 2 }

-- compliance statements

atmfM4Compliance MODULE-COMPLIANCE
     STATUS    current
     DESCRIPTION
          "The compliance statements are listed as a set up conformance
          units that correspond to each table.  Support for all tables
          is mandatory."
     MODULE  -- this module
     MANDATORY-GROUPS {
          atmfM4General,
          atmfM4PhysPathTpGroup,
          atmfM4TcAdapterGroup,
          atmfM4AtmLayerGroup,
          atmfM4VplGroup,
          atmfM4VclGroup,
          atmfM4VpXConnGroup,
          atmfM4VcXConnGroup,
          atmfM4VpNextVpiGroup,
          atmfM4VcNextVciGroup,
          atmfM4CellProtoCurrGroup,
          atmfM4CellProtoHistGroup,
          atmfM4CellProtoErrorGroup,
          atmfM4TcProtoCurrGroup,
          atmfM4TcProtoHistGroup,
          atmfM4VpUpcNpcCurrGroup,
          atmfM4VpUpcNpcHistGroup,
          atmfM4VcUpcNpcCurrGroup,
          atmfM4VcUpcNpcHistGroup,
          atmfM4VpTestGroup,
          atmfM4VcTestGroup,
          atmfM4EquipGroup,
          atmfM4EquipHolderGroup,
          atmfM4PlugInUnitGroup,
          atmfM4HwRunningSwGroup,
          atmfM4HwInstalledSwGroup,
          atmfM4AlarmSevGroup,
          atmfM4TrapForwardingGroup,
          atmfM4TrapLogGroup,
          atmfM4LoggedTrapGroup,
          atmfM4LoggedAlarmGroup,
          atmfM4NotificationsGroup
          }

     OBJECT atmfM4TcACellScrambling
     MIN-ACCESS     not-accessible
     DESCRIPTION
          "Support for this object is required only for a TC Adapter
          which allows deactivation of cell scrambling."

     OBJECT atmfM4IfLoopbackLocationCode
     MIN-ACCESS     not-accessible
     DESCRIPTION
          "Support for this object is only required for an ATM cell
          layer interface whose atmfM4IfType is not none(0)."

     OBJECT atmfM4IfSubscriberAddress
     MIN-ACCESS     not-accessible
     DESCRIPTION
          "Support for this object is required only for an ATM cell
          layer interface whose atmfM4IfType is uni(1)."

     OBJECT atmfM4IfPreferredCarrier
     MIN-ACCESS     not-accessible
     DESCRIPTION
          "Support for this object is only required for an ATM cell
          layer interface whose atmfM4IfType is uni(1) and which
          supports SVC services."

     OBJECT atmfM4IfFarEndCarrierNetwork
     MIN-ACCESS     not-accessible
     DESCRIPTION
          "Support for this object is only required for an ATM cell
          layer interface whose atmfM4IfType is bici(2) and which
          supports SVC services."

     OBJECT atmfM4VpNextVpiValue
     MIN-ACCESS     not-accessible
     DESCRIPTION
          "Support for this object to supply unused VPI values for
          use in creating entries in the atmVplTable is optional."

     OBJECT atmfM4VcNextVciValue
     MIN-ACCESS     not-accessible
     DESCRIPTION
          "Support for this object to supply unused VCI values for
          use in creating entries in the atmVclTable is optional."

     OBJECT atmfM4VpUpcNpcCurrDiscardedClp0
     MIN-ACCESS     not-accessible
     DESCRIPTION
          "Support for this object is required only if CLP=0 traffic
          is separately policed."

     OBJECT atmfM4VpUpcNpcCurrPassedClp0
     MIN-ACCESS     not-accessible
     DESCRIPTION
          "Support for this object is required only if CLP=0 traffic
          is separately policed."

     OBJECT atmfM4VpUpcNpcHistDiscardedClp0
     MIN-ACCESS     not-accessible
     DESCRIPTION
          "Support for this object is required only if CLP=0 traffic
          is separately policed."

     OBJECT atmfM4VpUpcNpcHistPassedClp0
     MIN-ACCESS     not-accessible
     DESCRIPTION
          "Support for this object is required only if CLP=0 traffic
          is separately policed."

     OBJECT atmfM4VcUpcNpcCurrDiscardedClp0
     MIN-ACCESS     not-accessible
     DESCRIPTION
          "Support for this object is required only if CLP=0 traffic
          is separately policed."

     OBJECT atmfM4VcUpcNpcCurrPassedClp0
     MIN-ACCESS     not-accessible
     DESCRIPTION
          "Support for this object is required only if CLP=0 traffic
          is separately policed."

     OBJECT atmfM4VcUpcNpcHistDiscardedClp0
     MIN-ACCESS     not-accessible
     DESCRIPTION
          "Support for this object is required only if CLP=0 traffic
          is separately policed."

     OBJECT atmfM4VcUpcNpcHistPassedClp0
     MIN-ACCESS     not-accessible
     DESCRIPTION
          "Support for this object is required only if CLP=0 traffic
          is separately policed."

     OBJECT atmfM4EquipHolderAcceptableTypes
     MIN-ACCESS     not-accessible
     DESCRIPTION
          "Support for this object is required only for an Equipment
          Holder that represents a slot."

     OBJECT atmfM4EquipHolderSlotStatus
     MIN-ACCESS     not-accessible
     DESCRIPTION
          "Support for this object is required only for an Equipment
          Holder that represents a slot."

     OBJECT atmfM4EquipHolderSwLoad
     MIN-ACCESS     not-accessible
     DESCRIPTION
          "Support for this object is required only for an Equipment
          Holder that represents a slot."

     OBJECT atmfM4LoggedAlarmBackedUp
     MIN-ACCESS     not-accessible
     DESCRIPTION
          "Support for this object is required only for a logged alarm
          trap table entry whose corresponding alarm trap included the
          atmfM4TrapAlarmBackup object."

     OBJECT atmfM4LoggedAlarmBUObject
     MIN-ACCESS     not-accessible
     DESCRIPTION
          "Support for this object is required only for a logged alarm
          trap table entry whose corresponding alarm trap included the
          atmfM4TrapAlarmBUObject object."

     OBJECT atmfM4LoggedAlarmSpecificProb
     MIN-ACCESS     not-accessible
     DESCRIPTION
          "Support for this object is required only for a logged alarm
          trap table entry whose corresponding alarm trap included the
          atmfM4TrapAlarmSpecificProb object."

     OBJECT atmfM4LoggedAlarmRepairAct
     MIN-ACCESS     not-accessible
     DESCRIPTION
          "Support for this object is required only for a logged alarm
          trap table entry whose corresponding alarm trap included the
          atmfM4TrapAlarmRepairAct object."

     ::= { atmfM4Compliances 1 }

-- units of conformance

atmfM4General OBJECT-GROUP
     OBJECTS {
          atmfM4NeVendor,
          atmfM4NeVersion,
          atmfM4NeStartTime,
          atmfM4NeAlarmSeverityIndex,
          atmfM4NeSuppressZeroStats
          }
     STATUS    current
     DESCRIPTION
          "The ATM Forum M4 ATM NE high-level objects."
     ::= { atmfM4Groups 1}

atmfM4PhysPathTpGroup OBJECT-GROUP
     OBJECTS {
          atmfM4PhysPathTpHwUnitIndex,
          atmfM4PhysPathTpPortID,
          atmfM4PhysPathTpAlarmSeverityIndex
          }
     STATUS    current
     DESCRIPTION
          "The ATM Forum M4 interface Configuration table extensions
          for the physical path termination point."
     ::= { atmfM4Groups 2 }

atmfM4TcAdapterGroup OBJECT-GROUP
     OBJECTS {
          atmfM4TcACellScrambling,
          atmfM4TcAlarmSeverityIndex
          }
     STATUS    current
     DESCRIPTION
          "The ATM Forum M4 interface Configuration table extensions
          for the TC Adapter."
     ::= { atmfM4Groups 3 }

atmfM4AtmLayerGroup OBJECT-GROUP
     OBJECTS {
          atmfM4IfType,
          atmfM4IfLoopbackLocationCode,
          atmfM4IfSubscriberAddress,
          atmfM4IfPreferredCarrier,
          atmfM4IfFarEndCarrierNetwork
          }
     STATUS    current
     DESCRIPTION
          "The ATM Forum M4 interface Configuration table extensions
          for the ATM cell layer."
     ::= { atmfM4Groups 4 }

atmfM4VplGroup OBJECT-GROUP
     OBJECTS {
          atmfM4VplSegEndPt
          }
     STATUS    current
     DESCRIPTION
          "The ATM Forum M4 VPL Termination Point Configuration
          table extensions. "
     ::= { atmfM4Groups 5 }

atmfM4VclGroup OBJECT-GROUP
     OBJECTS {
          atmfM4VclSegEndPt
          }
     STATUS    current
     DESCRIPTION
          "The ATM Forum M4 VCL Termination Point Configuration
          table extensions."
     ::= { atmfM4Groups 6 }

atmfM4VpXConnGroup OBJECT-GROUP
     OBJECTS {
          atmfM4VpXConnRecover
          }
     STATUS    current
     DESCRIPTION
          "The ATM Forum M4 VP Cross-Connect Configuration table
          extensions."
     ::= { atmfM4Groups 7 }

atmfM4VcXConnGroup OBJECT-GROUP
     OBJECTS {
          atmfM4VcXConnRecover
          }
     STATUS    current
     DESCRIPTION
          "The ATM Forum M4 VC Cross-Connect Configuration table
          extensions."
     ::= { atmfM4Groups 8 }

atmfM4VpNextVpiGroup OBJECT-GROUP
     OBJECTS {
          atmfM4VpNextVpiValue
          }
     STATUS    current
     DESCRIPTION
          "The ATM Forum M4 VP Next VPI value table."
     ::= { atmfM4Groups 9 }

atmfM4VcNextVciGroup OBJECT-GROUP
     OBJECTS {
          atmfM4VcNextVciValue
          }
     STATUS    current
     DESCRIPTION
          "The ATM Forum M4 VC Next VCI value table."
     ::= { atmfM4Groups 10 }

atmfM4CellProtoCurrGroup OBJECT-GROUP
     OBJECTS {
          atmfM4CellProtoCurrSuspect,
          atmfM4CellProtoCurrElapsedTime,
          atmfM4CellProtoCurrSupprIntvls,
          atmfM4CellProtoCurrProtoErrors,
          atmfM4CellProtoCurrInOAMCells
          }
     STATUS    current
     DESCRIPTION
          "The ATM Forum M4 Cell Protocol Monitoring Current Data
          table."
     ::= { atmfM4Groups 11 }

atmfM4CellProtoHistGroup OBJECT-GROUP
     OBJECTS {
          atmfM4CellProtoHistSuspect,
          atmfM4CellProtoHistElapsedTime,
          atmfM4CellProtoHistSupprIntvls,
          atmfM4CellProtoHistProtoErrors,
          atmfM4CellProtoHistInOAMCells
          }
     STATUS    current
     DESCRIPTION
          "The ATM Forum M4 Cell Protocol Monitoring History Data
          table."
     ::= { atmfM4Groups 12 }

atmfM4CellProtoErrorGroup OBJECT-GROUP
     OBJECTS {
          atmfM4CellProtoErrorTime,
          atmfM4CellProtoErrorReason,
          atmfM4CellProtoErrorVpi,
          atmfM4CellProtoErrorVci
          }
     STATUS    current
     DESCRIPTION
          "The ATM Forum M4 Cell Protocol Monitoring Error Log table."
     ::= { atmfM4Groups 13 }

atmfM4TcProtoCurrGroup OBJECT-GROUP
     OBJECTS {
          atmfM4TcProtoCurrSuspect,
          atmfM4TcProtoCurrElapsedTime,
          atmfM4TcProtoCurrSupprIntvls,
          atmfM4TcProtoCurrDiscardHECViol
          }
     STATUS    current
     DESCRIPTION
          "The ATM Forum M4 TC Adapter Protocol Monitoring Current
          Data table."
     ::= { atmfM4Groups 14 }

atmfM4TcProtoHistGroup OBJECT-GROUP
     OBJECTS {
          atmfM4TcProtoHistSuspect,
          atmfM4TcProtoHistElapsedTime,
          atmfM4TcProtoHistSupprIntvls,
          atmfM4TcProtoHistDiscardHECViol
          }
     STATUS    current
     DESCRIPTION
          "The ATM Forum M4 TC Adapter Protocol Monitoring History
          Data table."
     ::= { atmfM4Groups 15 }

atmfM4VpUpcNpcCurrGroup OBJECT-GROUP
     OBJECTS {
          atmfM4VpUpcNpcCurrSuspect,
          atmfM4VpUpcNpcCurrElapsedTime,
          atmfM4VpUpcNpcCurrSupprIntvls,
          atmfM4VpUpcNpcCurrDiscardedCells,
          atmfM4VpUpcNpcCurrDiscardedClp0,
          atmfM4VpUpcNpcCurrPassedCells,
          atmfM4VpUpcNpcCurrPassedClp0
          }
     STATUS    current
     DESCRIPTION
          "The ATM Forum M4 UPC/NPC Disagreement Monitoring Current
          Data table for VPL termination points."
     ::= { atmfM4Groups 16 }

atmfM4VpUpcNpcHistGroup OBJECT-GROUP
     OBJECTS {
          atmfM4VpUpcNpcHistSuspect,
          atmfM4VpUpcNpcHistElapsedTime,
          atmfM4VpUpcNpcHistSupprIntvls,
          atmfM4VpUpcNpcHistDiscardedCells,
          atmfM4VpUpcNpcHistDiscardedClp0,
          atmfM4VpUpcNpcHistPassedCells,
          atmfM4VpUpcNpcHistPassedClp0
          }
     STATUS    current
     DESCRIPTION
          "The ATM Forum M4 UPC/NPC Disagreement Monitoring History
          Data table for VPL termination points."
     ::= { atmfM4Groups 17 }

atmfM4VcUpcNpcCurrGroup OBJECT-GROUP
     OBJECTS {
          atmfM4VcUpcNpcCurrSuspect,
          atmfM4VcUpcNpcCurrElapsedTime,
          atmfM4VcUpcNpcCurrSupprIntvls,
          atmfM4VcUpcNpcCurrDiscardedCells,
          atmfM4VcUpcNpcCurrDiscardedClp0,
          atmfM4VcUpcNpcCurrPassedCells,
          atmfM4VcUpcNpcCurrPassedClp0
          }
     STATUS    current
     DESCRIPTION
          "The ATM Forum M4 UPC/NPC Disagreement Monitoring Current
          Data table for VCL termination points."
     ::= { atmfM4Groups 18 }

atmfM4VcUpcNpcHistGroup OBJECT-GROUP
     OBJECTS {
          atmfM4VcUpcNpcHistSuspect,
          atmfM4VcUpcNpcHistElapsedTime,
          atmfM4VcUpcNpcHistSupprIntvls,
          atmfM4VcUpcNpcHistDiscardedCells,
          atmfM4VcUpcNpcHistDiscardedClp0,
          atmfM4VcUpcNpcHistPassedCells,
          atmfM4VcUpcNpcHistPassedClp0
          }
     STATUS    current
     DESCRIPTION
          "The ATM Forum M4 UPC/NPC Disagreement Monitoring History
          Data table for VCL termination points."
     ::= { atmfM4Groups 19 }

atmfM4VpTestGroup OBJECT-GROUP
     OBJECTS {
          atmfM4VpTestId,
          atmfM4VpTestStatus,
          atmfM4VpTestType,
          atmfM4VpTestResult,
          atmfM4VpTestCode,
          atmfM4VpTestOwner
          }
     STATUS    current
     DESCRIPTION
          "The ATM Forum M4 VP Termination Point Test table."
     ::= { atmfM4Groups 20 }

atmfM4VcTestGroup OBJECT-GROUP
     OBJECTS {
          atmfM4VcTestId,
          atmfM4VcTestStatus,
          atmfM4VcTestType,
          atmfM4VcTestResult,
          atmfM4VcTestCode,
          atmfM4VcTestOwner
          }
     STATUS    current
     DESCRIPTION
          "The ATM Forum M4 VC Termination Point Test table."
     ::= { atmfM4Groups 21 }

atmfM4EquipGroup OBJECT-GROUP
     OBJECTS {
          atmfM4EquipAdminStatus,
          atmfM4EquipLocation,
          atmfM4EquipOperStatus,
          atmfM4EquipVendor,
          atmfM4EquipVersion,
          atmfM4EquipUserLabel,
          atmfM4EquipAlarmSeverityIndex
          }
     STATUS    current
     DESCRIPTION
          "The ATM Forum M4 Equipment table."
     ::= { atmfM4Groups 22 }

atmfM4EquipHolderGroup OBJECT-GROUP
     OBJECTS {
          atmfM4EquipHolderType,
          atmfM4EquipHolderAcceptableTypes,
          atmfM4EquipHolderSlotStatus,
          atmfM4EquipHolderSwLoad
          }
     STATUS    current
     DESCRIPTION
          "The ATM Forum M4 Equipment Holder table."
     ::= { atmfM4Groups 23 }

atmfM4PlugInUnitGroup OBJECT-GROUP
     OBJECTS {
          atmfM4PlugInUnitAdminStatus,
          atmfM4PlugInUnitAvailStatus,
          atmfM4PlugInUnitOperStatus,
          atmfM4PlugInUnitVendor,
          atmfM4PlugInUnitVersion,
          atmfM4PlugInUnitAlarmSeverityIndex
          }
     STATUS    current
     DESCRIPTION
          "The ATM Forum M4 Plug-In Unit table."
     ::= { atmfM4Groups 24 }

atmfM4HwRunningSwGroup OBJECT-GROUP
     OBJECTS {
          atmfM4HwRunningSwSwIndex
          }
     STATUS    current
     DESCRIPTION
          "The ATM Forum M4 Hardware Unit/Running Software table."
     ::= { atmfM4Groups 25 }

atmfM4HwInstalledSwGroup OBJECT-GROUP
     OBJECTS {
          atmfM4HwInstalledSwSwIndex,
          atmfM4HwSwAlarmSeverityIndex
          }
     STATUS    current
     DESCRIPTION
          "The ATM Forum M4 Hardware Unit/Installed Software table."
     ::= { atmfM4Groups 26 }

atmfM4AlarmSevGroup OBJECT-GROUP
     OBJECTS {
          atmfM4AlarmSevProfileRowStatus,
          atmfM4AlarmSeverity,
          atmfM4AlarmSevDefault,
          atmfM4AlarmSevProfileIndexNext
          }
     STATUS    current
     DESCRIPTION
          "The ATM Forum M4 Alarm handling objects."
     ::= { atmfM4Groups 27 }

atmfM4TrapForwardingGroup OBJECT-GROUP
     OBJECTS {
          atmfM4TrapForwardingDest,
          atmfM4ForwardedTrapId,
          atmfM4ForwardedTrapObject,
          atmfM4TrapForwardingPort,
          atmfM4LowestForwardedSeverity,
          atmfM4ForwardedIndeterminate,
          atmfM4TrapForwardingRowStatus
          }
     STATUS    current
     DESCRIPTION
          "The ATM Forum M4 Trap forwarding table."
     ::= { atmfM4Groups 28 }

atmfM4TrapLogGroup OBJECT-GROUP
     OBJECTS {
          atmfM4TrapLogAdminStatus,
          atmfM4TrapLogOperStatus,
          atmfM4TrapLogFullAction,
          atmfM4TrapLogRowStatus
          }
     STATUS    current
     DESCRIPTION
          "The ATM Forum M4 Trap Agent log table."
     ::= { atmfM4Groups 29 }

atmfM4LoggedTrapGroup OBJECT-GROUP
     OBJECTS {
          atmfM4LoggedTrapTime,
          atmfM4LoggedTrapID,
          atmfM4LoggedTrapObject,
          atmfM4LoggedTrapRowStatus
          }
     STATUS    current
     DESCRIPTION
          "The ATM Forum M4 Trap Agent logged trap table."
     ::= { atmfM4Groups 30 }

atmfM4LoggedAlarmGroup OBJECT-GROUP
     OBJECTS {
          atmfM4LoggedAlarmSeverity,
          atmfM4LoggedAlarmBackedUp,
          atmfM4LoggedAlarmBUObject,
          atmfM4LoggedAlarmSpecificProb,
          atmfM4LoggedAlarmRepairAct,
          atmfM4TrapAlarmSeverity,
          atmfM4TrapAlarmBackedUp,
          atmfM4TrapAlarmBUObject,
          atmfM4TrapAlarmSpecificProb,
          atmfM4TrapAlarmRepairAct
          }
     STATUS    current
     DESCRIPTION
          "The ATM Forum M4 Trap Agent logged alarm trap table."
     ::= { atmfM4Groups 31 }

atmfM4NotificationsGroup NOTIFICATION-GROUP
     NOTIFICATIONS {
          atmfM4IfAisAlarm,
          atmfM4IfLcdAlarm,
          atmfM4IfLofAlarm,
          atmfM4IfLopAlarm,
          atmfM4IfLosAlarm,
          atmfM4IfPayloadMismatchAlarm,
          atmfM4IfXmissionErrAlarm,
          atmfM4IfPathTraceMismatchAlarm,
          atmfM4IfRdiAlarm,
          atmfM4IfSignalLabelMismatchAlarm,
          atmfM4VplTpAisAlarm,
          atmfM4VplTpRdiAlarm,
          atmfM4VpcTpAisAlarm,
          atmfM4VpcTpRdiAlarm,
          atmfM4VclTpAisAlarm,
          atmfM4VclTpRdiAlarm,
          atmfM4VccTpAisAlarm,
          atmfM4VccTpRdiAlarm,
          atmfM4HwBackPlaneAlarm,
          atmfM4HwCallEstErrAlarm,
          atmfM4HwCongestionAlarm,
          atmfM4HwExtIfDevProbAlarm,
          atmfM4HwLineCardAlarm,
          atmfM4HwMultiplexerAlarm,
          atmfM4HwPowerAlarm,
          atmfM4HwProcessorAlarm,
          atmfM4HwProtectionPathAlarm,
          atmfM4HwReceiverFailAlarm,
          atmfM4HwPIUnitMissingAlarm,
          atmfM4HwPIUnitProbAlarm,
          atmfM4HwPIUnitMismatchAlarm,
          atmfM4HwTimingProbAlarm,
          atmfM4HwXmitterFailAlarm,
          atmfM4HwTrunkCardAlarm,
          atmfM4HwStorageCapacityAlarm,
          atmfM4HwMemoryMismatchAlarm,
          atmfM4HwCorruptDataAlarm,
          atmfM4HwSwEnvironAlarm,
          atmfM4HwSwDownloadFailAlarm,
          atmfM4HwVersionMismatchAlarm,
          atmfM4HwFanFailAlarm,
          atmfM4HwDoorOpenAlarm,
          atmfM4HwFuseFailAlarm,
          atmfM4HwHighTempAlarm,
          atmfM4SwVersionMismatchAlarm,
          atmfM4VplTpUp,
          atmfM4VplTpDown,
          atmfM4VclTpUp,
          atmfM4VclTpDown,
          atmfM4VplXConnUp,
          atmfM4VplXConnDown,
          atmfM4VclXConnUp,
          atmfM4VclXConnDown,
          atmfM4HwUnitUp,
          atmfM4HwUnitDown,
          atmfM4AtmCellIfCreated,
          atmfM4AtmCellIfDeleted,
          atmfM4VpcTpCreated,
          atmfM4VpcTpDeleted,
          atmfM4VccTpCreated,
          atmfM4VccTpDeleted,
          atmfM4VplXConnCreated,
          atmfM4VplXConnDeleted,
          atmfM4VclXConnCreated,
          atmfM4VclXConnDeleted,
          atmfM4HwUnitCreated,
          atmfM4HwUnitDeleted,
          atmfM4InstalledSwCreated,
          atmfM4InstalledSwDeleted,
          atmfM4IfChanged,
          atmfM4VplTpChanged,
          atmfM4VclTpChanged,
          atmfM4VplXConnChanged,
          atmfM4VclXConnChanged,
          atmfM4HwUnitChanged,
          atmfM4InstalledSwChanged
          }
     STATUS    current
     DESCRIPTION
          "The ATM Forum M4 notification list."
     ::= { atmfM4Groups 32 }

END


   RS-232-MIB DEFINITIONS ::= BEGIN

   IMPORTS
       MODULE-IDENTITY, OBJECT-TYPE, NOTIFICATION-TYPE,
       Counter32, Integer32
           FROM SNMPv2-SMI
       InterfaceIndex
           FROM IF-MIB
       transmission
           FROM RFC1213-MIB
       MODULE-COMPLIANCE, OBJECT-GROUP
           FROM SNMPv2-CONF;


   rs232 MODULE-IDENTITY
       LAST-UPDATED "9405261700Z"
       ORGANIZATION "IETF Character MIB Working Group"
       CONTACT-INFO
               "        Bob Stewart
                Postal: Xyplex, Inc.
                        295 Foster Street
                        Littleton, MA 01460

                   Tel: 508-952-4816
                   Fax: 508-952-4887
                E-mail: rlstewart@eng.xyplex.com"
       DESCRIPTION
               "The MIB module for RS-232-like hardware devices."
       ::= { transmission 33 }


   -- Generic RS-232-like information

   rs232Number OBJECT-TYPE
       SYNTAX Integer32
       MAX-ACCESS read-only
       STATUS current
       DESCRIPTION
           "The number of ports (regardless of their current
           state) in the RS-232-like general port table."
       ::= { rs232 1 }


   -- RS-232-like General Port Table

   rs232PortTable OBJECT-TYPE
       SYNTAX SEQUENCE OF Rs232PortEntry
       MAX-ACCESS not-accessible
       STATUS current
       DESCRIPTION
           "A list of port entries.  The number of entries is
           given by the value of rs232Number."
       ::= { rs232 2 }

   rs232PortEntry OBJECT-TYPE
       SYNTAX Rs232PortEntry
       MAX-ACCESS not-accessible
       STATUS current
       DESCRIPTION
           "Status and parameter values for a port."
       INDEX { rs232PortIndex }
       ::= { rs232PortTable 1 }

   Rs232PortEntry ::=
       SEQUENCE {
           rs232PortIndex
               InterfaceIndex,
           rs232PortType
               INTEGER,
           rs232PortInSigNumber
               Integer32,
           rs232PortOutSigNumber
               Integer32,
           rs232PortInSpeed
               Integer32,
           rs232PortOutSpeed
               Integer32,
           rs232PortInFlowType
               INTEGER,
           rs232PortOutFlowType
               INTEGER
       }

   rs232PortIndex OBJECT-TYPE
       SYNTAX InterfaceIndex
       MAX-ACCESS read-only
       STATUS current
       DESCRIPTION
           "The value of ifIndex for the port.  By convention
           and if possible, hardware port numbers map directly
           to external connectors.  The value for each port must
           remain constant at least from one re-initialization
           of the network management agent to the next."
       ::= { rs232PortEntry 1 }

   rs232PortType OBJECT-TYPE
       SYNTAX INTEGER { other(1), rs232(2), rs422(3),
                        rs423(4), v35(5), x21(6) }
       MAX-ACCESS read-only
       STATUS current
       DESCRIPTION
           "The port's hardware type."
       ::= { rs232PortEntry 2 }

   rs232PortInSigNumber OBJECT-TYPE
       SYNTAX Integer32
       MAX-ACCESS read-only
       STATUS current
       DESCRIPTION
           "The number of input signals for the port in the
           input signal table (rs232PortInSigTable).  The table
           contains entries only for those signals the software
           can detect and that are useful to observe."
       ::= { rs232PortEntry 3 }


   rs232PortOutSigNumber OBJECT-TYPE
       SYNTAX Integer32
       MAX-ACCESS read-only
       STATUS current
       DESCRIPTION
           "The number of output signals for the port in the
           output signal table (rs232PortOutSigTable).  The
           table contains entries only for those signals the
           software can assert and that are useful to observe."
       ::= { rs232PortEntry 4 }

   rs232PortInSpeed OBJECT-TYPE
       SYNTAX Integer32
       MAX-ACCESS read-write
       STATUS current
       DESCRIPTION
           "The port's input speed in bits per second.  Note that
           non-standard values, such as 9612, are probably not allowed
           on most implementations."
       ::= { rs232PortEntry 5 }

   rs232PortOutSpeed OBJECT-TYPE
       SYNTAX Integer32
       MAX-ACCESS read-write
       STATUS current
       DESCRIPTION
           "The port's output speed in bits per second.  Note that
           non-standard values, such as 9612, are probably not allowed
           on most implementations."
       ::= { rs232PortEntry 6 }

   rs232PortInFlowType OBJECT-TYPE
       SYNTAX INTEGER { none(1), ctsRts(2), dsrDtr(3) }
       MAX-ACCESS read-write
       STATUS current
       DESCRIPTION
           "The port's type of input flow control.  'none'
           indicates no flow control at this level.
           'ctsRts' and 'dsrDtr' indicate use of the indicated
           hardware signals."
       ::= { rs232PortEntry 7 }

   rs232PortOutFlowType OBJECT-TYPE
       SYNTAX INTEGER { none(1), ctsRts(2), dsrDtr(3) }
       MAX-ACCESS read-write
       STATUS current
       DESCRIPTION
           "The port's type of output flow control.  'none'
           indicates no flow control at this level.
           'ctsRts' and 'dsrDtr' indicate use of the indicated
           hardware signals."
       ::= { rs232PortEntry 8 }


   -- RS-232-like Asynchronous Port Table

   rs232AsyncPortTable OBJECT-TYPE
       SYNTAX SEQUENCE OF Rs232AsyncPortEntry
       MAX-ACCESS not-accessible
       STATUS current
       DESCRIPTION
           "A list of asynchronous port entries.  Entries need
           not exist for synchronous ports."
       ::= { rs232 3 }

   rs232AsyncPortEntry OBJECT-TYPE
       SYNTAX Rs232AsyncPortEntry
       MAX-ACCESS not-accessible
       STATUS current
       DESCRIPTION
           "Status and parameter values for an asynchronous
           port."
       INDEX { rs232AsyncPortIndex }
       ::= { rs232AsyncPortTable 1 }

   Rs232AsyncPortEntry ::=
       SEQUENCE {
           rs232AsyncPortIndex
               InterfaceIndex,
           rs232AsyncPortBits
               INTEGER,
           rs232AsyncPortStopBits
               INTEGER,
           rs232AsyncPortParity
               INTEGER,
           rs232AsyncPortAutobaud
               INTEGER,
           rs232AsyncPortParityErrs
               Counter32,
           rs232AsyncPortFramingErrs
               Counter32,
           rs232AsyncPortOverrunErrs
               Counter32

       }

   rs232AsyncPortIndex OBJECT-TYPE
       SYNTAX InterfaceIndex
       MAX-ACCESS read-only
       STATUS current
       DESCRIPTION
           "A unique value for each port.  Its value is the
           same as rs232PortIndex for the port."
       ::= { rs232AsyncPortEntry 1 }

   rs232AsyncPortBits OBJECT-TYPE
       SYNTAX INTEGER (5..8)
       MAX-ACCESS read-write
       STATUS current
       DESCRIPTION
           "The port's number of bits in a character."
       ::= { rs232AsyncPortEntry 2 }

   rs232AsyncPortStopBits OBJECT-TYPE
       SYNTAX INTEGER { one(1), two(2),
                        oneAndHalf(3), dynamic(4) }
       MAX-ACCESS read-write
       STATUS current
       DESCRIPTION
           "The port's number of stop bits."
       ::= { rs232AsyncPortEntry 3 }

   rs232AsyncPortParity OBJECT-TYPE
       SYNTAX INTEGER { none(1), odd(2), even(3),
                        mark(4), space(5) }
       MAX-ACCESS read-write
       STATUS current
       DESCRIPTION
           "The port's sense of a character parity bit."
       ::= { rs232AsyncPortEntry 4 }

   rs232AsyncPortAutobaud OBJECT-TYPE
       SYNTAX INTEGER { enabled(1), disabled(2) }
       MAX-ACCESS read-write
       STATUS current
       DESCRIPTION
           "A control for the port's ability to automatically
           sense input speed.

           When rs232PortAutoBaud is 'enabled', a port may
           autobaud to values different from the set values for
           speed, parity, and character size.  As a result a
           network management system may temporarily observe
           values different from what was previously set."
       ::= { rs232AsyncPortEntry 5 }

   rs232AsyncPortParityErrs OBJECT-TYPE
       SYNTAX Counter32
       MAX-ACCESS read-only
       STATUS current
       DESCRIPTION
           "Total number of characters with a parity error,
           input from the port since system re-initialization
           and while the port state was 'up' or 'test'."
       ::= { rs232AsyncPortEntry 6 }

   rs232AsyncPortFramingErrs OBJECT-TYPE
       SYNTAX Counter32
       MAX-ACCESS read-only
       STATUS current
       DESCRIPTION
           "Total number of characters with a framing error,
           input from the port since system re-initialization
           and while the port state was 'up' or 'test'."
       ::= { rs232AsyncPortEntry 7 }

   rs232AsyncPortOverrunErrs OBJECT-TYPE
       SYNTAX Counter32
       MAX-ACCESS read-only
       STATUS current
       DESCRIPTION
           "Total number of characters with an overrun error,
           input from the port since system re-initialization
           and while the port state was 'up' or 'test'."
       ::= { rs232AsyncPortEntry 8 }


   -- RS-232-like Synchronous Port Table

   rs232SyncPortTable OBJECT-TYPE
       SYNTAX SEQUENCE OF Rs232SyncPortEntry
       MAX-ACCESS not-accessible
       STATUS current
       DESCRIPTION
           "A list of asynchronous port entries.  Entries need
           not exist for synchronous ports."
       ::= { rs232 4 }

   rs232SyncPortEntry OBJECT-TYPE
       SYNTAX Rs232SyncPortEntry
       MAX-ACCESS not-accessible
       STATUS current
       DESCRIPTION
           "Status and parameter values for a synchronous
           port."
       INDEX { rs232SyncPortIndex }
       ::= { rs232SyncPortTable 1 }

   Rs232SyncPortEntry ::=
       SEQUENCE {
           rs232SyncPortIndex
               InterfaceIndex,
           rs232SyncPortClockSource
               INTEGER,
           rs232SyncPortFrameCheckErrs
               Counter32,
           rs232SyncPortTransmitUnderrunErrs
               Counter32,
           rs232SyncPortReceiveOverrunErrs
               Counter32,
           rs232SyncPortInterruptedFrames
               Counter32,
           rs232SyncPortAbortedFrames
               Counter32,
           rs232SyncPortRole
               INTEGER,
           rs232SyncPortEncoding
               INTEGER,
           rs232SyncPortRTSControl
               INTEGER,
           rs232SyncPortRTSCTSDelay
               Integer32,
           rs232SyncPortMode
               INTEGER,
           rs232SyncPortIdlePattern
               INTEGER,
           rs232SyncPortMinFlags
               Integer32
       }

   rs232SyncPortIndex OBJECT-TYPE
       SYNTAX InterfaceIndex
       MAX-ACCESS read-only
       STATUS current
       DESCRIPTION
           "A unique value for each port.  Its value is the
           same as rs232PortIndex for the port."
       ::= { rs232SyncPortEntry 1 }


   rs232SyncPortClockSource OBJECT-TYPE
       SYNTAX INTEGER { internal(1), external(2), split(3) }
       MAX-ACCESS read-write
       STATUS current
       DESCRIPTION
           "Source of the port's bit rate clock. 'split' means
           the tranmit clock is internal and the receive clock
           is external."
       ::= { rs232SyncPortEntry 2 }

   rs232SyncPortFrameCheckErrs OBJECT-TYPE
       SYNTAX Counter32
       MAX-ACCESS read-only
       STATUS current
       DESCRIPTION
           "Total number of frames with an invalid frame check
           sequence, input from the port since system
           re-initialization and while the port state was 'up'
           or 'test'."
       ::= { rs232SyncPortEntry 3 }

   rs232SyncPortTransmitUnderrunErrs OBJECT-TYPE
       SYNTAX Counter32
       MAX-ACCESS read-only
       STATUS current
       DESCRIPTION
           "Total number of frames that failed to be
           transmitted on the port since system
           re-initialization and while the port state was 'up'
           or 'test' because data was not available to the
           transmitter in time."
       ::= { rs232SyncPortEntry 4 }

   rs232SyncPortReceiveOverrunErrs OBJECT-TYPE
       SYNTAX Counter32
       MAX-ACCESS read-only
       STATUS current
       DESCRIPTION
           "Total number of frames that failed to be received
           on the port since system re-initialization and while
           the port state was 'up' or 'test' because the
           receiver did not accept the data in time."
       ::= { rs232SyncPortEntry 5 }

   rs232SyncPortInterruptedFrames OBJECT-TYPE
       SYNTAX Counter32
       MAX-ACCESS read-only
       STATUS current
       DESCRIPTION
           "Total number of frames that failed to be received
           or transmitted on the port due to loss of modem
           signals since system re-initialization and while the
           port state was 'up' or 'test'."
       ::= { rs232SyncPortEntry 6 }

   rs232SyncPortAbortedFrames OBJECT-TYPE
       SYNTAX Counter32
       MAX-ACCESS read-only
       STATUS current
       DESCRIPTION
           "Number of frames aborted on the port due to
           receiving an abort sequence since system
           re-initialization and while the port state was 'up'
           or 'test'."
       ::= { rs232SyncPortEntry 7 }

   rs232SyncPortRole OBJECT-TYPE
       SYNTAX INTEGER  { dte(1), dce(2) }
       MAX-ACCESS read-write
       STATUS current
       DESCRIPTION
           "The role the device is playing that is using this port.
              dte    means the device is performing the role of
                     data terminal equipment
              dce    means the device is performing the role of
                     data circuit-terminating equipment."
       DEFVAL { dce }
       ::= { rs232SyncPortEntry 8 }

   rs232SyncPortEncoding OBJECT-TYPE
       SYNTAX INTEGER  { nrz(1), nrzi(2) }
       MAX-ACCESS read-write
       STATUS current
       DESCRIPTION
           "The bit stream encoding technique that is in effect
            for this port.
              nrz    for Non-Return to Zero encoding
              nrzi   for Non-Return to Zero Inverted encoding."
       DEFVAL { nrz }
       ::= { rs232SyncPortEntry 9 }

   rs232SyncPortRTSControl OBJECT-TYPE
       SYNTAX INTEGER  { controlled(1), constant(2) }
       MAX-ACCESS read-write
       STATUS current
       DESCRIPTION
           "The method used to control the Request To Send (RTS)
            signal.

              controlled  when the DTE is asserts RTS each time
                          data needs to be transmitted and drops
                          RTS at some point after data
                          transmission begins.

                          If rs232SyncPortRole is 'dte', the
                          RTS is an output signal. The device
                          will issue a RTS and wait for a CTS
                          from the DCE before starting to
                          transmit.

                          If rs232SyncPortRole is 'dce', the
                          RTS is an input signal. The device
                          will issue a CTS only after having
                          received RTS and waiting the
                          rs232SyncPortRTSCTSDelay interval.

              constant    when the DTE constantly asserts RTS."
       DEFVAL { constant }
       ::= { rs232SyncPortEntry 10 }

   rs232SyncPortRTSCTSDelay OBJECT-TYPE
       SYNTAX Integer32
       MAX-ACCESS read-write
       STATUS current
       DESCRIPTION
           "The interval (in milliseconds) that the DCE must wait
            after it sees RTS asserted before asserting CTS.  This
            object exists in support of older synchronous devices
            that cannot recognize CTS within a certain interval
            after it asserts RTS."
       DEFVAL { 0 }
       ::= { rs232SyncPortEntry 11 }

   rs232SyncPortMode OBJECT-TYPE
       SYNTAX INTEGER  { fdx(1), hdx(2), simplex-receive(3),
                         simplex-send(4) }
       MAX-ACCESS read-write
       STATUS current
       DESCRIPTION
           "The mode of operation of the port with respect to the
            direction and simultaneity of data transfer.



              fdx              when frames on the data link can be
                               transmitted and received at the same
                               time

              hdx              when frames can either be received
                               from the data link or transmitted
                               onto the data link but not at the
                               same time.

              simplex-receive  when frames can only be received on
                               this data link.

              simplex-send     when frames can only be sent on this
                               data link."
       DEFVAL { fdx }
       ::= { rs232SyncPortEntry 12 }

   rs232SyncPortIdlePattern OBJECT-TYPE
       SYNTAX INTEGER  { mark(1), space(2) }
       MAX-ACCESS read-write
       STATUS current
       DESCRIPTION
           "The bit pattern used to indicate an idle line."
       DEFVAL { space }
       ::= { rs232SyncPortEntry 13 }

   rs232SyncPortMinFlags OBJECT-TYPE
       SYNTAX Integer32
       MAX-ACCESS read-write
       STATUS current
       DESCRIPTION
           "The minimum number of flag patterns this port needs in
            order to recognize the end of one frame and the start
            of the next.  Plausible values are 1 and 2."
       DEFVAL { 2 }
       ::= { rs232SyncPortEntry 14 }


   -- Input Signal Table

   rs232InSigTable OBJECT-TYPE
       SYNTAX SEQUENCE OF Rs232InSigEntry
       MAX-ACCESS not-accessible
       STATUS current
       DESCRIPTION
           "A list of port input control signal entries
           implemented and visible to the software on the port,
           and useful to monitor."
       ::= { rs232 5 }

   rs232InSigEntry OBJECT-TYPE
       SYNTAX Rs232InSigEntry
       MAX-ACCESS not-accessible
       STATUS current
       DESCRIPTION
           "Input control signal status for a hardware port."
       INDEX { rs232InSigPortIndex, rs232InSigName }
       ::= { rs232InSigTable 1 }

   Rs232InSigEntry ::=
       SEQUENCE {
           rs232InSigPortIndex
               InterfaceIndex,
           rs232InSigName
               INTEGER,
           rs232InSigState
               INTEGER,
           rs232InSigChanges
               Counter32
       }

   rs232InSigPortIndex OBJECT-TYPE
       SYNTAX InterfaceIndex
       MAX-ACCESS read-only
       STATUS current
       DESCRIPTION
           "The value of rs232PortIndex for the port to which
           this entry belongs."
       ::= { rs232InSigEntry 1 }

   rs232InSigName OBJECT-TYPE
       SYNTAX INTEGER { rts(1), cts(2), dsr(3), dtr(4), ri(5),
                        dcd(6), sq(7), srs(8), srts(9),
                        scts(10), sdcd(11) }
       MAX-ACCESS read-only
       STATUS current
       DESCRIPTION
           "Identification of a hardware signal, as follows:

               rts    Request to Send
               cts    Clear to Send
               dsr    Data Set Ready
               dtr    Data Terminal Ready
               ri     Ring Indicator
               dcd    Received Line Signal Detector
               sq     Signal Quality Detector
               srs    Data Signaling Rate Selector
               srts   Secondary Request to Send
               scts   Secondary Clear to Send
               sdcd   Secondary Received Line Signal Detector
           "
       REFERENCE
           "EIA Standard RS-232-C, August 1969."
       ::= { rs232InSigEntry 2 }

   rs232InSigState OBJECT-TYPE
       SYNTAX INTEGER { none(1), on(2), off(3) }
       MAX-ACCESS read-only
       STATUS current
       DESCRIPTION
           "The current signal state."
       ::= { rs232InSigEntry 3 }

   rs232InSigChanges OBJECT-TYPE
       SYNTAX Counter32
       MAX-ACCESS read-only
       STATUS current
       DESCRIPTION
           "The number of times the signal has changed from
           'on' to 'off' or from 'off' to 'on'."
       ::= { rs232InSigEntry 4 }


   -- Output Signal Table

   rs232OutSigTable OBJECT-TYPE
       SYNTAX SEQUENCE OF Rs232OutSigEntry
       MAX-ACCESS not-accessible
       STATUS current
       DESCRIPTION
           "A list of port output control signal entries
           implemented and visible to the software on the port,
           and useful to monitor."
       ::= { rs232 6 }

   rs232OutSigEntry OBJECT-TYPE
       SYNTAX Rs232OutSigEntry
       MAX-ACCESS not-accessible
       STATUS current
       DESCRIPTION
           "Output control signal status for a hardware port."
       INDEX { rs232OutSigPortIndex, rs232OutSigName }
       ::= { rs232OutSigTable 1 }

   Rs232OutSigEntry ::=
       SEQUENCE {
           rs232OutSigPortIndex
               InterfaceIndex,
           rs232OutSigName
               INTEGER,
           rs232OutSigState
               INTEGER,
           rs232OutSigChanges
               Counter32
       }

   rs232OutSigPortIndex OBJECT-TYPE
       SYNTAX InterfaceIndex
       MAX-ACCESS read-only
       STATUS current
       DESCRIPTION
           "The value of rs232PortIndex for the port to which
           this entry belongs."
       ::= { rs232OutSigEntry 1 }

   rs232OutSigName OBJECT-TYPE
       SYNTAX INTEGER { rts(1), cts(2), dsr(3), dtr(4), ri(5),
                        dcd(6), sq(7), srs(8), srts(9),
                        scts(10), sdcd(11) }
       MAX-ACCESS read-only
       STATUS current
       DESCRIPTION
           "Identification of a hardware signal, as follows:

               rts    Request to Send
               cts    Clear to Send
               dsr    Data Set Ready
               dtr    Data Terminal Ready
               ri     Ring Indicator
               dcd    Received Line Signal Detector
               sq     Signal Quality Detector
               srs    Data Signaling Rate Selector
               srts   Secondary Request to Send
               scts   Secondary Clear to Send
               sdcd   Secondary Received Line Signal Detector
           "
       REFERENCE
           "EIA Standard RS-232-C, August 1969."
       ::= { rs232OutSigEntry 2 }

   rs232OutSigState OBJECT-TYPE
       SYNTAX INTEGER { none(1), on(2), off(3) }
       MAX-ACCESS read-only
       STATUS current
       DESCRIPTION
           "The current signal state."
       ::= { rs232OutSigEntry 3 }

   rs232OutSigChanges OBJECT-TYPE
       SYNTAX Counter32
       MAX-ACCESS read-only
       STATUS current
       DESCRIPTION
           "The number of times the signal has changed from
           'on' to 'off' or from 'off' to 'on'."
       ::= { rs232OutSigEntry 4 }


   -- conformance information

   rs232Conformance OBJECT IDENTIFIER ::= { rs232 7 }

   rs232Groups      OBJECT IDENTIFIER ::= { rs232Conformance 1 }
   rs232Compliances OBJECT IDENTIFIER ::= { rs232Conformance 2 }


   -- compliance statements

   rs232Compliance MODULE-COMPLIANCE
       STATUS  current
       DESCRIPTION
               "The compliance statement for SNMPv2 entities
               which have RS-232-like hardware interfaces."

       MODULE  -- this module
           MANDATORY-GROUPS { rs232Group }

           GROUP   rs232AsyncGroup
           DESCRIPTION
               "The Asynch group is mandatory only for those
                SNMPv2 entities which have asynchronous
                interfaces Rs-232-like."

           GROUP   rs232SyncGroup
           DESCRIPTION
               "The Synch group is mandatory only for those
                SNMPv2 entities which have synchronous
                interfaces Rs-232-like."
       ::= { rs232Compliances 1 }

   -- units of conformance

   rs232Group    OBJECT-GROUP
       OBJECTS { rs232Number, rs232PortIndex, rs232PortType,
                 rs232PortInSigNumber, rs232PortOutSigNumber,
                 rs232PortInSpeed, rs232PortOutSpeed,
                 rs232PortInFlowType, rs232PortOutFlowType,
                 rs232InSigPortIndex, rs232InSigName,
                 rs232InSigState, rs232InSigChanges,
                 rs232OutSigPortIndex, rs232OutSigName,
                 rs232OutSigState, rs232OutSigChanges }
       STATUS  current
       DESCRIPTION
               "A collection of objects providing information
                applicable to all RS-232-like interfaces."
       ::= { rs232Groups 1 }

   rs232AsyncGroup OBJECT-GROUP
       OBJECTS { rs232AsyncPortIndex, rs232AsyncPortBits,
                 rs232AsyncPortStopBits, rs232AsyncPortParity,
                 rs232AsyncPortAutobaud, rs232AsyncPortParityErrs,
                 rs232AsyncPortFramingErrs, rs232AsyncPortOverrunErrs }
       STATUS  current
       DESCRIPTION
               "A collection of objects providing information
                applicable to asynchronous RS-232-like interfaces."
       ::= { rs232Groups 2 }

   rs232SyncGroup OBJECT-GROUP
       OBJECTS { rs232SyncPortIndex, rs232SyncPortClockSource,
                 rs232SyncPortFrameCheckErrs,
                 rs232SyncPortTransmitUnderrunErrs,
                 rs232SyncPortReceiveOverrunErrs,
                 rs232SyncPortInterruptedFrames,
                 rs232SyncPortAbortedFrames }
       STATUS  current
       DESCRIPTION
               "A collection of objects providing information
                applicable to synchronous RS-232-like interfaces."
       ::= { rs232Groups 3 }

   rs232SyncSDLCGroup OBJECT-GROUP
       OBJECTS { rs232SyncPortRole,
                 rs232SyncPortEncoding,
                 rs232SyncPortRTSControl,
                 rs232SyncPortRTSCTSDelay,
                 rs232SyncPortMode,
                 rs232SyncPortIdlePattern,
                 rs232SyncPortMinFlags }
       STATUS  current
       DESCRIPTION
               "A collection of objects providing information
                applicable to synchronous RS-232-like interfaces
                running SDLC."
       ::= { rs232Groups 4 }

END

EtherLike-MIB DEFINITIONS ::= BEGIN

    IMPORTS
        MODULE-IDENTITY, OBJECT-TYPE, OBJECT-IDENTITY,
        Counter32, mib-2, transmission
            FROM SNMPv2-SMI
        MODULE-COMPLIANCE, OBJECT-GROUP
            FROM SNMPv2-CONF
        ifIndex, InterfaceIndex
            FROM IF-MIB;

    etherMIB MODULE-IDENTITY
        LAST-UPDATED "9908240400Z"  -- August 24, 1999
        ORGANIZATION "IETF Ethernet Interfaces and Hub MIB
                     Working Group"
        CONTACT-INFO
            "WG E-mail: hubmib@hprnd.rose.hp.com
          To subscribe: hubmib-request@hprnd.rose.hp.com

                 Chair: Dan Romascanu
                Postal: Lucent Technologies
                        Atidum Technology Park, Bldg. 3
                        Tel Aviv 61131
                        Israel
                   Tel: +972 3 645 8414
                E-mail: dromasca@lucent.com

               Editor: John Flick
               Postal: Hewlett-Packard Company
                       8000 Foothills Blvd. M/S 5557
                       Roseville, CA 95747-5557
                       USA
                  Tel: +1 916 785 4018
                  Fax: +1 916 785 1199
               E-mail: johnf@rose.hp.com

               Editor: Jeffrey Johnson
               Postal: RedBack Networks
                       2570 North First Street, Suite 410
                       San Jose, CA, 95131
                       USA
                  Tel: +1 408 571 2699
                  Fax: +1 408 571 2698
               E-Mail: jeff@redbacknetworks.com"

        DESCRIPTION "The MIB module to describe generic objects for
                    Ethernet-like network interfaces.

                    The following reference is used throughout this
                    MIB module:

                    [IEEE 802.3 Std] refers to:
                       IEEE Std 802.3, 1998 Edition: 'Information
                       technology - Telecommunications and
                       information exchange between systems -
                       Local and metropolitan area networks -
                       Specific requirements - Part 3: Carrier
                       sense multiple access with collision
                       detection (CSMA/CD) access method and
                       physical layer specifications',
                       September 1998.

                    Of particular interest is Clause 30, '10Mb/s,
                    100Mb/s and 1000Mb/s Management'."

        REVISION    "9908240400Z"  -- August 24, 1999
        DESCRIPTION "Updated to include support for 1000 Mb/sec
                     interfaces and full-duplex interfaces.
                     This version published as RFC 2665."

        REVISION    "9806032150Z"
        DESCRIPTION "Updated to include support for 100 Mb/sec
                     interfaces.
                     This version published as RFC 2358."

        REVISION    "9402030400Z"
        DESCRIPTION "Initial version, published as RFC 1650."

        ::= { mib-2 35 }


    etherMIBObjects OBJECT IDENTIFIER ::= { etherMIB 1 }

    dot3    OBJECT IDENTIFIER ::= { transmission 7 }

    -- the Ethernet-like Statistics group

    dot3StatsTable OBJECT-TYPE
        SYNTAX     SEQUENCE OF Dot3StatsEntry
        MAX-ACCESS not-accessible
        STATUS     current
        DESCRIPTION "Statistics for a collection of ethernet-like
                    interfaces attached to a particular system.
                    There will be one row in this table for each
                    ethernet-like interface in the system."
        ::= { dot3 2 }

    dot3StatsEntry OBJECT-TYPE
        SYNTAX     Dot3StatsEntry
        MAX-ACCESS not-accessible
        STATUS     current
        DESCRIPTION "Statistics for a particular interface to an
                    ethernet-like medium."
        INDEX       { dot3StatsIndex }
        ::= { dot3StatsTable 1 }

    Dot3StatsEntry ::=
        SEQUENCE {
            dot3StatsIndex                      InterfaceIndex,
            dot3StatsAlignmentErrors            Counter32,
            dot3StatsFCSErrors                  Counter32,
            dot3StatsSingleCollisionFrames      Counter32,
            dot3StatsMultipleCollisionFrames    Counter32,
            dot3StatsSQETestErrors              Counter32,
            dot3StatsDeferredTransmissions      Counter32,
            dot3StatsLateCollisions             Counter32,
            dot3StatsExcessiveCollisions        Counter32,
            dot3StatsInternalMacTransmitErrors  Counter32,
            dot3StatsCarrierSenseErrors         Counter32,
            dot3StatsFrameTooLongs              Counter32,
            dot3StatsInternalMacReceiveErrors   Counter32,
            dot3StatsEtherChipSet               OBJECT IDENTIFIER,
            dot3StatsSymbolErrors               Counter32,
            dot3StatsDuplexStatus               INTEGER
        }

    dot3StatsIndex OBJECT-TYPE
        SYNTAX      InterfaceIndex
        MAX-ACCESS  read-only
        STATUS      current
        DESCRIPTION "An index value that uniquely identifies an
                    interface to an ethernet-like medium.  The
                    interface identified by a particular value of
                    this index is the same interface as identified
                    by the same value of ifIndex."
        REFERENCE   "RFC 2233, ifIndex"
        ::= { dot3StatsEntry 1 }

    dot3StatsAlignmentErrors OBJECT-TYPE
        SYNTAX      Counter32
        MAX-ACCESS  read-only
        STATUS      current
        DESCRIPTION "A count of frames received on a particular
                    interface that are not an integral number of
                    octets in length and do not pass the FCS check.

                    The count represented by an instance of this
                    object is incremented when the alignmentError
                    status is returned by the MAC service to the
                    LLC (or other MAC user). Received frames for
                    which multiple error conditions obtain are,
                    according to the conventions of IEEE 802.3
                    Layer Management, counted exclusively according
                    to the error status presented to the LLC.

                    This counter does not increment for 8-bit wide
                    group encoding schemes.

                    Discontinuities in the value of this counter can
                    occur at re-initialization of the management
                    system, and at other times as indicated by the
                    value of ifCounterDiscontinuityTime."
        REFERENCE   "[IEEE 802.3 Std.], 30.3.1.1.7,
                    aAlignmentErrors"
        ::= { dot3StatsEntry 2 }

    dot3StatsFCSErrors OBJECT-TYPE
        SYNTAX      Counter32
        MAX-ACCESS  read-only
        STATUS      current
        DESCRIPTION "A count of frames received on a particular
                    interface that are an integral number of octets
                    in length but do not pass the FCS check.  This
                    count does not include frames received with
                    frame-too-long or frame-too-short error.

                    The count represented by an instance of this
                    object is incremented when the frameCheckError
                    status is returned by the MAC service to the
                    LLC (or other MAC user). Received frames for
                    which multiple error conditions obtain are,
                    according to the conventions of IEEE 802.3
                    Layer Management, counted exclusively according
                    to the error status presented to the LLC.

                    Note:  Coding errors detected by the physical
                    layer for speeds above 10 Mb/s will cause the
                    frame to fail the FCS check.
                    Discontinuities in the value of this counter can
                    occur at re-initialization of the management
                    system, and at other times as indicated by the
                    value of ifCounterDiscontinuityTime."
        REFERENCE   "[IEEE 802.3 Std.], 30.3.1.1.6,
                    aFrameCheckSequenceErrors."
        ::= { dot3StatsEntry 3 }

    dot3StatsSingleCollisionFrames OBJECT-TYPE
        SYNTAX      Counter32
        MAX-ACCESS  read-only
        STATUS      current
        DESCRIPTION "A count of successfully transmitted frames on
                    a particular interface for which transmission
                    is inhibited by exactly one collision.

                    A frame that is counted by an instance of this
                    object is also counted by the corresponding
                    instance of either the ifOutUcastPkts,
                    ifOutMulticastPkts, or ifOutBroadcastPkts,
                    and is not counted by the corresponding
                    instance of the dot3StatsMultipleCollisionFrames
                    object.

                    This counter does not increment when the
                    interface is operating in full-duplex mode.

                    Discontinuities in the value of this counter can
                    occur at re-initialization of the management
                    system, and at other times as indicated by the
                    value of ifCounterDiscontinuityTime."
        REFERENCE   "[IEEE 802.3 Std.], 30.3.1.1.3,
                    aSingleCollisionFrames."
        ::= { dot3StatsEntry 4 }

    dot3StatsMultipleCollisionFrames OBJECT-TYPE
        SYNTAX      Counter32
        MAX-ACCESS  read-only
        STATUS      current
        DESCRIPTION "A count of successfully transmitted frames on
                    a particular interface for which transmission
                    is inhibited by more than one collision.

                    A frame that is counted by an instance of this
                    object is also counted by the corresponding
                    instance of either the ifOutUcastPkts,
                    ifOutMulticastPkts, or ifOutBroadcastPkts,
                    and is not counted by the corresponding
                    instance of the dot3StatsSingleCollisionFrames
                    object.
                    This counter does not increment when the
                    interface is operating in full-duplex mode.

                    Discontinuities in the value of this counter can
                    occur at re-initialization of the management
                    system, and at other times as indicated by the
                    value of ifCounterDiscontinuityTime."
        REFERENCE   "[IEEE 802.3 Std.], 30.3.1.1.4,
                    aMultipleCollisionFrames."
        ::= { dot3StatsEntry 5 }

    dot3StatsSQETestErrors OBJECT-TYPE
        SYNTAX      Counter32
        MAX-ACCESS  read-only
        STATUS      current
        DESCRIPTION "A count of times that the SQE TEST ERROR
                    message is generated by the PLS sublayer for a
                    particular interface. The SQE TEST ERROR
                    is set in accordance with the rules for
                    verification of the SQE detection mechanism in
                    the PLS Carrier Sense Function as described in
                    IEEE Std. 802.3, 1998 Edition, section 7.2.4.6.

                    This counter does not increment on interfaces
                    operating at speeds greater than 10 Mb/s, or on
                    interfaces operating in full-duplex mode.

                    Discontinuities in the value of this counter can
                    occur at re-initialization of the management
                    system, and at other times as indicated by the
                    value of ifCounterDiscontinuityTime."
        REFERENCE   "[IEEE 802.3 Std.], 7.2.4.6, also 30.3.2.1.4,
                    aSQETestErrors."
        ::= { dot3StatsEntry 6 }

    dot3StatsDeferredTransmissions OBJECT-TYPE
        SYNTAX      Counter32
        MAX-ACCESS  read-only
        STATUS      current
        DESCRIPTION "A count of frames for which the first
                    transmission attempt on a particular interface
                    is delayed because the medium is busy.
                    The count represented by an instance of this
                    object does not include frames involved in
                    collisions.

                    This counter does not increment when the
                    interface is operating in full-duplex mode.
                    Discontinuities in the value of this counter can
                    occur at re-initialization of the management
                    system, and at other times as indicated by the
                    value of ifCounterDiscontinuityTime."
        REFERENCE   "[IEEE 802.3 Std.], 30.3.1.1.9,
                    aFramesWithDeferredXmissions."
        ::= { dot3StatsEntry 7 }

    dot3StatsLateCollisions OBJECT-TYPE
        SYNTAX      Counter32
        MAX-ACCESS  read-only
        STATUS      current
        DESCRIPTION "The number of times that a collision is
                    detected on a particular interface later than
                    one slotTime into the transmission of a packet.

                    A (late) collision included in a count
                    represented by an instance of this object is
                    also considered as a (generic) collision for
                    purposes of other collision-related
                    statistics.

                    This counter does not increment when the
                    interface is operating in full-duplex mode.

                    Discontinuities in the value of this counter can
                    occur at re-initialization of the management
                    system, and at other times as indicated by the
                    value of ifCounterDiscontinuityTime."
        REFERENCE   "[IEEE 802.3 Std.], 30.3.1.1.10,
                    aLateCollisions."
        ::= { dot3StatsEntry 8 }

    dot3StatsExcessiveCollisions OBJECT-TYPE
        SYNTAX      Counter32
        MAX-ACCESS  read-only
        STATUS      current
        DESCRIPTION "A count of frames for which transmission on a
                    particular interface fails due to excessive
                    collisions.
                    This counter does not increment when the
                    interface is operating in full-duplex mode.

                    Discontinuities in the value of this counter can
                    occur at re-initialization of the management
                    system, and at other times as indicated by the
                    value of ifCounterDiscontinuityTime."
        REFERENCE   "[IEEE 802.3 Std.], 30.3.1.1.11,
                    aFramesAbortedDueToXSColls."
        ::= { dot3StatsEntry 9 }

    dot3StatsInternalMacTransmitErrors OBJECT-TYPE
        SYNTAX      Counter32
        MAX-ACCESS  read-only
        STATUS      current
        DESCRIPTION "A count of frames for which transmission on a
                    particular interface fails due to an internal
                    MAC sublayer transmit error. A frame is only
                    counted by an instance of this object if it is
                    not counted by the corresponding instance of
                    either the dot3StatsLateCollisions object, the
                    dot3StatsExcessiveCollisions object, or the
                    dot3StatsCarrierSenseErrors object.

                    The precise meaning of the count represented by
                    an instance of this object is implementation-
                    specific.  In particular, an instance of this
                    object may represent a count of transmission
                    errors on a particular interface that are not
                    otherwise counted.

                    Discontinuities in the value of this counter can
                    occur at re-initialization of the management
                    system, and at other times as indicated by the
                    value of ifCounterDiscontinuityTime."
        REFERENCE   "[IEEE 802.3 Std.], 30.3.1.1.12,
                    aFramesLostDueToIntMACXmitError."
        ::= { dot3StatsEntry 10 }

    dot3StatsCarrierSenseErrors OBJECT-TYPE
        SYNTAX      Counter32
        MAX-ACCESS  read-only
        STATUS      current
        DESCRIPTION "The number of times that the carrier sense
                    condition was lost or never asserted when
                    attempting to transmit a frame on a particular
                    interface.

                    The count represented by an instance of this
                    object is incremented at most once per
                    transmission attempt, even if the carrier sense
                    condition fluctuates during a transmission
                    attempt.

                    This counter does not increment when the
                    interface is operating in full-duplex mode.
                    Discontinuities in the value of this counter can
                    occur at re-initialization of the management
                    system, and at other times as indicated by the
                    value of ifCounterDiscontinuityTime."
        REFERENCE   "[IEEE 802.3 Std.], 30.3.1.1.13,
                    aCarrierSenseErrors."
        ::= { dot3StatsEntry 11 }

    -- { dot3StatsEntry 12 } is not assigned

    dot3StatsFrameTooLongs OBJECT-TYPE
        SYNTAX      Counter32
        MAX-ACCESS  read-only
        STATUS      current
        DESCRIPTION "A count of frames received on a particular
                    interface that exceed the maximum permitted
                    frame size.

                    The count represented by an instance of this
                    object is incremented when the frameTooLong
                    status is returned by the MAC service to the
                    LLC (or other MAC user). Received frames for
                    which multiple error conditions obtain are,
                    according to the conventions of IEEE 802.3
                    Layer Management, counted exclusively according
                    to the error status presented to the LLC.

                    Discontinuities in the value of this counter can
                    occur at re-initialization of the management
                    system, and at other times as indicated by the
                    value of ifCounterDiscontinuityTime."
        REFERENCE   "[IEEE 802.3 Std.], 30.3.1.1.25,
                    aFrameTooLongErrors."
        ::= { dot3StatsEntry 13 }

    -- { dot3StatsEntry 14 } is not assigned

    -- { dot3StatsEntry 15 } is not assigned

    dot3StatsInternalMacReceiveErrors OBJECT-TYPE
        SYNTAX      Counter32
        MAX-ACCESS  read-only
        STATUS      current
        DESCRIPTION "A count of frames for which reception on a
                    particular interface fails due to an internal
                    MAC sublayer receive error. A frame is only
                    counted by an instance of this object if it is
                    not counted by the corresponding instance of
                    either the dot3StatsFrameTooLongs object, the
                    dot3StatsAlignmentErrors object, or the
                    dot3StatsFCSErrors object.

                    The precise meaning of the count represented by
                    an instance of this object is implementation-
                    specific.  In particular, an instance of this
                    object may represent a count of receive errors
                    on a particular interface that are not
                    otherwise counted.

                    Discontinuities in the value of this counter can
                    occur at re-initialization of the management
                    system, and at other times as indicated by the
                    value of ifCounterDiscontinuityTime."
        REFERENCE   "[IEEE 802.3 Std.], 30.3.1.1.15,
                    aFramesLostDueToIntMACRcvError."
        ::= { dot3StatsEntry 16 }

    dot3StatsEtherChipSet OBJECT-TYPE
        SYNTAX      OBJECT IDENTIFIER
        MAX-ACCESS  read-only
        STATUS      deprecated
        DESCRIPTION "******** THIS OBJECT IS DEPRECATED ********

                    This object contains an OBJECT IDENTIFIER
                    which identifies the chipset used to
                    realize the interface. Ethernet-like
                    interfaces are typically built out of
                    several different chips. The MIB implementor
                    is presented with a decision of which chip
                    to identify via this object. The implementor
                    should identify the chip which is usually
                    called the Medium Access Control chip.
                    If no such chip is easily identifiable,
                    the implementor should identify the chip
                    which actually gathers the transmit
                    and receive statistics and error
                    indications. This would allow a
                    manager station to correlate the
                    statistics and the chip generating
                    them, giving it the ability to take
                    into account any known anomalies
                    in the chip."
        ::= { dot3StatsEntry 17 }

    dot3StatsSymbolErrors OBJECT-TYPE
        SYNTAX      Counter32
        MAX-ACCESS  read-only
        STATUS      current
        DESCRIPTION "For an interface operating at 100 Mb/s, the
                    number of times there was an invalid data symbol
                    when a valid carrier was present.

                    For an interface operating in half-duplex mode
                    at 1000 Mb/s, the number of times the receiving
                    media is non-idle (a carrier event) for a period
                    of time equal to or greater than slotTime, and
                    during which there was at least one occurrence
                    of an event that causes the PHY to indicate
                    'Data reception error' or 'carrier extend error'
                    on the GMII.

                    For an interface operating in full-duplex mode
                    at 1000 Mb/s, the number of times the receiving
                    media is non-idle a carrier event) for a period
                    of time equal to or greater than minFrameSize,
                    and during which there was at least one
                    occurrence of an event that causes the PHY to
                    indicate 'Data reception error' on the GMII.

                    The count represented by an instance of this
                    object is incremented at most once per carrier
                    event, even if multiple symbol errors occur
                    during the carrier event.  This count does
                    not increment if a collision is present.

                    Discontinuities in the value of this counter can
                    occur at re-initialization of the management
                    system, and at other times as indicated by the
                    value of ifCounterDiscontinuityTime."
        REFERENCE   "[IEEE 802.3 Std.], 30.3.2.1.5,
                    aSymbolErrorDuringCarrier."
        ::= { dot3StatsEntry 18 }

    dot3StatsDuplexStatus OBJECT-TYPE
        SYNTAX      INTEGER {
                        unknown(1),
                        halfDuplex(2),
                        fullDuplex(3)
                    }
        MAX-ACCESS  read-only
        STATUS      current
        DESCRIPTION "The current mode of operation of the MAC
                    entity.  'unknown' indicates that the current
                    duplex mode could not be determined.
                    Management control of the duplex mode is
                    accomplished through the MAU MIB.  When
                    an interface does not support autonegotiation,
                    or when autonegotiation is not enabled, the
                    duplex mode is controlled using
                    ifMauDefaultType.  When autonegotiation is
                    supported and enabled, duplex mode is controlled
                    using ifMauAutoNegAdvertisedBits.  In either
                    case, the currently operating duplex mode is
                    reflected both in this object and in ifMauType.

                    Note that this object provides redundant
                    information with ifMauType.  Normally, redundant
                    objects are discouraged.  However, in this
                    instance, it allows a management application to
                    determine the duplex status of an interface
                    without having to know every possible value of
                    ifMauType.  This was felt to be sufficiently
                    valuable to justify the redundancy."
        REFERENCE   "[IEEE 802.3 Std.], 30.3.1.1.32,
                    aDuplexStatus."
        ::= { dot3StatsEntry 19 }

    -- the Ethernet-like Collision Statistics group

    -- Implementation of this group is optional; it is appropriate
    -- for all systems which have the necessary metering

    dot3CollTable OBJECT-TYPE
        SYNTAX      SEQUENCE OF Dot3CollEntry
        MAX-ACCESS  not-accessible
        STATUS      current
        DESCRIPTION "A collection of collision histograms for a
                    particular set of interfaces."
        REFERENCE   "[IEEE 802.3 Std.], 30.3.1.1.30,
                    aCollisionFrames."
        ::= { dot3 5 }

    dot3CollEntry OBJECT-TYPE
        SYNTAX      Dot3CollEntry
        MAX-ACCESS  not-accessible
        STATUS      current
        DESCRIPTION "A cell in the histogram of per-frame
                    collisions for a particular interface.  An
                    instance of this object represents the
                    frequency of individual MAC frames for which
                    the transmission (successful or otherwise) on a
                    particular interface is accompanied by a
                    particular number of media collisions."
        INDEX       { ifIndex, dot3CollCount }
        ::= { dot3CollTable 1 }

    Dot3CollEntry ::=
        SEQUENCE {
            dot3CollCount        INTEGER,
            dot3CollFrequencies  Counter32
        }

    -- { dot3CollEntry 1 } is no longer in use

    dot3CollCount OBJECT-TYPE
        SYNTAX      INTEGER (1..16)
        MAX-ACCESS  not-accessible
        STATUS      current
        DESCRIPTION "The number of per-frame media collisions for
                    which a particular collision histogram cell
                    represents the frequency on a particular
                    interface."
        ::= { dot3CollEntry 2 }

    dot3CollFrequencies OBJECT-TYPE
        SYNTAX      Counter32
        MAX-ACCESS  read-only
        STATUS      current
        DESCRIPTION "A count of individual MAC frames for which the
                    transmission (successful or otherwise) on a
                    particular interface occurs after the
                    frame has experienced exactly the number
                    of collisions in the associated
                    dot3CollCount object.

                    For example, a frame which is transmitted
                    on interface 77 after experiencing
                    exactly 4 collisions would be indicated
                    by incrementing only dot3CollFrequencies.77.4.
                    No other instance of dot3CollFrequencies would
                    be incremented in this example.

                    This counter does not increment when the
                    interface is operating in full-duplex mode.

                    Discontinuities in the value of this counter can
                    occur at re-initialization of the management
                    system, and at other times as indicated by the
                    value of ifCounterDiscontinuityTime."
        ::= { dot3CollEntry 3 }
    dot3ControlTable OBJECT-TYPE
        SYNTAX      SEQUENCE OF Dot3ControlEntry
        MAX-ACCESS  not-accessible
        STATUS      current
        DESCRIPTION "A table of descriptive and status information
                    about the MAC Control sublayer on the
                    ethernet-like interfaces attached to a
                    particular system.  There will be one row in
                    this table for each ethernet-like interface in
                    the system which implements the MAC Control
                    sublayer.  If some, but not all, of the
                    ethernet-like interfaces in the system implement
                    the MAC Control sublayer, there will be fewer
                    rows in this table than in the dot3StatsTable."
        ::= { dot3 9 }

    dot3ControlEntry OBJECT-TYPE
        SYNTAX      Dot3ControlEntry
        MAX-ACCESS  not-accessible
        STATUS      current
        DESCRIPTION "An entry in the table, containing information
                    about the MAC Control sublayer on a single
                    ethernet-like interface."
        INDEX       { dot3StatsIndex }
        ::= { dot3ControlTable 1 }

    Dot3ControlEntry ::=
        SEQUENCE {
            dot3ControlFunctionsSupported       BITS,
            dot3ControlInUnknownOpcodes         Counter32
        }

    dot3ControlFunctionsSupported OBJECT-TYPE
        SYNTAX      BITS {
                        pause(0)   -- 802.3x flow control
                    }
        MAX-ACCESS  read-only
        STATUS      current
        DESCRIPTION "A list of the possible MAC Control functions
                    implemented for this interface."
        REFERENCE   "[IEEE 802.3 Std.], 30.3.3.2,
                    aMACControlFunctionsSupported."
        ::= { dot3ControlEntry 1 }

    dot3ControlInUnknownOpcodes OBJECT-TYPE
        SYNTAX      Counter32
        MAX-ACCESS  read-only
        STATUS      current
        DESCRIPTION "A count of MAC Control frames received on this
                    interface that contain an opcode that is not
                    supported by this device.

                    Discontinuities in the value of this counter can
                    occur at re-initialization of the management
                    system, and at other times as indicated by the
                    value of ifCounterDiscontinuityTime."
        REFERENCE   "[IEEE 802.3 Std.], 30.3.3.5,
                    aUnsupportedOpcodesReceived"
        ::= { dot3ControlEntry 2 }

    dot3PauseTable OBJECT-TYPE
        SYNTAX      SEQUENCE OF Dot3PauseEntry
        MAX-ACCESS  not-accessible
        STATUS      current
        DESCRIPTION "A table of descriptive and status information
                    about the MAC Control PAUSE function on the
                    ethernet-like interfaces attached to a
                    particular system. There will be one row in
                    this table for each ethernet-like interface in
                    the system which supports the MAC Control PAUSE
                    function (i.e., the 'pause' bit in the
                    corresponding instance of
                    dot3ControlFunctionsSupported is set).  If some,
                    but not all, of the ethernet-like interfaces in
                    the system implement the MAC Control PAUSE
                    function (for example, if some interfaces only
                    support half-duplex), there will be fewer rows
                    in this table than in the dot3StatsTable."
        ::= { dot3 10 }

    dot3PauseEntry OBJECT-TYPE
        SYNTAX      Dot3PauseEntry
        MAX-ACCESS  not-accessible
        STATUS      current
        DESCRIPTION "An entry in the table, containing information
                    about the MAC Control PAUSE function on a single
                    ethernet-like interface."
        INDEX       { dot3StatsIndex }
        ::= { dot3PauseTable 1 }

    Dot3PauseEntry ::=
        SEQUENCE {
            dot3PauseAdminMode                  INTEGER,
            dot3PauseOperMode                   INTEGER,
            dot3InPauseFrames                   Counter32,
            dot3OutPauseFrames                  Counter32
        }

    dot3PauseAdminMode OBJECT-TYPE
        SYNTAX      INTEGER {
                        disabled(1),
                        enabledXmit(2),
                        enabledRcv(3),
                        enabledXmitAndRcv(4)
                    }
        MAX-ACCESS  read-write
        STATUS      current
        DESCRIPTION "This object is used to configure the default
                    administrative PAUSE mode for this interface.

                    This object represents the
                    administratively-configured PAUSE mode for this
                    interface.  If auto-negotiation is not enabled
                    or is not implemented for the active MAU
                    attached to this interface, the value of this
                    object determines the operational PAUSE mode
                    of the interface whenever it is operating in
                    full-duplex mode.  In this case, a set to this
                    object will force the interface into the
                    specified mode.

                    If auto-negotiation is implemented and enabled
                    for the MAU attached to this interface, the
                    PAUSE mode for this interface is determined by
                    auto-negotiation, and the value of this object
                    denotes the mode to which the interface will
                    automatically revert if/when auto-negotiation is
                    later disabled.  Note that when auto-negotiation
                    is running, administrative control of the PAUSE
                    mode may be accomplished using the
                    ifMauAutoNegCapAdvertisedBits object in the
                    MAU-MIB.

                    Note that the value of this object is ignored
                    when the interface is not operating in
                    full-duplex mode.

                    An attempt to set this object to
                    'enabledXmit(2)' or 'enabledRcv(3)' will fail
                    on interfaces that do not support operation
                    at greater than 100 Mb/s."
        ::= { dot3PauseEntry 1 }

    dot3PauseOperMode OBJECT-TYPE
        SYNTAX      INTEGER {
                        disabled(1),
                        enabledXmit(2),
                        enabledRcv(3),
                        enabledXmitAndRcv(4)
                    }
        MAX-ACCESS  read-only
        STATUS      current
        DESCRIPTION "This object reflects the PAUSE mode currently
                    in use on this interface, as determined by
                    either (1) the result of the auto-negotiation
                    function or (2) if auto-negotiation is not
                    enabled or is not implemented for the active MAU
                    attached to this interface, by the value of
                    dot3PauseAdminMode.  Interfaces operating at
                    100 Mb/s or less will never return
                    'enabledXmit(2)' or 'enabledRcv(3)'.  Interfaces
                    operating in half-duplex mode will always return
                    'disabled(1)'.  Interfaces on which
                    auto-negotiation is enabled but not yet
                    completed should return the value
                    'disabled(1)'."
        ::= { dot3PauseEntry 2 }

    dot3InPauseFrames OBJECT-TYPE
        SYNTAX      Counter32
        MAX-ACCESS  read-only
        STATUS      current
        DESCRIPTION "A count of MAC Control frames received on this
                    interface with an opcode indicating the PAUSE
                    operation.

                    This counter does not increment when the
                    interface is operating in half-duplex mode.
                    Discontinuities in the value of this counter can
                    occur at re-initialization of the management
                    system, and at other times as indicated by the
                    value of ifCounterDiscontinuityTime."
        REFERENCE   "[IEEE 802.3 Std.], 30.3.4.3,
                    aPAUSEMACCtrlFramesReceived."
        ::= { dot3PauseEntry 3 }

    dot3OutPauseFrames OBJECT-TYPE
        SYNTAX      Counter32
        MAX-ACCESS  read-only
        STATUS      current
        DESCRIPTION "A count of MAC Control frames transmitted on
                    this interface with an opcode indicating the
                    PAUSE operation.

                    This counter does not increment when the
                    interface is operating in half-duplex mode.

                    Discontinuities in the value of this counter can
                    occur at re-initialization of the management
                    system, and at other times as indicated by the
                    value of ifCounterDiscontinuityTime."
        REFERENCE   "[IEEE 802.3 Std.], 30.3.4.2,
                    aPAUSEMACCtrlFramesTransmitted."
        ::= { dot3PauseEntry 4 }

    --  802.3 Tests

    dot3Tests   OBJECT IDENTIFIER ::= { dot3 6 }

    dot3Errors  OBJECT IDENTIFIER ::= { dot3 7 }

    --  TDR Test

    dot3TestTdr OBJECT-IDENTITY
        STATUS      current
        DESCRIPTION "The Time-Domain Reflectometry (TDR) test is
                    specific to ethernet-like interfaces of type
                    10Base5 and 10Base2.  The TDR value may be
                    useful in determining the approximate distance
                    to a cable fault.  It is advisable to repeat
                    this test to check for a consistent resulting
                    TDR value, to verify that there is a fault.

                    A TDR test returns as its result the time
                    interval, measured in 10 MHz ticks or 100 nsec
                    units, between the start of TDR test
                    transmission and the subsequent detection of a
                    collision or deassertion of carrier.  On
                    successful completion of a TDR test, the result
                    is stored as the value of an appropriate
                    instance of an appropriate vendor specific MIB
                    object, and the OBJECT IDENTIFIER of that
                    instance is stored in the appropriate instance
                    of the appropriate test result code object
                    (thereby indicating where the result has been
                    stored)."
        ::= { dot3Tests 1 }

    -- Loopback Test

    dot3TestLoopBack OBJECT-IDENTITY
        STATUS      current
        DESCRIPTION "This test configures the MAC chip and executes
                    an internal loopback test of memory, data paths,
                    and the MAC chip logic.  This loopback test can
                    only be executed if the interface is offline.
                    Once the test has completed, the MAC chip should
                    be reinitialized for network operation, but it
                    should remain offline.

                    If an error occurs during a test, the
                    appropriate test result object will be set
                    to indicate a failure.  The two OBJECT
                    IDENTIFIER values dot3ErrorInitError and
                    dot3ErrorLoopbackError may be used to provided
                    more information as values for an appropriate
                    test result code object."
        ::= { dot3Tests 2 }

    dot3ErrorInitError OBJECT-IDENTITY
        STATUS      current
        DESCRIPTION "Couldn't initialize MAC chip for test."
        ::= { dot3Errors 1 }

    dot3ErrorLoopbackError OBJECT-IDENTITY
        STATUS      current
        DESCRIPTION "Expected data not received (or not received
                    correctly) in loopback test."
        ::= { dot3Errors 2 }

    -- { dot3 8 }, the dot3ChipSets tree, is defined in [28]

    -- conformance information

    etherConformance OBJECT IDENTIFIER ::= { etherMIB 2 }

    etherGroups      OBJECT IDENTIFIER ::= { etherConformance 1 }
    etherCompliances OBJECT IDENTIFIER ::= { etherConformance 2 }

    -- compliance statements

    etherCompliance MODULE-COMPLIANCE
        STATUS      deprecated
        DESCRIPTION "******** THIS COMPLIANCE IS DEPRECATED ********

                    The compliance statement for managed network
                    entities which have ethernet-like network
                    interfaces.
                    This compliance is deprecated and replaced by
                    dot3Compliance."

        MODULE  -- this module
            MANDATORY-GROUPS { etherStatsGroup }

            GROUP       etherCollisionTableGroup
            DESCRIPTION "This group is optional. It is appropriate
                        for all systems which have the necessary
                        metering. Implementation in such systems is
                        highly recommended."
        ::= { etherCompliances 1 }

    ether100MbsCompliance MODULE-COMPLIANCE
        STATUS      deprecated
        DESCRIPTION "******** THIS COMPLIANCE IS DEPRECATED ********

                    The compliance statement for managed network
                    entities which have 100 Mb/sec ethernet-like
                    network interfaces.

                    This compliance is deprecated and replaced by
                    dot3Compliance."

        MODULE  -- this module
            MANDATORY-GROUPS { etherStats100MbsGroup }

            GROUP       etherCollisionTableGroup
            DESCRIPTION "This group is optional. It is appropriate
                        for all systems which have the necessary
                        metering. Implementation in such systems is
                        highly recommended."
        ::= { etherCompliances 2 }

    dot3Compliance MODULE-COMPLIANCE
        STATUS      current
        DESCRIPTION "The compliance statement for managed network
                    entities which have ethernet-like network
                    interfaces."

        MODULE  -- this module
            MANDATORY-GROUPS { etherStatsBaseGroup }

            GROUP       etherDuplexGroup
            DESCRIPTION "This group is mandatory for all
                        ethernet-like network interfaces which are
                        capable of operating in full-duplex mode.
                        It is highly recommended for all
                        ethernet-like network interfaces."

            GROUP       etherStatsLowSpeedGroup
            DESCRIPTION "This group is mandatory for all
                        ethernet-like network interfaces which are
                        capable of operating at 10 Mb/s or slower in
                        half-duplex mode."

            GROUP       etherStatsHighSpeedGroup
            DESCRIPTION "This group is mandatory for all
                        ethernet-like network interfaces which are
                        capable of operating at 100 Mb/s or faster."

            GROUP       etherControlGroup
            DESCRIPTION "This group is mandatory for all
                        ethernet-like network interfaces that
                        support the MAC Control sublayer."

            GROUP       etherControlPauseGroup
            DESCRIPTION "This group is mandatory for all
                        ethernet-like network interfaces that
                        support the MAC Control PAUSE function."

            GROUP       etherCollisionTableGroup
            DESCRIPTION "This group is optional. It is appropriate
                        for all ethernet-like network interfaces
                        which are capable of operating in
                        half-duplex mode and have the necessary
                        metering. Implementation in systems with
                        such interfaces is highly recommended."

        ::= { etherCompliances 3 }

    -- units of conformance

    etherStatsGroup OBJECT-GROUP
        OBJECTS     { dot3StatsIndex,
                      dot3StatsAlignmentErrors,
                      dot3StatsFCSErrors,
                      dot3StatsSingleCollisionFrames,
                      dot3StatsMultipleCollisionFrames,
                      dot3StatsSQETestErrors,
                      dot3StatsDeferredTransmissions,
                      dot3StatsLateCollisions,
                      dot3StatsExcessiveCollisions,
                      dot3StatsInternalMacTransmitErrors,
                      dot3StatsCarrierSenseErrors,
                      dot3StatsFrameTooLongs,
                      dot3StatsInternalMacReceiveErrors,
                      dot3StatsEtherChipSet
                    }
        STATUS      deprecated
        DESCRIPTION "********* THIS GROUP IS DEPRECATED **********

                    A collection of objects providing information
                    applicable to all ethernet-like network
                    interfaces.

                    This object group has been deprecated and
                    replaced by etherStatsBaseGroup and
                    etherStatsLowSpeedGroup."
        ::= { etherGroups 1 }

    etherCollisionTableGroup OBJECT-GROUP
        OBJECTS     { dot3CollFrequencies
                    }
        STATUS      current
        DESCRIPTION "A collection of objects providing a histogram
                    of packets successfully transmitted after
                    experiencing exactly N collisions."
        ::= { etherGroups 2 }

    etherStats100MbsGroup OBJECT-GROUP
        OBJECTS     { dot3StatsIndex,
                      dot3StatsAlignmentErrors,
                      dot3StatsFCSErrors,
                      dot3StatsSingleCollisionFrames,
                      dot3StatsMultipleCollisionFrames,
                      dot3StatsDeferredTransmissions,
                      dot3StatsLateCollisions,
                      dot3StatsExcessiveCollisions,
                      dot3StatsInternalMacTransmitErrors,
                      dot3StatsCarrierSenseErrors,
                      dot3StatsFrameTooLongs,
                      dot3StatsInternalMacReceiveErrors,
                      dot3StatsEtherChipSet,
                      dot3StatsSymbolErrors
                    }
        STATUS      deprecated
        DESCRIPTION "********* THIS GROUP IS DEPRECATED **********

                    A collection of objects providing information
                    applicable to 100 Mb/sec ethernet-like network
                    interfaces.

                    This object group has been deprecated and
                    replaced by etherStatsBaseGroup and
                    etherStatsHighSpeedGroup."
        ::= { etherGroups 3 }

    etherStatsBaseGroup OBJECT-GROUP
        OBJECTS     { dot3StatsIndex,
                      dot3StatsAlignmentErrors,
                      dot3StatsFCSErrors,
                      dot3StatsSingleCollisionFrames,
                      dot3StatsMultipleCollisionFrames,
                      dot3StatsDeferredTransmissions,
                      dot3StatsLateCollisions,
                      dot3StatsExcessiveCollisions,
                      dot3StatsInternalMacTransmitErrors,
                      dot3StatsCarrierSenseErrors,
                      dot3StatsFrameTooLongs,
                      dot3StatsInternalMacReceiveErrors
                    }
        STATUS      current
        DESCRIPTION "A collection of objects providing information
                    applicable to all ethernet-like network
                    interfaces."
        ::= { etherGroups 4 }

    etherStatsLowSpeedGroup OBJECT-GROUP
        OBJECTS     { dot3StatsSQETestErrors }
        STATUS      current
        DESCRIPTION "A collection of objects providing information
                    applicable to ethernet-like network interfaces
                    capable of operating at 10 Mb/s or slower in
                    half-duplex mode."

        ::= { etherGroups 5 }

    etherStatsHighSpeedGroup OBJECT-GROUP
        OBJECTS     { dot3StatsSymbolErrors }
        STATUS      current
        DESCRIPTION "A collection of objects providing information
                    applicable to ethernet-like network interfaces
                    capable of operating at 100 Mb/s or faster."
        ::= { etherGroups 6 }

    etherDuplexGroup OBJECT-GROUP
        OBJECTS     { dot3StatsDuplexStatus }
        STATUS      current
        DESCRIPTION "A collection of objects providing information
                    about the duplex mode of an ethernet-like
                    network interface."
        ::= { etherGroups 7 }

    etherControlGroup OBJECT-GROUP
        OBJECTS     { dot3ControlFunctionsSupported,
                      dot3ControlInUnknownOpcodes
                    }
        STATUS      current
        DESCRIPTION "A collection of objects providing information
                    about the MAC Control sublayer on ethernet-like
                    network interfaces."
        ::= { etherGroups 8 }

    etherControlPauseGroup OBJECT-GROUP
        OBJECTS     { dot3PauseAdminMode,
                      dot3PauseOperMode,
                      dot3InPauseFrames,
                      dot3OutPauseFrames
                    }
        STATUS      current
        DESCRIPTION "A collection of objects providing information
                    about and control of the MAC Control PAUSE
                    function on ethernet-like network interfaces."
        ::= { etherGroups 9 }

END

MAU-MIB DEFINITIONS ::= BEGIN

       IMPORTS
           Counter32, Integer32,
           OBJECT-TYPE, MODULE-IDENTITY, NOTIFICATION-TYPE,
           OBJECT-IDENTITY, mib-2
               FROM SNMPv2-SMI
           TruthValue, TEXTUAL-CONVENTION
               FROM SNMPv2-TC
           OBJECT-GROUP, MODULE-COMPLIANCE, NOTIFICATION-GROUP
               FROM SNMPv2-CONF;

       mauMod MODULE-IDENTITY
           LAST-UPDATED "9908240400Z"  -- August 24, 1999
           ORGANIZATION "IETF Ethernet Interfaces and Hub MIB
                        Working Group"
           CONTACT-INFO
               "WG E-mail: hubmib@hprnd.rose.hp.com
             To subscribe: hubmib-request@hprnd.rose.hp.com

                    Chair: Dan Romascanu
                   Postal: Lucent Technologies
                           Atidim Technology Park, Bldg. 3
                           Tel Aviv 61131
                           Israel
                      Tel: +972 3 645 8414, 6458458
                      Fax: +972 3 648 7146
                   E-mail: dromasca@lucent.com

                  Editors: Andrew Smith
                   Postal: Extreme Networks, Inc.
                           10460 Bandley Drive
                           Cupertino, CA 95014
                           USA
                      Tel: +1 408 579-2821
                   E-mail: andrew@extremenetworks.com

                           John Flick
                   Postal: Hewlett-Packard Company
                           8000 Foothills Blvd. M/S 5557
                          Roseville, CA 95747-5557
                          USA
                     Tel: +1 916 785 4018
                     Fax: +1 916 785 1199
                  E-mail: johnf@rose.hp.com


                          Kathryn de Graaf
                  Postal: Argon Networks
                          25 Porter Road
                          Littleton, MA  01460
                          USA
                     Tel: +1 978 486 0665 x163
                     Fax: +1 978 486 9379
                  E-mail: kdegraaf@argon.com"
          DESCRIPTION "Management information for 802.3 MAUs.

                      The following reference is used throughout
                      this MIB module:

                      [IEEE 802.3 Std] refers to
                         IEEE Std 802.3, 1998 Edition: 'Information
                         technology - Telecommunications and
                         information exchange between systems -
                         Local and metropolitan area networks -
                         Specific requirements - Part 3: Carrier
                         sense multiple access with collision
                         detection (CSMA/CD) access method and
                         physical layer specifications',
                         September 1998.

                      Of particular interest is Clause 30, '10Mb/s,
                      100Mb/s and 1000Mb/s Management'."

          REVISION    "9908240400Z" -- August 24, 1999
          DESCRIPTION "This version published as RFC 2668. Updated
                       to include support for 1000 Mb/sec
                       MAUs and flow control negotiation."

          REVISION    "9710310000Z" -- October 31, 1997
          DESCRIPTION "This version published as RFC 2239."

          REVISION    "9309300000Z" -- September 30, 1993
          DESCRIPTION "Initial version, published as RFC 1515."

          ::= { snmpDot3MauMgt 6 }

      snmpDot3MauMgt OBJECT IDENTIFIER ::= { mib-2 26 }

      -- textual conventions

      JackType ::= TEXTUAL-CONVENTION
          STATUS      current
          DESCRIPTION "Common enumeration values for repeater
                      and interface MAU jack types."


          SYNTAX      INTEGER {
                          other(1),
                          rj45(2),
                          rj45S(3), -- rj45 shielded
                          db9(4),
                          bnc(5),
                          fAUI(6),  -- female aui
                          mAUI(7),  -- male aui
                          fiberSC(8),
                          fiberMIC(9),
                          fiberST(10),
                          telco(11),
                          mtrj(12),  -- fiber MT-RJ
                          hssdc(13)  -- fiber channel style-2
                      }

      dot3RpMauBasicGroup
          OBJECT IDENTIFIER ::= { snmpDot3MauMgt 1 }
      dot3IfMauBasicGroup
          OBJECT IDENTIFIER ::= { snmpDot3MauMgt 2 }
      dot3BroadMauBasicGroup
          OBJECT IDENTIFIER ::= { snmpDot3MauMgt 3 }

      dot3IfMauAutoNegGroup
          OBJECT IDENTIFIER ::= { snmpDot3MauMgt 5 }

      -- object identities for MAU types
      --  (see rpMauType and ifMauType for usage)

      dot3MauType
          OBJECT IDENTIFIER ::= { snmpDot3MauMgt 4 }

      dot3MauTypeAUI OBJECT-IDENTITY
          STATUS      current
          DESCRIPTION "no internal MAU, view from AUI"
          ::= { dot3MauType 1 }

      dot3MauType10Base5 OBJECT-IDENTITY
          STATUS      current
          DESCRIPTION "thick coax MAU (per 802.3 section 8)"
          ::= { dot3MauType 2 }
      dot3MauTypeFoirl OBJECT-IDENTITY
          STATUS      current
          DESCRIPTION "FOIRL MAU (per 802.3 section 9.9)"
          ::= { dot3MauType 3 }

      dot3MauType10Base2 OBJECT-IDENTITY
          STATUS      current


          DESCRIPTION "thin coax MAU (per 802.3 section 10)"
          ::= { dot3MauType 4 }

      dot3MauType10BaseT OBJECT-IDENTITY
          STATUS      current
          DESCRIPTION "UTP MAU (per 802.3 section 14).
                      Note that it is strongly recommended that
                      agents return either dot3MauType10BaseTHD or
                      dot3MauType10BaseTFD if the duplex mode is
                      known.  However, management applications should
                      be prepared to receive this MAU type value from
                      older agent implementations."
          ::= { dot3MauType 5 }

      dot3MauType10BaseFP OBJECT-IDENTITY
          STATUS      current
          DESCRIPTION "passive fiber MAU (per 802.3 section 16)"
          ::= { dot3MauType 6 }

      dot3MauType10BaseFB OBJECT-IDENTITY
          STATUS      current
          DESCRIPTION "sync fiber MAU (per 802.3 section 17)"
          ::= { dot3MauType 7 }

      dot3MauType10BaseFL OBJECT-IDENTITY
          STATUS      current
          DESCRIPTION "async fiber MAU (per 802.3 section 18)
                      Note that it is strongly recommended that
                      agents return either dot3MauType10BaseFLHD or
                      dot3MauType10BaseFLFD if the duplex mode is
                      known.  However, management applications should
                      be prepared to receive this MAU type value from
                      older agent implementations."
          ::= { dot3MauType 8 }

      dot3MauType10Broad36 OBJECT-IDENTITY
          STATUS      current
          DESCRIPTION "broadband DTE MAU (per 802.3 section 11).
                      Note that 10BROAD36 MAUs can be attached to
                      interfaces but not to repeaters."
          ::= { dot3MauType 9 }
      ------ new since RFC 1515:
      dot3MauType10BaseTHD OBJECT-IDENTITY
          STATUS      current
          DESCRIPTION "UTP MAU (per 802.3 section 14), half duplex
                      mode"
          ::= { dot3MauType 10 }


      dot3MauType10BaseTFD OBJECT-IDENTITY
          STATUS      current
          DESCRIPTION "UTP MAU (per 802.3 section 14), full duplex
                      mode"
          ::= { dot3MauType 11 }

      dot3MauType10BaseFLHD OBJECT-IDENTITY
          STATUS      current
          DESCRIPTION "async fiber MAU (per 802.3 section 18), half
                      duplex mode"
          ::= { dot3MauType 12 }

      dot3MauType10BaseFLFD OBJECT-IDENTITY
          STATUS      current
          DESCRIPTION "async fiber MAU (per 802.3 section 18), full
                      duplex mode"
          ::= { dot3MauType 13 }

      dot3MauType100BaseT4 OBJECT-IDENTITY
          STATUS      current
          DESCRIPTION "4 pair categ. 3 UTP (per 802.3 section 23)"
          ::= { dot3MauType 14 }

      dot3MauType100BaseTXHD OBJECT-IDENTITY
          STATUS      current
          DESCRIPTION "2 pair categ. 5 UTP (per 802.3 section 25),
                      half duplex mode"
          ::= { dot3MauType 15 }

      dot3MauType100BaseTXFD OBJECT-IDENTITY
          STATUS      current
          DESCRIPTION "2 pair categ. 5 UTP (per 802.3 section 25),
                      full duplex mode"
          ::= { dot3MauType 16 }

      dot3MauType100BaseFXHD OBJECT-IDENTITY
          STATUS      current
          DESCRIPTION "X fiber over PMT (per 802.3 section 26), half
                      duplex mode"
          ::= { dot3MauType 17 }
      dot3MauType100BaseFXFD OBJECT-IDENTITY
          STATUS      current
          DESCRIPTION "X fiber over PMT (per 802.3 section 26), full
                      duplex mode"
          ::= { dot3MauType 18 }

      dot3MauType100BaseT2HD OBJECT-IDENTITY
          STATUS      current


          DESCRIPTION "2 pair categ. 3 UTP (per 802.3 section 32),
                      half duplex mode"
          ::= { dot3MauType 19 }

      dot3MauType100BaseT2FD OBJECT-IDENTITY
          STATUS      current
          DESCRIPTION "2 pair categ. 3 UTP (per 802.3 section 32),
                      full duplex mode"
          ::= { dot3MauType 20 }

      ------ new since RFC 2239:

      dot3MauType1000BaseXHD OBJECT-IDENTITY
          STATUS      current
          DESCRIPTION "PCS/PMA (per 802.3 section 36), unknown PMD,
                      half duplex mode"
          ::= { dot3MauType 21 }

      dot3MauType1000BaseXFD OBJECT-IDENTITY
          STATUS      current
          DESCRIPTION "PCS/PMA (per 802.3 section 36), unknown PMD,
                      full duplex mode"
          ::= { dot3MauType 22 }

      dot3MauType1000BaseLXHD OBJECT-IDENTITY
          STATUS      current
          DESCRIPTION "Fiber over long-wavelength laser (per 802.3
                      section 38), half duplex mode"
          ::= { dot3MauType 23 }

      dot3MauType1000BaseLXFD OBJECT-IDENTITY
          STATUS      current
          DESCRIPTION "Fiber over long-wavelength laser (per 802.3
                      section 38), full duplex mode"
          ::= { dot3MauType 24 }

      dot3MauType1000BaseSXHD OBJECT-IDENTITY
          STATUS      current
          DESCRIPTION "Fiber over short-wavelength laser (per 802.3
                      section 38), half duplex mode"
          ::= { dot3MauType 25 }

      dot3MauType1000BaseSXFD OBJECT-IDENTITY
          STATUS      current
          DESCRIPTION "Fiber over short-wavelength laser (per 802.3
                      section 38), full duplex mode"
          ::= { dot3MauType 26 }


      dot3MauType1000BaseCXHD OBJECT-IDENTITY
          STATUS      current
          DESCRIPTION "Copper over 150-Ohm balanced cable (per 802.3
                      section 39), half duplex mode"
          ::= { dot3MauType 27 }

      dot3MauType1000BaseCXFD OBJECT-IDENTITY
          STATUS      current
          DESCRIPTION "Copper over 150-Ohm balanced cable (per 802.3
                      section 39), full duplex mode"
          ::= { dot3MauType 28 }

      dot3MauType1000BaseTHD OBJECT-IDENTITY
          STATUS      current
          DESCRIPTION "Four-pair Category 5 UTP (per 802.3 section
                      40), half duplex mode"
          ::= { dot3MauType 29 }

      dot3MauType1000BaseTFD OBJECT-IDENTITY
          STATUS      current
          DESCRIPTION "Four-pair Category 5 UTP (per 802.3 section
                      40), full duplex mode"
          ::= { dot3MauType 30 }

      --
      -- The Basic Repeater MAU Table
      --

      rpMauTable OBJECT-TYPE
          SYNTAX      SEQUENCE OF RpMauEntry
          MAX-ACCESS  not-accessible
          STATUS      current
          DESCRIPTION "Table of descriptive and status information
                      about the MAU(s) attached to the ports of a
                      repeater."
          ::= { dot3RpMauBasicGroup 1 }

      rpMauEntry OBJECT-TYPE
          SYNTAX      RpMauEntry
          MAX-ACCESS  not-accessible
          STATUS      current
          DESCRIPTION "An entry in the table, containing information
                      about a single MAU."
          INDEX       { rpMauGroupIndex,
                        rpMauPortIndex,
                        rpMauIndex
                      }
          ::= { rpMauTable 1 }


      RpMauEntry ::=
          SEQUENCE {
              rpMauGroupIndex                     Integer32,
              rpMauPortIndex                      Integer32,
              rpMauIndex                          Integer32,
              rpMauType                           OBJECT IDENTIFIER,
              rpMauStatus                         INTEGER,
              rpMauMediaAvailable                 INTEGER,
              rpMauMediaAvailableStateExits       Counter32,
              rpMauJabberState                    INTEGER,
              rpMauJabberingStateEnters           Counter32,
              rpMauFalseCarriers                  Counter32
      }

      rpMauGroupIndex OBJECT-TYPE
          SYNTAX      Integer32 (1..2147483647)
          MAX-ACCESS  read-only
          STATUS      current
          DESCRIPTION "This variable uniquely identifies the group
                      containing the port to which the MAU described
                      by this entry is connected.

                      Note:  In practice, a group will generally be
                      a field-replaceable unit (i.e., module, card,
                      or board) that can fit in the physical system
                      enclosure, and the group number will correspond
                      to a number marked on the physical enclosure.

                      The group denoted by a particular value of this
                      object is the same as the group denoted by the
                      same value of rptrGroupIndex."
          REFERENCE   "Reference RFC 2108, rptrGroupIndex."
          ::= { rpMauEntry 1 }

      rpMauPortIndex OBJECT-TYPE
          SYNTAX      Integer32 (1..2147483647)
          MAX-ACCESS  read-only
          STATUS      current
          DESCRIPTION "This variable uniquely identifies the repeater
                      port within group rpMauGroupIndex to which the
                      MAU described by this entry is connected."
          REFERENCE   "Reference RFC 2108, rptrPortIndex."
          ::= { rpMauEntry 2 }

      rpMauIndex OBJECT-TYPE
          SYNTAX      Integer32 (1..2147483647)
          MAX-ACCESS  read-only
          STATUS      current


          DESCRIPTION "This variable uniquely identifies the MAU
                      described by this entry from among other
                      MAUs connected to the same port
                      (rpMauPortIndex)."
          REFERENCE   "[IEEE 802.3 Std], 30.5.1.1.1, aMAUID."
          ::= { rpMauEntry 3 }

      rpMauType OBJECT-TYPE
          SYNTAX      OBJECT IDENTIFIER
          MAX-ACCESS  read-only
          STATUS      current
          DESCRIPTION "This object identifies the MAU type.  An
                      initial set of MAU types are defined above.  The
                      assignment of OBJECT IDENTIFIERs to new types of
                      MAUs is managed by the IANA.  If the MAU type is
                      unknown, the object identifier

                      unknownMauType OBJECT IDENTIFIER ::= { 0 0 }

                      is returned.  Note that unknownMauType is a
                      syntactically valid object identifier, and any
                      conformant implementation of ASN.1 and the BER
                      must be able to generate and recognize this
                      value."
          REFERENCE   "[IEEE 802.3 Std], 30.5.1.1.2, aMAUType."
          ::= { rpMauEntry 4 }

      rpMauStatus OBJECT-TYPE
          SYNTAX      INTEGER {
                          other(1),
                          unknown(2),
                          operational(3),
                          standby(4),
                          shutdown(5),
                          reset(6)
                      }
          MAX-ACCESS  read-write
          STATUS      current
          DESCRIPTION "The current state of the MAU.  This object MAY
                      be implemented as a read-only object by those
                      agents and MAUs that do not implement software
                      control of the MAU state.  Some agents may not
                      support setting the value of this object to some
                      of the enumerated values.

                      The value other(1) is returned if the MAU is in
                      a state other than one of the states 2 through
                      6.


                      The value unknown(2) is returned when the MAU's
                      true state is unknown; for example, when it is
                      being initialized.

                      A MAU in the operational(3) state is fully
                      functional, operates, and passes signals to its
                      attached DTE or repeater port in accordance to
                      its specification.

                      A MAU in standby(4) state forces DI and CI to
                      idle and the media transmitter to idle or fault,
                      if supported.  Standby(4) mode only applies to
                      link type MAUs.  The state of
                      rpMauMediaAvailable is unaffected.

                      A MAU in shutdown(5) state assumes the same
                      condition on DI, CI, and the media transmitter
                      as though it were powered down or not connected.
                      The MAU MAY return other(1) value for the
                      rpMauJabberState and rpMauMediaAvailable objects
                      when it is in this state.  For an AUI, this
                      state will remove power from the AUI.

                      Setting this variable to the value reset(6)
                      resets the MAU in the same manner as a
                      power-off, power-on cycle of at least one-half
                      second would.  The agent is not required to
                      return the value reset (6).

                      Setting this variable to the value
                      operational(3), standby(4), or shutdown(5)
                      causes the MAU to assume the respective state
                      except that setting a mixing-type MAU or an AUI
                      to standby(4) will cause the MAU to enter the
                      shutdown state."
          REFERENCE   "[IEEE 802.3 Std], 30.5.1.1.7, aMAUAdminState,
                          30.5.1.2.2, acMAUAdminControl, and 30.5.1.2.1,
                      acResetMAU."
          ::= { rpMauEntry 5 }

      rpMauMediaAvailable OBJECT-TYPE
          SYNTAX      INTEGER {
                          other(1),
                          unknown(2),
                          available(3),
                          notAvailable(4),
                          remoteFault(5),
                          invalidSignal(6),


                          remoteJabber(7),
                          remoteLinkLoss(8),
                          remoteTest(9),
                          offline(10),
                          autoNegError(11)
                      }
          MAX-ACCESS  read-only
          STATUS      current
          DESCRIPTION "If the MAU is a link or fiber type (FOIRL,
                      10BASE-T, 10BASE-F) then this is equivalent to
                      the link test fail state/low light function.
                      For an AUI or a coax (including broadband) MAU
                      this indicates whether or not loopback is
                      detected on the DI circuit.  The value of this
                      attribute persists between packets for MAU types
                      AUI, 10BASE5, 10BASE2, 10BROAD36, and 10BASE-FP.

                      The value other(1) is returned if the
                      mediaAvailable state is not one of 2 through 11.

                      The value unknown(2) is returned when the MAU's
                      true state is unknown; for example, when it is
                      being initialized.  At power-up or following a
                      reset, the value of this attribute will be
                      unknown for AUI, coax, and 10BASE-FP MAUs.  For
                      these MAUs loopback will be tested on each
                      transmission during which no collision is
                      detected.  If DI is receiving input when DO
                      returns to IDL after a transmission and there
                      has been no collision during the transmission
                      then loopback will be detected.  The value of
                      this attribute will only change during
                      non-collided transmissions for AUI, coax, and
                      10BASE-FP MAUs.

                      For 100Mbps and 1000Mbps MAUs, the enumerations
                      match the states within the respective link
                      integrity state diagrams, fig 32-16, 23-12 and
                      24-15 of sections 32, 23 and 24 of [16].  Any
                      MAU which implements management of
                      auto-negotiation will map remote fault
                      indication to remote fault.

                      The value available(3) indicates that the link,
                      light, or loopback is normal.  The value
                      notAvailable(4) indicates link loss, low light,
                      or no loopback.


                      The value remoteFault(5) indicates that a fault
                      has been detected at the remote end of the link.
                      This value applies to 10BASE-FB, 100BASE-T4 Far
                      End Fault Indication and non-specified remote
                      faults from a system running auto-negotiation.
                      The values remoteJabber(7), remoteLinkLoss(8),
                      and remoteTest(9) SHOULD be used instead of
                      remoteFault(5) where the reason for remote fault
                      is identified in the remote signaling protocol.

                      The value invalidSignal(6) indicates that an
                      invalid signal has been received from the other
                      end of the link.  InvalidSignal(6) applies only
                      to MAUs of type 10BASE-FB.

                      Where an IEEE Std 802.3u-1995 clause 22 MII
                      is present, a logic one in the remote fault bit
                      (reference section 22.2.4.2.8 of that document)
                      maps to the value remoteFault(5), and a logic
                      zero in the link status bit (reference section
                      22.2.4.2.10 of that document) maps to the value
                      notAvailable(4).  The value notAvailable(4)
                      takes precedence over the value remoteFault(5).

                      Any MAU that implements management of clause 37
                      Auto-Negotiation will map the received Remote
                      Fault (RF1 and RF2) bit values for Offline to
                      offline(10), Link Failure to remoteFault(5) and
                      Auto-Negotiation Error to autoNegError(11)."

          REFERENCE   "[IEEE 802.3 Std], 30.5.1.1.4, aMediaAvailable."
          ::= { rpMauEntry 6 }

      rpMauMediaAvailableStateExits OBJECT-TYPE
          SYNTAX      Counter32
          MAX-ACCESS  read-only
          STATUS      current
          DESCRIPTION "A count of the number of times that
                      rpMauMediaAvailable for this MAU instance leaves
                      the state available(3).

                      Discontinuities in the value of this counter can
                      occur at re-initialization of the management
                      system, and at other times as indicated by the
                      value of rptrMonitorPortLastChange."
          REFERENCE   "[IEEE 802.3 Std], 30.5.1.1.5,
                      aLoseMediaCounter.
                      RFC 2108, rptrMonitorPortLastChange"


          ::= { rpMauEntry 7 }

      rpMauJabberState OBJECT-TYPE
          SYNTAX      INTEGER {
                          other(1),
                          unknown(2),
                          noJabber(3),
                          jabbering(4)
                      }
          MAX-ACCESS  read-only
          STATUS      current
          DESCRIPTION "The value other(1) is returned if the jabber
                      state is not 2, 3, or 4.  The agent MUST always
                      return other(1) for MAU type dot3MauTypeAUI.

                      The value unknown(2) is returned when the MAU's
                      true state is unknown; for example, when it is
                      being initialized.

                      If the MAU is not jabbering the agent returns
                      noJabber(3).  This is the 'normal' state.

                      If the MAU is in jabber state the agent returns
                      the jabbering(4) value."
          REFERENCE "[IEEE 802.3 Std], 30.5.1.1.6,
                    aJabber.jabberFlag."
          ::= { rpMauEntry 8 }

      rpMauJabberingStateEnters OBJECT-TYPE
          SYNTAX      Counter32
          MAX-ACCESS  read-only
          STATUS      current
          DESCRIPTION "A count of the number of times that
                      mauJabberState for this MAU instance enters the
                      state jabbering(4).  For MAUs of type
                      dot3MauTypeAUI, dot3MauType100BaseT4,
                      dot3MauType100BaseTX, dot3MauType100BaseFX and
                          all 1000Mbps types, this counter will always
                          indicate zero.

                          Discontinuities in the value of this counter
                          can occur at re-initialization of the
                          management system, and at other times as
                          indicated by the value of
                          rptrMonitorPortLastChange."
              REFERENCE   "[IEEE 802.3 Std], 30.5.1.1.6,
                          aJabber.jabberCounter.
                          RFC 2108, rptrMonitorPortLastChange"


          ::= { rpMauEntry 9 }

      rpMauFalseCarriers OBJECT-TYPE
          SYNTAX      Counter32
          MAX-ACCESS  read-only
          STATUS      current
          DESCRIPTION "A count of the number of false carrier events
                      during IDLE in 100BASE-X links.  This counter
                      does not increment at the symbol rate.  It can
                      increment after a valid carrier completion at a
                      maximum rate of once per 100 ms until the next
                      carrier event.

                      This counter increments only for MAUs of type
                      dot3MauType100BaseT4, dot3MauType100BaseTX, and
                      dot3MauType100BaseFX and all 1000Mbps types.
                      For all other MAU types, this counter will
                      always indicate zero.

                      The approximate minimum time for rollover of
                      this counter is 7.4 hours.

                      Discontinuities in the value of this counter can
                      occur at re-initialization of the management
                      system, and at other times as indicated by the
                      value of rptrMonitorPortLastChange."
          REFERENCE   "[IEEE 802.3 Std], 30.5.1.1.10, aFalseCarriers.
                      RFC 2108, rptrMonitorPortLastChange"
          ::= { rpMauEntry 10 }

      -- The rpJackTable applies to MAUs attached to repeaters
      -- which have one or more external jacks (connectors).

      rpJackTable OBJECT-TYPE
          SYNTAX      SEQUENCE OF RpJackEntry
          MAX-ACCESS  not-accessible
          STATUS      current
          DESCRIPTION "Information about the external jacks attached
                      to MAUs attached to the ports of a repeater."
          ::= { dot3RpMauBasicGroup 2 }

      rpJackEntry OBJECT-TYPE
          SYNTAX      RpJackEntry
          MAX-ACCESS  not-accessible
          STATUS      current
          DESCRIPTION "An entry in the table, containing information
                      about a particular jack."
          INDEX       { rpMauGroupIndex,


                        rpMauPortIndex,
                        rpMauIndex,
                        rpJackIndex
                      }
          ::= { rpJackTable 1 }

      RpJackEntry ::=
          SEQUENCE {
              rpJackIndex                         Integer32,
              rpJackType                          JackType
          }

      rpJackIndex OBJECT-TYPE
          SYNTAX      Integer32 (1..2147483647)
          MAX-ACCESS  not-accessible
          STATUS      current
          DESCRIPTION "This variable uniquely identifies the jack
                      described by this entry from among other jacks
                      attached to the same MAU (rpMauIndex)."
          ::= { rpJackEntry 1 }

      rpJackType OBJECT-TYPE
          SYNTAX      JackType
          MAX-ACCESS  read-only
          STATUS      current
          DESCRIPTION "The jack connector type, as it appears on the
                      outside of the system."
          ::= { rpJackEntry 2 }

      --
      -- The Basic Interface MAU Table
      --

      ifMauTable OBJECT-TYPE
          SYNTAX      SEQUENCE OF IfMauEntry
          MAX-ACCESS  not-accessible
          STATUS      current
          DESCRIPTION "Table of descriptive and status information
                      about MAU(s) attached to an interface."
          ::= { dot3IfMauBasicGroup 1 }

      ifMauEntry OBJECT-TYPE
          SYNTAX      IfMauEntry
          MAX-ACCESS  not-accessible
          STATUS      current
          DESCRIPTION "An entry in the table, containing information
                      about a single MAU."
          INDEX       { ifMauIfIndex,


                        ifMauIndex
                      }
          ::= { ifMauTable 1 }

      IfMauEntry ::=
          SEQUENCE {
              ifMauIfIndex                        Integer32,
              ifMauIndex                          Integer32,
              ifMauType                           OBJECT IDENTIFIER,
              ifMauStatus                         INTEGER,
              ifMauMediaAvailable                 INTEGER,
              ifMauMediaAvailableStateExits       Counter32,
              ifMauJabberState                    INTEGER,
              ifMauJabberingStateEnters           Counter32,
              ifMauFalseCarriers                  Counter32,
              ifMauTypeList                       Integer32,
              ifMauDefaultType                    OBJECT IDENTIFIER,
              ifMauAutoNegSupported               TruthValue,
              ifMauTypeListBits                   BITS
          }

      ifMauIfIndex OBJECT-TYPE
          SYNTAX      Integer32 (1..2147483647)
          MAX-ACCESS  read-only
          STATUS      current
          DESCRIPTION "This variable uniquely identifies the interface
                      to which the MAU described by this entry is
                      connected."
          REFERENCE   "RFC 1213, ifIndex"
          ::= { ifMauEntry 1 }

      ifMauIndex OBJECT-TYPE
          SYNTAX      Integer32 (1..2147483647)
          MAX-ACCESS  read-only
          STATUS      current
          DESCRIPTION "This variable uniquely identifies the MAU
                      described by this entry from among other MAUs
                      connected to the same interface (ifMauIfIndex)."
          REFERENCE   "[IEEE 802.3 Std], 30.5.1.1.1, aMAUID."
          ::= { ifMauEntry 2 }

      ifMauType OBJECT-TYPE
          SYNTAX      OBJECT IDENTIFIER
          MAX-ACCESS  read-only
          STATUS      current
          DESCRIPTION "This object identifies the MAU type.  An
                      initial set of MAU types are defined above.  The
                      assignment of OBJECT IDENTIFIERs to new types of


                      MAUs is managed by the IANA.  If the MAU type is
                      unknown, the object identifier

                      unknownMauType OBJECT IDENTIFIER ::= { 0 0 }

                      is returned.  Note that unknownMauType is a
                      syntactically valid object identifier, and any
                      conformant implementation of ASN.1 and the BER
                      must be able to generate and recognize this
                      value.

                      This object represents the operational type of
                      the MAU, as determined by either (1) the result
                      of the auto-negotiation function or (2) if
                      auto-negotiation is not enabled or is not
                      implemented for this MAU, by the value of the
                      object ifMauDefaultType.  In case (2), a set to
                      the object ifMauDefaultType will force the MAU
                      into the new operating mode."
          REFERENCE   "[IEEE 802.3 Std], 30.5.1.1.2, aMAUType."
          ::= { ifMauEntry 3 }

      ifMauStatus OBJECT-TYPE
          SYNTAX      INTEGER {
                          other(1),
                          unknown(2),
                          operational(3),
                          standby(4),
                          shutdown(5),
                          reset(6)
                      }
          MAX-ACCESS  read-write
          STATUS      current
          DESCRIPTION "The current state of the MAU.  This object MAY
                      be implemented as a read-only object by those
                      agents and MAUs that do not implement software
                      control of the MAU state.  Some agents may not
                      support setting the value of this object to some
                      of the enumerated values.

                      The value other(1) is returned if the MAU is in
                      a state other than one of the states 2 through
                      6.

                      The value unknown(2) is returned when the MAU's
                      true state is unknown; for example, when it is
                      being initialized.


                      A MAU in the operational(3) state is fully
                      functional, operates, and passes signals to its
                      attached DTE or repeater port in accordance to
                      its specification.

                      A MAU in standby(4) state forces DI and CI to
                      idle and the media transmitter to idle or fault,
                      if supported.  Standby(4) mode only applies to
                      link type MAUs.  The state of
                      ifMauMediaAvailable is unaffected.

                      A MAU in shutdown(5) state assumes the same
                      condition on DI, CI, and the media transmitter
                      as though it were powered down or not connected.
                      The MAU MAY return other(1) value for the
                      ifMauJabberState and ifMauMediaAvailable objects
                      when it is in this state.  For an AUI, this
                      state will remove power from the AUI.

                      Setting this variable to the value reset(6)
                      resets the MAU in the same manner as a
                      power-off, power-on cycle of at least one-half
                      second would.  The agent is not required to
                      return the value reset (6).

                      Setting this variable to the value
                      operational(3), standby(4), or shutdown(5)
                      causes the MAU to assume the respective state
                      except that setting a mixing-type MAU or an AUI
                      to standby(4) will cause the MAU to enter the
                      shutdown state."
          REFERENCE   "[IEEE 802.3 Std], 30.5.1.1.7, aMAUAdminState,
                      30.5.1.2.2, acMAUAdminControl, and 30.5.1.2.1,
                      acResetMAU."
          ::= { ifMauEntry 4 }
      ifMauMediaAvailable OBJECT-TYPE
          SYNTAX      INTEGER {
                          other(1),
                          unknown(2),
                          available(3),
                          notAvailable(4),
                          remoteFault(5),
                          invalidSignal(6),
                          remoteJabber(7),
                          remoteLinkLoss(8),
                          remoteTest(9),
                          offline(10),
                          autoNegError(11)


                      }
          MAX-ACCESS  read-only
          STATUS      current
          DESCRIPTION "If the MAU is a link or fiber type (FOIRL,
                      10BASE-T, 10BASE-F) then this is equivalent to
                      the link test fail state/low light function.
                      For an AUI or a coax (including broadband) MAU
                      this indicates whether or not loopback is
                      detected on the DI circuit.  The value of this
                      attribute persists between packets for MAU types
                      AUI, 10BASE5, 10BASE2, 10BROAD36, and 10BASE-FP.

                      The value other(1) is returned if the
                      mediaAvailable state is not one of 2 through 11.

                      The value unknown(2) is returned when the MAU's
                      true state is unknown; for example, when it is
                      being initialized.  At power-up or following a
                      reset, the value of this attribute will be
                      unknown for AUI, coax, and 10BASE-FP MAUs.  For
                      these MAUs loopback will be tested on each
                      transmission during which no collision is
                      detected.  If DI is receiving input when DO
                      returns to IDL after a transmission and there
                      has been no collision during the transmission
                      then loopback will be detected.  The value of
                      this attribute will only change during
                      non-collided transmissions for AUI, coax, and
                      10BASE-FP MAUs.

                      For 100Mbps and 1000Mbps MAUs, the enumerations
                      match the states within the respective link
                      integrity state diagrams, fig 32-16, 23-12 and
                      24-15 of sections 32, 23 and 24 of [16].  Any
                      MAU which implements management of
                      auto-negotiation will map remote fault
                      indication to remote fault.

                      The value available(3) indicates that the link,
                      light, or loopback is normal.  The value
                      notAvailable(4) indicates link loss, low light,
                      or no loopback.

                      The value remoteFault(5) indicates that a fault
                      has been detected at the remote end of the link.
                      This value applies to 10BASE-FB, 100BASE-T4 Far
                      End Fault Indication and non-specified remote
                      faults from a system running auto-negotiation.


                      The values remoteJabber(7), remoteLinkLoss(8),
                      and remoteTest(9) SHOULD be used instead of
                      remoteFault(5) where the reason for remote fault
                      is identified in the remote signaling protocol.

                      The value invalidSignal(6) indicates that an
                      invalid signal has been received from the other
                      end of the link.  InvalidSignal(6) applies only
                      to MAUs of type 10BASE-FB.

                      Where an IEEE Std 802.3u-1995 clause 22 MII
                      is present, a logic one in the remote fault bit
                      (reference section 22.2.4.2.8 of that document)
                      maps to the value remoteFault(5), and a logic
                      zero in the link status bit (reference section
                      22.2.4.2.10 of that document) maps to the value
                      notAvailable(4).  The value notAvailable(4)
                      takes precedence over the value remoteFault(5).

                      Any MAU that implements management of clause 37
                      Auto-Negotiation will map the received RF1 and
                      RF2 bit values for Offline to offline(10), Link
                      Failure to remoteFault(5) and Auto-Negotiation
                      Error to autoNegError(11)."
          REFERENCE   "[IEEE 802.3 Std], 30.5.1.1.4, aMediaAvailable."
          ::= { ifMauEntry 5 }

      ifMauMediaAvailableStateExits OBJECT-TYPE
          SYNTAX      Counter32
          MAX-ACCESS  read-only
          STATUS      current
          DESCRIPTION "A count of the number of times that
                      ifMauMediaAvailable for this MAU instance leaves
                      the state available(3).
                      Discontinuities in the value of this counter can
                      occur at re-initialization of the management
                      system, and at other times as indicated by the
                      value of ifCounterDiscontinuityTime."
          REFERENCE   "[IEEE 802.3 Std], 30.5.1.1.5,
                      aLoseMediaCounter.
                      RFC 2233, ifCounterDiscontinuityTime."
          ::= { ifMauEntry 6 }

      ifMauJabberState OBJECT-TYPE
          SYNTAX      INTEGER {
                          other(1),
                          unknown(2),
                          noJabber(3),


                          jabbering(4)
                      }
          MAX-ACCESS  read-only
          STATUS      current
          DESCRIPTION "The value other(1) is returned if the jabber
                      state is not 2, 3, or 4.  The agent MUST always
                      return other(1) for MAU type dot3MauTypeAUI.

                      The value unknown(2) is returned when the MAU's
                      true state is unknown; for example, when it is
                      being initialized.

                      If the MAU is not jabbering the agent returns
                      noJabber(3).  This is the 'normal' state.

                      If the MAU is in jabber state the agent returns
                      the jabbering(4) value."
          REFERENCE   "[IEEE 802.3 Std], 30.5.1.1.6,
                      aJabber.jabberFlag."
          ::= { ifMauEntry 7 }

      ifMauJabberingStateEnters OBJECT-TYPE
          SYNTAX      Counter32
          MAX-ACCESS  read-only
          STATUS      current
          DESCRIPTION "A count of the number of times that
                      mauJabberState for this MAU instance enters the
                      state jabbering(4). This counter will always
                      indicate zero for MAUs of type dot1MauTypeAUI
                      and those of speeds above 10Mbps.

                      Discontinuities in the value of this counter can
                      occur at re-initialization of the management
                      system, and at other times as indicated by the
                      value of ifCounterDiscontinuityTime."
          REFERENCE   "[IEEE 802.3 Std], 30.5.1.1.6,
                      aJabber.jabberCounter.
                      RFC 2233, ifCounterDiscontinuityTime."
          ::= { ifMauEntry 8 }

      ifMauFalseCarriers OBJECT-TYPE
          SYNTAX      Counter32
          MAX-ACCESS  read-only
          STATUS      current
          DESCRIPTION "A count of the number of false carrier events
                      during IDLE in 100BASE-X and 1000BASE-X links.

                      For all other MAU types, this counter will


                      always indicate zero. This counter does not
                      increment at the symbol rate.

                      It can increment after a valid carrier
                      completion at a maximum rate of once per 100 ms
                      for 100BASE-X and once per 10us for 1000BASE-X
                      until the next CarrierEvent.

                      Discontinuities in the value of this counter can
                      occur at re-initialization of the management
                      system, and at other times as indicated by the
                      value of ifCounterDiscontinuityTime."
          REFERENCE   "[IEEE 802.3 Std], 30.5.1.1.10, aFalseCarriers.
                      RFC 2233, ifCounterDiscontinuityTime."
          ::= { ifMauEntry 9 }

      ifMauTypeList OBJECT-TYPE
          SYNTAX      Integer32
          MAX-ACCESS  read-only
          STATUS      deprecated
          DESCRIPTION "********* THIS OBJECT IS DEPRECATED **********

                      A value that uniquely identifies the set of
                      possible IEEE 802.3 types that the MAU could be.
                      The value is a sum which initially takes the
                      value zero.  Then, for each type capability of
                      this MAU, 2 raised to the power noted below is
                      added to the sum. For example, a MAU which has
                      the capability to be only 10BASE-T would have a
                      value of 512 (2**9).  In contrast, a MAU which
                      supports both 10Base-T (full duplex) and
                      100BASE-TX (full duplex) would have a value of
                      ((2**11) + (2**16)) or 67584.

                      The powers of 2 assigned to the capabilities are
                      these:

                      Power  Capability
                        0      other or unknown
                        1      AUI
                        2      10BASE-5
                        3      FOIRL
                        4      10BASE-2
                        5      10BASE-T duplex mode unknown
                        6      10BASE-FP
                        7      10BASE-FB
                        8      10BASE-FL duplex mode unknown
                        9      10BROAD36


                       10      10BASE-T  half duplex mode
                       11      10BASE-T  full duplex mode
                       12      10BASE-FL half duplex mode
                       13      10BASE-FL full duplex mode
                       14      100BASE-T4
                       15      100BASE-TX half duplex mode
                       16      100BASE-TX full duplex mode
                       17      100BASE-FX half duplex mode
                       18      100BASE-FX full duplex mode
                       19      100BASE-T2 half duplex mode
                       20      100BASE-T2 full duplex mode

                      If auto-negotiation is present on this MAU, this
                      object will map to ifMauAutoNegCapability.

                      This object has been deprecated in favour of
                      ifMauTypeListBits."
          ::= { ifMauEntry 10 }

      ifMauDefaultType OBJECT-TYPE
          SYNTAX      OBJECT IDENTIFIER
          MAX-ACCESS  read-write
          STATUS      current
          DESCRIPTION "This object identifies the default
                      administrative baseband MAU type, to be used in
                      conjunction with the operational MAU type
                      denoted by ifMauType.

                      The set of possible values for this object is
                      the same as the set defined for the ifMauType
                      object.

                      This object represents the
                      administratively-configured type of the MAU.  If
                      auto-negotiation is not enabled or is not
                      implemented for this MAU, the value of this
                      object determines the operational type of the
                      MAU.  In this case, a set to this object will
                      force the MAU into the specified operating mode.

                      If auto-negotiation is implemented and enabled
                      for this MAU, the operational type of the MAU
                      is determined by auto-negotiation, and the value
                      of this object denotes the type to which the MAU
                      will automatically revert if/when
                      auto-negotiation is later disabled.

                      NOTE TO IMPLEMENTORS:  It may be necessary to


                      provide for underlying hardware implementations
                      which do not follow the exact behavior specified
                      above.  In particular, when
                      ifMauAutoNegAdminStatus transitions from enabled
                      to disabled, the agent implementation MUST
                      ensure that the operational type of the MAU (as
                      reported by ifMauType) correctly transitions to
                      the value specified by this object, rather than
                      continuing to operate at the value earlier
                      determined by the auto-negotiation function."
          REFERENCE   "[IEEE 802.3 Std], 30.5.1.1.1, aMAUID, and
                      22.2.4.1.4."
          ::= { ifMauEntry 11 }

      ifMauAutoNegSupported OBJECT-TYPE
          SYNTAX      TruthValue
          MAX-ACCESS  read-only
          STATUS      current
          DESCRIPTION "This object indicates whether or not
                      auto-negotiation is supported on this MAU."
          ::= { ifMauEntry 12 }

      ifMauTypeListBits OBJECT-TYPE
          SYNTAX      BITS {
              bOther(0),         -- other or unknown
              bAUI(1),           -- AUI
              b10base5(2),       -- 10BASE-5
              bFoirl(3),         -- FOIRL

              b10base2(4),       -- 10BASE-2
              b10baseT(5),       -- 10BASE-T duplex mode unknown
              b10baseFP(6),      -- 10BASE-FP
              b10baseFB(7),      -- 10BASE-FB
              b10baseFL(8),      -- 10BASE-FL duplex mode unknown
              b10broad36(9),     -- 10BROAD36
              b10baseTHD(10),    -- 10BASE-T  half duplex mode
              b10baseTFD(11),    -- 10BASE-T  full duplex mode
              b10baseFLHD(12),   -- 10BASE-FL half duplex mode
              b10baseFLFD(13),   -- 10BASE-FL full duplex mode

              b100baseT4(14),    -- 100BASE-T4
              b100baseTXHD(15),  -- 100BASE-TX half duplex mode
              b100baseTXFD(16),  -- 100BASE-TX full duplex mode
              b100baseFXHD(17),  -- 100BASE-FX half duplex mode
              b100baseFXFD(18),  -- 100BASE-FX full duplex mode
              b100baseT2HD(19),  -- 100BASE-T2 half duplex mode
              b100baseT2FD(20),  -- 100BASE-T2 full duplex mode


              b1000baseXHD(21),  -- 1000BASE-X half duplex mode
              b1000baseXFD(22),  -- 1000BASE-X full duplex mode
              b1000baseLXHD(23), -- 1000BASE-LX half duplex mode
              b1000baseLXFD(24), -- 1000BASE-LX full duplex mode
              b1000baseSXHD(25), -- 1000BASE-SX half duplex mode
              b1000baseSXFD(26), -- 1000BASE-SX full duplex mode
              b1000baseCXHD(27), -- 1000BASE-CX half duplex mode
              b1000baseCXFD(28), -- 1000BASE-CX full duplex mode
              b1000baseTHD(29),  -- 1000BASE-T half duplex mode
              b1000baseTFD(30)   -- 1000BASE-T full duplex mode
          }
          MAX-ACCESS  read-only
          STATUS      current
          DESCRIPTION "A value that uniquely identifies the set of
                      possible IEEE 802.3 types that the MAU could be.
                      If auto-negotiation is present on this MAU, this
                      object will map to ifMauAutoNegCapability.

                      Note that this MAU may be capable of operating
                      as a MAU type that is beyond the scope of this
                      MIB.  This is indicated by returning the
                      bit value bOther in addition to any bit values
                      for capabilities that are listed above."
          ::= { ifMauEntry 13 }

      -- The ifJackTable applies to MAUs attached to interfaces
      -- which have one or more external jacks (connectors).

      ifJackTable OBJECT-TYPE
          SYNTAX      SEQUENCE OF IfJackEntry
          MAX-ACCESS  not-accessible
          STATUS      current
          DESCRIPTION "Information about the external jacks attached
                      to MAUs attached to an interface."
          ::= { dot3IfMauBasicGroup 2 }

      ifJackEntry OBJECT-TYPE
          SYNTAX      IfJackEntry
          MAX-ACCESS  not-accessible
          STATUS      current
          DESCRIPTION "An entry in the table, containing information
                      about a particular jack."
          INDEX       { ifMauIfIndex,
                        ifMauIndex,
                        ifJackIndex
                      }
          ::= { ifJackTable 1 }


      IfJackEntry ::=
          SEQUENCE {
              ifJackIndex                         Integer32,
              ifJackType                          JackType
          }

      ifJackIndex OBJECT-TYPE
          SYNTAX      Integer32 (1..2147483647)
          MAX-ACCESS  not-accessible
          STATUS      current
          DESCRIPTION "This variable uniquely identifies the jack
                      described by this entry from among other jacks
                      attached to the same MAU."
          ::= { ifJackEntry 1 }

      ifJackType OBJECT-TYPE
          SYNTAX      JackType
          MAX-ACCESS  read-only
          STATUS      current
          DESCRIPTION "The jack connector type, as it appears on the
                      outside of the system."
          ::= { ifJackEntry 2 }

      -- The ifMauAutoNegTable applies to systems in which
      -- auto-negotiation is supported on one or more MAUs
      -- attached to interfaces.  Note that if auto-negotiation
      -- is present and enabled, the ifMauType object reflects
      -- the result of the auto-negotiation function.

      ifMauAutoNegTable OBJECT-TYPE
          SYNTAX      SEQUENCE OF IfMauAutoNegEntry
          MAX-ACCESS  not-accessible
          STATUS      current
          DESCRIPTION "Configuration and status objects for the
                      auto-negotiation function of MAUs attached to
                      interfaces."
          ::= { dot3IfMauAutoNegGroup 1 }

      ifMauAutoNegEntry OBJECT-TYPE
          SYNTAX      IfMauAutoNegEntry
          MAX-ACCESS  not-accessible
          STATUS      current
          DESCRIPTION "An entry in the table, containing configuration
                      and status information for the auto-negotiation
                      function of a particular MAU."
          INDEX       { ifMauIfIndex,
                        ifMauIndex
                      }


          ::= { ifMauAutoNegTable 1 }

      IfMauAutoNegEntry ::=
          SEQUENCE {
              ifMauAutoNegAdminStatus             INTEGER,
              ifMauAutoNegRemoteSignaling         INTEGER,
              ifMauAutoNegConfig                  INTEGER,
              ifMauAutoNegCapability              Integer32,
              ifMauAutoNegCapAdvertised           Integer32,
              ifMauAutoNegCapReceived             Integer32,
              ifMauAutoNegRestart                 INTEGER,
              ifMauAutoNegCapabilityBits          BITS,
              ifMauAutoNegCapAdvertisedBits       BITS,
              ifMauAutoNegCapReceivedBits         BITS,
              ifMauAutoNegRemoteFaultAdvertised   INTEGER,
              ifMauAutoNegRemoteFaultReceived     INTEGER
          }

      ifMauAutoNegAdminStatus OBJECT-TYPE
          SYNTAX      INTEGER {
                          enabled(1),
                          disabled(2)
                      }
          MAX-ACCESS  read-write
          STATUS      current
          DESCRIPTION "Setting this object to enabled(1) will cause
                      the interface which has the auto-negotiation
                      signaling ability to be enabled.

                      If the value of this object is disabled(2) then
                      the interface will act as it would if it had no
                      auto-negotiation signaling.  Under these
                      conditions, an IEEE 802.3 MAU will immediately
                      be forced to the state indicated by the value of
                      the object ifMauDefaultType.

                      NOTE TO IMPLEMENTORS:  When
                      ifMauAutoNegAdminStatus transitions from enabled
                      to disabled, the agent implementation MUST
                      ensure that the operational type of the MAU (as
                      reported by ifMauType) correctly transitions to
                      the value specified by the ifMauDefaultType
                      object, rather than continuing to operate at the
                      value earlier determined by the auto-negotiation
                      function."
          REFERENCE   "[IEEE 802.3 Std], 30.6.1.1.2,
                      aAutoNegAdminState and 30.6.1.2.2,
                      acAutoNegAdminControl."


          ::= { ifMauAutoNegEntry 1 }

      ifMauAutoNegRemoteSignaling OBJECT-TYPE
          SYNTAX      INTEGER {
                          detected(1),
                          notdetected(2)
                      }
          MAX-ACCESS  read-only
          STATUS      current
          DESCRIPTION "A value indicating whether the remote end of
                      the link is using auto-negotiation signaling. It
                      takes the value detected(1) if and only if,
                      during the previous link negotiation, FLP Bursts
                      were received."
          REFERENCE   "[IEEE 802.3 Std], 30.6.1.1.3,
                      aAutoNegRemoteSignaling."
          ::= { ifMauAutoNegEntry 2 }

      ifMauAutoNegConfig OBJECT-TYPE
          SYNTAX      INTEGER {
                          other(1),
                          configuring(2),
                          complete(3),
                          disabled(4),
                          parallelDetectFail(5)
                      }
          MAX-ACCESS  read-only
          STATUS      current
          DESCRIPTION "A value indicating the current status of the
                      auto-negotiation process.  The enumeration
                      parallelDetectFail(5) maps to a failure in
                      parallel detection as defined in 28.2.3.1 of
                      [IEEE 802.3 Std]."
          REFERENCE   "[IEEE 802.3 Std], 30.6.1.1.4,
                      aAutoNegAutoConfig."
          ::= { ifMauAutoNegEntry 4 }

      ifMauAutoNegCapability OBJECT-TYPE
          SYNTAX      Integer32
          MAX-ACCESS  read-only
          STATUS      deprecated
          DESCRIPTION "********* THIS OBJECT IS DEPRECATED **********

                      A value that uniquely identifies the set of
                      capabilities of the local auto-negotiation
                      entity.  The value is a sum which initially
                      takes the value zero.  Then, for each capability
                      of this interface, 2 raised to the power noted


                      below is added to the sum. For example, an
                      interface which has the capability to support
                      only 100Base-TX half duplex would have a value
                      of 32768 (2**15).  In contrast, an interface
                      which supports both 100Base-TX half duplex and
                      and 100Base-TX full duplex would have a value of
                      98304 ((2**15) + (2**16)).

                      The powers of 2 assigned to the capabilities are
                      these:

                      Power   Capability
                        0       other or unknown
                       (1-9)    (reserved)
                       10       10BASE-T  half duplex mode
                       11       10BASE-T  full duplex mode
                       12       (reserved)
                       13       (reserved)
                       14       100BASE-T4
                       15       100BASE-TX half duplex mode
                       16       100BASE-TX full duplex mode
                       17       (reserved)
                       18       (reserved)
                       19      100BASE-T2 half duplex mode
                       20      100BASE-T2 full duplex mode

                      Note that interfaces that support this MIB may
                      have capabilities that extend beyond the scope
                      of this MIB.
                      This object has been deprecated in favour of
                      ifMauAutoNegCapabilityBits"
          REFERENCE   "[IEEE 802.3 Std], 30.6.1.1.5,
                      aAutoNegLocalTechnologyAbility."
          ::= { ifMauAutoNegEntry 5 }

      ifMauAutoNegCapAdvertised OBJECT-TYPE
          SYNTAX      Integer32
          MAX-ACCESS  read-write
          STATUS      deprecated
          DESCRIPTION "********* THIS OBJECT IS DEPRECATED **********

                      A value that uniquely identifies the set of
                      capabilities advertised by the local
                      auto-negotiation entity. Refer to
                      ifMauAutoNegCapability for a description of the
                      possible values of this object.

                      Capabilities in this object that are not


                      available in ifMauAutoNegCapability cannot be
                      enabled.

                      This object has been deprecated in favour of
                      ifMauAutoNegCapAdvertisedBits"
          REFERENCE   "[IEEE 802.3 Std], 30.6.1.1.6,
                      aAutoNegAdvertisedTechnologyAbility."
          ::= { ifMauAutoNegEntry 6 }

      ifMauAutoNegCapReceived OBJECT-TYPE
          SYNTAX      Integer32
          MAX-ACCESS  read-only
          STATUS      deprecated
          DESCRIPTION "********* THIS OBJECT IS DEPRECATED **********

                      A value that uniquely identifies the set of
                      capabilities received from the remote
                      auto-negotiation entity. Refer to
                      ifMauAutoNegCapability for a description of the
                      possible values of this object.

                      Note that interfaces that support this MIB may
                      be attached to remote auto-negotiation entities
                      which have capabilities beyond the scope of this
                      MIB.

                      This object has been deprecated in favour of
                      ifMauAutoNegCapReceivedBits"
          REFERENCE   "[IEEE 802.3 Std], 30.6.1.1.7,
                      aAutoNegReceivedTechnologyAbility."
          ::= { ifMauAutoNegEntry 7 }

      ifMauAutoNegRestart OBJECT-TYPE
          SYNTAX      INTEGER {
                          restart(1),
                          norestart(2)
                      }
          MAX-ACCESS  read-write
          STATUS      current
          DESCRIPTION "If the value of this object is set to
                      restart(1) then this will force auto-negotiation
                      to begin link renegotiation. If auto-negotiation
                      signaling is disabled, a write to this object
                      has no effect.

                      Setting the value of this object to norestart(2)
                      has no effect."
          REFERENCE   "[IEEE 802.3 Std], 30.6.1.2.1,


                      acAutoNegRestartAutoConfig."
          ::= { ifMauAutoNegEntry 8 }

      ifMauAutoNegCapabilityBits OBJECT-TYPE
          SYNTAX      BITS {
              bOther(0),        -- other or unknown
              b10baseT(1),      -- 10BASE-T  half duplex mode
              b10baseTFD(2),    -- 10BASE-T  full duplex mode
              b100baseT4(3),    -- 100BASE-T4
              b100baseTX(4),    -- 100BASE-TX half duplex mode
              b100baseTXFD(5),  -- 100BASE-TX full duplex mode
              b100baseT2(6),    -- 100BASE-T2 half duplex mode
              b100baseT2FD(7),  -- 100BASE-T2 full duplex mode
              bfdxPause(8),     -- PAUSE for full-duplex links
              bfdxAPause(9),    -- Asymmetric PAUSE for full-duplex
                                --     links
              bfdxSPause(10),   -- Symmetric PAUSE for full-duplex
                                --     links
              bfdxBPause(11),   -- Asymmetric and Symmetric PAUSE for
                                --     full-duplex links
              b1000baseX(12),   -- 1000BASE-X, -LX, -SX, -CX half
                                --     duplex mode
              b1000baseXFD(13), -- 1000BASE-X, -LX, -SX, -CX full
                                --     duplex mode
              b1000baseT(14),   -- 1000BASE-T half duplex mode
              b1000baseTFD(15)  -- 1000BASE-T full duplex mode
          }
          MAX-ACCESS  read-only
          STATUS      current
          DESCRIPTION "A value that uniquely identifies the set of
                      capabilities of the local auto-negotiation
                      entity.  Note that interfaces that support this
                      MIB may have capabilities that extend beyond the
                      scope of this MIB.

                      Note that the local auto-negotiation entity may
                      support some capabilities beyond the scope of
                      this MIB.  This is indicated by returning the
                      bit value bOther in addition to any bit values
                      for capabilities that are listed above."
          REFERENCE   "[IEEE 802.3 Std], 30.6.1.1.5,
                      aAutoNegLocalTechnologyAbility."
          ::= { ifMauAutoNegEntry 9 }

      ifMauAutoNegCapAdvertisedBits OBJECT-TYPE
          SYNTAX      BITS {
              bOther(0),        -- other or unknown
              b10baseT(1),      -- 10BASE-T  half duplex mode


              b10baseTFD(2),    -- 10BASE-T  full duplex mode
              b100baseT4(3),    -- 100BASE-T4
              b100baseTX(4),    -- 100BASE-TX half duplex mode
              b100baseTXFD(5),  -- 100BASE-TX full duplex mode
              b100baseT2(6),    -- 100BASE-T2 half duplex mode
              b100baseT2FD(7),  -- 100BASE-T2 full duplex mode
              bFdxPause(8),     -- PAUSE for full-duplex links
              bFdxAPause(9),    -- Asymmetric PAUSE for full-duplex
                                --     links
              bFdxSPause(10),   -- Symmetric PAUSE for full-duplex
                                --     links
              bFdxBPause(11),   -- Asymmetric and Symmetric PAUSE for
                                --     full-duplex links
              b1000baseX(12),   -- 1000BASE-X, -LX, -SX, -CX half
                                --     duplex mode
              b1000baseXFD(13), -- 1000BASE-X, -LX, -SX, -CX full
                                --     duplex mode
              b1000baseT(14),   -- 1000BASE-T half duplex mode
              b1000baseTFD(15)  -- 1000BASE-T full duplex mode
          }
          MAX-ACCESS  read-write
          STATUS      current
          DESCRIPTION "A value that uniquely identifies the set of
                      capabilities advertised by the local
                      auto-negotiation entity.

                      Capabilities in this object that are not
                      available in ifMauAutoNegCapabilityBits cannot
                      be enabled.
                      Note that the local auto-negotiation entity may
                      advertise some capabilities beyond the scope of
                      this MIB.  This is indicated by returning the
                      bit value bOther in addition to any bit values
                      for capabilities that are listed above."
          REFERENCE   "[IEEE 802.3 Std], 30.6.1.1.6,
                      aAutoNegAdvertisedTechnologyAbility."
          ::= { ifMauAutoNegEntry 10 }

      ifMauAutoNegCapReceivedBits OBJECT-TYPE
          SYNTAX      BITS {
               bOther(0),        -- other or unknown
               b10baseT(1),      -- 10BASE-T  half duplex mode
               b10baseTFD(2),    -- 10BASE-T  full duplex mode
               b100baseT4(3),    -- 100BASE-T4
               b100baseTX(4),    -- 100BASE-TX half duplex mode
               b100baseTXFD(5),  -- 100BASE-TX full duplex mode
               b100baseT2(6),    -- 100BASE-T2 half duplex mode
               b100baseT2FD(7),  -- 100BASE-T2 full duplex mode


               bFdxPause(8),     -- PAUSE for full-duplex links
               bFdxAPause(9),    -- Asymmetric PAUSE for full-duplex
                                 --     links
               bFdxSPause(10),   -- Symmetric PAUSE for full-duplex
                                 --     links
               bFdxBPause(11),   -- Asymmetric and Symmetric PAUSE for
                                 --     full-duplex links
               b1000baseX(12),   -- 1000BASE-X, -LX, -SX, -CX half
                                 --     duplex mode
               b1000baseXFD(13), -- 1000BASE-X, -LX, -SX, -CX full
                                 --     duplex mode
               b1000baseT(14),   -- 1000BASE-T half duplex mode
               b1000baseTFD(15)  -- 1000BASE-T full duplex mode
          }
          MAX-ACCESS  read-only
          STATUS      current
          DESCRIPTION "A value that uniquely identifies the set of
                      capabilities received from the remote
                      auto-negotiation entity.

                      Note that interfaces that support this MIB may
                      be attached to remote auto-negotiation entities
                      which have capabilities beyond the scope of this
                      MIB.  This is indicated by returning the bit
                      value bOther in addition to any bit values for
                      capabilities that are listed above."
          REFERENCE   "[IEEE 802.3 Std], 30.6.1.1.7,
                      aAutoNegReceivedTechnologyAbility."
          ::= { ifMauAutoNegEntry 11 }
      ifMauAutoNegRemoteFaultAdvertised OBJECT-TYPE
          SYNTAX      INTEGER {
                          noError(1),
                          offline(2),
                          linkFailure(3),
                          autoNegError(4)
                      }
          MAX-ACCESS  read-write
          STATUS      current
          DESCRIPTION "A value that identifies any local fault
                      indications that this MAU has detected and will
                      advertise at the next auto-negotiation
                      interaction for 1000Mbps MAUs."
          REFERENCE   "[IEEE 802.3 Std], 30.6.1.1.6,
                      aAutoNegAdvertisedTechnologyAbility."
          ::= { ifMauAutoNegEntry 12 }

      ifMauAutoNegRemoteFaultReceived OBJECT-TYPE
          SYNTAX      INTEGER {


                          noError(1),
                          offline(2),
                          linkFailure(3),
                          autoNegError(4)
                      }
          MAX-ACCESS  read-only
          STATUS      current
          DESCRIPTION "A value that identifies any fault indications
                      received from the far end of a link by the
                      local auto-negotiation entity for 1000Mbps
                      MAUs."
          REFERENCE   "[IEEE 802.3 Std], 30.6.1.1.7,
                      aAutoNegReceivedTechnologyAbility."
          ::= { ifMauAutoNegEntry 13 }

      --
      -- The Basic Broadband MAU Table
      --

      broadMauBasicTable OBJECT-TYPE
          SYNTAX      SEQUENCE OF BroadMauBasicEntry
          MAX-ACCESS  not-accessible
          STATUS      deprecated
          DESCRIPTION "********* THIS OBJECT IS DEPRECATED **********

                      Table of descriptive and status information
                      about the broadband MAUs connected to
                      interfaces."
          ::= { dot3BroadMauBasicGroup 1 }

      broadMauBasicEntry OBJECT-TYPE
          SYNTAX      BroadMauBasicEntry
          MAX-ACCESS  not-accessible
          STATUS      deprecated
          DESCRIPTION "********* THIS OBJECT IS DEPRECATED **********

                      An entry in the table, containing information
                      about a single broadband MAU."
          INDEX       { broadMauIfIndex,
                        broadMauIndex
                      }
          ::= { broadMauBasicTable 1 }

      BroadMauBasicEntry ::=
          SEQUENCE {
              broadMauIfIndex                     Integer32,
              broadMauIndex                       Integer32,
              broadMauXmtRcvSplitType             INTEGER,


              broadMauXmtCarrierFreq              Integer32,
              broadMauTranslationFreq             Integer32
          }

      broadMauIfIndex OBJECT-TYPE
          SYNTAX      Integer32 (1..2147483647)
          MAX-ACCESS  read-only
          STATUS      deprecated
          DESCRIPTION "********* THIS OBJECT IS DEPRECATED **********

                      This variable uniquely identifies the interface
                      to which the MAU described by this entry is
                      connected."
          REFERENCE   "Reference RFC 1213, ifIndex."
          ::= { broadMauBasicEntry 1 }

      broadMauIndex OBJECT-TYPE
          SYNTAX      Integer32 (1..2147483647)
          MAX-ACCESS  read-only
          STATUS      deprecated
          DESCRIPTION "********* THIS OBJECT IS DEPRECATED **********

                      This variable uniquely identifies the MAU
                      connected to interface broadMauIfIndex that is
                      described by this entry."
          REFERENCE   "[IEEE 802.3 Std], 30.5.1.1.1, aMAUID."
          ::= { broadMauBasicEntry 2 }

      broadMauXmtRcvSplitType OBJECT-TYPE
          SYNTAX      INTEGER {
                          other(1),
                          single(2),
                          dual(3)
                      }
          MAX-ACCESS  read-only
          STATUS      deprecated
          DESCRIPTION "********* THIS OBJECT IS DEPRECATED **********

                      This object indicates the type of frequency
                      multiplexing/cabling system used to separate the
                      transmit and receive paths for the 10BROAD36
                      MAU.

                      The value other(1) is returned if the split type
                      is not either single or dual.

                      The value single(2) indicates a single cable
                      system.  The value dual(3) indicates a dual


                      cable system, offset normally zero."
          REFERENCE   "[IEEE 802.3 Std], 30.5.1.1.8,
                      aBbMAUXmitRcvSplitType."
          ::= { broadMauBasicEntry 3 }

      broadMauXmtCarrierFreq OBJECT-TYPE
          SYNTAX      Integer32
          MAX-ACCESS  read-only
          STATUS      deprecated
          DESCRIPTION "********* THIS OBJECT IS DEPRECATED **********

                      This variable indicates the transmit carrier
                      frequency of the 10BROAD36 MAU in MHz/4; that
                      is, in units of 250 kHz."
          REFERENCE   "[IEEE 802.3 Std], 30.5.1.1.9,
                      aBroadbandFrequencies.xmitCarrierFrequency."
          ::= { broadMauBasicEntry 4 }

      broadMauTranslationFreq OBJECT-TYPE
          SYNTAX      Integer32
          MAX-ACCESS  read-only
          STATUS      deprecated
          DESCRIPTION "********* THIS OBJECT IS DEPRECATED **********

                      This variable indicates the translation offset
                      frequency of the 10BROAD36 MAU in MHz/4; that
                      is, in units of 250 kHz."
          REFERENCE   "[IEEE 802.3 Std], 30.5.1.1.9,
                      aBroadbandFrequencies.translationFrequency."
          ::= { broadMauBasicEntry 5 }

      -- Notifications for use by 802.3 MAUs

      snmpDot3MauTraps OBJECT IDENTIFIER ::= { snmpDot3MauMgt 0 }

      rpMauJabberTrap NOTIFICATION-TYPE
          OBJECTS     { rpMauJabberState }
          STATUS      current
          DESCRIPTION "This trap is sent whenever a managed repeater
                      MAU enters the jabber state.

                      The agent MUST throttle the generation of
                      consecutive rpMauJabberTraps so that there is at
                      least a five-second gap between them."
          REFERENCE   "[IEEE 802.3 Mgt], 30.5.1.3.1, nJabber
                      notification."
          ::= { snmpDot3MauTraps 1 }


      ifMauJabberTrap NOTIFICATION-TYPE
          OBJECTS     { ifMauJabberState }
          STATUS      current
          DESCRIPTION "This trap is sent whenever a managed interface
                      MAU enters the jabber state.

                      The agent MUST throttle the generation of
                      consecutive ifMauJabberTraps so that there is at
                      least a five-second gap between them."
          REFERENCE   "[IEEE 802.3 Mgt], 30.5.1.3.1, nJabber
                      notification."
          ::= { snmpDot3MauTraps 2 }

      -- Conformance information

      mauModConf
              OBJECT IDENTIFIER ::= { mauMod 1 }
        mauModCompls
              OBJECT IDENTIFIER ::= { mauModConf 1 }
        mauModObjGrps
              OBJECT IDENTIFIER ::= { mauModConf 2 }
        mauModNotGrps
              OBJECT IDENTIFIER ::= { mauModConf 3 }
      -- Object groups

      mauRpGrpBasic OBJECT-GROUP
          OBJECTS     { rpMauGroupIndex,
                        rpMauPortIndex,
                        rpMauIndex,
                        rpMauType,
                        rpMauStatus,
                        rpMauMediaAvailable,
                        rpMauMediaAvailableStateExits,
                        rpMauJabberState,
                        rpMauJabberingStateEnters
                      }
          STATUS      current
          DESCRIPTION "Basic conformance group for MAUs attached to
                      repeater ports.  This group is also the
                      conformance specification for RFC 1515
                      implementations."
          ::= { mauModObjGrps 1 }

      mauRpGrp100Mbs OBJECT-GROUP
          OBJECTS     { rpMauFalseCarriers }
          STATUS      current
          DESCRIPTION "Conformance group for MAUs attached to
                      repeater ports with 100 Mb/s or greater


                      capability."
          ::= { mauModObjGrps 2 }

      mauRpGrpJack OBJECT-GROUP
          OBJECTS     { rpJackType }
          STATUS      current
          DESCRIPTION "Conformance group for MAUs attached to
                      repeater ports with managed jacks."
          ::= { mauModObjGrps 3 }

      mauIfGrpBasic OBJECT-GROUP
          OBJECTS     { ifMauIfIndex,
                        ifMauIndex,
                        ifMauType,
                        ifMauStatus,
                        ifMauMediaAvailable,
                        ifMauMediaAvailableStateExits,
                        ifMauJabberState,
                        ifMauJabberingStateEnters
                      }
          STATUS      current
          DESCRIPTION "Basic conformance group for MAUs attached to
                      interfaces.  This group also provides a
                      conformance specification for RFC 1515
                      implementations."
          ::= { mauModObjGrps 4 }

      mauIfGrp100Mbs OBJECT-GROUP
          OBJECTS     { ifMauFalseCarriers,
                        ifMauTypeList,
                        ifMauDefaultType,
                        ifMauAutoNegSupported
                      }
          STATUS      deprecated
          DESCRIPTION "********* THIS GROUP IS DEPRECATED **********

                      Conformance group for MAUs attached to
                      interfaces with 100 Mb/s capability.

                      This object group has been deprecated in favor
                      of mauIfGrpHighCapacity."
          ::= { mauModObjGrps 5 }

      mauIfGrpJack OBJECT-GROUP
          OBJECTS     { ifJackType }
          STATUS      current
          DESCRIPTION "Conformance group for MAUs attached to
                      interfaces with managed jacks."


          ::= { mauModObjGrps 6 }

      mauIfGrpAutoNeg OBJECT-GROUP
          OBJECTS     { ifMauAutoNegAdminStatus,
                        ifMauAutoNegRemoteSignaling,
                        ifMauAutoNegConfig,
                        ifMauAutoNegCapability,
                        ifMauAutoNegCapAdvertised,
                        ifMauAutoNegCapReceived,
                        ifMauAutoNegRestart
                      }
          STATUS      deprecated
          DESCRIPTION "********* THIS GROUP IS DEPRECATED **********

                      Conformance group for MAUs attached to
                      interfaces with managed auto-negotiation.

                      This object group has been deprecated in favor
                      of mauIfGrpAutoNeg2."
          ::= { mauModObjGrps 7 }

      mauBroadBasic OBJECT-GROUP
          OBJECTS     { broadMauIfIndex,
                        broadMauIndex,
                        broadMauXmtRcvSplitType,
                        broadMauXmtCarrierFreq,
                        broadMauTranslationFreq
                      }
          STATUS      deprecated
          DESCRIPTION "********* THIS GROUP IS DEPRECATED **********

                      Conformance group for broadband MAUs attached
                      to interfaces.

                      This object group is deprecated.  There have
                      been no reported implementations of this group,
                      and it was felt to be unlikely that there will
                      be any future implementations."
          ::= { mauModObjGrps 8 }

      mauIfGrpHighCapacity OBJECT-GROUP
          OBJECTS     { ifMauFalseCarriers,
                        ifMauTypeListBits,
                        ifMauDefaultType,
                        ifMauAutoNegSupported
                      }
          STATUS      current
          DESCRIPTION "Conformance group for MAUs attached to


                      interfaces with 100 Mb/s or greater capability."
          ::= { mauModObjGrps 9 }

      mauIfGrpAutoNeg2 OBJECT-GROUP
          OBJECTS     { ifMauAutoNegAdminStatus,
                        ifMauAutoNegRemoteSignaling,
                        ifMauAutoNegConfig,
                        ifMauAutoNegCapabilityBits,
                        ifMauAutoNegCapAdvertisedBits,
                        ifMauAutoNegCapReceivedBits,
                        ifMauAutoNegRestart
                      }
          STATUS      current
          DESCRIPTION "Conformance group for MAUs attached to
                      interfaces with managed auto-negotiation."
          ::= { mauModObjGrps 10 }

      mauIfGrpAutoNeg1000Mbps OBJECT-GROUP
          OBJECTS     { ifMauAutoNegRemoteFaultAdvertised,
                        ifMauAutoNegRemoteFaultReceived
                      }
          STATUS      current
          DESCRIPTION "Conformance group for 1000Mbps MAUs attached to
                      interfaces with managed auto-negotiation."
          ::= { mauModObjGrps 11 }

      -- Notification groups

      rpMauNotifications NOTIFICATION-GROUP
          NOTIFICATIONS { rpMauJabberTrap }
          STATUS      current
          DESCRIPTION "Notifications for repeater MAUs."
          ::= { mauModNotGrps 1 }

      ifMauNotifications NOTIFICATION-GROUP
          NOTIFICATIONS { ifMauJabberTrap }
          STATUS      current
          DESCRIPTION "Notifications for interface MAUs."
          ::= { mauModNotGrps 2 }

      -- Compliances

      mauModRpCompl MODULE-COMPLIANCE
          STATUS      deprecated
          DESCRIPTION "******** THIS COMPLIANCE IS DEPRECATED ********

                      Compliance for MAUs attached to repeater
                      ports.


                      This compliance is deprecated and replaced by
                      mauModRpCompl2, which corrects an oversight by
                      allowing rpMauStatus to be implemented
                      read-only."

          MODULE -- this module
              MANDATORY-GROUPS { mauRpGrpBasic }

              GROUP       mauRpGrp100Mbs
              DESCRIPTION "Implementation of this optional group is
                          recommended for MAUs which have 100Mb/s or
                          greater capability."

              GROUP       mauRpGrpJack
              DESCRIPTION "Implementation of this optional group is
                          recommended for MAUs which have one or more
                          external jacks."

              GROUP       rpMauNotifications
              DESCRIPTION "Implementation of this group is recommended
                          for MAUs attached to repeater ports."
          ::= { mauModCompls 1 }

      mauModIfCompl MODULE-COMPLIANCE
          STATUS      deprecated
          DESCRIPTION "******** THIS COMPLIANCE IS DEPRECATED ********

                      Compliance for MAUs attached to interfaces.

                      This compliance is deprecated and replaced by
                      mauModIfCompl2."

          MODULE -- this module
              MANDATORY-GROUPS { mauIfGrpBasic }

              GROUP       mauIfGrp100Mbs
              DESCRIPTION "Implementation of this optional group is
                          recommended for MAUs which have 100Mb/s
                          capability."

              GROUP       mauIfGrpJack
              DESCRIPTION "Implementation of this optional group is
                          recommended for MAUs which have one or more
                          external jacks."

              GROUP       mauIfGrpAutoNeg
              DESCRIPTION "Implementation of this group is mandatory
                          for MAUs which support managed


                          auto-negotiation."

              GROUP       mauBroadBasic
              DESCRIPTION "Implementation of this group is mandatory
                          for broadband MAUs."

              GROUP       ifMauNotifications
              DESCRIPTION "Implementation of this group is recommended
                          for MAUs attached to interfaces."
          ::= { mauModCompls 2 }

      mauModIfCompl2 MODULE-COMPLIANCE
          STATUS      current
          DESCRIPTION "Compliance for MAUs attached to interfaces."

          MODULE -- this module
              MANDATORY-GROUPS { mauIfGrpBasic }

              GROUP       mauIfGrpHighCapacity
              DESCRIPTION "Implementation of this optional group is
                          recommended for MAUs which have 100Mb/s
                          or greater capability."

              GROUP       mauIfGrpJack
              DESCRIPTION "Implementation of this optional group is
                          recommended for MAUs which have one or more
                          external jacks."

              GROUP       mauIfGrpAutoNeg2
              DESCRIPTION "Implementation of this group is mandatory
                          for MAUs which support managed
                          auto-negotiation."

              GROUP       mauIfGrpAutoNeg1000Mbps
              DESCRIPTION "Implementation of this group is mandatory
                          for MAUs which have 1000Mb/s or greater
                          capability and support managed
                          auto-negotiation."

              GROUP       ifMauNotifications
              DESCRIPTION "Implementation of this group is recommended
                          for MAUs attached to interfaces."

              OBJECT      ifMauStatus
              MIN-ACCESS  read-only
              DESCRIPTION "Write access is not required."
          ::= { mauModCompls 3 }


      mauModRpCompl2 MODULE-COMPLIANCE
          STATUS      current
          DESCRIPTION "Compliance for MAUs attached to repeater
                      ports."

          MODULE -- this module
              MANDATORY-GROUPS { mauRpGrpBasic }

              GROUP       mauRpGrp100Mbs
              DESCRIPTION "Implementation of this optional group is
                          recommended for MAUs which have 100Mb/s or
                          greater capability."

              GROUP       mauRpGrpJack
              DESCRIPTION "Implementation of this optional group is
                          recommended for MAUs which have one or more
                          external jacks."

              GROUP       rpMauNotifications
              DESCRIPTION "Implementation of this group is recommended
                          for MAUs attached to repeater ports."

              OBJECT      rpMauStatus
              MIN-ACCESS  read-only
              DESCRIPTION "Write access is not required."
          ::= { mauModCompls 4 }

END

PerfHist-TC-MIB DEFINITIONS ::= BEGIN

     IMPORTS
        MODULE-IDENTITY,
        Gauge32, mib-2
            FROM SNMPv2-SMI
        TEXTUAL-CONVENTION
            FROM SNMPv2-TC;

     perfHistTCMIB MODULE-IDENTITY


          LAST-UPDATED "9811071100Z"
          ORGANIZATION "IETF AToMMIB and TrunkMIB WGs"
          CONTACT-INFO
                       "Kaj Tesink
              Postal:  Bellcore
                       331 Newman Springs Road
                       Red Bank, NJ 07701
                       USA
              Tel:     +1 732 758 5254
              Fax:     +1 732 758 2269
              E-mail:  kaj@bellcore.com"
          DESCRIPTION
           "This MIB Module provides Textual Conventions
             to be used by systems supporting 15 minute
             based performance history counts."
          ::= { mib-2 58 }

     -- The Textual Conventions defined below are organized
     -- alphabetically

     -- Use of these TCs assumes the following:
     -- 0  The agent supports 15 minute based history
     --    counters.
     -- 0  The agent is capable of keeping a history of n
     --    intervals of 15 minute performance data. The
     --    value of n is defined by the specific MIB
     --    module but shall be 0 < n =< 96.
     -- 0  The agent may optionally support performance
     --    data aggregating the history intervals.
     -- 0  The agent will keep separate tables for the
     --    current interval, the history intervals, and
     --    the total aggregates.
     -- 0  The agent will keep the following objects.
     --    If performance data is kept for multiple instances
     --    of a measured entity, then
     --    these objects are applied to each instance of
     --    the measured entity (e.g., interfaces).
     --

     -- xyzTimeElapsed OBJECT-TYPE
     --       SYNTAX  INTEGER (0..899)
     --       MAX-ACCESS  read-only
     --       STATUS  current
     --       DESCRIPTION


     --       "The number of seconds that have elapsed since
     --       the beginning of the current measurement period.
     --       If, for some reason, such as an adjustment in the
     --       system's time-of-day clock, the current interval
     --       exceeds the maximum value, the agent will return
     --       the maximum value."
     --       ::= { xxx }

     -- xyzValidIntervals OBJECT-TYPE
     --       SYNTAX  INTEGER (0..<n>)
     --       MAX-ACCESS  read-only
     --       STATUS  current
     --       DESCRIPTION
     --       "The number of previous near end intervals
     --       for which data was collected.
     --          [ The overall constraint on <n> is 1 =< n =< 96; ]
     --          [ Define any additional constraints on <n> here. ]
     --       The value will be <n> unless the measurement was
     --       (re-)started within the last (<n>*15) minutes, in which
     --       case the value will be the number of complete 15
     --       minute intervals for which the agent has at least
     --       some data. In certain cases (e.g., in the case
     --       where the agent is a proxy) it is possible that some
     --       intervals are unavailable.  In this case, this
     --       interval is the maximum interval number for
     --       which data is available."
     --       ::= { xxx }

     -- xyzInvalidIntervals OBJECT-TYPE
     --     SYNTAX  INTEGER (0..<n>)
     --     MAX-ACCESS  read-only
     --     STATUS  current
     --     DESCRIPTION
     --       "The number of intervals in the range from
     --        0 to xyzValidIntervals for which no
     --        data is available. This object will typically
     --        be zero except in cases where the data for some
     --        intervals are not available (e.g., in proxy
     --        situations)."
     --       ::= { xxx }

     PerfCurrentCount ::= TEXTUAL-CONVENTION
           STATUS  current
           DESCRIPTION
              "A counter associated with a
               performance measurement in a current 15
               minute measurement interval. The value
               of this counter starts from zero and is


               increased when associated events occur,
               until the end of the 15 minute interval.
               At that time the value of the counter is
               stored in the first 15 minute history
               interval, and the CurrentCount is
               restarted at zero. In the
               case where the agent has no valid data
               available for the current interval the
               corresponding object instance is not
               available and upon a retrieval request
               a corresponding error message shall be
               returned to indicate that this instance
               does not exist (for example, a noSuchName
               error for SNMPv1 and a noSuchInstance for
               SNMPv2 GET operation)."
            SYNTAX  Gauge32

     PerfIntervalCount ::= TEXTUAL-CONVENTION
           STATUS  current
           DESCRIPTION
              "A counter associated with a
               performance measurement in a previous
               15 minute measurement interval. In the
               case where the agent has no valid data
               available for a particular interval the
               corresponding object instance is not
               available and upon a retrieval request
               a corresponding error message shall be
               returned to indicate that this instance
               does not exist (for example, a noSuchName
               error for SNMPv1 and a noSuchInstance for
               SNMPv2 GET operation).
               In a system supporting
               a history of n intervals with
               IntervalCount(1) and IntervalCount(n) the
               most and least recent intervals
               respectively, the following applies at
               the end of a 15 minute interval:
               - discard the value of IntervalCount(n)
               - the value of IntervalCount(i) becomes that
                 of IntervalCount(i-1) for n >= i > 1
               - the value of IntervalCount(1) becomes that
                 of CurrentCount
               - the TotalCount, if supported, is adjusted."
            SYNTAX  Gauge32

     PerfTotalCount ::= TEXTUAL-CONVENTION
           STATUS  current


           DESCRIPTION
              "A counter associated with a
               performance measurements aggregating the
               previous valid 15 minute measurement
               intervals. (Intervals for which no valid
               data was available are not counted)"
            SYNTAX  Gauge32

END

ADSL-TC-MIB DEFINITIONS ::= BEGIN

IMPORTS
    transmission,
    MODULE-IDENTITY, Gauge32            FROM SNMPv2-SMI
    TEXTUAL-CONVENTION                  FROM SNMPv2-TC;

adsltcmib MODULE-IDENTITY

LAST-UPDATED "9908190000Z"

ORGANIZATION "IETF ADSL MIB Working Group"

CONTACT-INFO
    "
    Gregory Bathrick
    AG Communication Systems
    A Subsidiary of Lucent Technologies
    2500 W Utopia Rd.
    Phoenix, AZ 85027 USA
    Tel: +1 602-582-7679
    Fax: +1 602-582-7697
    E-mail: bathricg@agcs.com

    Faye Ly
    Copper Mountain Networks
    Norcal Office
    2470 Embarcadero Way
    Palo Alto, CA 94303
    Tel: +1 650-858-8500
    Fax: +1 650-858-8085
    E-Mail: faye@coppermountain.com

    IETF ADSL MIB Working Group (adsl@xlist.agcs.com)
    "
    DESCRIPTION
        "The MIB module which provides a ADSL
        Line Coding Textual Convention to be used
        by ADSL Lines."

    --  Revision history
    REVISION     "9908190000Z"  -- 19 August 1999, midnight
    DESCRIPTION  "Initial Version, published as RFC 2662"

    ::= { transmission 94 2 } -- adslMIB 2

    AdslLineCodingType ::= TEXTUAL-CONVENTION
        STATUS       current
        DESCRIPTION
            "This data type is used as the syntax for the ADSL
            Line Code."
        SYNTAX  INTEGER {
            other(1),-- none of the following
            dmt (2), -- Discrete MultiTone
            cap (3), -- Carrierless Amplitude & Phase modulation
            qam (4)  -- Quadrature Amplitude Modulation
        }

    AdslPerfCurrDayCount ::= TEXTUAL-CONVENTION
        STATUS  current
        DESCRIPTION
            "A counter associated with interface performance
            measurements in a current 1-day (24 hour) measurement
            interval.

            The value of this counter starts at zero at the
            beginning of an interval and is increased when
            associated events occur, until the end of the
            1-day interval.  At that time the value of the
            counter is stored in the previous 1-day history
            interval, if available, and the current interval
            counter is restarted at zero.

            In the case where the agent has no valid data available
            for this interval the corresponding object
            instance is not available and upon a retrieval
            request a corresponding error message shall be
            returned to indicate that this instance does
            not exist (for example, a noSuchName error for
            SNMPv1 and a noSuchInstance for SNMPv2 GET
            operation)."

         SYNTAX  Gauge32

    AdslPerfPrevDayCount ::= TEXTUAL-CONVENTION
        STATUS  current
        DESCRIPTION
            "A counter associated with interface performance
            measurements during the most previous 1-day (24 hour)
            measurement interval.  The value of this counter is
            equal to the value of the current day counter at
            the end of its most recent interval.

            In the case where the agent has no valid data available
            for this interval the corresponding object
            instance is not available and upon a retrieval
            request a corresponding error message shall be
            returned to indicate that this instance does
            not exist (for example, a noSuchName error for
            SNMPv1 and a noSuchInstance for SNMPv2 GET
            operation)."
        SYNTAX  Gauge32

    AdslPerfTimeElapsed ::= TEXTUAL-CONVENTION
        STATUS current
        DESCRIPTION
            "The number of seconds that have elapsed since
            the beginning of the current measurement period.
            If, for some reason, such as an adjustment in the
            system's time-of-day clock, the current interval
            exceeds the maximum value, the agent will return
            the maximum value."
        SYNTAX  Gauge32

END


ADSL-TC-MIB DEFINITIONS ::= BEGIN

IMPORTS
    transmission,
    MODULE-IDENTITY, Gauge32            FROM SNMPv2-SMI
    TEXTUAL-CONVENTION                  FROM SNMPv2-TC;

adsltcmib MODULE-IDENTITY

LAST-UPDATED "9908190000Z"

ORGANIZATION "IETF ADSL MIB Working Group"

CONTACT-INFO
    "
    Gregory Bathrick
    AG Communication Systems
    A Subsidiary of Lucent Technologies
    2500 W Utopia Rd.
    Phoenix, AZ 85027 USA
    Tel: +1 602-582-7679
    Fax: +1 602-582-7697
    E-mail: bathricg@agcs.com

    Faye Ly
    Copper Mountain Networks
    Norcal Office
    2470 Embarcadero Way
    Palo Alto, CA 94303
    Tel: +1 650-858-8500
    Fax: +1 650-858-8085
    E-Mail: faye@coppermountain.com

    IETF ADSL MIB Working Group (adsl@xlist.agcs.com)
    "
    DESCRIPTION
        "The MIB module which provides a ADSL
        Line Coding Textual Convention to be used
        by ADSL Lines."

    --  Revision history
    REVISION     "9908190000Z"  -- 19 August 1999, midnight
    DESCRIPTION  "Initial Version, published as RFC 2662"

    ::= { transmission 94 2 } -- adslMIB 2

    AdslLineCodingType ::= TEXTUAL-CONVENTION
        STATUS       current
        DESCRIPTION
            "This data type is used as the syntax for the ADSL
            Line Code."
        SYNTAX  INTEGER {
            other(1),-- none of the following
            dmt (2), -- Discrete MultiTone
            cap (3), -- Carrierless Amplitude & Phase modulation
            qam (4)  -- Quadrature Amplitude Modulation
        }

    AdslPerfCurrDayCount ::= TEXTUAL-CONVENTION
        STATUS  current
        DESCRIPTION
            "A counter associated with interface performance
            measurements in a current 1-day (24 hour) measurement
            interval.

            The value of this counter starts at zero at the
            beginning of an interval and is increased when
            associated events occur, until the end of the
            1-day interval.  At that time the value of the
            counter is stored in the previous 1-day history
            interval, if available, and the current interval
            counter is restarted at zero.

            In the case where the agent has no valid data available
            for this interval the corresponding object
            instance is not available and upon a retrieval
            request a corresponding error message shall be
            returned to indicate that this instance does
            not exist (for example, a noSuchName error for
            SNMPv1 and a noSuchInstance for SNMPv2 GET
            operation)."

         SYNTAX  Gauge32

    AdslPerfPrevDayCount ::= TEXTUAL-CONVENTION
        STATUS  current
        DESCRIPTION
            "A counter associated with interface performance
            measurements during the most previous 1-day (24 hour)
            measurement interval.  The value of this counter is
            equal to the value of the current day counter at
            the end of its most recent interval.

            In the case where the agent has no valid data available
            for this interval the corresponding object
            instance is not available and upon a retrieval
            request a corresponding error message shall be
            returned to indicate that this instance does
            not exist (for example, a noSuchName error for
            SNMPv1 and a noSuchInstance for SNMPv2 GET
            operation)."
        SYNTAX  Gauge32

    AdslPerfTimeElapsed ::= TEXTUAL-CONVENTION
        STATUS current
        DESCRIPTION
            "The number of seconds that have elapsed since
            the beginning of the current measurement period.
            If, for some reason, such as an adjustment in the
            system's time-of-day clock, the current interval
            exceeds the maximum value, the agent will return
            the maximum value."
        SYNTAX  Gauge32

END

ADSL-LINE-MIB DEFINITIONS ::= BEGIN

IMPORTS
    MODULE-IDENTITY, OBJECT-TYPE,
    Counter32, Gauge32,
    NOTIFICATION-TYPE,
    transmission, Unsigned32          FROM SNMPv2-SMI
    RowStatus,
    TruthValue, VariablePointer       FROM SNMPv2-TC
    MODULE-COMPLIANCE, OBJECT-GROUP,
    NOTIFICATION-GROUP                FROM SNMPv2-CONF
    ifIndex                           FROM IF-MIB
    PerfCurrentCount,
    PerfIntervalCount                 FROM PerfHist-TC-MIB

    SnmpAdminString                   FROM SNMP-FRAMEWORK-MIB
    AdslPerfCurrDayCount,
    AdslPerfPrevDayCount,
    AdslPerfTimeElapsed,
    AdslLineCodingType                FROM ADSL-TC-MIB
    ;

adslMIB MODULE-IDENTITY

LAST-UPDATED "9908190000Z"

ORGANIZATION "IETF ADSL MIB Working Group"

CONTACT-INFO
    "
    Gregory Bathrick
    AG Communication Systems
    A Subsidiary of Lucent Technologies
    2500 W Utopia Rd.
    Phoenix, AZ 85027 USA
    Tel: +1 602-582-7679
    Fax: +1 602-582-7697
    E-mail: bathricg@agcs.com

    Faye Ly
    Copper Mountain Networks
    Norcal Office
    2470 Embarcadero Way
    Palo Alto, CA 94303
    Tel: +1 650-858-8500
    Fax: +1 650-858-8085
    E-Mail: faye@coppermountain.com

    (ADSL Forum input only)
    John Burgess
    Predictive Systems, Inc.
    25A Vreeland Rd.
    Florham Park, NJ 07932 USA
    Tel: +1 973-301-5610
    Fax: +1 973-301-5699
    E-mail: jtburgess@predictive.com

    IETF ADSL MIB Working Group (adsl@xlist.agcs.com)
    "

DESCRIPTION
    "The MIB module defining objects for the management of a pair of
    ADSL modems at each end of the ADSL line.  Each such line has

    an entry in an ifTable which may include multiple modem lines.
    An agent may reside at either end of the ADSL line however the
    MIB is designed to require no management communication between
    them beyond that inherent in the low-level ADSL line protocol.
    The agent may monitor and control this protocol for its needs.

    ADSL lines may support optional Fast or Interleaved channels.
    If these are supported, additional entries corresponding to the
    supported channels must be created in the ifTable. Thus an ADSL
    line that supports both channels will have three entries in the
    ifTable, one for each physical, fast, and interleaved, whose
    ifType values are equal to adsl(94), fast(125), and
    interleaved(124), respectively. The ifStackTable is used to
    represent the relationship between the entries.

    Naming Conventions:
              Atuc -- (ATUC) modem at near (Central) end of line
              Atur -- (ATUR) modem at Remote end of line
              Curr -- Current
              Prev -- Previous
              Atn -- Attenuation
              ES  -- Errored Second.
              LCS -- Line Code Specific
              Lof -- Loss of Frame
              Lol -- Loss of Link
              Los -- Loss of Signal
              Lpr -- Loss of Power
              xxxs-- interval of Seconds in which xxx occurs
                      (e.g., xxx=Lof, Los, Lpr)
              Max -- Maximum
              Mgn -- Margin
              Min -- Minimum
              Psd -- Power Spectral Density
              Snr -- Signal to Noise Ratio
              Tx  -- Transmit
              Blks-- Blocks, a data unit, see
                     adslAtuXChanCrcBlockLength
      "
      --  Revision history
      REVISION     "9908190000Z"  -- 19 August 1999, midnight
      DESCRIPTION  "Initial Version, published as RFC 2662"

::= { transmission 94 }

adslLineMib OBJECT IDENTIFIER ::= { adslMIB 1 }

adslMibObjects OBJECT IDENTIFIER ::= { adslLineMib 1 }


-- objects
      adslLineTable   OBJECT-TYPE
          SYNTAX          SEQUENCE OF AdslLineEntry
          MAX-ACCESS      not-accessible
          STATUS          current
          DESCRIPTION
              "This table includes common attributes describing
              both ends of the line.  It is required for all ADSL
              physical interfaces.  ADSL physical interfaces are
              those ifEntries where ifType is equal to adsl(94)."
      ::= { adslMibObjects 1 }

      adslLineEntry   OBJECT-TYPE
          SYNTAX          AdslLineEntry
          MAX-ACCESS      not-accessible
          STATUS          current
          DESCRIPTION     "An entry in adslLineTable."
          INDEX           { ifIndex }
      ::= { adslLineTable 1 }

      AdslLineEntry ::=
          SEQUENCE {
          adslLineCoding           AdslLineCodingType,
          adslLineType             INTEGER,
          adslLineSpecific         VariablePointer,
          adslLineConfProfile      SnmpAdminString,
          adslLineAlarmConfProfile SnmpAdminString
          }

      adslLineCoding OBJECT-TYPE
          SYNTAX      AdslLineCodingType
          MAX-ACCESS  read-only
          STATUS      current
          DESCRIPTION
              "Specifies the ADSL coding type used on this
              line."
      ::= { adslLineEntry 1 }

     adslLineType OBJECT-TYPE
          SYNTAX      INTEGER {
              noChannel (1),        -- no channels exist
              fastOnly (2),         -- fast channel exists only
              interleavedOnly (3),  -- interleaved channel exists
                                    -- only
              fastOrInterleaved (4),-- either fast or interleaved
                                    -- channels can exist, but
                                    -- only one at any time
              fastAndInterleaved (5)-- both fast or interleaved

                                    -- channels exist
          }
          MAX-ACCESS  read-only
          STATUS      current
          DESCRIPTION
              "Defines the type of ADSL physical line
              entity that exists, by defining whether and how
              the line is channelized.  If the line is channelized,
              the value will be other than noChannel(1).  This
              object defines which channel type(s) are supported.

              In the case that the line is channelized, the manager
              can use the ifStackTable to determine the ifIndex for
              the associated channel(s)."
      ::= { adslLineEntry 2 }

      adslLineSpecific OBJECT-TYPE
          SYNTAX      VariablePointer
          MAX-ACCESS  read-only
          STATUS      current
          DESCRIPTION
              "OID instance in vendor-specific MIB. The Instance may
              be used to determine shelf/slot/port of the ATUC
              interface in a DSLAM."
      ::= { adslLineEntry 3 }

     adslLineConfProfile OBJECT-TYPE
          SYNTAX      SnmpAdminString (SIZE (1..32))
          MAX-ACCESS  read-write
          STATUS      current
          DESCRIPTION
              "The value of this object identifies the row
              in the ADSL Line Configuration Profile Table,
              (adslLineConfProfileTable), which applies for this
              ADSL line, and channels if applicable.

              For `dynamic' mode, in the case which the
              configuration profile has not been set, the
              value will be set to `DEFVAL'.

              If the implementator of this MIB has chosen not
              to implement `dynamic assignment' of profiles, this
              object's MIN-ACCESS is read-only."
      ::= { adslLineEntry 4 }

     adslLineAlarmConfProfile OBJECT-TYPE
          SYNTAX      SnmpAdminString (SIZE (1..32))
          MAX-ACCESS  read-write

          STATUS      current
          DESCRIPTION
              "The value of this object identifies the row
              in the ADSL Line Alarm Configuration Profile Table,
              (adslLineAlarmConfProfileTable), which applies to this
              ADSL line, and channels if applicable.

              For `dynamic' mode, in the case which the
              alarm profile has not been set, the
              value will be set to `DEFVAL'.

              If the implementator of this MIB has chosen not
              to implement `dynamic assignment' of profiles, this
              object's MIN-ACCESS is read-only."
      ::= { adslLineEntry 5 }

      adslAtucPhysTable       OBJECT-TYPE
          SYNTAX          SEQUENCE OF AdslAtucPhysEntry
          MAX-ACCESS      not-accessible
          STATUS          current
          DESCRIPTION
              "This table provides one row for each ATUC.
              Each row contains the Physical Layer Parameters
              table for that ATUC. ADSL physical interfaces are
              those ifEntries where ifType is equal to adsl(94)."
      ::= { adslMibObjects 2 }

      adslAtucPhysEntry       OBJECT-TYPE
          SYNTAX          AdslAtucPhysEntry
          MAX-ACCESS      not-accessible
          STATUS          current
          DESCRIPTION     "An entry in the adslAtucPhysTable."
          INDEX           { ifIndex }
      ::= { adslAtucPhysTable 1 }

      AdslAtucPhysEntry ::=
          SEQUENCE {
          adslAtucInvSerialNumber         SnmpAdminString,
          adslAtucInvVendorID             SnmpAdminString,
          adslAtucInvVersionNumber        SnmpAdminString,
          adslAtucCurrSnrMgn              INTEGER,
          adslAtucCurrAtn                 Gauge32,
          adslAtucCurrStatus              BITS,
          adslAtucCurrOutputPwr           INTEGER,
          adslAtucCurrAttainableRate      Gauge32
          }

      -- inventory group

      --
      -- These items should describe the lowest level identifiable
      -- component, be it a stand-alone modem, a card in a rack,
      -- a child-board, etc.
      --
      adslAtucInvSerialNumber OBJECT-TYPE
          SYNTAX      SnmpAdminString (SIZE (0..32))
          MAX-ACCESS  read-only
          STATUS      current
          DESCRIPTION
              "The vendor specific string that identifies the
              vendor equipment."
      ::= { adslAtucPhysEntry 1 }

      adslAtucInvVendorID OBJECT-TYPE
          SYNTAX      SnmpAdminString (SIZE (0..16))
          MAX-ACCESS  read-only
          STATUS      current
          DESCRIPTION
              "The vendor ID code is a copy of the binary
              vendor identification field defined by the
              PHY[10] and expressed as readable characters."

          REFERENCE "ANSI T1.413[10]"
      ::= { adslAtucPhysEntry 2 }

      adslAtucInvVersionNumber OBJECT-TYPE
          SYNTAX      SnmpAdminString (SIZE (0..16))
          MAX-ACCESS  read-only
          STATUS      current
          DESCRIPTION
              "The vendor specific version number sent by this ATU
              as part of the initialization messages.  It is a copy
              of the binary version number field defined by the
              PHY[10] and expressed as readable characters."
          REFERENCE "ANSI T1.413[10]"
      ::= { adslAtucPhysEntry 3 }

      -- current status group
      --
      adslAtucCurrSnrMgn OBJECT-TYPE
          SYNTAX      INTEGER (-640..640)
          UNITS       "tenth dB"
          MAX-ACCESS  read-only
          STATUS      current
          DESCRIPTION
              "Noise Margin as seen by this ATU with respect to its
              received signal in tenth dB."

      ::= { adslAtucPhysEntry 4 }

      adslAtucCurrAtn OBJECT-TYPE
          SYNTAX      Gauge32(0..630)
          UNITS       "tenth dB"
          MAX-ACCESS  read-only
          STATUS      current
          DESCRIPTION
              "Measured difference in the total power transmitted by
              the peer ATU and the total power received by this ATU."
      ::= { adslAtucPhysEntry 5 }

     adslAtucCurrStatus OBJECT-TYPE
          SYNTAX      BITS {
                            noDefect(0),
                            lossOfFraming(1),
                            lossOfSignal(2),
                            lossOfPower(3),
                            lossOfSignalQuality(4),
                            lossOfLink(5),
                            dataInitFailure(6),
                            configInitFailure(7),
                            protocolInitFailure(8),
                            noPeerAtuPresent(9)
                           }
          MAX-ACCESS  read-only
          STATUS      current
          DESCRIPTION
              "Indicates current state of the ATUC line.  This is a
              bit-map of possible conditions.  The various bit
              positions are:

       0      noDefect             There no defects on the line

       1      lossOfFraming        ATUC failure due to not
                                   receiving valid frame.

       2      lossOfSignal         ATUC failure due to not
                                   receiving signal.

       3      lossOfPower          ATUC failure due to loss of
                                   power.
                                   Note: the Agent may still
                                   function.

       4      lossOfSignalQuality  Loss of Signal Quality is
                                   declared when the Noise Margin
                                   falls below the Minimum Noise

                                   Margin, or the bit-error-rate
                                   exceeds 10^-7.

       5      lossOfLink           ATUC failure due to inability
                                   to link with ATUR.

       6      dataInitFailure      ATUC failure during
                                   initialization due to bit
                                   errors corrupting startup
                                   exchange data.

       7      configInitFailure    ATUC failure during
                                   initialization due to peer
                                   ATU not able to support
                                   requested configuration

       8      protocolInitFailure  ATUC failure during
                                   initialization due to
                                   incompatible protocol used by
                                   the peer ATU.

       9      noPeerAtuPresent     ATUC failure during
                                   initialization due to no
                                   activation sequence detected
                                   from peer ATU.

              This is intended to supplement ifOperStatus."
      ::= { adslAtucPhysEntry 6 }

      adslAtucCurrOutputPwr OBJECT-TYPE
          SYNTAX      INTEGER (-310..310)
          UNITS       "tenth dBm"
          MAX-ACCESS  read-only
          STATUS      current
          DESCRIPTION
              "Measured total output power transmitted by this ATU.
              This is the measurement that was reported during
              the last activation sequence."
      ::= { adslAtucPhysEntry 7 }

      adslAtucCurrAttainableRate OBJECT-TYPE
          SYNTAX      Gauge32
          UNITS       "bps"
          MAX-ACCESS  read-only
          STATUS      current
          DESCRIPTION
              "Indicates the maximum currently attainable data rate
              by the ATU.  This value will be equal or greater than

              the current line rate."
      ::= { adslAtucPhysEntry 8 }

      adslAturPhysTable        OBJECT-TYPE
          SYNTAX          SEQUENCE OF AdslAturPhysEntry
          MAX-ACCESS      not-accessible
          STATUS          current
          DESCRIPTION
              "This table provides one row for each ATUR
              Each row contains the Physical Layer Parameters
              table for that ATUR. ADSL physical interfaces are
              those ifEntries where ifType is equal to adsl(94)."
      ::= { adslMibObjects 3 }

      adslAturPhysEntry       OBJECT-TYPE
          SYNTAX          AdslAturPhysEntry
          MAX-ACCESS      not-accessible
          STATUS          current
          DESCRIPTION     "An entry in the adslAturPhysTable."
          INDEX           { ifIndex }
      ::= { adslAturPhysTable 1 }

      AdslAturPhysEntry ::=
          SEQUENCE {
          adslAturInvSerialNumber         SnmpAdminString,
          adslAturInvVendorID             SnmpAdminString,
          adslAturInvVersionNumber        SnmpAdminString,
          adslAturCurrSnrMgn              INTEGER,
          adslAturCurrAtn                 Gauge32,
          adslAturCurrStatus              BITS,
          adslAturCurrOutputPwr           INTEGER,
          adslAturCurrAttainableRate      Gauge32
          }

      -- inventory group
      --
      adslAturInvSerialNumber OBJECT-TYPE
          SYNTAX      SnmpAdminString (SIZE (0..32))
          MAX-ACCESS  read-only
          STATUS      current
          DESCRIPTION
              "The vendor specific string that identifies the
              vendor equipment."
      ::= { adslAturPhysEntry 1 }

      adslAturInvVendorID OBJECT-TYPE
          SYNTAX      SnmpAdminString (SIZE (0..16))
          MAX-ACCESS  read-only

          STATUS      current
          DESCRIPTION
              "The vendor ID code is a copy of the binary
              vendor identification field defined by the
              PHY[10] and expressed as readable characters."
          REFERENCE "ANSI T1.413"
      ::= { adslAturPhysEntry 2 }

      adslAturInvVersionNumber OBJECT-TYPE
          SYNTAX      SnmpAdminString (SIZE (0..16))
          MAX-ACCESS  read-only
          STATUS      current
          DESCRIPTION
              "The vendor specific version number sent by this ATU
              as part of the initialization messages.  It is a copy
              of the binary version number field defined by the
              PHY[10] and expressed as readable characters."
          REFERENCE "ANSI T1.413"
      ::= { adslAturPhysEntry 3 }

      -- current status group
      --
      adslAturCurrSnrMgn OBJECT-TYPE
          SYNTAX      INTEGER (-640..640)
          UNITS       "tenth dB"
          MAX-ACCESS  read-only
          STATUS      current
          DESCRIPTION
              "Noise Margin as seen by this ATU with respect to its
              received signal in tenth dB."
      ::= { adslAturPhysEntry 4 }

      adslAturCurrAtn OBJECT-TYPE
          SYNTAX      Gauge32(0..630)
          UNITS       "tenth dB"
          MAX-ACCESS  read-only
          STATUS      current
          DESCRIPTION
              "Measured difference in the total power transmitted by
              the peer ATU and the total power received by this ATU."
      ::= { adslAturPhysEntry 5 }

     adslAturCurrStatus OBJECT-TYPE
          SYNTAX     BITS {
                           noDefect(0),
                           lossOfFraming(1),
                           lossOfSignal(2),
                           lossOfPower(3),

                           lossOfSignalQuality(4)
                          }
          MAX-ACCESS  read-only
          STATUS      current
          DESCRIPTION
              "Indicates current state of the ATUR line.  This is a
              bit-map of possible conditions.  Due to the isolation
              of the ATUR when line problems occur, many state
              conditions like loss of power, loss of quality signal,
              and initialization errors,  can not be determined.
              While trouble shooting ATUR, also use object,
              adslAtucCurrStatus.  The various bit positions are:

       0      noDefect             There no defects on the line

       1      lossOfFraming        ATUR failure due to not
                                   receiving valid frame

       2      lossOfSignal         ATUR failure due to not
                                   receiving signal

       3      lossOfPower          ATUR failure due to loss of
                                   power

       4      lossOfSignalQuality  Loss of Signal Quality is
                                   declared when the Noise Margin
                                   falls below the Minimum Noise
                                   Margin, or the
                                   bit-error-rate exceeds 10^-7.

              This is intended to supplement ifOperStatus."
      ::= { adslAturPhysEntry 6 }

      adslAturCurrOutputPwr OBJECT-TYPE
          SYNTAX      INTEGER (-310..310)
          UNITS       "tenth dBm"
          MAX-ACCESS  read-only
          STATUS      current
          DESCRIPTION
              "Measured total output power transmitted by this ATU.
              This is the measurement that was reported during
              the last activation sequence."
      ::= { adslAturPhysEntry 7 }

      adslAturCurrAttainableRate OBJECT-TYPE
          SYNTAX      Gauge32
          UNITS       "bps"
          MAX-ACCESS  read-only

          STATUS      current
          DESCRIPTION
              "Indicates the maximum currently attainable data rate
              by the ATU.  This value will be equal or greater than
              the current line rate."
      ::= { adslAturPhysEntry 8 }

      adslAtucChanTable       OBJECT-TYPE
          SYNTAX          SEQUENCE OF AdslAtucChanEntry
          MAX-ACCESS      not-accessible
          STATUS          current
          DESCRIPTION
              "This table provides one row for each ATUC channel.
              ADSL channel interfaces are those ifEntries
              where ifType is equal to adslInterleave(124)
              or adslFast(125)."
      ::= { adslMibObjects 4 }

      adslAtucChanEntry       OBJECT-TYPE
          SYNTAX          AdslAtucChanEntry
          MAX-ACCESS      not-accessible
          STATUS          current
          DESCRIPTION     "An entry in the adslAtucChanTable."
          INDEX           { ifIndex }
      ::= { adslAtucChanTable 1 }

      AdslAtucChanEntry ::=
          SEQUENCE {
          adslAtucChanInterleaveDelay     Gauge32,
          adslAtucChanCurrTxRate          Gauge32,
          adslAtucChanPrevTxRate          Gauge32,
          adslAtucChanCrcBlockLength      Gauge32
          }

      -- current group
      --
      adslAtucChanInterleaveDelay OBJECT-TYPE
          SYNTAX      Gauge32
          UNITS       "milli-seconds"
          MAX-ACCESS  read-only
          STATUS      current
          DESCRIPTION
              "Interleave Delay for this channel.

              Interleave delay applies only to the
              interleave channel and defines the mapping
              (relative spacing) between subsequent input
              bytes at the interleaver input and their placement

              in the bit stream at the interleaver output.
              Larger numbers provide greater separation between
              consecutive input bytes in the output bit stream
              allowing for improved impulse noise immunity at
              the expense of payload latency.

              In the case where the ifType is Fast(125), use
              noSuchObject."
      ::= { adslAtucChanEntry 1 }

      adslAtucChanCurrTxRate  OBJECT-TYPE
          SYNTAX      Gauge32
          UNITS       "bps"
          MAX-ACCESS  read-only
          STATUS      current
          DESCRIPTION
              "Actual transmit rate on this channel."
      ::= { adslAtucChanEntry 2 }

      adslAtucChanPrevTxRate OBJECT-TYPE
          SYNTAX      Gauge32
          UNITS        "bps"
          MAX-ACCESS  read-only
          STATUS      current
          DESCRIPTION
              "The rate at the time of the last
              adslAtucRateChangeTrap event. It is also set at
              initialization to prevent a trap being sent.

              Rate changes less than adslAtucThresh(*)RateDown
              or less than adslAtucThresh(*)RateUp will not
              cause a trap or cause this object to change.
              (*) == Fast or Interleave.
              See AdslLineAlarmConfProfileEntry."
      ::= { adslAtucChanEntry 3 }

      adslAtucChanCrcBlockLength OBJECT-TYPE
          SYNTAX      Gauge32
          UNITS        "byte"
          MAX-ACCESS  read-only
          STATUS      current
          DESCRIPTION
              "Indicates the length of the channel data-block
              on which the CRC operates.  Refer to Line Code
              Specific MIBs, [11] and [12] for more
              information."
      ::= { adslAtucChanEntry 4 }


     adslAturChanTable       OBJECT-TYPE
          SYNTAX          SEQUENCE OF AdslAturChanEntry
          MAX-ACCESS      not-accessible
          STATUS          current
          DESCRIPTION
              "This table provides one row for each ATUR channel.
              ADSL channel interfaces are those ifEntries
              where ifType is equal to adslInterleave(124)
              or adslFast(125)."
      ::= { adslMibObjects 5 }

      adslAturChanEntry       OBJECT-TYPE
          SYNTAX          AdslAturChanEntry
          MAX-ACCESS      not-accessible
          STATUS          current
          DESCRIPTION     "An entry in the adslAturChanTable."
          INDEX           { ifIndex }
      ::= { adslAturChanTable 1 }

      AdslAturChanEntry ::=
          SEQUENCE {
          adslAturChanInterleaveDelay     Gauge32,
          adslAturChanCurrTxRate          Gauge32,
          adslAturChanPrevTxRate          Gauge32,
          adslAturChanCrcBlockLength      Gauge32
          }

      -- current group
      --
      adslAturChanInterleaveDelay OBJECT-TYPE
          SYNTAX      Gauge32
          UNITS       "milli-seconds"
          MAX-ACCESS  read-only
          STATUS      current
          DESCRIPTION
              "Interleave Delay for this channel.

              Interleave delay applies only to the
              interleave channel and defines the mapping
              (relative spacing) between subsequent input
              bytes at the interleaver input and their placement
              in the bit stream at the interleaver output.
              Larger numbers provide greater separation between
              consecutive input bytes in the output bit stream
              allowing for improved impulse noise immunity at
              the expense of payload latency.

              In the case where the ifType is Fast(125), use

              noSuchObject."
      ::= { adslAturChanEntry 1 }

      adslAturChanCurrTxRate  OBJECT-TYPE
          SYNTAX      Gauge32
          UNITS       "bps"
          MAX-ACCESS  read-only
          STATUS      current
          DESCRIPTION
              "Actual transmit rate on this channel."
      ::= { adslAturChanEntry 2 }

      adslAturChanPrevTxRate OBJECT-TYPE
          SYNTAX      Gauge32
          UNITS       "bps"
          MAX-ACCESS  read-only
          STATUS      current
          DESCRIPTION
             "The rate at the time of the last
              adslAturRateChangeTrap event. It is also set at
              initialization to prevent a trap being sent.
              Rate changes less than adslAturThresh(*)RateDown
              or less than adslAturThresh(*)RateUp will not
              cause a trap or cause this object to change.
              (*) == Fast or Interleave.
              See AdslLineAlarmConfProfileEntry."
      ::= { adslAturChanEntry 3 }

      adslAturChanCrcBlockLength OBJECT-TYPE
          SYNTAX      Gauge32
          MAX-ACCESS  read-only
          STATUS      current
          DESCRIPTION
              "Indicates the length of the channel data-block
              on which the CRC operates.  Refer to Line Code
              Specific MIBs, [11] and [12] for more
              information."
      ::= { adslAturChanEntry 4 }

      adslAtucPerfDataTable   OBJECT-TYPE
          SYNTAX          SEQUENCE OF AdslAtucPerfDataEntry
          MAX-ACCESS      not-accessible
          STATUS          current
          DESCRIPTION
              "This table provides one row for each ATUC.
              ADSL physical interfaces are
              those ifEntries where ifType is equal to adsl(94)."
      ::= { adslMibObjects 6 }

      adslAtucPerfDataEntry       OBJECT-TYPE
          SYNTAX          AdslAtucPerfDataEntry
          MAX-ACCESS      not-accessible
          STATUS          current
          DESCRIPTION     "An entry in adslAtucPerfDataTable."
          INDEX           { ifIndex }
      ::= { adslAtucPerfDataTable 1 }

      AdslAtucPerfDataEntry ::=
          SEQUENCE {
          adslAtucPerfLofs                 Counter32,
          adslAtucPerfLoss                 Counter32,
          adslAtucPerfLols                 Counter32,
          adslAtucPerfLprs                 Counter32,
          adslAtucPerfESs                  Counter32,
          adslAtucPerfInits                Counter32,
          adslAtucPerfValidIntervals       INTEGER,
          adslAtucPerfInvalidIntervals     INTEGER,
          adslAtucPerfCurr15MinTimeElapsed AdslPerfTimeElapsed,
          adslAtucPerfCurr15MinLofs        PerfCurrentCount,
          adslAtucPerfCurr15MinLoss        PerfCurrentCount,
          adslAtucPerfCurr15MinLols        PerfCurrentCount,
          adslAtucPerfCurr15MinLprs        PerfCurrentCount,
          adslAtucPerfCurr15MinESs         PerfCurrentCount,
          adslAtucPerfCurr15MinInits       PerfCurrentCount,
          adslAtucPerfCurr1DayTimeElapsed  AdslPerfTimeElapsed,
          adslAtucPerfCurr1DayLofs         AdslPerfCurrDayCount,
          adslAtucPerfCurr1DayLoss         AdslPerfCurrDayCount,
          adslAtucPerfCurr1DayLols         AdslPerfCurrDayCount,
          adslAtucPerfCurr1DayLprs         AdslPerfCurrDayCount,
          adslAtucPerfCurr1DayESs          AdslPerfCurrDayCount,
          adslAtucPerfCurr1DayInits        AdslPerfCurrDayCount,
          adslAtucPerfPrev1DayMoniSecs     INTEGER,
          adslAtucPerfPrev1DayLofs         AdslPerfPrevDayCount,
          adslAtucPerfPrev1DayLoss         AdslPerfPrevDayCount,
          adslAtucPerfPrev1DayLols         AdslPerfPrevDayCount,
          adslAtucPerfPrev1DayLprs         AdslPerfPrevDayCount,
          adslAtucPerfPrev1DayESs          AdslPerfPrevDayCount,
          adslAtucPerfPrev1DayInits        AdslPerfPrevDayCount
          }

      -- Event Counters
      --
      -- Also see adslAtucIntervalTable for 15 minute interval
      -- elapsed counters.
      --
      adslAtucPerfLofs OBJECT-TYPE
          SYNTAX      Counter32

          MAX-ACCESS  read-only
          STATUS      current
          DESCRIPTION
              "Count of the number of Loss of Framing failures since
              agent reset."
      ::= { adslAtucPerfDataEntry 1 }

      adslAtucPerfLoss  OBJECT-TYPE
          SYNTAX      Counter32
          MAX-ACCESS  read-only
          STATUS      current
          DESCRIPTION
              "Count of the number of Loss of Signal failures since
              agent reset."
      ::= { adslAtucPerfDataEntry 2 }

      adslAtucPerfLols OBJECT-TYPE
          SYNTAX      Counter32
          MAX-ACCESS  read-only
          STATUS      current
          DESCRIPTION
              "Count of the number of Loss of Link failures since
              agent reset."
      ::= { adslAtucPerfDataEntry 3 }

      adslAtucPerfLprs OBJECT-TYPE
          SYNTAX      Counter32
          MAX-ACCESS  read-only
          STATUS      current
          DESCRIPTION
              "Count of the number of Loss of Power failures since
              agent reset."
      ::= { adslAtucPerfDataEntry 4 }

      adslAtucPerfESs OBJECT-TYPE
          SYNTAX      Counter32
          MAX-ACCESS  read-only
          STATUS      current
          DESCRIPTION
              "Count of the number of Errored Seconds since agent
              reset.  The errored second parameter is a count of
              one-second intervals containing one or more crc
              anomalies, or one or more los or sef defects."
      ::= { adslAtucPerfDataEntry 5 }

      adslAtucPerfInits OBJECT-TYPE
          SYNTAX      Counter32
          MAX-ACCESS  read-only

          STATUS      current
          DESCRIPTION
              "Count of the line initialization attempts since
              agent reset. Includes both successful and failed
              attempts."
      ::= { adslAtucPerfDataEntry 6 }

      -- general 15 min interval information
      --

      adslAtucPerfValidIntervals OBJECT-TYPE
          SYNTAX      INTEGER(0..96)
          MAX-ACCESS  read-only
          STATUS      current
          DESCRIPTION
              "The number of previous 15-minute intervals in the
              interval table for which data was collected.  Given
              that <n> is the maximum # of intervals supported.
              The value will be <n> unless the measurement was
              (re-)started within the last (<n>*15) minutes, in which
              case the value will be the number of complete 15
              minute intervals for which the agent has at least
              some data. In certain cases (e.g., in the case
              where the agent is a proxy) it is possible that some
              intervals are unavailable.  In this case, this
              interval is the maximum interval number for
              which data is available."
      ::= { adslAtucPerfDataEntry 7 }

      adslAtucPerfInvalidIntervals OBJECT-TYPE
          SYNTAX      INTEGER(0..96)
          MAX-ACCESS  read-only
          STATUS      current
          DESCRIPTION
              "The number of intervals in the range from
              0 to the value of adslAtucPerfValidIntervals
              for which no data is available. This object
              will typically be zero except in cases where
              the data for some intervals are not available
              (e.g., in proxy situations)."
      ::= { adslAtucPerfDataEntry 8 }

      -- 15 min current performance group
      --
      adslAtucPerfCurr15MinTimeElapsed OBJECT-TYPE
          SYNTAX      AdslPerfTimeElapsed(0..899)
          UNITS       "seconds"
          MAX-ACCESS  read-only

          STATUS      current
          DESCRIPTION
              "Total elapsed seconds in this interval."
      ::= { adslAtucPerfDataEntry 9 }

      adslAtucPerfCurr15MinLofs OBJECT-TYPE
          SYNTAX      PerfCurrentCount
          UNITS       "seconds"
          MAX-ACCESS  read-only
          STATUS      current
          DESCRIPTION
              "Count of seconds in the current 15 minute interval
              when there was Loss of Framing."
      ::= { adslAtucPerfDataEntry 10 }

      adslAtucPerfCurr15MinLoss  OBJECT-TYPE
          SYNTAX      PerfCurrentCount
          UNITS       "seconds"
          MAX-ACCESS  read-only
          STATUS      current
          DESCRIPTION
              "Count of seconds in the current 15 minute interval
              when there was Loss of Signal."
      ::= { adslAtucPerfDataEntry 11 }

      adslAtucPerfCurr15MinLols  OBJECT-TYPE
          SYNTAX      PerfCurrentCount
          UNITS       "seconds"
          MAX-ACCESS  read-only
          STATUS      current
          DESCRIPTION
              "Count of seconds in the current 15 minute interval
              when there was Loss of Link."
      ::= { adslAtucPerfDataEntry 12 }

      adslAtucPerfCurr15MinLprs  OBJECT-TYPE
          SYNTAX      PerfCurrentCount
          UNITS       "seconds"
          MAX-ACCESS  read-only
          STATUS      current
          DESCRIPTION
              "Count of seconds in the current 15 minute interval
              when there was Loss of Power."
      ::= { adslAtucPerfDataEntry 13 }

      adslAtucPerfCurr15MinESs OBJECT-TYPE
          SYNTAX      PerfCurrentCount
          UNITS       "seconds"

          MAX-ACCESS  read-only
          STATUS      current
          DESCRIPTION
              "Count of Errored Seconds in the current 15 minute
              interval.  The errored second parameter is a count of
              one-second intervals containing one or more crc
              anomalies, or one or more los or sef defects."
      ::= { adslAtucPerfDataEntry 14 }

      adslAtucPerfCurr15MinInits  OBJECT-TYPE
          SYNTAX      PerfCurrentCount
          MAX-ACCESS  read-only
          STATUS      current
          DESCRIPTION
              "Count of the line initialization attempts in the
              current 15 minute interval. Includes both successful
              and failed attempts."
      ::= { adslAtucPerfDataEntry 15 }

      -- 1-day current and previous performance group
      --
      adslAtucPerfCurr1DayTimeElapsed OBJECT-TYPE
          SYNTAX      AdslPerfTimeElapsed(0..86399)
          UNITS       "seconds"
          MAX-ACCESS  read-only
          STATUS      current
          DESCRIPTION
              "Number of seconds that have elapsed since the
              beginning of the current 1-day interval."
      ::= { adslAtucPerfDataEntry 16 }

      adslAtucPerfCurr1DayLofs  OBJECT-TYPE
          SYNTAX      AdslPerfCurrDayCount
          UNITS       "seconds"
          MAX-ACCESS  read-only
          STATUS      current
          DESCRIPTION
              "Count of the number of seconds when there was Loss of
              Framing during the current day as measured by
              adslAtucPerfCurr1DayTimeElapsed."
      ::= { adslAtucPerfDataEntry 17 }

      adslAtucPerfCurr1DayLoss  OBJECT-TYPE
          SYNTAX      AdslPerfCurrDayCount
          UNITS       "seconds"
          MAX-ACCESS  read-only
          STATUS      current
          DESCRIPTION

              "Count of the number of seconds when there was Loss of
              Signal during the current day as measured by
              adslAtucPerfCurr1DayTimeElapsed."
      ::= { adslAtucPerfDataEntry 18 }

      adslAtucPerfCurr1DayLols  OBJECT-TYPE
          SYNTAX      AdslPerfCurrDayCount
          UNITS       "seconds"
          MAX-ACCESS  read-only
          STATUS      current
          DESCRIPTION
              "Count of the number of seconds when there was Loss of
              Link during the current day as measured by
              adslAtucPerfCurr1DayTimeElapsed."
      ::= { adslAtucPerfDataEntry 19 }

      adslAtucPerfCurr1DayLprs  OBJECT-TYPE
          SYNTAX      AdslPerfCurrDayCount
          UNITS       "seconds"
          MAX-ACCESS  read-only
          STATUS      current
          DESCRIPTION
              "Count of the number of seconds when there was Loss of
              Power during the current day as measured by
              adslAtucPerfCurr1DayTimeElapsed."
      ::= { adslAtucPerfDataEntry 20 }

      adslAtucPerfCurr1DayESs OBJECT-TYPE
          SYNTAX      AdslPerfCurrDayCount
          UNITS       "seconds"
          MAX-ACCESS  read-only
          STATUS      current
          DESCRIPTION
              "Count of Errored Seconds during the current day as
              measured by adslAtucPerfCurr1DayTimeElapsed.
              The errored second parameter is a count of
              one-second intervals containing one or more crc
              anomalies, or one or more los or sef defects."
      ::= { adslAtucPerfDataEntry 21 }

      adslAtucPerfCurr1DayInits  OBJECT-TYPE
          SYNTAX      AdslPerfCurrDayCount
          MAX-ACCESS  read-only
          STATUS      current
          DESCRIPTION
              "Count of the line initialization attempts in the
              day as measured by adslAtucPerfCurr1DayTimeElapsed.
              Includes both successful and failed attempts."

      ::= { adslAtucPerfDataEntry 22 }

      adslAtucPerfPrev1DayMoniSecs OBJECT-TYPE
          SYNTAX      INTEGER(0..86400)
          UNITS       "seconds"
          MAX-ACCESS  read-only
          STATUS      current
          DESCRIPTION
              "The amount of time in the previous 1-day interval
              over which the performance monitoring information
              is actually counted. This value will be the same as
              the interval duration except in a situation where
              performance monitoring data could not be collected
              for any reason."
      ::= { adslAtucPerfDataEntry 23 }

      adslAtucPerfPrev1DayLofs  OBJECT-TYPE
          SYNTAX      AdslPerfPrevDayCount
          UNITS       "seconds"
          MAX-ACCESS  read-only
          STATUS      current
          DESCRIPTION
              "Count of seconds in the interval when there was
              Loss of Framing within the most recent previous
              1-day period."
      ::= { adslAtucPerfDataEntry 24 }

      adslAtucPerfPrev1DayLoss  OBJECT-TYPE
          SYNTAX      AdslPerfPrevDayCount
          UNITS       "seconds"
          MAX-ACCESS  read-only
          STATUS      current
          DESCRIPTION
              "Count of seconds in the interval when there was
              Loss of Signal within the most recent previous
              1-day period."
      ::= { adslAtucPerfDataEntry 25 }

      adslAtucPerfPrev1DayLols  OBJECT-TYPE
          SYNTAX      AdslPerfPrevDayCount
          UNITS       "seconds"
          MAX-ACCESS  read-only
          STATUS      current
          DESCRIPTION
              "Count of seconds in the interval when there was
              Loss of Link within the most recent previous
              1-day period."
      ::= { adslAtucPerfDataEntry 26 }

      adslAtucPerfPrev1DayLprs  OBJECT-TYPE
          SYNTAX      AdslPerfPrevDayCount
          UNITS       "seconds"
          MAX-ACCESS  read-only
          STATUS      current
          DESCRIPTION
              "Count of seconds in the interval when there was
              Loss of Power within the most recent previous
              1-day period."
      ::= { adslAtucPerfDataEntry 27 }

      adslAtucPerfPrev1DayESs OBJECT-TYPE
          SYNTAX      AdslPerfPrevDayCount
          UNITS       "seconds"
          MAX-ACCESS  read-only
          STATUS      current
          DESCRIPTION
              "Count of Errored Seconds within the most recent
              previous 1-day period. The errored second parameter is
              a count of one-second intervals containing one or more
              crc anomalies, or one or more los or sef defects."
      ::= { adslAtucPerfDataEntry 28 }

      adslAtucPerfPrev1DayInits  OBJECT-TYPE
          SYNTAX      AdslPerfPrevDayCount
          MAX-ACCESS  read-only
          STATUS      current
          DESCRIPTION
              "Count of the line initialization attempts in the most
              recent previous 1-day period. Includes both successful
              and failed attempts."
      ::= { adslAtucPerfDataEntry 29 }

      adslAturPerfDataTable   OBJECT-TYPE
          SYNTAX          SEQUENCE OF AdslAturPerfDataEntry
          MAX-ACCESS      not-accessible
          STATUS          current
          DESCRIPTION
              "This table provides one row for each ATUR.
              ADSL physical interfaces are
              those ifEntries where ifType is equal to adsl(94)."
      ::= { adslMibObjects 7 }

      adslAturPerfDataEntry       OBJECT-TYPE
          SYNTAX          AdslAturPerfDataEntry
          MAX-ACCESS      not-accessible
          STATUS          current
          DESCRIPTION     "An entry in adslAturPerfDataTable."

          INDEX           { ifIndex }
      ::= { adslAturPerfDataTable 1 }

      AdslAturPerfDataEntry ::=
          SEQUENCE {
          adslAturPerfLofs                 Counter32,
          adslAturPerfLoss                 Counter32,
          adslAturPerfLprs                 Counter32,
          adslAturPerfESs                  Counter32,
          adslAturPerfValidIntervals       INTEGER,
          adslAturPerfInvalidIntervals     INTEGER,
          adslAturPerfCurr15MinTimeElapsed AdslPerfTimeElapsed,
          adslAturPerfCurr15MinLofs        PerfCurrentCount,
          adslAturPerfCurr15MinLoss        PerfCurrentCount,
          adslAturPerfCurr15MinLprs        PerfCurrentCount,
          adslAturPerfCurr15MinESs         PerfCurrentCount,
          adslAturPerfCurr1DayTimeElapsed  AdslPerfTimeElapsed,
          adslAturPerfCurr1DayLofs         AdslPerfCurrDayCount,
          adslAturPerfCurr1DayLoss         AdslPerfCurrDayCount,
          adslAturPerfCurr1DayLprs         AdslPerfCurrDayCount,
          adslAturPerfCurr1DayESs          AdslPerfCurrDayCount,
          adslAturPerfPrev1DayMoniSecs     INTEGER,
          adslAturPerfPrev1DayLofs         AdslPerfPrevDayCount,
          adslAturPerfPrev1DayLoss         AdslPerfPrevDayCount,
          adslAturPerfPrev1DayLprs         AdslPerfPrevDayCount,
          adslAturPerfPrev1DayESs          AdslPerfPrevDayCount
          }

      -- Event (Raw) Counters
      --
      -- Also see adslAturIntervalTable for 15 minute interval
      -- elapsed counters.
      --
      adslAturPerfLofs OBJECT-TYPE
          SYNTAX      Counter32
          UNITS       "seconds"
          MAX-ACCESS  read-only
          STATUS      current
          DESCRIPTION
              "Count of the number of Loss of Framing failures since
              agent reset."
      ::= { adslAturPerfDataEntry 1 }

      adslAturPerfLoss  OBJECT-TYPE
          SYNTAX      Counter32
          UNITS       "seconds"
          MAX-ACCESS  read-only
          STATUS      current

          DESCRIPTION
              "Count of the number of Loss of Signal failures since
              agent reset."
      ::= { adslAturPerfDataEntry 2 }

     adslAturPerfLprs  OBJECT-TYPE
          SYNTAX      Counter32
          UNITS       "seconds"
          MAX-ACCESS  read-only
          STATUS      current
          DESCRIPTION
              "Count of the number of Loss of Power failures since
              agent reset."
      ::= { adslAturPerfDataEntry 3 }

      adslAturPerfESs  OBJECT-TYPE
          SYNTAX      Counter32
          UNITS       "seconds"
          MAX-ACCESS  read-only
          STATUS      current
          DESCRIPTION
              "Count of the number of Errored Seconds since agent
              reset.  The errored second parameter is a count of
              one-second intervals containing one or more crc
              anomalies, or one or more los or sef defects."
      ::= { adslAturPerfDataEntry 4 }

      -- general 15 min interval information
      --
      adslAturPerfValidIntervals OBJECT-TYPE
          SYNTAX      INTEGER(0..96)
          MAX-ACCESS  read-only
          STATUS      current
          DESCRIPTION
              "The number of previous 15-minute intervals in the
              interval table for which data was collected.  Given
              that <n> is the maximum # of intervals supported.
              The value will be <n> unless the measurement was
              (re-)started within the last (<n>*15) minutes, in which
              case the value will be the number of complete 15
              minute intervals for which the agent has at least
              some data. In certain cases (e.g., in the case
              where the agent is a proxy) it is possible that some
              intervals are unavailable.  In this case, this
              interval is the maximum interval number for
              which data is available."
      ::= { adslAturPerfDataEntry 5 }


      adslAturPerfInvalidIntervals OBJECT-TYPE
          SYNTAX      INTEGER(0..96)
          MAX-ACCESS  read-only
          STATUS      current
          DESCRIPTION
              "The number of intervals in the range from
              0 to the value of adslAturPerfValidIntervals
              for which no data is available. This object
              will typically be zero except in cases where
              the data for some intervals are not available
              (e.g., in proxy situations)."
      ::= { adslAturPerfDataEntry 6 }

      -- 15 min current performance group
      --
      adslAturPerfCurr15MinTimeElapsed OBJECT-TYPE
          SYNTAX      AdslPerfTimeElapsed(0..899)
          UNITS       "seconds"
          MAX-ACCESS  read-only
          STATUS      current
          DESCRIPTION
              "Total elapsed seconds in this interval."
      ::= { adslAturPerfDataEntry 7 }

      adslAturPerfCurr15MinLofs OBJECT-TYPE
          SYNTAX      PerfCurrentCount
          UNITS       "seconds"
          MAX-ACCESS  read-only
          STATUS      current
          DESCRIPTION
              "Count of seconds in the current 15 minute interval
              when there was Loss of Framing."
      ::= { adslAturPerfDataEntry 8 }

      adslAturPerfCurr15MinLoss  OBJECT-TYPE
          SYNTAX      PerfCurrentCount
          UNITS       "seconds"
          MAX-ACCESS  read-only
          STATUS      current
          DESCRIPTION
              "Count of seconds in the current 15 minute interval
              when there was Loss of Signal."
      ::= { adslAturPerfDataEntry 9 }

      adslAturPerfCurr15MinLprs  OBJECT-TYPE
          SYNTAX      PerfCurrentCount
          UNITS       "seconds"
          MAX-ACCESS  read-only

          STATUS      current
          DESCRIPTION
              "Count of seconds in the current 15 minute interval
              when there was Loss of Power."
      ::= { adslAturPerfDataEntry 10 }

      adslAturPerfCurr15MinESs OBJECT-TYPE
          SYNTAX      PerfCurrentCount
          UNITS       "seconds"
          MAX-ACCESS  read-only
          STATUS      current
          DESCRIPTION
             "Count of Errored Seconds in the current 15 minute
             interval.  The errored second parameter is a count of
             one-second intervals containing one or more crc
             anomalies, or one or more los or sef defects."

      ::= { adslAturPerfDataEntry 11 }

      -- 1-day current and previous performance group
      --
      adslAturPerfCurr1DayTimeElapsed OBJECT-TYPE
          SYNTAX      AdslPerfTimeElapsed(0..86399)
          UNITS       "seconds"
          MAX-ACCESS  read-only
          STATUS      current
          DESCRIPTION
              "Number of seconds that have elapsed since the
              beginning of the current 1-day interval."
      ::= { adslAturPerfDataEntry 12 }

      adslAturPerfCurr1DayLofs  OBJECT-TYPE
          SYNTAX      AdslPerfCurrDayCount
          UNITS       "seconds"
          MAX-ACCESS  read-only
          STATUS      current
          DESCRIPTION
              "Count of the number of seconds when there was Loss
              of Framing during the current day as measured by
              adslAturPerfCurr1DayTimeElapsed."
      ::= { adslAturPerfDataEntry 13 }

      adslAturPerfCurr1DayLoss  OBJECT-TYPE
          SYNTAX      AdslPerfCurrDayCount
          UNITS       "seconds"
          MAX-ACCESS  read-only
          STATUS      current
          DESCRIPTION

              "Count of the number of seconds when there was Loss
              of Signal during the current day as measured by
              adslAturPerfCurr1DayTimeElapsed."
      ::= { adslAturPerfDataEntry 14 }

      adslAturPerfCurr1DayLprs  OBJECT-TYPE
          SYNTAX      AdslPerfCurrDayCount
          UNITS       "seconds"
          MAX-ACCESS  read-only
          STATUS      current
          DESCRIPTION
              "Count of the number of seconds when there was Loss
              of Power during the current day as measured by
              adslAturPerfCurr1DayTimeElapsed."
      ::= { adslAturPerfDataEntry 15 }

 adslAturPerfCurr1DayESs OBJECT-TYPE
          SYNTAX      AdslPerfCurrDayCount
          UNITS       "seconds"
          MAX-ACCESS  read-only
          STATUS      current
          DESCRIPTION
              "Count of Errored Seconds during the current day as
              measured by adslAturPerfCurr1DayTimeElapsed.
              The errored second parameter is a count of
              one-second intervals containing one or more crc
              anomalies, or one or more los or sef defects."
      ::= { adslAturPerfDataEntry 16 }

      adslAturPerfPrev1DayMoniSecs OBJECT-TYPE
          SYNTAX      INTEGER(0..86400)
          UNITS       "seconds"
          MAX-ACCESS  read-only
          STATUS      current
          DESCRIPTION
              "The amount of time in the previous 1-day interval
              over which the performance monitoring information
              is actually counted. This value will be the same as
              the interval duration except in a situation where
              performance monitoring data could not be collected
              for any reason."
      ::= { adslAturPerfDataEntry 17 }

      adslAturPerfPrev1DayLofs  OBJECT-TYPE
          SYNTAX      AdslPerfPrevDayCount
          UNITS       "seconds"
          MAX-ACCESS  read-only
          STATUS      current

          DESCRIPTION
              "Count of seconds in the interval when there was
              Loss of Framing within the most recent previous
              1-day period."
      ::= { adslAturPerfDataEntry 18 }

      adslAturPerfPrev1DayLoss  OBJECT-TYPE
          SYNTAX      AdslPerfPrevDayCount
          UNITS       "seconds"
          MAX-ACCESS  read-only
          STATUS      current
          DESCRIPTION
              "Count of seconds in the interval when there was
              Loss of Signal within the most recent previous
              1-day period."
      ::= { adslAturPerfDataEntry 19 }

      adslAturPerfPrev1DayLprs  OBJECT-TYPE
          SYNTAX      AdslPerfPrevDayCount
          UNITS       "seconds"
          MAX-ACCESS  read-only
          STATUS      current
          DESCRIPTION
              "Count of seconds in the interval when there was
              Loss of Power within the most recent previous
              1-day period."
      ::= { adslAturPerfDataEntry 20 }

      adslAturPerfPrev1DayESs OBJECT-TYPE
          SYNTAX      AdslPerfPrevDayCount
          UNITS       "seconds"
          MAX-ACCESS  read-only
          STATUS      current
          DESCRIPTION
              "Count of Errored Seconds within the most recent
              previous 1-day period. The errored second parameter is
              a count of one-second intervals containing one or more
              crc anomalies, or one or more los or sef defects."
      ::= { adslAturPerfDataEntry 21 }

      adslAtucIntervalTable   OBJECT-TYPE
          SYNTAX          SEQUENCE OF AdslAtucIntervalEntry
          MAX-ACCESS      not-accessible
          STATUS          current
          DESCRIPTION
              "This table provides one row for each ATUC
              performance data collection interval.
              ADSL physical interfaces are

              those ifEntries where ifType is equal to adsl(94)."
      ::= { adslMibObjects 8 }

      adslAtucIntervalEntry   OBJECT-TYPE
          SYNTAX          AdslAtucIntervalEntry
          MAX-ACCESS      not-accessible
          STATUS          current
          DESCRIPTION     "An entry in the adslAtucIntervalTable."
          INDEX           { ifIndex, adslAtucIntervalNumber }
      ::= { adslAtucIntervalTable 1 }

      AdslAtucIntervalEntry ::=
          SEQUENCE {
          adslAtucIntervalNumber          INTEGER,
          adslAtucIntervalLofs            PerfIntervalCount,
          adslAtucIntervalLoss            PerfIntervalCount,
          adslAtucIntervalLols            PerfIntervalCount,
          adslAtucIntervalLprs            PerfIntervalCount,
          adslAtucIntervalESs             PerfIntervalCount,
          adslAtucIntervalInits           PerfIntervalCount,
          adslAtucIntervalValidData       TruthValue
          }

      adslAtucIntervalNumber OBJECT-TYPE
          SYNTAX      INTEGER(1..96)
          MAX-ACCESS  not-accessible
          STATUS      current
          DESCRIPTION
              "Performance Data Interval number 1 is the
              the most recent previous interval; interval
              96 is 24 hours ago.  Intervals 2..96 are
              optional."
      ::= { adslAtucIntervalEntry 1 }

      adslAtucIntervalLofs OBJECT-TYPE
          SYNTAX      PerfIntervalCount
          UNITS       "seconds"
          MAX-ACCESS  read-only
          STATUS      current
          DESCRIPTION
              "Count of seconds in the interval when there was Loss
              of Framing."
      ::= { adslAtucIntervalEntry 2 }

      adslAtucIntervalLoss  OBJECT-TYPE
          SYNTAX      PerfIntervalCount
          UNITS       "seconds"
          MAX-ACCESS  read-only

          STATUS      current
          DESCRIPTION
              "Count of seconds in the interval when there was Loss
              of Signal."
      ::= { adslAtucIntervalEntry 3 }

      adslAtucIntervalLols  OBJECT-TYPE
          SYNTAX      PerfIntervalCount
          UNITS       "seconds"
          MAX-ACCESS  read-only
          STATUS      current
          DESCRIPTION
              "Count of seconds in the interval when there was Loss
              of Link."
      ::= { adslAtucIntervalEntry 4 }

      adslAtucIntervalLprs  OBJECT-TYPE
          SYNTAX      PerfIntervalCount
          UNITS       "seconds"
          MAX-ACCESS  read-only
          STATUS      current
          DESCRIPTION
              "Count of seconds in the interval when there was Loss
              of Power."
      ::= { adslAtucIntervalEntry 5 }

      adslAtucIntervalESs OBJECT-TYPE
          SYNTAX      PerfIntervalCount
          UNITS       "seconds"
          MAX-ACCESS  read-only
          STATUS      current
          DESCRIPTION
              "Count of Errored Seconds in the interval.
              The errored second parameter is a count of
              one-second intervals containing one or more crc
              anomalies, or one or more los or sef defects."
      ::= { adslAtucIntervalEntry 6 }

      adslAtucIntervalInits  OBJECT-TYPE
          SYNTAX      PerfIntervalCount
          MAX-ACCESS  read-only
          STATUS      current
          DESCRIPTION
              "Count of the line initialization attempts
              during the interval. Includes both successful
              and failed attempts."
      ::= { adslAtucIntervalEntry 7 }


      adslAtucIntervalValidData OBJECT-TYPE
          SYNTAX TruthValue
          MAX-ACCESS read-only
          STATUS current
          DESCRIPTION
              "This variable indicates if the data for this
              interval is valid."
      ::= { adslAtucIntervalEntry 8 }

      adslAturIntervalTable   OBJECT-TYPE
          SYNTAX          SEQUENCE OF AdslAturIntervalEntry
          MAX-ACCESS      not-accessible
          STATUS          current
          DESCRIPTION
              "This table provides one row for each ATUR
              performance data collection interval.
              ADSL physical interfaces are those
              ifEntries where ifType is equal to adsl(94)."
      ::= { adslMibObjects 9 }

      adslAturIntervalEntry   OBJECT-TYPE
          SYNTAX          AdslAturIntervalEntry
          MAX-ACCESS      not-accessible
          STATUS          current
          DESCRIPTION     "An entry in the adslAturIntervalTable."
          INDEX           { ifIndex, adslAturIntervalNumber }
      ::= { adslAturIntervalTable 1 }

      AdslAturIntervalEntry ::=
          SEQUENCE {
          adslAturIntervalNumber          INTEGER,
          adslAturIntervalLofs            PerfIntervalCount,
          adslAturIntervalLoss            PerfIntervalCount,
          adslAturIntervalLprs            PerfIntervalCount,
          adslAturIntervalESs             PerfIntervalCount,
          adslAturIntervalValidData       TruthValue
          }

      adslAturIntervalNumber OBJECT-TYPE
          SYNTAX      INTEGER(1..96)
          MAX-ACCESS  not-accessible
          STATUS      current
          DESCRIPTION
              "Performance Data Interval number 1 is the
              the most recent previous interval; interval
              96 is 24 hours ago.  Intervals 2..96 are
              optional."
      ::= { adslAturIntervalEntry 1 }

      adslAturIntervalLofs OBJECT-TYPE
          SYNTAX      PerfIntervalCount
          UNITS       "seconds"
          MAX-ACCESS  read-only
          STATUS      current
          DESCRIPTION
              "Count of seconds in the interval when there was
              Loss of Framing."
      ::= { adslAturIntervalEntry 2 }

      adslAturIntervalLoss  OBJECT-TYPE
          SYNTAX      PerfIntervalCount
          UNITS       "seconds"
          MAX-ACCESS  read-only
          STATUS      current
          DESCRIPTION
              "Count of seconds in the interval when there was
              Loss of Signal."
      ::= { adslAturIntervalEntry 3 }

      adslAturIntervalLprs  OBJECT-TYPE
          SYNTAX      PerfIntervalCount
          UNITS       "seconds"
          MAX-ACCESS  read-only
          STATUS      current
          DESCRIPTION
              "Count of seconds in the interval when there was
              Loss of Power."
      ::= { adslAturIntervalEntry 4 }

      adslAturIntervalESs OBJECT-TYPE
          SYNTAX      PerfIntervalCount
          UNITS       "seconds"
          MAX-ACCESS  read-only
          STATUS      current
          DESCRIPTION
              "Count of Errored Seconds in the interval.
              The errored second parameter is a count of
              one-second intervals containing one or more crc
              anomalies, or one or more los or sef defects."
      ::= { adslAturIntervalEntry 5 }

      adslAturIntervalValidData OBJECT-TYPE
          SYNTAX TruthValue
          MAX-ACCESS read-only
          STATUS current
          DESCRIPTION
              "This variable indicates if the data for this

              interval is valid."
      ::= { adslAturIntervalEntry 6 }

      adslAtucChanPerfDataTable       OBJECT-TYPE
          SYNTAX          SEQUENCE OF AdslAtucChanPerfDataEntry
          MAX-ACCESS      not-accessible
          STATUS          current
          DESCRIPTION
              "This table provides one row for each ATUC channel.
              ADSL channel interfaces are those ifEntries
              where ifType is equal to adslInterleave(124)
              or adslFast(125)."
      ::= { adslMibObjects 10 }

      adslAtucChanPerfDataEntry       OBJECT-TYPE

          SYNTAX          AdslAtucChanPerfDataEntry
          MAX-ACCESS      not-accessible
          STATUS          current
          DESCRIPTION     "An entry in adslAtucChanPerfDataTable."
          INDEX           { ifIndex }
      ::= { adslAtucChanPerfDataTable 1 }

      AdslAtucChanPerfDataEntry ::=
       SEQUENCE {
       adslAtucChanReceivedBlks                 Counter32,
       adslAtucChanTransmittedBlks              Counter32,
       adslAtucChanCorrectedBlks                Counter32,
       adslAtucChanUncorrectBlks                Counter32,
       adslAtucChanPerfValidIntervals           INTEGER,
       adslAtucChanPerfInvalidIntervals         INTEGER,
       adslAtucChanPerfCurr15MinTimeElapsed     AdslPerfTimeElapsed,
       adslAtucChanPerfCurr15MinReceivedBlks    PerfCurrentCount,
       adslAtucChanPerfCurr15MinTransmittedBlks PerfCurrentCount,
       adslAtucChanPerfCurr15MinCorrectedBlks   PerfCurrentCount,
       adslAtucChanPerfCurr15MinUncorrectBlks   PerfCurrentCount,
       adslAtucChanPerfCurr1DayTimeElapsed      AdslPerfTimeElapsed,
       adslAtucChanPerfCurr1DayReceivedBlks     AdslPerfCurrDayCount,
       adslAtucChanPerfCurr1DayTransmittedBlks  AdslPerfCurrDayCount,
       adslAtucChanPerfCurr1DayCorrectedBlks    AdslPerfCurrDayCount,
       adslAtucChanPerfCurr1DayUncorrectBlks    AdslPerfCurrDayCount,
       adslAtucChanPerfPrev1DayMoniSecs         INTEGER,
       adslAtucChanPerfPrev1DayReceivedBlks     AdslPerfPrevDayCount,
       adslAtucChanPerfPrev1DayTransmittedBlks  AdslPerfPrevDayCount,
       adslAtucChanPerfPrev1DayCorrectedBlks    AdslPerfPrevDayCount,
       adslAtucChanPerfPrev1DayUncorrectBlks    AdslPerfPrevDayCount
      }
      -- performance group

      --
      -- Note: block is intended to be the length of the channel
      --       data-block on which the CRC operates. See
      --       adslAtucChanCrcBlockLength for more information.
      --
      adslAtucChanReceivedBlks OBJECT-TYPE
          SYNTAX      Counter32
          MAX-ACCESS  read-only
          STATUS      current
          DESCRIPTION
              "Count of all encoded blocks received on this channel
              since agent reset."
      ::= { adslAtucChanPerfDataEntry 1 }

      adslAtucChanTransmittedBlks  OBJECT-TYPE
          SYNTAX      Counter32
          MAX-ACCESS  read-only
          STATUS      current
          DESCRIPTION
              "Count of all encoded blocks transmitted on this
              channel since agent reset."
      ::= { adslAtucChanPerfDataEntry 2 }

      adslAtucChanCorrectedBlks  OBJECT-TYPE
          SYNTAX      Counter32
          MAX-ACCESS  read-only
          STATUS      current
          DESCRIPTION
              "Count of all blocks received with errors that were
              corrected since agent reset.  These blocks are passed
              on as good data."
      ::= { adslAtucChanPerfDataEntry 3 }

      adslAtucChanUncorrectBlks  OBJECT-TYPE
          SYNTAX      Counter32
          MAX-ACCESS  read-only
          STATUS      current
          DESCRIPTION
              "Count of all blocks received with uncorrectable
              errors since agent reset."
      ::= { adslAtucChanPerfDataEntry 4 }

      -- general 15 min interval information
      --
      adslAtucChanPerfValidIntervals OBJECT-TYPE
          SYNTAX      INTEGER(0..96)
          MAX-ACCESS  read-only
          STATUS      current

          DESCRIPTION
              "The number of previous 15-minute intervals in the
              interval table for which data was collected.  Given
              that <n> is the maximum # of intervals supported.
              The value will be <n> unless the measurement was
              (re-)started within the last (<n>*15) minutes, in which
              case the value will be the number of complete 15
              minute intervals for which the agent has at least
              some data. In certain cases (e.g., in the case
              where the agent is a proxy) it is possible that some
              intervals are unavailable.  In this case, this
              interval is the maximum interval number for
              which data is available."
      ::= { adslAtucChanPerfDataEntry 5 }

      adslAtucChanPerfInvalidIntervals OBJECT-TYPE
          SYNTAX      INTEGER(0..96)
          MAX-ACCESS  read-only
          STATUS      current
          DESCRIPTION
              "The number of intervals in the range from
              0 to the value of adslAtucChanPerfValidIntervals
              for which no data is available. This object
              will typically be zero except in cases where
              the data for some intervals are not available
              (e.g., in proxy situations)."
      ::= { adslAtucChanPerfDataEntry 6 }

      -- 15 min current performance group
      --
      adslAtucChanPerfCurr15MinTimeElapsed OBJECT-TYPE
          SYNTAX      AdslPerfTimeElapsed(0..899)
          UNITS       "seconds"
          MAX-ACCESS  read-only
          STATUS      current
          DESCRIPTION
              "Total elapsed seconds in this interval."
      ::= { adslAtucChanPerfDataEntry 7 }

      adslAtucChanPerfCurr15MinReceivedBlks OBJECT-TYPE
          SYNTAX      PerfCurrentCount
          MAX-ACCESS  read-only
          STATUS      current
          DESCRIPTION
              "Count of all encoded blocks received on this channel
              within the current 15 minute interval."
      ::= { adslAtucChanPerfDataEntry 8 }


      adslAtucChanPerfCurr15MinTransmittedBlks OBJECT-TYPE
          SYNTAX      PerfCurrentCount
          MAX-ACCESS  read-only
          STATUS      current
          DESCRIPTION
              "Count of all encoded blocks transmitted on this
              channel within the current 15 minute interval."
      ::= { adslAtucChanPerfDataEntry 9 }

      adslAtucChanPerfCurr15MinCorrectedBlks  OBJECT-TYPE
          SYNTAX      PerfCurrentCount
          MAX-ACCESS  read-only
          STATUS      current
          DESCRIPTION
              "Count of all blocks received with errors that were
              corrected on this channel within the current 15 minute
              interval."
      ::= { adslAtucChanPerfDataEntry 10 }

      adslAtucChanPerfCurr15MinUncorrectBlks  OBJECT-TYPE
          SYNTAX      PerfCurrentCount
          MAX-ACCESS  read-only
          STATUS      current
          DESCRIPTION
              "Count of all blocks received with uncorrectable
              errors on this channel within the current 15 minute
              interval."
      ::= { adslAtucChanPerfDataEntry 11 }

      -- 1-day current and previous performance group
      --
      adslAtucChanPerfCurr1DayTimeElapsed OBJECT-TYPE
          SYNTAX      AdslPerfTimeElapsed(0..86399)
          UNITS       "seconds"
          MAX-ACCESS  read-only
          STATUS      current
          DESCRIPTION
              "Number of seconds that have elapsed since the
              beginning of the current 1-day interval."
      ::= { adslAtucChanPerfDataEntry 12 }

      adslAtucChanPerfCurr1DayReceivedBlks  OBJECT-TYPE
          SYNTAX      AdslPerfCurrDayCount
          MAX-ACCESS  read-only
          STATUS      current
          DESCRIPTION
              "Count of all encoded blocks received on this
              channel during the current day as measured by

              adslAtucChanPerfCurr1DayTimeElapsed."
      ::= { adslAtucChanPerfDataEntry 13 }

      adslAtucChanPerfCurr1DayTransmittedBlks  OBJECT-TYPE
          SYNTAX      AdslPerfCurrDayCount
          MAX-ACCESS  read-only
          STATUS      current
          DESCRIPTION
              "Count of all encoded blocks transmitted on this
              channel during the current day as measured by
              adslAtucChanPerfCurr1DayTimeElapsed."
      ::= { adslAtucChanPerfDataEntry 14 }

      adslAtucChanPerfCurr1DayCorrectedBlks  OBJECT-TYPE
          SYNTAX      AdslPerfCurrDayCount
          MAX-ACCESS  read-only
          STATUS      current
          DESCRIPTION
              "Count of all blocks received with errors that were
              corrected on this channel during the current day as
              measured by adslAtucChanPerfCurr1DayTimeElapsed."
      ::= { adslAtucChanPerfDataEntry 15 }

      adslAtucChanPerfCurr1DayUncorrectBlks  OBJECT-TYPE
          SYNTAX      AdslPerfCurrDayCount
          MAX-ACCESS  read-only
          STATUS      current
          DESCRIPTION
              "Count of all blocks received with uncorrectable
              errors on this channel during the current day as
              measured by adslAtucChanPerfCurr1DayTimeElapsed."
      ::= { adslAtucChanPerfDataEntry 16 }

      adslAtucChanPerfPrev1DayMoniSecs OBJECT-TYPE
          SYNTAX      INTEGER(0..86400)
          UNITS       "seconds"
          MAX-ACCESS  read-only
          STATUS      current
          DESCRIPTION
              "The amount of time in the previous 1-day interval
              over which the performance monitoring information
              is actually counted. This value will be the same as
              the interval duration except in a situation where
              performance monitoring data could not be collected
              for any reason."
      ::= { adslAtucChanPerfDataEntry 17 }

      adslAtucChanPerfPrev1DayReceivedBlks  OBJECT-TYPE

          SYNTAX      AdslPerfPrevDayCount
          MAX-ACCESS  read-only
          STATUS      current
          DESCRIPTION
              "Count of all encoded blocks received on this
              channel within the most recent previous 1-day
              period."
      ::= { adslAtucChanPerfDataEntry 18 }

      adslAtucChanPerfPrev1DayTransmittedBlks  OBJECT-TYPE
          SYNTAX      AdslPerfPrevDayCount
          MAX-ACCESS  read-only
          STATUS      current
          DESCRIPTION
              "Count of all encoded blocks transmitted on this
              channel within the most recent previous 1-day
              period."
      ::= { adslAtucChanPerfDataEntry 19 }

      adslAtucChanPerfPrev1DayCorrectedBlks  OBJECT-TYPE
          SYNTAX      AdslPerfPrevDayCount
          MAX-ACCESS  read-only
          STATUS      current
          DESCRIPTION
              "Count of all blocks received with errors that were
              corrected on this channel within the most recent
              previous 1-day period."
      ::= { adslAtucChanPerfDataEntry 20 }

      adslAtucChanPerfPrev1DayUncorrectBlks  OBJECT-TYPE
          SYNTAX      AdslPerfPrevDayCount
          MAX-ACCESS  read-only
          STATUS      current
          DESCRIPTION
              "Count of all blocks received with uncorrectable
              errors on this channel within the most recent previous
              1-day period."
      ::= { adslAtucChanPerfDataEntry 21 }

      adslAturChanPerfDataTable       OBJECT-TYPE
          SYNTAX          SEQUENCE OF AdslAturChanPerfDataEntry
          MAX-ACCESS      not-accessible
          STATUS          current
          DESCRIPTION
              "This table provides one row for each ATUR channel.
              ADSL channel interfaces are those ifEntries
              where ifType is equal to adslInterleave(124)
              or adslFast(125)."

      ::= { adslMibObjects 11 }

      adslAturChanPerfDataEntry       OBJECT-TYPE
          SYNTAX          AdslAturChanPerfDataEntry
          MAX-ACCESS      not-accessible
          STATUS          current
          DESCRIPTION     "An entry in adslAturChanPerfDataTable."
          INDEX           { ifIndex }
      ::= { adslAturChanPerfDataTable 1 }

      AdslAturChanPerfDataEntry ::=
       SEQUENCE {
       adslAturChanReceivedBlks                 Counter32,
       adslAturChanTransmittedBlks              Counter32,
       adslAturChanCorrectedBlks                Counter32,
       adslAturChanUncorrectBlks                Counter32,
       adslAturChanPerfValidIntervals           INTEGER,
       adslAturChanPerfInvalidIntervals         INTEGER,
       adslAturChanPerfCurr15MinTimeElapsed     AdslPerfTimeElapsed,
       adslAturChanPerfCurr15MinReceivedBlks    PerfCurrentCount,
       adslAturChanPerfCurr15MinTransmittedBlks PerfCurrentCount,
       adslAturChanPerfCurr15MinCorrectedBlks   PerfCurrentCount,
       adslAturChanPerfCurr15MinUncorrectBlks   PerfCurrentCount,
       adslAturChanPerfCurr1DayTimeElapsed      AdslPerfTimeElapsed,
       adslAturChanPerfCurr1DayReceivedBlks     AdslPerfCurrDayCount,
       adslAturChanPerfCurr1DayTransmittedBlks  AdslPerfCurrDayCount,
       adslAturChanPerfCurr1DayCorrectedBlks    AdslPerfCurrDayCount,
       adslAturChanPerfCurr1DayUncorrectBlks    AdslPerfCurrDayCount,
       adslAturChanPerfPrev1DayMoniSecs         INTEGER,
       adslAturChanPerfPrev1DayReceivedBlks     AdslPerfPrevDayCount,
       adslAturChanPerfPrev1DayTransmittedBlks  AdslPerfPrevDayCount,
       adslAturChanPerfPrev1DayCorrectedBlks    AdslPerfPrevDayCount,
       adslAturChanPerfPrev1DayUncorrectBlks    AdslPerfPrevDayCount
       }
      -- performance group
      --
      -- Note: block is intended to be the length of the channel
      --       data-block on which the CRC operates. See
      --       adslAturChanCrcBlockLength for more information.
      --
      adslAturChanReceivedBlks OBJECT-TYPE
          SYNTAX      Counter32
          MAX-ACCESS  read-only
          STATUS      current
          DESCRIPTION
              "Count of all encoded blocks received on this channel
              since agent reset."
      ::= { adslAturChanPerfDataEntry 1 }

      adslAturChanTransmittedBlks  OBJECT-TYPE
          SYNTAX      Counter32
          MAX-ACCESS  read-only
          STATUS      current
          DESCRIPTION
              "Count of all encoded blocks transmitted on this
              channel since agent reset."
      ::= { adslAturChanPerfDataEntry 2 }

      adslAturChanCorrectedBlks  OBJECT-TYPE
          SYNTAX      Counter32
          MAX-ACCESS  read-only
          STATUS      current
          DESCRIPTION
              "Count of all blocks received with errors that were
              corrected since agent reset.  These blocks are passed
              on as good data."
      ::= { adslAturChanPerfDataEntry 3 }

      adslAturChanUncorrectBlks  OBJECT-TYPE
          SYNTAX      Counter32
          MAX-ACCESS  read-only
          STATUS      current
          DESCRIPTION
              "Count of all blocks received with uncorrectable
              errors since agent reset."
      ::= { adslAturChanPerfDataEntry 4 }

      -- general 15 min interval information
      --
      adslAturChanPerfValidIntervals OBJECT-TYPE
          SYNTAX      INTEGER(0..96)
          MAX-ACCESS  read-only
          STATUS      current
          DESCRIPTION
              "The number of previous 15-minute intervals in the
              interval table for which data was collected.  Given
              that <n> is the maximum # of intervals supported.
              The value will be <n> unless the measurement was
              (re-)started within the last (<n>*15) minutes, in which
              case the value will be the number of complete 15
              minute intervals for which the agent has at least
              some data. In certain cases (e.g., in the case
              where the agent is a proxy) it is possible that some
              intervals are unavailable.  In this case, this
              interval is the maximum interval number for
              which data is available."
      ::= { adslAturChanPerfDataEntry 5 }

      adslAturChanPerfInvalidIntervals OBJECT-TYPE
          SYNTAX      INTEGER(0..96)
          MAX-ACCESS  read-only
          STATUS      current
          DESCRIPTION
              "The number of intervals in the range from
              0 to the value of adslAturChanPerfValidIntervals
              for which no data is available. This object
              will typically be zero except in cases where
              the data for some intervals are not available
              (e.g., in proxy situations)."
      ::= { adslAturChanPerfDataEntry 6 }

      -- 15 min current performance group
      --
      adslAturChanPerfCurr15MinTimeElapsed OBJECT-TYPE
          SYNTAX      AdslPerfTimeElapsed(0..899)
          UNITS       "seconds"
          MAX-ACCESS  read-only
          STATUS      current
          DESCRIPTION
              "Total elapsed seconds in this interval.
              A full interval is 900 seconds."
      ::= { adslAturChanPerfDataEntry 7 }

      adslAturChanPerfCurr15MinReceivedBlks OBJECT-TYPE
          SYNTAX      PerfCurrentCount
          MAX-ACCESS  read-only
          STATUS      current
          DESCRIPTION
              "Count of all encoded blocks received on this
              channel within the current 15 minute interval."
      ::= { adslAturChanPerfDataEntry 8 }

      adslAturChanPerfCurr15MinTransmittedBlks OBJECT-TYPE
          SYNTAX      PerfCurrentCount
          MAX-ACCESS  read-only
          STATUS      current
          DESCRIPTION
              "Count of all encoded blocks transmitted on this
              channel within the current 15 minute interval."
      ::= { adslAturChanPerfDataEntry 9 }

      adslAturChanPerfCurr15MinCorrectedBlks  OBJECT-TYPE
          SYNTAX      PerfCurrentCount
          MAX-ACCESS  read-only
          STATUS      current
          DESCRIPTION

              "Count of all blocks received with errors that were
              corrected on this channel within the current 15 minute
              interval."
      ::= { adslAturChanPerfDataEntry 10 }

      adslAturChanPerfCurr15MinUncorrectBlks  OBJECT-TYPE
          SYNTAX      PerfCurrentCount
          MAX-ACCESS  read-only
          STATUS      current
          DESCRIPTION
              "Count of all blocks received with uncorrectable
              errors on this channel within the current 15 minute
              interval."
      ::= { adslAturChanPerfDataEntry 11 }

      -- 1-day current and previous performance group
      --
      adslAturChanPerfCurr1DayTimeElapsed OBJECT-TYPE
          SYNTAX      AdslPerfTimeElapsed(0..86399)
          UNITS       "seconds"
          MAX-ACCESS  read-only
          STATUS      current
          DESCRIPTION
              "Number of seconds that have elapsed since the
              beginning of the current 1-day interval."
      ::= { adslAturChanPerfDataEntry 12 }

      adslAturChanPerfCurr1DayReceivedBlks  OBJECT-TYPE
          SYNTAX      AdslPerfCurrDayCount
          MAX-ACCESS  read-only
          STATUS      current
          DESCRIPTION
              "Count of all encoded blocks received on this
              channel during the current day as measured by
              adslAturChanPerfCurr1DayTimeElapsed."
      ::= { adslAturChanPerfDataEntry 13 }

      adslAturChanPerfCurr1DayTransmittedBlks  OBJECT-TYPE
          SYNTAX      AdslPerfCurrDayCount
          MAX-ACCESS  read-only
          STATUS      current
          DESCRIPTION
              "Count of all encoded blocks transmitted on this
              channel during the current day as measured by
              adslAturChanPerfCurr1DayTimeElapsed."

      ::= { adslAturChanPerfDataEntry 14 }


      adslAturChanPerfCurr1DayCorrectedBlks  OBJECT-TYPE
          SYNTAX      AdslPerfCurrDayCount
          MAX-ACCESS  read-only
          STATUS      current
          DESCRIPTION
              "Count of all blocks received with errors that were
              corrected on this channel during the current day as
              measured by adslAturChanPerfCurr1DayTimeElapsed."
      ::= { adslAturChanPerfDataEntry 15 }

      adslAturChanPerfCurr1DayUncorrectBlks  OBJECT-TYPE
          SYNTAX      AdslPerfCurrDayCount
          MAX-ACCESS  read-only
          STATUS      current
          DESCRIPTION
              "Count of all blocks received with uncorrectable
              errors on this channel during the current day as
              measured by adslAturChanPerfCurr1DayTimeElapsed."
      ::= { adslAturChanPerfDataEntry 16 }

      adslAturChanPerfPrev1DayMoniSecs OBJECT-TYPE
          SYNTAX      INTEGER(0..86400)
          UNITS       "seconds"
          MAX-ACCESS  read-only
          STATUS      current
          DESCRIPTION
              "The amount of time in the previous 1-day interval
              over which the performance monitoring information
              is actually counted. This value will be the same as
              the interval duration except in a situation where
              performance monitoring data could not be collected
              for any reason."
      ::= { adslAturChanPerfDataEntry 17 }

      adslAturChanPerfPrev1DayReceivedBlks  OBJECT-TYPE
          SYNTAX      AdslPerfPrevDayCount
          MAX-ACCESS  read-only
          STATUS      current
          DESCRIPTION
              "Count of all encoded blocks received on this
              channel within the most recent previous 1-day
              period."
      ::= { adslAturChanPerfDataEntry 18 }

      adslAturChanPerfPrev1DayTransmittedBlks  OBJECT-TYPE
          SYNTAX      AdslPerfPrevDayCount
          MAX-ACCESS  read-only
          STATUS      current

          DESCRIPTION
              "Count of all encoded blocks transmitted on this
              channel within the most recent previous 1-day
              period."
      ::= { adslAturChanPerfDataEntry 19 }

      adslAturChanPerfPrev1DayCorrectedBlks  OBJECT-TYPE
          SYNTAX      AdslPerfPrevDayCount
          MAX-ACCESS  read-only
          STATUS      current
          DESCRIPTION
              "Count of all blocks received with errors that were
              corrected on this channel within the most recent
              previous 1-day period."
      ::= { adslAturChanPerfDataEntry 20 }

      adslAturChanPerfPrev1DayUncorrectBlks  OBJECT-TYPE
          SYNTAX      AdslPerfPrevDayCount
          MAX-ACCESS  read-only
          STATUS      current
          DESCRIPTION
              "Count of all blocks received with uncorrectable
              errors on this channel within the most recent previous
              1-day period."
      ::= { adslAturChanPerfDataEntry 21 }

      adslAtucChanIntervalTable   OBJECT-TYPE
          SYNTAX          SEQUENCE OF AdslAtucChanIntervalEntry
          MAX-ACCESS      not-accessible
          STATUS          current
          DESCRIPTION
              "This table provides one row for each ATUC channel's
              performance data collection interval.
              ADSL channel interfaces are those ifEntries
              where ifType is equal to adslInterleave(124)
              or adslFast(125)."
      ::= { adslMibObjects 12 }

      adslAtucChanIntervalEntry   OBJECT-TYPE
          SYNTAX          AdslAtucChanIntervalEntry
          MAX-ACCESS      not-accessible
          STATUS          current
          DESCRIPTION     "An entry in the adslAtucIntervalTable."
          INDEX           { ifIndex, adslAtucChanIntervalNumber }
      ::= { adslAtucChanIntervalTable 1 }

      AdslAtucChanIntervalEntry ::=
          SEQUENCE {

          adslAtucChanIntervalNumber          INTEGER,
          adslAtucChanIntervalReceivedBlks    PerfIntervalCount,
          adslAtucChanIntervalTransmittedBlks PerfIntervalCount,
          adslAtucChanIntervalCorrectedBlks   PerfIntervalCount,
          adslAtucChanIntervalUncorrectBlks   PerfIntervalCount,
          adslAtucChanIntervalValidData       TruthValue
          }
      adslAtucChanIntervalNumber OBJECT-TYPE
          SYNTAX      INTEGER(1..96)
          MAX-ACCESS  not-accessible
          STATUS      current
          DESCRIPTION
              "Performance Data Interval number 1 is the
              the most recent previous interval; interval
              96 is 24 hours ago.  Intervals 2..96 are
              optional."
      ::= { adslAtucChanIntervalEntry 1 }

      adslAtucChanIntervalReceivedBlks OBJECT-TYPE
          SYNTAX      PerfIntervalCount
          MAX-ACCESS  read-only
          STATUS      current
          DESCRIPTION
              "Count of all encoded blocks received on this channel
              during this interval."
      ::= { adslAtucChanIntervalEntry 2 }

      adslAtucChanIntervalTransmittedBlks  OBJECT-TYPE
          SYNTAX      PerfIntervalCount
          MAX-ACCESS  read-only
          STATUS      current
          DESCRIPTION
              "Count of all encoded blocks transmitted on this
              channel during this interval."
      ::= { adslAtucChanIntervalEntry 3 }

      adslAtucChanIntervalCorrectedBlks  OBJECT-TYPE
          SYNTAX      PerfIntervalCount
          MAX-ACCESS  read-only
          STATUS      current
          DESCRIPTION
              "Count of all blocks received with errors that were
              corrected on this channel during this interval."
      ::= { adslAtucChanIntervalEntry 4 }

      adslAtucChanIntervalUncorrectBlks  OBJECT-TYPE
          SYNTAX      PerfIntervalCount
          MAX-ACCESS  read-only

          STATUS      current
          DESCRIPTION
              "Count of all blocks received with uncorrectable
              errors on this channel during this interval."
      ::= { adslAtucChanIntervalEntry 5 }

      adslAtucChanIntervalValidData OBJECT-TYPE
          SYNTAX TruthValue
          MAX-ACCESS read-only
          STATUS current
          DESCRIPTION
              "This variable indicates if the data for this
              interval is valid."
      ::= { adslAtucChanIntervalEntry 6 }

      adslAturChanIntervalTable   OBJECT-TYPE
          SYNTAX          SEQUENCE OF AdslAturChanIntervalEntry
          MAX-ACCESS      not-accessible
          STATUS          current
          DESCRIPTION
              "This table provides one row for each ATUR channel's
              performance data collection interval.
              ADSL channel interfaces are those ifEntries
              where ifType is equal to adslInterleave(124)
              or adslFast(125)."
      ::= { adslMibObjects 13 }

      adslAturChanIntervalEntry   OBJECT-TYPE
          SYNTAX          AdslAturChanIntervalEntry
          MAX-ACCESS      not-accessible
          STATUS          current
          DESCRIPTION     "An entry in the adslAturIntervalTable."
          INDEX           { ifIndex, adslAturChanIntervalNumber }
      ::= { adslAturChanIntervalTable 1 }

      AdslAturChanIntervalEntry ::=
          SEQUENCE {
          adslAturChanIntervalNumber               INTEGER,
          adslAturChanIntervalReceivedBlks         PerfIntervalCount,
          adslAturChanIntervalTransmittedBlks      PerfIntervalCount,
          adslAturChanIntervalCorrectedBlks        PerfIntervalCount,
          adslAturChanIntervalUncorrectBlks        PerfIntervalCount,
          adslAturChanIntervalValidData            TruthValue
          }
      adslAturChanIntervalNumber OBJECT-TYPE
          SYNTAX      INTEGER(1..96)
          MAX-ACCESS  not-accessible
          STATUS      current

          DESCRIPTION
              "Performance Data Interval number 1 is the
              the most recent previous interval; interval
              96 is 24 hours ago.  Intervals 2..96 are
              optional."
      ::= { adslAturChanIntervalEntry 1 }

      adslAturChanIntervalReceivedBlks OBJECT-TYPE
          SYNTAX      PerfIntervalCount
          MAX-ACCESS  read-only
          STATUS      current
          DESCRIPTION
              "Count of all encoded blocks received on this channel
              during this interval."
      ::= { adslAturChanIntervalEntry 2 }

      adslAturChanIntervalTransmittedBlks  OBJECT-TYPE
          SYNTAX      PerfIntervalCount
          MAX-ACCESS  read-only
          STATUS      current
          DESCRIPTION
              "Count of all encoded blocks transmitted on this
              channel during this interval."
      ::= { adslAturChanIntervalEntry 3 }

      adslAturChanIntervalCorrectedBlks  OBJECT-TYPE
          SYNTAX      PerfIntervalCount
          MAX-ACCESS  read-only
          STATUS      current
          DESCRIPTION
              "Count of all blocks received with errors that were
              corrected on this channel during this interval."
      ::= { adslAturChanIntervalEntry 4 }

      adslAturChanIntervalUncorrectBlks  OBJECT-TYPE
          SYNTAX      PerfIntervalCount
          MAX-ACCESS  read-only
          STATUS      current
          DESCRIPTION
              "Count of all blocks received with uncorrectable
              errors on this channel during this interval."
      ::= { adslAturChanIntervalEntry 5 }

      adslAturChanIntervalValidData OBJECT-TYPE
          SYNTAX TruthValue
          MAX-ACCESS read-only
          STATUS current
          DESCRIPTION

              "This variable indicates if the data for this
              interval is valid."
      ::= { adslAturChanIntervalEntry 6 }

      -- Profile Group
      --

      adslLineConfProfileTable    OBJECT-TYPE
          SYNTAX          SEQUENCE OF AdslLineConfProfileEntry
          MAX-ACCESS      not-accessible
          STATUS          current
          DESCRIPTION
              "This table contains information on the ADSL line
              configuration.  One entry in this table reflects a
              profile defined by a manager which can be used to
              configure the ADSL line."
      ::= { adslMibObjects 14}

      adslLineConfProfileEntry    OBJECT-TYPE
          SYNTAX          AdslLineConfProfileEntry
          MAX-ACCESS      not-accessible
          STATUS          current
          DESCRIPTION
              "Each entry consists of a list of parameters that
              represents the configuration of an ADSL modem.

              When `dynamic' profiles are implemented, a default
              profile will always exist.  This profile's name will
              be set to `DEFVAL' and its parameters will be set
              to vendor specific values, unless otherwise specified
              in this document.

              When `static' profiles are implemented, profiles
              are automaticly created or destroyed as ADSL
              physical lines are discovered and removed by
              the system.  The name of the profile will be
              equivalent to the decimal value of the line's
              interface index.
              "
          INDEX { IMPLIED adslLineConfProfileName}
      ::= { adslLineConfProfileTable 1}

      AdslLineConfProfileEntry ::=
          SEQUENCE {
          adslLineConfProfileName               SnmpAdminString,
          adslAtucConfRateMode                  INTEGER,
          adslAtucConfRateChanRatio             INTEGER,
          adslAtucConfTargetSnrMgn              INTEGER,

          adslAtucConfMaxSnrMgn                 INTEGER,
          adslAtucConfMinSnrMgn                 INTEGER,
          adslAtucConfDownshiftSnrMgn           INTEGER,
          adslAtucConfUpshiftSnrMgn             INTEGER,
          adslAtucConfMinUpshiftTime            INTEGER,
          adslAtucConfMinDownshiftTime          INTEGER,
          adslAtucChanConfFastMinTxRate         Unsigned32,
          adslAtucChanConfInterleaveMinTxRate   Unsigned32,
          adslAtucChanConfFastMaxTxRate         Unsigned32,
          adslAtucChanConfInterleaveMaxTxRate   Unsigned32,
          adslAtucChanConfMaxInterleaveDelay    INTEGER,
          adslAturConfRateMode                  INTEGER,
          adslAturConfRateChanRatio             INTEGER,
          adslAturConfTargetSnrMgn              INTEGER,
          adslAturConfMaxSnrMgn                 INTEGER,
          adslAturConfMinSnrMgn                 INTEGER,
          adslAturConfDownshiftSnrMgn           INTEGER,
          adslAturConfUpshiftSnrMgn             INTEGER,
          adslAturConfMinUpshiftTime            INTEGER,
          adslAturConfMinDownshiftTime          INTEGER,
          adslAturChanConfFastMinTxRate         Unsigned32,
          adslAturChanConfInterleaveMinTxRate   Unsigned32,
          adslAturChanConfFastMaxTxRate         Unsigned32,
          adslAturChanConfInterleaveMaxTxRate   Unsigned32,
          adslAturChanConfMaxInterleaveDelay    INTEGER,
          adslLineConfProfileRowStatus          RowStatus
      }

      adslLineConfProfileName    OBJECT-TYPE
              SYNTAX          SnmpAdminString (SIZE (1..32))
              MAX-ACCESS      not-accessible
              STATUS          current
              DESCRIPTION
              "This object is used by the line configuration table
              in order to identify a row of this table.

              When `dynamic' profiles are implemented, the profile
              name is user specified.  Also, the system will always
              provide a default profile whose name is `DEFVAL'.

              When `static' profiles are implemented, there is an
              one-to-one relationship between each line and its
              profile.  In which case, the profile name will
              need to algorithmicly represent the Line's ifIndex.
              Therefore, the profile's name is a decimalized string
              of the ifIndex that is fixed-length (i.e., 10) with
              leading zero(s).  For example, the profile name for
              ifIndex which equals '15' will be '0000000015'."

      ::= { adslLineConfProfileEntry 1 }

      adslAtucConfRateMode OBJECT-TYPE
          SYNTAX      INTEGER {
              fixed (1),              -- no rate adaptation
              adaptAtStartup (2),     -- perform rate adaptation
                                      -- only at initialization
              adaptAtRuntime (3)      -- perform rate adaptation at
                                      -- any time
          }
          MAX-ACCESS  read-create
          STATUS      current
          DESCRIPTION
              "Defines what form of transmit rate adaptation is
              configured on this modem.  See ADSL Forum TR-005 [3]
              for more information."
      ::= { adslLineConfProfileEntry 2 }

      adslAtucConfRateChanRatio OBJECT-TYPE
          SYNTAX      INTEGER(0..100)
          UNITS        "%"
          MAX-ACCESS  read-create
          STATUS      current
          DESCRIPTION
              "Configured allocation ratio of excess transmit
              bandwidth between fast and interleaved channels.  Only
              applies when two channel mode and RADSL are supported.
              Distribute bandwidth on each channel in excess of the
              corresponding ChanConfMinTxRate so that:
              adslAtucConfRateChanRatio =

                      [Fast / (Fast + Interleaved)] * 100

              In other words this value is the fast channel
              percentage."
      ::= { adslLineConfProfileEntry 3 }

    adslAtucConfTargetSnrMgn OBJECT-TYPE
          SYNTAX      INTEGER (0..310)
          UNITS       "tenth dB"
          MAX-ACCESS  read-create
          STATUS      current
          DESCRIPTION
              "Configured Target Signal/Noise Margin.
              This is the Noise Margin the modem must achieve
              with a BER of 10-7 or better to successfully complete
              initialization."
      ::= { adslLineConfProfileEntry 4 }

    adslAtucConfMaxSnrMgn OBJECT-TYPE
          SYNTAX      INTEGER (0..310)
          UNITS       "tenth dB"
          MAX-ACCESS  read-create
          STATUS      current
          DESCRIPTION
              "Configured Maximum acceptable Signal/Noise Margin.
              If the Noise Margin is above this the modem should
              attempt to reduce its power output to optimize its
              operation."
      ::= { adslLineConfProfileEntry 5 }

      adslAtucConfMinSnrMgn  OBJECT-TYPE
          SYNTAX      INTEGER (0..310)
          UNITS       "tenth dB"
          MAX-ACCESS  read-create
          STATUS      current
          DESCRIPTION
              "Configured Minimum acceptable Signal/Noise Margin.
              If the noise margin falls below this level, the modem
              should attempt to increase its power output.  If that
              is not possible the modem will attempt to
              re-initialize or shut down."
      ::= { adslLineConfProfileEntry 6 }

      adslAtucConfDownshiftSnrMgn  OBJECT-TYPE
          SYNTAX      INTEGER (0..310)
          UNITS       "tenth dB"
          MAX-ACCESS  read-create
          STATUS      current
          DESCRIPTION
              "Configured Signal/Noise Margin for rate downshift.
              If the noise margin falls below this level, the modem
              should attempt to decrease its transmit rate.  In
              the case that RADSL mode is not present,
              the value will be `0'."
      ::= { adslLineConfProfileEntry 7 }

      adslAtucConfUpshiftSnrMgn  OBJECT-TYPE
          SYNTAX      INTEGER (0..310)
          UNITS       "tenth dB"
          MAX-ACCESS  read-create
          STATUS      current
          DESCRIPTION
              "Configured Signal/Noise Margin for rate upshift.
              If the noise margin rises above this level, the modem
              should attempt to increase its transmit rate.    In
              the case that RADSL is not present, the value will

              be `0'."
      ::= { adslLineConfProfileEntry 8 }

      adslAtucConfMinUpshiftTime OBJECT-TYPE
          SYNTAX      INTEGER(0..16383)
          UNITS       "seconds"
          MAX-ACCESS  read-create
          STATUS      current
          DESCRIPTION
              "Minimum time that the current margin is above
              UpshiftSnrMgn before an upshift occurs.
              In the case that RADSL is not present, the value will
              be `0'."
      ::= { adslLineConfProfileEntry 9 }
     adslAtucConfMinDownshiftTime OBJECT-TYPE
          SYNTAX      INTEGER(0..16383)
          UNITS       "seconds"
          MAX-ACCESS  read-create
          STATUS      current
          DESCRIPTION
              "Minimum time that the current margin is below
              DownshiftSnrMgn before a downshift occurs.
              In the case that RADSL mode is not present,
              the value will be `0'."
      ::= { adslLineConfProfileEntry 10 }

      adslAtucChanConfFastMinTxRate  OBJECT-TYPE
          SYNTAX      Unsigned32
          UNITS       "bps"
          MAX-ACCESS  read-create
          STATUS      current
          DESCRIPTION
              "Configured Minimum Transmit rate for `Fast' channels,
              in bps.  See adslAtucConfRateChanRatio for information
              regarding RADSL mode and ATUR transmit rate for
              ATUC receive rates."
      ::= { adslLineConfProfileEntry 11 }

      adslAtucChanConfInterleaveMinTxRate OBJECT-TYPE
          SYNTAX      Unsigned32
          UNITS       "bps"
          MAX-ACCESS  read-create
          STATUS      current
          DESCRIPTION
              "Configured Minimum Transmit rate for `Interleave'
              channels, in bps.  See adslAtucConfRateChanRatio for
              information regarding RADSL mode and see
              ATUR transmit rate for receive rates."

      ::= { adslLineConfProfileEntry 12 }

      adslAtucChanConfFastMaxTxRate  OBJECT-TYPE
          SYNTAX      Unsigned32
          UNITS       "bps"
          MAX-ACCESS  read-create
          STATUS      current
          DESCRIPTION
              "Configured Maximum Transmit rate for `Fast' channels,
              in bps.  See adslAtucConfRateChanRatio for information
              regarding RADSL mode and see ATUR transmit rate for
              ATUC receive rates."
      ::= { adslLineConfProfileEntry 13 }

      adslAtucChanConfInterleaveMaxTxRate OBJECT-TYPE
          SYNTAX      Unsigned32
          UNITS       "bps"
          MAX-ACCESS  read-create
          STATUS      current
          DESCRIPTION
              "Configured Maximum Transmit rate for `Interleave'
              channels, in bps.  See adslAtucConfRateChanRatio for
              information regarding RADSL mode and ATUR transmit
              rate for ATUC receive rates."
      ::= { adslLineConfProfileEntry 14 }

      adslAtucChanConfMaxInterleaveDelay OBJECT-TYPE
          SYNTAX      INTEGER(0..255)
          UNITS        "milli-seconds"
          MAX-ACCESS  read-create
          STATUS      current
          DESCRIPTION
              "Configured maximum Interleave Delay for this channel.

              Interleave delay applies only to the interleave channel
              and defines the mapping (relative spacing) between
              subsequent input bytes at the interleaver input and
              their placement in the bit stream at the interleaver
              output.  Larger numbers provide greater separation
              between consecutive input bytes in the output bit
              stream allowing for improved impulse noise immunity
              at the expense of payload latency."
      ::= { adslLineConfProfileEntry 15 }

      adslAturConfRateMode OBJECT-TYPE
          SYNTAX      INTEGER {
              fixed (1),              -- no rate adaptation
              adaptAtStartup (2),     -- perform rate adaptation

                                      -- only at initialization
              adaptAtRuntime (3)      -- perform rate adaptation at
                                      -- any time
          }
          MAX-ACCESS  read-create
          STATUS      current
          DESCRIPTION
              "Defines what form of transmit rate adaptation is
              configured on this modem.  See ADSL Forum TR-005 [3]
              for more information."
      ::= { adslLineConfProfileEntry 16 }

      adslAturConfRateChanRatio OBJECT-TYPE
          SYNTAX      INTEGER(0..100)
          UNITS        "%"
          MAX-ACCESS  read-create
          STATUS      current
          DESCRIPTION
              "Configured allocation ratio of excess transmit
              bandwidth between fast and interleaved channels.  Only
              applies when two channel mode and RADSL are supported.
              Distribute bandwidth on each channel in excess of the
              corresponding ChanConfMinTxRate so that:
              adslAturConfRateChanRatio =

                      [Fast / (Fast + Interleaved)] * 100

              In other words this value is the fast channel
              percentage."
      ::= { adslLineConfProfileEntry 17 }

    adslAturConfTargetSnrMgn OBJECT-TYPE
          SYNTAX      INTEGER (0..310)
          UNITS       "tenth dB"
          MAX-ACCESS  read-create
          STATUS      current
          DESCRIPTION
              "Configured Target Signal/Noise Margin.
              This is the Noise Margin the modem must achieve
              with a BER of 10-7 or better to successfully complete
              initialization."
      ::= { adslLineConfProfileEntry 18 }

    adslAturConfMaxSnrMgn OBJECT-TYPE
          SYNTAX      INTEGER (0..310)
          UNITS       "tenth dB"
          MAX-ACCESS  read-create
          STATUS      current

          DESCRIPTION
              "Configured Maximum acceptable Signal/Noise Margin.
              If the Noise Margin is above this the modem should
              attempt to reduce its power output to optimize its
              operation."
      ::= { adslLineConfProfileEntry 19 }

     adslAturConfMinSnrMgn  OBJECT-TYPE
          SYNTAX      INTEGER (0..310)
          UNITS       "tenth dB"
          MAX-ACCESS  read-create
          STATUS      current
          DESCRIPTION
              "Configured Minimum acceptable Signal/Noise Margin.
              If the noise margin falls below this level, the modem
              should attempt to increase its power output.  If that
              is not possible the modem will attempt to
              re-initialize or shut down."
      ::= { adslLineConfProfileEntry 20 }

      adslAturConfDownshiftSnrMgn  OBJECT-TYPE
          SYNTAX      INTEGER (0..310)
          UNITS       "tenth dB"
          MAX-ACCESS  read-create
          STATUS      current
          DESCRIPTION
              "Configured Signal/Noise Margin for rate downshift.
              If the noise margin falls below this level, the modem
              should attempt to decrease its transmit rate.
              In the case that RADSL mode is not present,
              the value will be `0'."
      ::= { adslLineConfProfileEntry 21 }

      adslAturConfUpshiftSnrMgn  OBJECT-TYPE
          SYNTAX      INTEGER (0..310)
          UNITS       "tenth dB"
          MAX-ACCESS  read-create
          STATUS      current
          DESCRIPTION
              "Configured Signal/Noise Margin for rate upshift.
              If the noise margin rises above this level, the modem
              should attempt to increase its transmit rate.
              In the case that RADSL is not present,
              the value will be `0'."
      ::= { adslLineConfProfileEntry 22 }

      adslAturConfMinUpshiftTime OBJECT-TYPE
          SYNTAX      INTEGER(0..16383)

          UNITS       "seconds"
          MAX-ACCESS  read-create
          STATUS      current
          DESCRIPTION
              "Minimum time that the current margin is above
              UpshiftSnrMgn before an upshift occurs.
              In the case that RADSL is not present, the value will
              be `0'."
      ::= { adslLineConfProfileEntry 23 }

     adslAturConfMinDownshiftTime OBJECT-TYPE
          SYNTAX      INTEGER(0..16383)
          UNITS       "seconds"
          MAX-ACCESS  read-create
          STATUS      current
          DESCRIPTION
              "Minimum time that the current margin is below
              DownshiftSnrMgn before a downshift occurs.
              In the case that RADSL mode is not present,
              the value will be `0'."
      ::= { adslLineConfProfileEntry 24 }

      adslAturChanConfFastMinTxRate  OBJECT-TYPE
          SYNTAX      Unsigned32
          UNITS       "bps"
          MAX-ACCESS  read-create
          STATUS      current
          DESCRIPTION
              "Configured Minimum Transmit rate for `Fast' channels,
              in bps.  See adslAturConfRateChanRatio for information
              regarding RADSL mode and ATUC transmit rate
              for ATUR receive rates."
      ::= { adslLineConfProfileEntry 25 }

      adslAturChanConfInterleaveMinTxRate OBJECT-TYPE
          SYNTAX      Unsigned32
          UNITS       "bps"
          MAX-ACCESS  read-create
          STATUS      current
          DESCRIPTION
              "Configured Minimum Transmit rate for `Interleave'
              channels, in bps.  See adslAturConfRateChanRatio for
              information regarding RADSL mode and ATUC transmit rate
              for ATUR receive rates."
      ::= { adslLineConfProfileEntry 26 }

      adslAturChanConfFastMaxTxRate  OBJECT-TYPE
          SYNTAX      Unsigned32

          UNITS       "bps"
          MAX-ACCESS  read-create
          STATUS      current
          DESCRIPTION
              "Configured Maximum Transmit rate for `Fast' channels,
              in bps.  See adslAturConfRateChanRatio for information
              regarding RADSL mode and ATUC transmit rate
              for ATUR receive rates."
      ::= { adslLineConfProfileEntry 27 }

      adslAturChanConfInterleaveMaxTxRate OBJECT-TYPE
          SYNTAX      Unsigned32
          UNITS       "bps"
          MAX-ACCESS  read-create
          STATUS      current
          DESCRIPTION
              "Configured Maximum Transmit rate for `Interleave'
              channels, in bps.  See adslAturConfRateChanRatio for
              information regarding RADSL mode and see
              ATUC transmit rate for ATUR receive rates."
      ::= { adslLineConfProfileEntry 28 }

      adslAturChanConfMaxInterleaveDelay OBJECT-TYPE
          SYNTAX      INTEGER(0..255)
          UNITS        "milli-seconds"
          MAX-ACCESS  read-create
          STATUS      current
          DESCRIPTION
              "Configured maximum Interleave Delay for this channel.

              Interleave delay applies only to the interleave channel
              and defines the mapping (relative spacing) between
              subsequent input bytes at the interleaver input and
              their placement in the bit stream at the interleaver
              output.  Larger numbers provide greater separation
              between consecutive input bytes in the output bit
              stream allowing for improved impulse noise immunity
              at the expense of payload latency."
      ::= { adslLineConfProfileEntry 29 }

      adslLineConfProfileRowStatus OBJECT-TYPE
          SYNTAX          RowStatus
          MAX-ACCESS      read-create
          STATUS          current
          DESCRIPTION
              "This object is used to create a new row or modify or
              delete an existing row in this table.


              A profile activated by setting this object to
              `active'.  When `active' is set, the system
              will validate the profile.

              Before a profile can be deleted or taken out of
              service, (by setting this object to `destroy' or
              `outOfService') it must be first unreferenced
              from all associated lines.

              If the implementator of this MIB has chosen not
              to implement `dynamic assignment' of profiles, this
              object's MIN-ACCESS is read-only and its value
              is always to be `active'."
      ::= { adslLineConfProfileEntry 30 }

      adslLineAlarmConfProfileTable    OBJECT-TYPE
          SYNTAX          SEQUENCE OF AdslLineAlarmConfProfileEntry
          MAX-ACCESS      not-accessible
          STATUS          current
          DESCRIPTION
              "This table contains information on the ADSL line
              configuration.  One entry in this table reflects a
              profile defined by a manager which can be used to
              configure the modem for a physical line"
      ::= { adslMibObjects 15}

      adslLineAlarmConfProfileEntry    OBJECT-TYPE
          SYNTAX          AdslLineAlarmConfProfileEntry
          MAX-ACCESS      not-accessible
          STATUS          current
          DESCRIPTION
              "Each entry consists of a list of parameters that
              represents the configuration of an ADSL modem.

              When `dynamic' profiles are implemented, a default
              profile will always exist.  This profile's name will
              be set to `DEFVAL' and its parameters will be set to
              vendor specific values, unless otherwise specified
              in this document.

              When `static' profiles are implemented, profiles
              are automaticly created or destroyed as ADSL
              physical lines are discovered and removed by
              the system.  The name of the profile will be
              equivalent to the decimal value of the line's
              interface index.
              "
          INDEX { IMPLIED adslLineAlarmConfProfileName}

      ::= { adslLineAlarmConfProfileTable 1}

      AdslLineAlarmConfProfileEntry ::=
          SEQUENCE {
          adslLineAlarmConfProfileName          SnmpAdminString,
          adslAtucThresh15MinLofs               INTEGER,
          adslAtucThresh15MinLoss               INTEGER,
          adslAtucThresh15MinLols               INTEGER,
          adslAtucThresh15MinLprs               INTEGER,
          adslAtucThresh15MinESs                INTEGER,
          adslAtucThreshFastRateUp              Unsigned32,
          adslAtucThreshInterleaveRateUp        Unsigned32,
          adslAtucThreshFastRateDown            Unsigned32,
          adslAtucThreshInterleaveRateDown      Unsigned32,
          adslAtucInitFailureTrapEnable         INTEGER,
          adslAturThresh15MinLofs               INTEGER,
          adslAturThresh15MinLoss               INTEGER,
          adslAturThresh15MinLprs               INTEGER,
          adslAturThresh15MinESs                INTEGER,
          adslAturThreshFastRateUp              Unsigned32,
          adslAturThreshInterleaveRateUp        Unsigned32,
          adslAturThreshFastRateDown            Unsigned32,
          adslAturThreshInterleaveRateDown      Unsigned32,
          adslLineAlarmConfProfileRowStatus     RowStatus
          }

      adslLineAlarmConfProfileName    OBJECT-TYPE
          SYNTAX          SnmpAdminString (SIZE (1..32))
          MAX-ACCESS      not-accessible
          STATUS          current
          DESCRIPTION
              "This object is used by the line alarm configuration
              table in order to identify a row of this table.

              When `dynamic' profiles are implemented, the profile
              name is user specified.  Also, the system will always
              provide a default profile whose name is `DEFVAL'.

              When `static' profiles are implemented, there is an
              one-to-one relationship between each line and its
              profile.  In which case, the profile name will
              need to algorithmicly represent the Line's ifIndex.
              Therefore, the profile's name is a decimalized string
              of the ifIndex that is fixed-length (i.e., 10) with
              leading zero(s).  For example, the profile name for
              ifIndex which equals '15' will be '0000000015'."
      ::= { adslLineAlarmConfProfileEntry 1}


      adslAtucThresh15MinLofs OBJECT-TYPE
          SYNTAX      INTEGER(0..900)
          UNITS       "seconds"
          MAX-ACCESS  read-create
          STATUS      current
          DESCRIPTION
              "The number of Loss of Frame Seconds
              encountered by an ADSL interface within any given 15
              minutes performance data collection period, which
              causes the SNMP agent to send an
              adslAtucPerfLofsThreshTrap.
              One trap will be sent per interval per interface.
              A value of `0' will disable the trap."
      ::= { adslLineAlarmConfProfileEntry 2}

      adslAtucThresh15MinLoss  OBJECT-TYPE
          SYNTAX      INTEGER(0..900)
          UNITS       "seconds"
          MAX-ACCESS  read-create
          STATUS      current
          DESCRIPTION
              "The number of Loss of Signal Seconds
              encountered by an ADSL interface within any given 15
              minutes performance data collection period, which
              causes the SNMP agent to send an
              adslAtucPerfLossThreshTrap.
              One trap will be sent per interval per interface.
              A value of `0' will disable the trap."
      ::= { adslLineAlarmConfProfileEntry 3}

      adslAtucThresh15MinLols  OBJECT-TYPE
          SYNTAX      INTEGER(0..900)
          UNITS       "seconds"
          MAX-ACCESS  read-create
          STATUS      current
          DESCRIPTION
              "The number of Loss of Link Seconds
              encountered by an ADSL interface within any given 15
              minutes performance data collection period, which
              causes the SNMP agent to send an
              adslAtucPerfLolsThreshTrap.
              One trap will be sent per interval per interface.
              A value of `0' will disable the trap."
      ::= { adslLineAlarmConfProfileEntry 4}

      adslAtucThresh15MinLprs  OBJECT-TYPE
          SYNTAX      INTEGER(0..900)
          UNITS       "seconds"

          MAX-ACCESS  read-create
          STATUS      current
          DESCRIPTION
              "The number of Loss of Power Seconds
              encountered by an ADSL interface within any given 15
              minutes performance data collection period, which
              causes the SNMP agent to send an
              adslAtucPerfLprsThreshTrap.
              One trap will be sent per interval per interface.
              A value of `0' will disable the trap."
      ::= { adslLineAlarmConfProfileEntry 5}

      adslAtucThresh15MinESs  OBJECT-TYPE
          SYNTAX      INTEGER(0..900)
          UNITS       "seconds"
          MAX-ACCESS  read-create
          STATUS      current
          DESCRIPTION
              "The number of Errored Seconds
              encountered by an ADSL interface within any given 15
              minutes performance data collection period, which
              causes the SNMP agent to send an
              adslAtucPerfESsThreshTrap.
              One trap will be sent per interval per interface.
              A value of `0' will disable the trap."
      ::= { adslLineAlarmConfProfileEntry 6}

      adslAtucThreshFastRateUp OBJECT-TYPE
          SYNTAX      Unsigned32
          UNITS       "bps"
          MAX-ACCESS  read-create
          STATUS      current
          DESCRIPTION
              "Applies to `Fast' channels only.
              Configured change in rate causing an
              adslAtucRateChangeTrap. A trap is produced when:
              ChanCurrTxRate >= ChanPrevTxRate plus the value of
              this object. A value of `0' will disable the trap."
      ::= { adslLineAlarmConfProfileEntry 7}

      adslAtucThreshInterleaveRateUp OBJECT-TYPE
          SYNTAX      Unsigned32
          UNITS       "bps"
          MAX-ACCESS  read-create
          STATUS      current
          DESCRIPTION
              "Applies to `Interleave' channels only.
              Configured change in rate causing an

              adslAtucRateChangeTrap.  A trap is produced when:
              ChanCurrTxRate >= ChanPrevTxRate plus the value of
              this object. A value of `0' will disable the trap."
      ::= { adslLineAlarmConfProfileEntry 8}

      adslAtucThreshFastRateDown OBJECT-TYPE
          SYNTAX      Unsigned32
          UNITS       "bps"
          MAX-ACCESS  read-create
          STATUS      current
          DESCRIPTION
              "Applies to `Fast' channels only.
              Configured change in rate causing an
              adslAtucRateChangeTrap.  A trap is produced when:
              ChanCurrTxRate <= ChanPrevTxRate minus the value of
              this object. A value of `0' will disable the trap."
      ::= { adslLineAlarmConfProfileEntry 9 }

      adslAtucThreshInterleaveRateDown OBJECT-TYPE
          SYNTAX      Unsigned32
          UNITS       "bps"
          MAX-ACCESS  read-create
          STATUS      current
          DESCRIPTION
              "Applies to `Interleave' channels only.
              Configured change in rate causing an
              adslAtucRateChangeTrap.  A trap is produced when:
              ChanCurrTxRate <= ChanPrevTxRate minus the value of
              this object. A value of `0' will disable the trap."
      ::= { adslLineAlarmConfProfileEntry 10 }

      adslAtucInitFailureTrapEnable OBJECT-TYPE
          SYNTAX      INTEGER {
              enable (1),
              disable (2)
          }
          MAX-ACCESS  read-create
          STATUS      current
          DESCRIPTION
              "Enables and disables the InitFailureTrap.  This
              object is defaulted disable(2)."
      DEFVAL { disable }
      ::= { adslLineAlarmConfProfileEntry 11 }

      adslAturThresh15MinLofs OBJECT-TYPE
          SYNTAX      INTEGER(0..900)
          UNITS       "seconds"
          MAX-ACCESS  read-create

          STATUS      current
          DESCRIPTION
              "The number of Loss of Frame Seconds
              encountered by an ADSL interface within any given 15
              minutes performance data collection period, which
              causes the SNMP agent to send an
              adslAturPerfLofsThreshTrap.
              One trap will be sent per interval per interface.
              A value of `0' will disable the trap."
      ::= { adslLineAlarmConfProfileEntry 12 }

      adslAturThresh15MinLoss  OBJECT-TYPE
          SYNTAX      INTEGER(0..900)
          UNITS       "seconds"
          MAX-ACCESS  read-create
          STATUS      current
          DESCRIPTION
              "The number of Loss of Signal Seconds
              encountered by an ADSL interface within any given 15
              minutes performance data collection period, which
              causes the SNMP agent to send an
              adslAturPerfLossThreshTrap.
              One trap will be sent per interval per interface.
              A value of `0' will disable the trap."
      ::= { adslLineAlarmConfProfileEntry 13 }

      adslAturThresh15MinLprs  OBJECT-TYPE
          SYNTAX      INTEGER(0..900)
          UNITS       "seconds"
          MAX-ACCESS  read-create
          STATUS      current
          DESCRIPTION
              "The number of Loss of Power Seconds
              encountered by an ADSL interface within any given 15
              minutes performance data collection period, which
              causes the SNMP agent to send an
              adslAturPerfLprsThreshTrap.
              One trap will be sent per interval per interface.
              A value of `0' will disable the trap."
      ::= { adslLineAlarmConfProfileEntry 14 }

      adslAturThresh15MinESs  OBJECT-TYPE
          SYNTAX      INTEGER(0..900)
          UNITS       "seconds"
          MAX-ACCESS  read-create
          STATUS      current
          DESCRIPTION
              "The number of Errored Seconds

              encountered by an ADSL interface within any given 15
              minutes performance data collection period, which
              causes the SNMP agent to send an
              adslAturPerfESsThreshTrap.
              One trap will be sent per interval per interface.
              A value of `0' will disable the trap."
      ::= { adslLineAlarmConfProfileEntry 15 }

      adslAturThreshFastRateUp OBJECT-TYPE
          SYNTAX      Unsigned32
          UNITS       "bps"
          MAX-ACCESS  read-create
          STATUS      current
          DESCRIPTION
              "Applies to `Fast' channels only.
              Configured change in rate causing an
              adslAturRateChangeTrap.  A trap is produced when:
              ChanCurrTxRate >= ChanPrevTxRate plus the value of
              this object. A value of `0' will disable the trap."
      ::= { adslLineAlarmConfProfileEntry 16 }

      adslAturThreshInterleaveRateUp OBJECT-TYPE
          SYNTAX      Unsigned32
          UNITS       "bps"
          MAX-ACCESS  read-create
          STATUS      current
          DESCRIPTION
              "Applies to `Interleave' channels only.
              configured change in rate causing an
              adslAturRateChangeTrap.  A trap is produced when:
              ChanCurrTxRate >= ChanPrevTxRate plus the value of
              this object. A value of `0' will disable the trap."
      ::= { adslLineAlarmConfProfileEntry 17 }

      adslAturThreshFastRateDown OBJECT-TYPE
          SYNTAX      Unsigned32
          UNITS       "bps"
          MAX-ACCESS  read-create
          STATUS      current
          DESCRIPTION
              "Applies to `Fast' channels only.
              Configured change in rate causing an
              adslAturRateChangeTrap.  A trap is produced when:
              ChanCurrTxRate <= ChanPrevTxRate minus the value of
              this object. A value of `0' will disable the trap."
      ::= { adslLineAlarmConfProfileEntry 18 }

      adslAturThreshInterleaveRateDown OBJECT-TYPE

          SYNTAX      Unsigned32
          UNITS       "bps"
          MAX-ACCESS  read-create
          STATUS      current
          DESCRIPTION
              "Applies to `Interleave' channels only.
              Configured change in rate causing an
              adslAturRateChangeTrap.  A trap is produced when:
              ChanCurrTxRate <= ChanPrevTxRate minus the value of
              this object. A value of `0' will disable the trap."
      ::= { adslLineAlarmConfProfileEntry 19 }

      adslLineAlarmConfProfileRowStatus OBJECT-TYPE
          SYNTAX          RowStatus
          MAX-ACCESS      read-create
          STATUS          current
          DESCRIPTION
              "This object is used to create a new row or modify or
              delete an existing row in this table.

              A profile activated by setting this object to
              `active'.  When `active' is set, the system
              will validate the profile.

              Before a profile can be deleted or taken out of
              service, (by setting this object to `destroy' or
              `outOfService') it must be first unreferenced
              from all associated lines.

              If the implementator of this MIB has chosen not
              to implement `dynamic assignment' of profiles, this
              object's MIN-ACCESS is read-only and its value
              is always to be `active'."
      ::= { adslLineAlarmConfProfileEntry 20 }

      -- Line Code Specific Tables

      -- These are place holders for the Line Code Specific MIBs
      -- once they become available.

      adslLCSMib  OBJECT IDENTIFIER ::= { adslMibObjects 16 }

-- trap definitions

adslTraps OBJECT IDENTIFIER ::= { adslLineMib 2 }

adslAtucTraps OBJECT IDENTIFIER ::= { adslTraps 1 }


      adslAtucPerfLofsThreshTrap      NOTIFICATION-TYPE
          OBJECTS { adslAtucPerfCurr15MinLofs,
                    adslAtucThresh15MinLofs }
          STATUS  current
          DESCRIPTION
              "Loss of Framing 15-minute interval threshold reached."
      ::= { adslAtucTraps 0 1 }

      adslAtucPerfLossThreshTrap      NOTIFICATION-TYPE
          OBJECTS { adslAtucPerfCurr15MinLoss,
                    adslAtucThresh15MinLoss }
          STATUS  current
          DESCRIPTION
              "Loss of Signal 15-minute interval threshold reached."
      ::= { adslAtucTraps 0 2 }

      adslAtucPerfLprsThreshTrap      NOTIFICATION-TYPE
          OBJECTS { adslAtucPerfCurr15MinLprs,
                    adslAtucThresh15MinLprs }
          STATUS  current
          DESCRIPTION
              "Loss of Power 15-minute interval threshold reached."
      ::= { adslAtucTraps 0 3 }

      adslAtucPerfESsThreshTrap       NOTIFICATION-TYPE
          OBJECTS { adslAtucPerfCurr15MinESs,
                    adslAtucThresh15MinESs }
          STATUS  current
          DESCRIPTION
              "Errored Second 15-minute interval threshold reached."
      ::= { adslAtucTraps 0 4 }

      adslAtucRateChangeTrap  NOTIFICATION-TYPE
          OBJECTS { adslAtucChanCurrTxRate,
                    adslAtucChanPrevTxRate }
          STATUS  current
          DESCRIPTION
              "The ATUCs transmit rate has changed (RADSL mode only)"
      ::= { adslAtucTraps 0 5 }

      adslAtucPerfLolsThreshTrap      NOTIFICATION-TYPE
          OBJECTS { adslAtucPerfCurr15MinLols,
                    adslAtucThresh15MinLols }
          STATUS  current
          DESCRIPTION
              "Loss of Link 15-minute interval threshold reached."
      ::= { adslAtucTraps 0 6 }


      adslAtucInitFailureTrap NOTIFICATION-TYPE
          OBJECTS { adslAtucCurrStatus }
          STATUS  current
          DESCRIPTION
              "ATUC initialization failed. See adslAtucCurrStatus
              for potential reasons."
      ::= { adslAtucTraps 0 7 }

adslAturTraps OBJECT IDENTIFIER ::= { adslTraps 2 }

      adslAturPerfLofsThreshTrap      NOTIFICATION-TYPE
          OBJECTS { adslAturPerfCurr15MinLofs,
                    adslAturThresh15MinLofs }
          STATUS  current
          DESCRIPTION
              "Loss of Framing 15-minute interval threshold reached."
      ::= { adslAturTraps 0 1 }

      adslAturPerfLossThreshTrap      NOTIFICATION-TYPE
          OBJECTS { adslAturPerfCurr15MinLoss,
                    adslAturThresh15MinLoss }
          STATUS  current
          DESCRIPTION
              "Loss of Signal 15-minute interval threshold reached."
      ::= { adslAturTraps 0 2 }

      adslAturPerfLprsThreshTrap      NOTIFICATION-TYPE
          OBJECTS { adslAturPerfCurr15MinLprs,
                    adslAturThresh15MinLprs }
          STATUS  current
          DESCRIPTION
              "Loss of Power 15-minute interval threshold reached."
      ::= { adslAturTraps 0 3 }

      adslAturPerfESsThreshTrap       NOTIFICATION-TYPE
          OBJECTS { adslAturPerfCurr15MinESs,
                    adslAturThresh15MinESs }
          STATUS  current
          DESCRIPTION
              "Errored Second 15-minute interval threshold reached."
      ::= { adslAturTraps 0 4 }

      adslAturRateChangeTrap  NOTIFICATION-TYPE
          OBJECTS { adslAturChanCurrTxRate,
                    adslAturChanPrevTxRate }
          STATUS  current
          DESCRIPTION
              "The ATURs transmit rate has changed (RADSL mode only)"

      ::= { adslAturTraps 0 5 }

      -- no adslAturPerfLolsThreshTrap possible { 0 6 }

      -- no adslAturInitFailureTrap possible { 0 7 }

-- conformance information

adslConformance OBJECT IDENTIFIER ::= { adslLineMib 3 }

adslGroups OBJECT IDENTIFIER ::= { adslConformance 1 }
adslCompliances OBJECT IDENTIFIER ::= { adslConformance 2 }

      -- ATU-C agent compliance statements

      adslLineMibAtucCompliance MODULE-COMPLIANCE
          STATUS  current
          DESCRIPTION
              "The compliance statement for SNMP entities
               which manage ADSL ATU-C interfaces."

          MODULE  -- this module
          MANDATORY-GROUPS
             {
             adslLineGroup, adslPhysicalGroup, adslChannelGroup,
             adslAtucPhysPerfIntervalGroup,
             adslAturPhysPerfIntervalGroup, adslLineConfProfileGroup,
             adslLineAlarmConfProfileGroup,
             adslLineConfProfileControlGroup
             }

          GROUP       adslAtucPhysPerfRawCounterGroup
          DESCRIPTION
              "This group is optional.  Implementations which
               require continuous ATU-C physical event counters
               should implement this group."

          GROUP       adslAturPhysPerfRawCounterGroup
          DESCRIPTION
              "This group is optional.  Implementations which
               require continuous ATU-R physical event counters
               should implement this group."

          GROUP       adslAtucChanPerformanceGroup
          DESCRIPTION
              "This group is optional.  Implementations which
               require ATU-C channel block event counters should
               implement this group."

          GROUP       adslAturChanPerformanceGroup
          DESCRIPTION
              "This group is optional.  Implementations which
               require ATU-R channel block event counters should
               implement this group."

          OBJECT      adslLineConfProfile
          MIN-ACCESS  read-only
          DESCRIPTION
              "Read-only access is applicable when static
               profiles are implemented."

          OBJECT      adslAtucConfRateMode
          MIN-ACCESS  read-write
          DESCRIPTION
              "Read-write access is applicable when
               static profiles are implemented."

          OBJECT      adslAtucConfRateChanRatio
          MIN-ACCESS  read-write
          DESCRIPTION
              "Read-write access is applicable when
               static profiles are implemented."

          OBJECT      adslAtucConfTargetSnrMgn
          MIN-ACCESS  read-write
          DESCRIPTION
              "Read-write access is applicable when
               static profiles are implemented."

          OBJECT      adslAtucConfMaxSnrMgn
          MIN-ACCESS  read-write
          DESCRIPTION
              "Read-write access is applicable when
               static profiles are implemented."

          OBJECT      adslAtucConfMinSnrMgn
          MIN-ACCESS  read-write
          DESCRIPTION
              "Read-write access is applicable when
               static profiles are implemented."

          OBJECT      adslAtucConfDownshiftSnrMgn
          MIN-ACCESS  read-write
          DESCRIPTION
              "Read-write access is applicable when
               static profiles are implemented."

          OBJECT      adslAtucConfUpshiftSnrMgn
          MIN-ACCESS  read-write
          DESCRIPTION
              "Read-write access is applicable when
               static profiles are implemented."

          OBJECT      adslAtucConfMinUpshiftTime
          MIN-ACCESS  read-write
          DESCRIPTION
              "Read-write access is applicable when
               static profiles are implemented."

          OBJECT      adslAtucConfMinDownshiftTime
          MIN-ACCESS  read-write
          DESCRIPTION
              "Read-write access is applicable when
               static profiles are implemented."

          OBJECT      adslAtucChanConfFastMinTxRate
          MIN-ACCESS  read-write
          DESCRIPTION
              "Read-write access is applicable when
               static profiles are implemented."

          OBJECT      adslAtucChanConfInterleaveMinTxRate
          MIN-ACCESS  read-write
          DESCRIPTION
              "Read-write access is applicable when
               static profiles are implemented."

          OBJECT      adslAtucChanConfFastMaxTxRate
          MIN-ACCESS  read-write
          DESCRIPTION
              "Read-write access is applicable when
               static profiles are implemented."

          OBJECT      adslAtucChanConfInterleaveMaxTxRate
          MIN-ACCESS  read-write
          DESCRIPTION
              "Read-write access is applicable when
               static profiles are implemented."

          OBJECT      adslAtucChanConfMaxInterleaveDelay
          MIN-ACCESS  read-write
          DESCRIPTION
              "Read-write access is applicable when
               static profiles are implemented."


          OBJECT      adslAturConfRateMode
          MIN-ACCESS  read-write
          DESCRIPTION
              "Read-write access is applicable when
               static profiles are implemented."

          OBJECT      adslAturConfRateChanRatio
          MIN-ACCESS  read-write
          DESCRIPTION
              "Read-write access is applicable when
               static profiles are implemented."

          OBJECT      adslAturConfTargetSnrMgn
          MIN-ACCESS  read-write
          DESCRIPTION
              "Read-write access is applicable when
               static profiles are implemented."

          OBJECT      adslAturConfMaxSnrMgn
          MIN-ACCESS  read-write
          DESCRIPTION
              "Read-write access is applicable when
               static profiles are implemented."

          OBJECT      adslAturConfMinSnrMgn
          MIN-ACCESS  read-write
          DESCRIPTION
              "Read-write access is applicable when
               static profiles are implemented."

          OBJECT      adslAturConfDownshiftSnrMgn
          MIN-ACCESS  read-write
          DESCRIPTION
              "Read-write access is applicable when
               static profiles are implemented."

          OBJECT      adslAturConfUpshiftSnrMgn
          MIN-ACCESS  read-write
          DESCRIPTION
              "Read-write access is applicable when
               static profiles are implemented."

          OBJECT      adslAturConfMinUpshiftTime
          MIN-ACCESS  read-write
          DESCRIPTION
              "Read-write access is applicable when
               static profiles are implemented."


          OBJECT      adslAturConfMinDownshiftTime
          MIN-ACCESS  read-write
          DESCRIPTION
              "Read-write access is applicable when
               static profiles are implemented."

          OBJECT      adslAturChanConfFastMinTxRate
          MIN-ACCESS  read-write
          DESCRIPTION
              "Read-write access is applicable when
               static profiles are implemented."

          OBJECT      adslAturChanConfInterleaveMinTxRate
          MIN-ACCESS  read-write
          DESCRIPTION
              "Read-write access is applicable when
               static profiles are implemented."

          OBJECT      adslAturChanConfFastMaxTxRate
          MIN-ACCESS  read-write
          DESCRIPTION
              "Read-write access is applicable when
               static profiles are implemented."

          OBJECT      adslAturChanConfInterleaveMaxTxRate
          MIN-ACCESS  read-write
          DESCRIPTION
              "Read-write access is applicable when
               static profiles are implemented."

          OBJECT      adslAturChanConfMaxInterleaveDelay
          MIN-ACCESS  read-write
          DESCRIPTION
              "Read-write access is applicable when
               static profiles are implemented."

          OBJECT      adslLineConfProfileRowStatus
          MIN-ACCESS  read-only
          DESCRIPTION
              "Read-only access is applicable only when static
               profiles are implemented."

          OBJECT      adslLineAlarmConfProfile
          MIN-ACCESS  read-only
          DESCRIPTION
              "Read-only access is applicable only when static
               profiles are implemented."


          OBJECT      adslAtucThresh15MinLofs
          MIN-ACCESS  read-write
          DESCRIPTION
              "Read-write access is applicable when
               static profiles are implemented."

          OBJECT      adslAtucThresh15MinLoss
          MIN-ACCESS  read-write
          DESCRIPTION
              "Read-write access is applicable when
               static profiles are implemented."

          OBJECT      adslAtucThresh15MinLols
          MIN-ACCESS  read-write
          DESCRIPTION
              "Read-write access is applicable when
               static profiles are implemented."

          OBJECT      adslAtucThresh15MinLprs
          MIN-ACCESS  read-write
          DESCRIPTION
              "Read-write access is applicable when
               static profiles are implemented."

          OBJECT      adslAtucThresh15MinESs
          MIN-ACCESS  read-write
          DESCRIPTION
              "Read-write access is applicable when
               static profiles are implemented."

          OBJECT      adslAtucThreshFastRateUp
          MIN-ACCESS  read-write
          DESCRIPTION
              "Read-write access is applicable when
               static profiles are implemented."

          OBJECT      adslAtucThreshInterleaveRateUp
          MIN-ACCESS  read-write
          DESCRIPTION
              "Read-write access is applicable when
               static profiles are implemented."

          OBJECT      adslAtucThreshFastRateDown
          MIN-ACCESS  read-write
          DESCRIPTION
              "Read-write access is applicable when
               static profiles are implemented."


          OBJECT      adslAtucThreshInterleaveRateDown
          MIN-ACCESS  read-write
          DESCRIPTION
              "Read-write access is applicable when
               static profiles are implemented."

          OBJECT      adslAtucInitFailureTrapEnable
          MIN-ACCESS  read-write
          DESCRIPTION
              "Read-write access is applicable when
               static profiles are implemented."

          OBJECT      adslAturThresh15MinLofs
          MIN-ACCESS  read-write
          DESCRIPTION
              "Read-write access is applicable when
               static profiles are implemented."

          OBJECT      adslAturThresh15MinLoss
          MIN-ACCESS  read-write
          DESCRIPTION
              "Read-write access is applicable when
               static profiles are implemented."

          OBJECT      adslAturThresh15MinLprs
          MIN-ACCESS  read-write
          DESCRIPTION
              "Read-write access is applicable when
               static profiles are implemented."

          OBJECT      adslAturThresh15MinESs
          MIN-ACCESS  read-write
          DESCRIPTION
              "Read-write access is applicable when
               static profiles are implemented."

          OBJECT      adslAturThreshFastRateUp
          MIN-ACCESS  read-write
          DESCRIPTION
              "Read-write access is applicable when
               static profiles are implemented."

          OBJECT      adslAturThreshInterleaveRateUp
          MIN-ACCESS  read-write
          DESCRIPTION
              "Read-write access is applicable when
               static profiles are implemented."


          OBJECT      adslAturThreshFastRateDown
          MIN-ACCESS  read-write
          DESCRIPTION
              "Read-write access is applicable when
               static profiles are implemented."

          OBJECT      adslAturThreshInterleaveRateDown
          MIN-ACCESS  read-write
          DESCRIPTION
              "Read-write access is applicable when
               static profiles are implemented."

          OBJECT      adslLineAlarmConfProfileRowStatus
          MIN-ACCESS  read-only
          DESCRIPTION
              "Read-only access is applicable only when static
               profiles are implemented."

      ::= { adslCompliances 1 }

      -- ATU-R agent compliance statements

      adslLineMibAturCompliance MODULE-COMPLIANCE
          STATUS  current
          DESCRIPTION
              "The compliance statement for SNMP entities
               which manage ADSL ATU-R interfaces."

          MODULE  -- this module
          MANDATORY-GROUPS
              {
              adslAturLineGroup, adslAturPhysicalGroup,
              adslAturChannelGroup,
              adslAturAtucPhysPerfIntervalGroup,
              adslAturAturPhysPerfIntervalGroup,
              adslAturLineAlarmConfProfileGroup,
              adslAturLineConfProfileControlGroup
              }

          GROUP       adslAturAtucPhysPerfRawCounterGroup
          DESCRIPTION
              "This group is optional.  Implementations which
               require continuous ATU-C physical event counters
               should implement this group."

          GROUP       adslAturAturPhysPerfRawCounterGroup
          DESCRIPTION
              "This group is optional.  Implementations which

               require continuous ATU-R physical event counters
               should implement this group."

          GROUP       adslAturAtucChanPerformanceGroup
          DESCRIPTION
              "This group is optional.  Implementations which
               require ATU-C channel block event counters should
               implement this group."

          GROUP       adslAturAturChanPerformanceGroup
          DESCRIPTION
              "This group is optional.  Implementations which
               require ATU-R channel block event counters should
               implement this group."

          OBJECT      adslLineAlarmConfProfile
          MIN-ACCESS  read-only
          DESCRIPTION
              "Read-only access is applicable only when static
               profiles are implemented."

          OBJECT      adslAtucThresh15MinLofs
          MIN-ACCESS  read-write
          DESCRIPTION
              "Read-write access is applicable when
               static profiles are implemented."

          OBJECT      adslAtucThresh15MinLoss
          MIN-ACCESS  read-write
          DESCRIPTION
              "Read-write access is applicable when
               static profiles are implemented."

          OBJECT      adslAtucThresh15MinESs
          MIN-ACCESS  read-write
          DESCRIPTION
              "Read-write access is applicable when
               static profiles are implemented."

          OBJECT      adslAtucThreshFastRateUp
          MIN-ACCESS  read-write
          DESCRIPTION
              "Read-write access is applicable when
               static profiles are implemented."

          OBJECT      adslAtucThreshInterleaveRateUp
          MIN-ACCESS  read-write
          DESCRIPTION

              "Read-write access is applicable when
               static profiles are implemented."

          OBJECT      adslAtucThreshFastRateDown
          MIN-ACCESS  read-write
          DESCRIPTION
              "Read-write access is applicable when
               static profiles are implemented."

          OBJECT      adslAtucInitFailureTrapEnable
          MIN-ACCESS  read-write

          DESCRIPTION
              "Read-write access is applicable when
               static profiles are implemented."

          OBJECT      adslAturThresh15MinLofs
          MIN-ACCESS  read-write
          DESCRIPTION
              "Read-write access is applicable when
               static profiles are implemented."

          OBJECT      adslAturThresh15MinLoss
          MIN-ACCESS  read-write
          DESCRIPTION
              "Read-write access is applicable when
               static profiles are implemented."

          OBJECT      adslAturThresh15MinLprs
          MIN-ACCESS  read-write
          DESCRIPTION
              "Read-write access is applicable when
               static profiles are implemented."

          OBJECT      adslAturThresh15MinESs
          MIN-ACCESS  read-write
          DESCRIPTION
              "Read-write access is applicable when
               static profiles are implemented."

          OBJECT      adslAturThreshFastRateUp
          MIN-ACCESS  read-write
          DESCRIPTION
              "Read-write access is applicable when
               static profiles are implemented."

          OBJECT      adslAturThreshInterleaveRateUp
          MIN-ACCESS  read-write

          DESCRIPTION
              "Read-write access is applicable when
               static profiles are implemented."

          OBJECT      adslAturThreshFastRateDown
          MIN-ACCESS  read-write
          DESCRIPTION
              "Read-write access is applicable when
               static profiles are implemented."

          OBJECT      adslAturThreshInterleaveRateDown
          MIN-ACCESS  read-write
          DESCRIPTION
              "Read-write access is applicable when
               static profiles are implemented."

          OBJECT      adslLineAlarmConfProfileRowStatus
          MIN-ACCESS  read-only
          DESCRIPTION
              "Read-only access is applicable only when static
               profiles are implemented."

          OBJECT     adslAtucCurrStatus
          SYNTAX   BITS {
                         noDefect(0),
                         lossOfFraming(1),
                         lossOfSignal(2)
                        }
          DESCRIPTION
              "It is allowable to implement only noDefect(0),
              lossOfFraming(1) and lossOfSignal(2) by the ATU-R
              agent."

     ::= { adslCompliances 2 }

      -- units of conformance
      adslLineGroup    OBJECT-GROUP
          OBJECTS {
             adslLineCoding, adslLineType, adslLineSpecific
             }
          STATUS     current
          DESCRIPTION
              "A collection of objects providing configuration
              information about an ADSL Line."
      ::= { adslGroups 1 }

      adslPhysicalGroup    OBJECT-GROUP
          OBJECTS {

             adslAtucInvSerialNumber, adslAtucInvVendorID,
             adslAtucInvVersionNumber, adslAtucCurrSnrMgn,
             adslAtucCurrAtn, adslAtucCurrStatus,
             adslAtucCurrOutputPwr, adslAtucCurrAttainableRate,
             adslAturInvSerialNumber, adslAturInvVendorID,
             adslAturInvVersionNumber, adslAturCurrSnrMgn,
             adslAturCurrAtn, adslAturCurrStatus,
             adslAturCurrOutputPwr, adslAturCurrAttainableRate
             }
          STATUS     current
          DESCRIPTION
              "A collection of objects providing physical
              configuration information of the ADSL Line."
      ::= { adslGroups 2 }

      adslChannelGroup    OBJECT-GROUP
          OBJECTS {
             adslAtucChanInterleaveDelay, adslAtucChanCurrTxRate,
             adslAtucChanPrevTxRate, adslAtucChanCrcBlockLength,
             adslAturChanInterleaveDelay, adslAturChanCurrTxRate,
             adslAturChanPrevTxRate, adslAturChanCrcBlockLength
             }
          STATUS     current
          DESCRIPTION
              "A collection of objects providing configuration
              information about an ADSL channel."
      ::= { adslGroups 3 }

      adslAtucPhysPerfRawCounterGroup OBJECT-GROUP
          OBJECTS {
             adslAtucPerfLofs, adslAtucPerfLoss,
             adslAtucPerfLols, adslAtucPerfLprs,
             adslAtucPerfESs, adslAtucPerfInits
             }
          STATUS     current
          DESCRIPTION
              "A collection of objects providing raw performance
              counts on an ADSL Line (ATU-C end)."
      ::= { adslGroups 4 }

      adslAtucPhysPerfIntervalGroup OBJECT-GROUP
          OBJECTS {
             adslAtucPerfValidIntervals,
             adslAtucPerfInvalidIntervals,
             adslAtucPerfCurr15MinTimeElapsed,
             adslAtucPerfCurr15MinLofs, adslAtucPerfCurr15MinLoss,
             adslAtucPerfCurr15MinLols, adslAtucPerfCurr15MinLprs,
             adslAtucPerfCurr15MinESs, adslAtucPerfCurr15MinInits,

             adslAtucPerfCurr1DayLofs, adslAtucPerfCurr1DayLoss,
             adslAtucPerfCurr1DayLols, adslAtucPerfCurr1DayLprs,
             adslAtucPerfCurr1DayESs, adslAtucPerfCurr1DayInits,
             adslAtucPerfPrev1DayMoniSecs,
             adslAtucPerfPrev1DayLofs, adslAtucPerfPrev1DayLoss,
             adslAtucPerfPrev1DayLols, adslAtucPerfPrev1DayLprs,
             adslAtucPerfPrev1DayESs, adslAtucPerfPrev1DayInits,
             adslAtucIntervalLofs, adslAtucIntervalLoss,
             adslAtucIntervalLols, adslAtucIntervalLprs,
             adslAtucIntervalESs, adslAtucIntervalInits,
             adslAtucIntervalValidData
             }

          STATUS     current
          DESCRIPTION
              "A collection of objects providing current 15-minute,
              1-day; and previous 1-day performance counts on
              ADSL Line (ATU-C end) ."
      ::= { adslGroups 5 }

      adslAturPhysPerfRawCounterGroup OBJECT-GROUP
          OBJECTS {
             adslAturPerfLofs, adslAturPerfLoss,
             adslAturPerfLprs, adslAturPerfESs
             }
          STATUS     current
          DESCRIPTION
              "A collection of objects providing raw performance
              counts on an ADSL Line (ATU-R end)."
      ::= { adslGroups 6 }

      adslAturPhysPerfIntervalGroup OBJECT-GROUP
          OBJECTS {
             adslAturPerfValidIntervals,
             adslAturPerfInvalidIntervals,
             adslAturPerfCurr15MinTimeElapsed,
             adslAturPerfCurr15MinLofs, adslAturPerfCurr15MinLoss,
             adslAturPerfCurr15MinLprs, adslAturPerfCurr15MinESs,
             adslAturPerfCurr1DayTimeElapsed,
             adslAturPerfCurr1DayLofs, adslAturPerfCurr1DayLoss,
             adslAturPerfCurr1DayLprs, adslAturPerfCurr1DayESs,
             adslAturPerfPrev1DayMoniSecs,
             adslAturPerfPrev1DayLofs, adslAturPerfPrev1DayLoss,
             adslAturPerfPrev1DayLprs, adslAturPerfPrev1DayESs,
             adslAturIntervalLofs,
             adslAturIntervalLoss, adslAturIntervalLprs,
             adslAturIntervalESs, adslAturIntervalValidData
             }

          STATUS     current
          DESCRIPTION
              "A collection of objects providing current 15-minute,
              1-day; and previous 1-day performance counts on
              ADSL Line (ATU-R end)."
      ::= { adslGroups 7 }

      adslAtucChanPerformanceGroup OBJECT-GROUP
          OBJECTS {
             adslAtucChanReceivedBlks,
             adslAtucChanTransmittedBlks,
             adslAtucChanCorrectedBlks,
             adslAtucChanUncorrectBlks,
             adslAtucChanPerfValidIntervals,
             adslAtucChanPerfInvalidIntervals,
             adslAtucChanPerfCurr15MinTimeElapsed,
             adslAtucChanPerfCurr15MinReceivedBlks,
             adslAtucChanPerfCurr15MinTransmittedBlks,
             adslAtucChanPerfCurr15MinCorrectedBlks,
             adslAtucChanPerfCurr15MinUncorrectBlks,
             adslAtucChanPerfCurr1DayTimeElapsed,
             adslAtucChanPerfCurr1DayReceivedBlks,
             adslAtucChanPerfCurr1DayTransmittedBlks,
             adslAtucChanPerfCurr1DayCorrectedBlks,
             adslAtucChanPerfCurr1DayUncorrectBlks,
             adslAtucChanPerfPrev1DayMoniSecs,
             adslAtucChanPerfPrev1DayReceivedBlks,
             adslAtucChanPerfPrev1DayTransmittedBlks,
             adslAtucChanPerfPrev1DayCorrectedBlks,
             adslAtucChanPerfPrev1DayUncorrectBlks,
             adslAtucChanIntervalReceivedBlks,
             adslAtucChanIntervalTransmittedBlks,
             adslAtucChanIntervalCorrectedBlks,
             adslAtucChanIntervalUncorrectBlks,
             adslAtucChanIntervalValidData
             }
          STATUS     current
          DESCRIPTION
              "A collection of objects providing channel block
              performance information on an ADSL channel
              (ATU-C end)."
      ::= { adslGroups 8 }

      adslAturChanPerformanceGroup OBJECT-GROUP
          OBJECTS {
             adslAturChanReceivedBlks,
             adslAturChanTransmittedBlks,
             adslAturChanCorrectedBlks,

             adslAturChanUncorrectBlks,
             adslAturChanPerfValidIntervals,
             adslAturChanPerfInvalidIntervals,
             adslAturChanPerfCurr15MinTimeElapsed,
             adslAturChanPerfCurr15MinReceivedBlks,
             adslAturChanPerfCurr15MinTransmittedBlks,
             adslAturChanPerfCurr15MinCorrectedBlks,
             adslAturChanPerfCurr15MinUncorrectBlks,
             adslAturChanPerfCurr1DayTimeElapsed,
             adslAturChanPerfCurr1DayReceivedBlks,
             adslAturChanPerfCurr1DayTransmittedBlks,
             adslAturChanPerfCurr1DayCorrectedBlks,
             adslAturChanPerfCurr1DayUncorrectBlks,
             adslAturChanPerfPrev1DayMoniSecs,
             adslAturChanPerfPrev1DayReceivedBlks,
             adslAturChanPerfPrev1DayTransmittedBlks,
             adslAturChanPerfPrev1DayCorrectedBlks,
             adslAturChanPerfPrev1DayUncorrectBlks,
             adslAturChanIntervalReceivedBlks,
             adslAturChanIntervalTransmittedBlks,
             adslAturChanIntervalCorrectedBlks,
             adslAturChanIntervalUncorrectBlks,
             adslAturChanIntervalValidData
             }
          STATUS     current
          DESCRIPTION
              "A collection of objects providing channel block
              performance information on an ADSL channel
              (ATU-C end)."
      ::= { adslGroups 9 }

      adslLineConfProfileGroup OBJECT-GROUP
          OBJECTS {
             adslAtucConfRateMode, adslAtucConfRateChanRatio,
             adslAtucConfTargetSnrMgn, adslAtucConfMaxSnrMgn,
             adslAtucConfMinSnrMgn,
             adslAtucConfDownshiftSnrMgn,
             adslAtucConfUpshiftSnrMgn,
             adslAtucConfMinUpshiftTime,
             adslAtucConfMinDownshiftTime,
             adslAtucChanConfFastMinTxRate,
             adslAtucChanConfInterleaveMinTxRate,
             adslAtucChanConfFastMaxTxRate,
             adslAtucChanConfInterleaveMaxTxRate,
             adslAtucChanConfMaxInterleaveDelay,
             adslAturConfRateMode, adslAturConfRateChanRatio,
             adslAturConfTargetSnrMgn, adslAturConfMaxSnrMgn,
             adslAturConfMinSnrMgn, adslAturConfDownshiftSnrMgn,

             adslAturConfUpshiftSnrMgn,
             adslAturConfMinUpshiftTime,
             adslAturConfMinDownshiftTime,
             adslAturChanConfFastMinTxRate,
             adslAturChanConfInterleaveMinTxRate,
             adslAturChanConfFastMaxTxRate,
             adslAturChanConfInterleaveMaxTxRate,
             adslAturChanConfMaxInterleaveDelay
             }
          STATUS     current
          DESCRIPTION
              "A collection of objects providing provisioning
              information about an ADSL Line."
      ::= { adslGroups 10 }

      adslLineAlarmConfProfileGroup OBJECT-GROUP
          OBJECTS {
             adslAtucThresh15MinLofs, adslAtucThresh15MinLoss,
             adslAtucThresh15MinLols, adslAtucThresh15MinLprs,
             adslAtucThresh15MinESs, adslAtucThreshFastRateUp,
             adslAtucThreshInterleaveRateUp,
             adslAtucThreshFastRateDown,
             adslAtucThreshInterleaveRateDown,
             adslAtucInitFailureTrapEnable,
             adslAturThresh15MinLofs, adslAturThresh15MinLoss,
             adslAturThresh15MinLprs, adslAturThresh15MinESs,
             adslAturThreshFastRateUp,
             adslAturThreshInterleaveRateUp,
             adslAturThreshFastRateDown,
             adslAturThreshInterleaveRateDown
             }
          STATUS     current
          DESCRIPTION
              "A collection of objects providing alarm provisioning
              information about an ADSL Line."
      ::= { adslGroups 11 }

      adslLineConfProfileControlGroup OBJECT-GROUP
          OBJECTS {
             adslLineConfProfile, adslLineAlarmConfProfile,
             adslLineConfProfileRowStatus,
             adslLineAlarmConfProfileRowStatus
             }
          STATUS     current
          DESCRIPTION
              "A collection of objects providing profile
              control for the ADSL system."
      ::= { adslGroups 12 }

      adslNotificationsGroup NOTIFICATION-GROUP
          NOTIFICATIONS {
             adslAtucPerfLofsThreshTrap,
             adslAtucPerfLossThreshTrap,
             adslAtucPerfLprsThreshTrap,
             adslAtucPerfESsThreshTrap,
             adslAtucRateChangeTrap,
             adslAtucPerfLolsThreshTrap,
             adslAtucInitFailureTrap,
             adslAturPerfLofsThreshTrap,
             adslAturPerfLossThreshTrap,
             adslAturPerfLprsThreshTrap,
             adslAturPerfESsThreshTrap,
             adslAturRateChangeTrap
             }
          STATUS        current
          DESCRIPTION
              "The collection of adsl notifications."
      ::= { adslGroups 13 }

-- units of conformance for ATU-R agent

         adslAturLineGroup    OBJECT-GROUP
             OBJECTS {
                adslLineCoding
                }
             STATUS     current
             DESCRIPTION
                 "A collection of objects providing configuration
                 information about an ADSL Line on the ATU-R side."
         ::= { adslGroups 14 }

         adslAturPhysicalGroup    OBJECT-GROUP
             OBJECTS {
                adslAtucInvVendorID,
                adslAtucInvVersionNumber,
                adslAtucCurrOutputPwr, adslAtucCurrAttainableRate,
                adslAturInvSerialNumber, adslAturInvVendorID,
                adslAturInvVersionNumber, adslAturCurrSnrMgn,
                adslAturCurrAtn, adslAturCurrStatus,
                adslAturCurrOutputPwr, adslAturCurrAttainableRate,
                adslAtucCurrStatus
                }
             STATUS     current
             DESCRIPTION
                 "A collection of objects providing physical
                 configuration information of the ADSL Line on the
                 ATU-R side."

         ::= { adslGroups 15 }

         adslAturChannelGroup    OBJECT-GROUP
             OBJECTS {
                adslAtucChanInterleaveDelay, adslAtucChanCurrTxRate,
                adslAtucChanPrevTxRate,
                adslAturChanInterleaveDelay, adslAturChanCurrTxRate,
                adslAturChanPrevTxRate, adslAturChanCrcBlockLength
                }
             STATUS     current
             DESCRIPTION
                 "A collection of objects providing configuration
                information about an ADSL channel on the ATU-R
                side."
         ::= { adslGroups 16 }

         adslAturAtucPhysPerfRawCounterGroup OBJECT-GROUP
             OBJECTS {
                adslAtucPerfLofs, adslAtucPerfLoss,
                adslAtucPerfESs, adslAtucPerfInits
                }
             STATUS     current
             DESCRIPTION
                 "A collection of objects providing raw performance
                counts on an ADSL Line (ATU-C end) provided by the
                ATU-R agent."
         ::= { adslGroups 17 }

         adslAturAtucPhysPerfIntervalGroup OBJECT-GROUP
             OBJECTS {
                adslAtucPerfValidIntervals,
                adslAtucPerfInvalidIntervals,
                adslAtucPerfCurr15MinTimeElapsed,
                adslAtucPerfCurr15MinLofs, adslAtucPerfCurr15MinLoss,
                adslAtucPerfCurr15MinESs, adslAtucPerfCurr15MinInits,
                adslAtucPerfCurr1DayTimeElapsed,
                adslAtucPerfCurr1DayLofs, adslAtucPerfCurr1DayLoss,
                adslAtucPerfCurr1DayESs, adslAtucPerfCurr1DayInits,
                adslAtucPerfPrev1DayMoniSecs,
                adslAtucPerfPrev1DayLofs, adslAtucPerfPrev1DayLoss,
                adslAtucPerfPrev1DayESs, adslAtucPerfPrev1DayInits,
                adslAtucIntervalLofs, adslAtucIntervalLoss,
                adslAtucIntervalESs, adslAtucIntervalInits,
                adslAtucIntervalValidData
                }
             STATUS     current
             DESCRIPTION
                 "A collection of objects providing current

                15-minute, 1-day; and previous 1-day performance
                counts on ADSL Line (ATU-C end) provided by the
                ATU-R agent."
         ::= { adslGroups 18 }

         adslAturAturPhysPerfRawCounterGroup OBJECT-GROUP
             OBJECTS {
                adslAturPerfLofs, adslAturPerfLoss,
                adslAturPerfLprs, adslAturPerfESs
                }
             STATUS     current
             DESCRIPTION
                 "A collection of objects providing raw performance
                counts on an ADSL Line (ATU-R end) provided by the
                ATU-R agent."
         ::= { adslGroups 19 }

         adslAturAturPhysPerfIntervalGroup OBJECT-GROUP
             OBJECTS {
                adslAturPerfValidIntervals,
                adslAturPerfInvalidIntervals,
                adslAturPerfCurr15MinTimeElapsed,
                adslAturPerfCurr15MinLofs, adslAturPerfCurr15MinLoss,
                adslAturPerfCurr15MinLprs, adslAturPerfCurr15MinESs,
                adslAturPerfCurr1DayTimeElapsed,
                adslAturPerfCurr1DayLofs, adslAturPerfCurr1DayLoss,
                adslAturPerfCurr1DayLprs, adslAturPerfCurr1DayESs,
                adslAturPerfPrev1DayMoniSecs,
                adslAturPerfPrev1DayLofs, adslAturPerfPrev1DayLoss,
                adslAturPerfPrev1DayLprs, adslAturPerfPrev1DayESs,
                adslAturIntervalLofs,
                adslAturIntervalLoss, adslAturIntervalLprs,
                adslAturIntervalESs, adslAturIntervalValidData
                }
             STATUS     current
             DESCRIPTION
                 "A collection of objects providing current
                15-minute, 1-day; and previous 1-day performance
                counts on ADSL Line (ATU-R end) provided by the
                ATU-R agent."
         ::= { adslGroups 20 }

         adslAturAtucChanPerformanceGroup OBJECT-GROUP
             OBJECTS {
                adslAtucChanReceivedBlks,
                adslAtucChanTransmittedBlks,
                adslAtucChanCorrectedBlks,
                adslAtucChanUncorrectBlks,

                adslAtucChanPerfCurr15MinTimeElapsed,
                adslAtucChanPerfCurr15MinReceivedBlks,
                adslAtucChanPerfCurr15MinTransmittedBlks,
                adslAtucChanPerfCurr15MinCorrectedBlks,
                adslAtucChanPerfCurr15MinUncorrectBlks,
                adslAtucChanPerfCurr1DayTimeElapsed,
                adslAtucChanPerfCurr1DayReceivedBlks,
                adslAtucChanPerfCurr1DayTransmittedBlks,
                adslAtucChanPerfCurr1DayCorrectedBlks,
                adslAtucChanPerfCurr1DayUncorrectBlks,
                adslAtucChanPerfPrev1DayMoniSecs,
                adslAtucChanPerfPrev1DayReceivedBlks,
                adslAtucChanPerfPrev1DayTransmittedBlks,
                adslAtucChanPerfPrev1DayCorrectedBlks,
                adslAtucChanPerfPrev1DayUncorrectBlks,
                adslAtucChanPerfValidIntervals,
                adslAtucChanPerfInvalidIntervals,
                adslAtucChanIntervalReceivedBlks,
                adslAtucChanIntervalTransmittedBlks,
                adslAtucChanIntervalCorrectedBlks,
                adslAtucChanIntervalUncorrectBlks,
                adslAtucChanIntervalValidData
                }
             STATUS     current
             DESCRIPTION
                 "A collection of objects providing channel block
                 performance information on an ADSL channel
                 (ATU-C end) provided by the ATU-R agent."
         ::= { adslGroups 21 }

         adslAturAturChanPerformanceGroup OBJECT-GROUP
             OBJECTS {
                adslAturChanReceivedBlks,
                adslAturChanTransmittedBlks,
                adslAturChanCorrectedBlks,
                adslAturChanUncorrectBlks,
                adslAturChanPerfValidIntervals,
                adslAturChanPerfInvalidIntervals,
                adslAturChanPerfCurr15MinTimeElapsed,
                adslAturChanPerfCurr15MinReceivedBlks,
                adslAturChanPerfCurr15MinTransmittedBlks,
                adslAturChanPerfCurr15MinCorrectedBlks,
                adslAturChanPerfCurr15MinUncorrectBlks,
                adslAturChanPerfCurr1DayTimeElapsed,
                adslAturChanPerfCurr1DayReceivedBlks,
                adslAturChanPerfCurr1DayTransmittedBlks,
                adslAturChanPerfCurr1DayCorrectedBlks,
                adslAturChanPerfCurr1DayUncorrectBlks,

                adslAturChanPerfPrev1DayMoniSecs,
                adslAturChanPerfPrev1DayReceivedBlks,
                adslAturChanPerfPrev1DayTransmittedBlks,
                adslAturChanPerfPrev1DayCorrectedBlks,
                adslAturChanPerfPrev1DayUncorrectBlks,
                adslAturChanIntervalReceivedBlks,
                adslAturChanIntervalTransmittedBlks,
                adslAturChanIntervalCorrectedBlks,
                adslAturChanIntervalUncorrectBlks,
                adslAturChanIntervalValidData
                }
             STATUS     current
             DESCRIPTION
                 "A collection of objects providing channel block
                 performance information on an ADSL channel
                 (ATU-R end) provided by the ATU-R agent."
         ::= { adslGroups 22 }

         adslAturLineAlarmConfProfileGroup OBJECT-GROUP
             OBJECTS {
                adslAtucThresh15MinLofs, adslAtucThresh15MinLoss,
                adslAtucThresh15MinESs, adslAtucThreshFastRateUp,
                adslAtucThreshInterleaveRateUp,
                adslAtucThreshFastRateDown,
                adslAtucThreshInterleaveRateDown,
                adslAtucInitFailureTrapEnable,
                adslAturThresh15MinLofs, adslAturThresh15MinLoss,
                adslAturThresh15MinLprs, adslAturThresh15MinESs,
                adslAturThreshFastRateUp,
                adslAturThreshInterleaveRateUp,
                adslAturThreshFastRateDown,
                adslAturThreshInterleaveRateDown
                }
             STATUS     current
             DESCRIPTION
                 "A collection of objects providing alarm
provisioning
                 information about an ADSL Line provided by the
                 ATU-R agent."
         ::= { adslGroups 23 }

         adslAturLineConfProfileControlGroup OBJECT-GROUP
             OBJECTS {
                adslLineAlarmConfProfile,
                adslLineAlarmConfProfileRowStatus
                }
             STATUS     current
             DESCRIPTION

                 "A collection of objects providing profile
                 control for the ADSL system by the ATU-R agent."
         ::= { adslGroups 24 }

         adslAturNotificationsGroup NOTIFICATION-GROUP
             NOTIFICATIONS {
                 adslAtucPerfLofsThreshTrap,
                 adslAtucPerfLossThreshTrap,
                 adslAtucPerfESsThreshTrap,
                 adslAtucRateChangeTrap,
                 adslAturPerfLofsThreshTrap,
                 adslAturPerfLossThreshTrap,
                 adslAturPerfLprsThreshTrap,
                 adslAturPerfESsThreshTrap,
                 adslAturRateChangeTrap
                 }
             STATUS        current
             DESCRIPTION
                 "The collection of ADSL notifications implemented by
                 the ATU-R agent."
         ::= { adslGroups 25 }

END

ADSL-LINE-EXT-MIB DEFINITIONS ::= BEGIN

   IMPORTS
      Counter32,
      Integer32,
      NOTIFICATION-TYPE,
      MODULE-IDENTITY,
      OBJECT-TYPE                       FROM SNMPv2-SMI
      MODULE-COMPLIANCE, OBJECT-GROUP,
      NOTIFICATION-GROUP                FROM SNMPv2-CONF
      TEXTUAL-CONVENTION                FROM SNMPv2-TC
      PerfCurrentCount,


      PerfIntervalCount                 FROM PerfHist-TC-MIB
      AdslPerfCurrDayCount,
      AdslPerfPrevDayCount              FROM ADSL-TC-MIB
      SnmpAdminString                   FROM SNMP-FRAMEWORK-MIB
      adslLineAlarmConfProfileEntry,
      adslLineConfProfileEntry,
      adslAturIntervalEntry,
      adslAturPerfDataEntry,
      adslAtucIntervalEntry,
      adslAtucPerfDataEntry,
      adslLineEntry,
      adslMIB                           FROM ADSL-LINE-MIB
      ;

   adslExtMIB MODULE-IDENTITY

   LAST-UPDATED "200212100000Z"  -- 10 Dec 2002

   ORGANIZATION "IETF ADSL MIB Working Group"

   CONTACT-INFO
         "
          Faye Ly
          Pedestal Networks
          6503 Dumbarton Circle,
          Fremont, CA 94555
          Tel: +1 510-578-0158
          Fax: +1 510-744-5152
          E-Mail: faye@pedestalnetworks.com

          Gregory Bathrick
          Nokia Networks
          2235 Mercury Way,
          Fax: +1 707-535-7300
          E-Mail: greg.bathrick@nokia.com

          General Discussion:adslmib@ietf.org
          To Subscribe: https://www1.ietf.org/mailman/listinfo/adslmib
          Archive: https://www1.ietf.org/mailman/listinfo/adslmib
          "
   DESCRIPTION
           "Copyright (C) The Internet Society (2002). This version of
           this MIB module is part of RFC 3440; see the RFC itself for
           full legal notices.

           This MIB Module is a supplement to the ADSL-LINE-MIB
           [RFC2662]."


   REVISION     "200212100000Z"  -- 10 dec 2002
   DESCRIPTION  "Initial Version, published as RFC 3440. This MIB
                 module supplements the ADSL-LINE-MIB [RFC2662]."
          ::= { adslMIB 3 }

       adslExtMibObjects  OBJECT IDENTIFIER ::= { adslExtMIB 1 }

       AdslTransmissionModeType ::= TEXTUAL-CONVENTION
           STATUS       current
           DESCRIPTION
               "A set of ADSL line transmission modes, with one bit
                per mode.  The notes (F) and (L) denote Full-Rate
                and G.Lite respectively:
                  Bit 00 : Regional Std. (ANSI T1.413) (F)
                  Bit 01 : Regional Std. (ETSI DTS/TM06006) (F)
                  Bit 02 : G.992.1 POTS non-overlapped (F)
                  Bit 03 : G.992.1 POTS overlapped (F)
                  Bit 04 : G.992.1 ISDN non-overlapped (F)
                  Bit 05 : G.992.1 ISDN overlapped (F)
                  Bit 06 : G.992.1 TCM-ISDN non-overlapped (F)
                  Bit 07 : G.992.1 TCM-ISDN overlapped (F)
                  Bit 08 : G.992.2 POTS non-overlapped (L)
                  Bit 09 : G.992.2 POTS overlapped (L)
                  Bit 10 : G.992.2 with TCM-ISDN non-overlapped (L)
                  Bit 11 : G.992.2 with TCM-ISDN overlapped (L)
                  Bit 12 : G.992.1 TCM-ISDN symmetric (F)
               "
           SYNTAX      BITS {
               ansit1413(0),
               etsi(1),
               q9921PotsNonOverlapped(2),
               q9921PotsOverlapped(3),
               q9921IsdnNonOverlapped(4),
               q9921isdnOverlapped(5),
               q9921tcmIsdnNonOverlapped(6),
               q9921tcmIsdnOverlapped(7),
               q9922potsNonOverlapeed(8),
               q9922potsOverlapped(9),
               q9922tcmIsdnNonOverlapped(10),
               q9922tcmIsdnOverlapped(11),
               q9921tcmIsdnSymmetric(12)
           }

         adslLineExtTable   OBJECT-TYPE
             SYNTAX          SEQUENCE OF AdslLineExtEntry
             MAX-ACCESS      not-accessible
             STATUS          current
             DESCRIPTION


                 "This table is an extension of RFC 2662.  It
                  contains ADSL line configuration and
                  monitoring information. This includes the ADSL
                  line's capabilities and actual ADSL transmission
                  system."
         ::= { adslExtMibObjects 17 }

         adslLineExtEntry   OBJECT-TYPE
             SYNTAX          AdslLineExtEntry
             MAX-ACCESS      not-accessible
             STATUS          current
             DESCRIPTION
                 "An entry extends the adslLineEntry defined in
                  [RFC2662].  Each entry corresponds to an ADSL
                  line."
             AUGMENTS { adslLineEntry }
         ::= { adslLineExtTable 1 }

         AdslLineExtEntry ::=
             SEQUENCE {
             adslLineTransAtucCap        AdslTransmissionModeType,
             adslLineTransAtucConfig     AdslTransmissionModeType,
             adslLineTransAtucActual     AdslTransmissionModeType,
             adslLineGlitePowerState     INTEGER,
             adslLineConfProfileDualLite SnmpAdminString
             }

         adslLineTransAtucCap OBJECT-TYPE
             SYNTAX      AdslTransmissionModeType
             MAX-ACCESS  read-only
             STATUS      current
             DESCRIPTION
                 "The transmission modes, represented by a
                  bitmask that the ATU-C is capable of
                  supporting.  The modes available are limited
                  by the design of the equipment."
             REFERENCE "Section 7.3.2 ITU G.997.1"
         ::= { adslLineExtEntry 1 }

         adslLineTransAtucConfig OBJECT-TYPE
             SYNTAX      AdslTransmissionModeType
             MAX-ACCESS  read-write
             STATUS      current

             DESCRIPTION
                 "The transmission modes, represented by a bitmask,
                  currently enabled by the ATU-C.  The manager can
                  only set those modes that are supported by the


                  ATU-C.  An ATU-C's supported modes are provided by
                  AdslLineTransAtucCap."
             REFERENCE "Section 7.3.2 ITU G.997.1"
         ::= { adslLineExtEntry 2 }

         adslLineTransAtucActual OBJECT-TYPE
             SYNTAX      AdslTransmissionModeType
             MAX-ACCESS  read-only
             STATUS      current
             DESCRIPTION
                 "The actual transmission mode of the ATU-C.
                  During ADSL line initialization, the ADSL
                  Transceiver Unit - Remote terminal end (ATU-R)
                  will determine the mode used for the link.
                  This value will be limited a single transmission
                  mode that is a subset of those modes enabled
                  by the ATU-C and denoted by
                  adslLineTransAtucConfig. After an initialization
                  has occurred, its mode is saved as the 'Current'
                  mode and is persistence should the link go
                  down. This object returns 0 (i.e. BITS with no
                  mode bit set) if the mode is not known."
             REFERENCE "Section 7.3.2 ITU G.997.1 "
         ::= { adslLineExtEntry 3 }

         adslLineGlitePowerState OBJECT-TYPE
             SYNTAX      INTEGER {
                         none(1),
                         l0(2),          -- L0 Power on
                         l1(3),          -- L1 Power on but reduced
                         l3(4)           -- L3 Power off
                         }
             MAX-ACCESS  read-only
             STATUS      current
             DESCRIPTION
                 "The value of this object specifies the power
                  state of this interface.  L0 is power on, L1 is
                  power on but reduced and L3 is power off.  Power
                  state cannot be configured by an operator but it
                  can be viewed via the ifOperStatus object for the
                  managed ADSL interface.  The value of the object
                  ifOperStatus is set to down(2) if the ADSL
                  interface is in power state L3 and is set to up(1)
                  if the ADSL line interface is in power state L0 or
                  L1. If the object adslLineTransAtucActual is set to
                  a G.992.2 (G.Lite)-type transmission mode, the
                  value of this object will be one of the valid power
                  states: L0(2), L1(3), or L3(4).  Otherwise, its


                  value will be none(1)."
         ::= { adslLineExtEntry 4 }

         adslLineConfProfileDualLite OBJECT-TYPE
             SYNTAX SnmpAdminString
             MAX-ACCESS  read-write
             STATUS current
             DESCRIPTION
                 "This object extends the definition an ADSL line and
                  associated channels (when applicable) for cases
                  when it is configured in dual mode, and operating
                  in a G.Lite-type mode as denoted by
                  adslLineTransAtucActual.  Dual mode exists when the
                  object, adslLineTransAtucConfig, is configured with
                  one or more full-rate modes and one or more G.Lite
                  modes simultaneously.

                  When 'dynamic' profiles are implemented, the value
                  of object is equal to the index of the applicable
                  row in the ADSL Line Configuration Profile Table,
                  AdslLineConfProfileTable defined in ADSL-MIB
                  [RFC2662].

                  In the case when dual-mode has not been enabled,
                  the value of the object will be equal to the value
                  of the object adslLineConfProfile [RFC2662].

                  When `static' profiles are implemented, in much
                  like the case of the object,
                  adslLineConfProfileName [RFC2662], this object's
                  value will need to algorithmically represent the
                  characteristics of the line.  In this case, the
                  value of the line's ifIndex plus a value indicating
                  the line mode type (e.g., G.Lite, Full-rate) will
                  be used. Therefore, the profile's name is a string
                  concatenating the ifIndex and one of the follow
                  values: Full or Lite. This string will be
                  fixed-length (i.e., 14) with leading zero(s).  For
                  example, the profile name for ifIndex that equals
                  '15' and is a full rate line, it will be
                  '0000000015Full'."
             REFERENCE "Section 5.4 Profiles, RFC 2662"
         ::= { adslLineExtEntry 5 }

         adslAtucPerfDataExtTable   OBJECT-TYPE

             SYNTAX          SEQUENCE OF AdslAtucPerfDataExtEntry
             MAX-ACCESS      not-accessible


             STATUS          current
             DESCRIPTION
                 "This table extends adslAtucPerfDataTable [RFC2662]
                  with additional ADSL physical line counter
                  information such as unavailable seconds-line and
                  severely errored seconds-line."
         ::= { adslExtMibObjects 18 }

         adslAtucPerfDataExtEntry   OBJECT-TYPE
             SYNTAX          AdslAtucPerfDataExtEntry
             MAX-ACCESS      not-accessible
             STATUS          current
             DESCRIPTION
                 "An entry extends the adslAtucPerfDataEntry defined
                  in [RFC2662].  Each entry corresponds to an ADSL
                  line."
         AUGMENTS { adslAtucPerfDataEntry }
         ::= { adslAtucPerfDataExtTable 1 }

         AdslAtucPerfDataExtEntry ::=
             SEQUENCE {
             adslAtucPerfStatFastR            Counter32,
             adslAtucPerfStatFailedFastR      Counter32,
             adslAtucPerfStatSesL             Counter32,
             adslAtucPerfStatUasL             Counter32,
             adslAtucPerfCurr15MinFastR       PerfCurrentCount,
             adslAtucPerfCurr15MinFailedFastR PerfCurrentCount,
             adslAtucPerfCurr15MinSesL        PerfCurrentCount,
             adslAtucPerfCurr15MinUasL        PerfCurrentCount,
             adslAtucPerfCurr1DayFastR        AdslPerfCurrDayCount,
             adslAtucPerfCurr1DayFailedFastR  AdslPerfCurrDayCount,
             adslAtucPerfCurr1DaySesL         AdslPerfCurrDayCount,
             adslAtucPerfCurr1DayUasL         AdslPerfCurrDayCount,
             adslAtucPerfPrev1DayFastR        AdslPerfPrevDayCount,
             adslAtucPerfPrev1DayFailedFastR  AdslPerfPrevDayCount,
             adslAtucPerfPrev1DaySesL         AdslPerfPrevDayCount,
             adslAtucPerfPrev1DayUasL         AdslPerfPrevDayCount
         }

         adslAtucPerfStatFastR OBJECT-TYPE
             SYNTAX      Counter32
             UNITS       "line retrains"
             MAX-ACCESS  read-only
             STATUS      current
             DESCRIPTION
                 "The value of this object reports the count of
                  the number of fast line bs since last
                  agent reset."


             REFERENCE "ITU G.997.1 Section 7.4.15.1 "
         ::= { adslAtucPerfDataExtEntry 1 }

         adslAtucPerfStatFailedFastR OBJECT-TYPE
             SYNTAX      Counter32
             UNITS       "line retrains"
             MAX-ACCESS  read-only
             STATUS      current
             DESCRIPTION
                 "The value of this object reports the count of
                  the number of failed fast line retrains since
                  last agent reset."
             REFERENCE "ITU G.997.1 Section 7.4.15.2 "
         ::= { adslAtucPerfDataExtEntry 2 }

         adslAtucPerfStatSesL OBJECT-TYPE
             SYNTAX      Counter32
             UNITS       "seconds"
             MAX-ACCESS  read-only
             STATUS      current
             DESCRIPTION
                 "The value of this object reports the count of
                  the number of severely errored seconds-line since
                  last agent reset."
             REFERENCE "ITU G.997.1 Section 7.2.1.1.7 "
         ::= { adslAtucPerfDataExtEntry 3 }

         adslAtucPerfStatUasL OBJECT-TYPE
             SYNTAX      Counter32
             UNITS       "seconds"
             MAX-ACCESS  read-only
             STATUS      current
             DESCRIPTION
                 "The value of this object reports the count of
                  the number of unavailable seconds-line since
                  last agent reset."
             REFERENCE "ITU G.997.1 Section 7.2.1.1.9 "
         ::= { adslAtucPerfDataExtEntry 4 }

         adslAtucPerfCurr15MinFastR OBJECT-TYPE
             SYNTAX      PerfCurrentCount
             UNITS       "seconds"
             MAX-ACCESS  read-only
             STATUS      current
             DESCRIPTION
                 "For the current 15-minute interval,
                  adslAtucPerfCurr15MinFastR reports the current
                  number of seconds during which there have been


                  fast retrains."
             REFERENCE "ITU G.997.1 Section 7.4.15.1 "
         ::= { adslAtucPerfDataExtEntry 5 }

         adslAtucPerfCurr15MinFailedFastR   OBJECT-TYPE
             SYNTAX      PerfCurrentCount
             UNITS       "seconds"
             MAX-ACCESS  read-only
             STATUS      current
             DESCRIPTION
                 "For the current 15-minute interval,
                  adslAtucPerfCurr15MinFailedFastR reports the
                  current number of seconds during which there
                  have been failed fast retrains."
             REFERENCE "ITU G.997.1 Section 7.4.15.2 "
         ::= { adslAtucPerfDataExtEntry 6 }

         adslAtucPerfCurr15MinSesL OBJECT-TYPE
             SYNTAX      PerfCurrentCount
             UNITS       "seconds"
             MAX-ACCESS  read-only
             STATUS      current
             DESCRIPTION
                 "For the current 15-minute interval,
                  adslAtucPerfCurr15MinSesL reports the current
                  number of seconds during which there have been
                  severely errored seconds-line."
             REFERENCE "ITU G.997.1 Section 7.2.1.1.7 "
         ::= { adslAtucPerfDataExtEntry 7 }

         adslAtucPerfCurr15MinUasL   OBJECT-TYPE
             SYNTAX      PerfCurrentCount
             UNITS       "seconds"
             MAX-ACCESS  read-only
             STATUS      current
             DESCRIPTION
                 "For the current 15-minute interval,
                  adslAtucPerfCurr15MinUasL reports the current
                  number of seconds during which there have been
                  unavailable seconds-line."
             REFERENCE "ITU G.997.1 Section 7.2.1.1.9 "
         ::= { adslAtucPerfDataExtEntry 8 }

         adslAtucPerfCurr1DayFastR    OBJECT-TYPE
             SYNTAX      AdslPerfCurrDayCount
             UNITS       "seconds"
             MAX-ACCESS  read-only
             STATUS      current


             DESCRIPTION
                 "For the current day as measured by
                  adslAtucPerfCurr1DayTimeElapsed [RFC2662],
                  adslAtucPerfCurr1DayFastR reports the number
                  of seconds during which there have been
                  fast retrains."
             REFERENCE "ITU G.997.1 Section 7.4.15.1 "
         ::= { adslAtucPerfDataExtEntry 9 }

         adslAtucPerfCurr1DayFailedFastR    OBJECT-TYPE
             SYNTAX      AdslPerfCurrDayCount
             UNITS       "seconds"
             MAX-ACCESS  read-only
             STATUS      current
             DESCRIPTION
                 "For the current day as measured by
                  adslAtucPerfCurr1DayTimeElapsed [RFC2662],
                  adslAtucPerfCurr1DayFailedFastR reports the
                  number of seconds during which there have been
                  failed fast retrains."
             REFERENCE "ITU G.997.1 Section 7.4.15.2 "
         ::= { adslAtucPerfDataExtEntry 10 }

         adslAtucPerfCurr1DaySesL    OBJECT-TYPE
             SYNTAX      AdslPerfCurrDayCount
             UNITS       "seconds"
             MAX-ACCESS  read-only
             STATUS      current
             DESCRIPTION
                 "For the current day as measured by
                  adslAtucPerfCurr1DayTimeElapsed [RFC2662],
                  adslAtucPerfCurr1DaySesL reports the
                  number of seconds during which there have been
                  severely errored seconds-line."
             REFERENCE "ITU G.997.1 Section 7.2.1.1.7 "
         ::= { adslAtucPerfDataExtEntry 11 }

         adslAtucPerfCurr1DayUasL    OBJECT-TYPE
             SYNTAX      AdslPerfCurrDayCount
             UNITS       "seconds"
             MAX-ACCESS  read-only
             STATUS      current
             DESCRIPTION
                 "For the current day as measured by
                  adslAtucPerfCurr1DayTimeElapsed [RFC2662],
                  adslAtucPerfCurr1DayUasL reports the
                  number of seconds during which there have been
                  unavailable seconds-line."


             REFERENCE "ITU G.997.1 Section 7.2.1.1.9 "
         ::= { adslAtucPerfDataExtEntry 12 }

         adslAtucPerfPrev1DayFastR     OBJECT-TYPE
             SYNTAX      AdslPerfPrevDayCount
             UNITS       "seconds"
             MAX-ACCESS  read-only
             STATUS      current
             DESCRIPTION
                 "For the previous day, adslAtucPerfPrev1DayFastR
                  reports the number of seconds during which there
                  were fast retrains."
             REFERENCE "ITU G.997.1 Section 7.4.15.1 "
         ::= { adslAtucPerfDataExtEntry 13 }

         adslAtucPerfPrev1DayFailedFastR OBJECT-TYPE
             SYNTAX      AdslPerfPrevDayCount
             UNITS       "seconds"
             MAX-ACCESS  read-only
             STATUS      current
             DESCRIPTION
                 "For the previous day,
                  adslAtucPerfPrev1DayFailedFastR reports the number
                  of seconds during which there were failed fast
                  retrains."
             REFERENCE "ITU G.997.1 Section 7.4.15.2 "
         ::= { adslAtucPerfDataExtEntry 14 }

         adslAtucPerfPrev1DaySesL     OBJECT-TYPE
             SYNTAX      AdslPerfPrevDayCount
             UNITS       "seconds"
             MAX-ACCESS  read-only
             STATUS      current
             DESCRIPTION
                 "For the previous day, adslAtucPerfPrev1DaySesL
                  reports the number of seconds during which there
                  were severely errored seconds-line."
             REFERENCE "ITU G.997.1 Section 7.2.1.1.7 "
         ::= { adslAtucPerfDataExtEntry 15 }

         adslAtucPerfPrev1DayUasL OBJECT-TYPE
             SYNTAX      AdslPerfPrevDayCount
             UNITS       "seconds"
             MAX-ACCESS  read-only
             STATUS      current
             DESCRIPTION
                 "For the previous day, adslAtucPerfPrev1DayUasL
                  reports the number of seconds during which there


                  were unavailable seconds-line."
             REFERENCE "ITU G.997.1 Section 7.2.1.1.9 "
         ::= { adslAtucPerfDataExtEntry 16 }

         adslAtucIntervalExtTable   OBJECT-TYPE
             SYNTAX          SEQUENCE OF AdslAtucIntervalExtEntry
             MAX-ACCESS      not-accessible
             STATUS          current
             DESCRIPTION
                 "This table provides one row for each ATU-C
                  performance data collection interval for
                  ADSL physical interfaces whose
                  IfEntries' ifType is equal to adsl(94)."
         ::= { adslExtMibObjects 19 }

         adslAtucIntervalExtEntry   OBJECT-TYPE
             SYNTAX          AdslAtucIntervalExtEntry
             MAX-ACCESS      not-accessible
             STATUS          current
             DESCRIPTION     "An entry in the
                              adslAtucIntervalExtTable."
             AUGMENTS        { adslAtucIntervalEntry }
         ::= { adslAtucIntervalExtTable 1 }

         AdslAtucIntervalExtEntry ::=
             SEQUENCE {
             adslAtucIntervalFastR            PerfIntervalCount,
             adslAtucIntervalFailedFastR      PerfIntervalCount,
             adslAtucIntervalSesL             PerfIntervalCount,
             adslAtucIntervalUasL             PerfIntervalCount
             }

         adslAtucIntervalFastR OBJECT-TYPE
             SYNTAX      PerfIntervalCount
             UNITS       "seconds"
             MAX-ACCESS  read-only
             STATUS      current
             DESCRIPTION
                 "For the current interval, adslAtucIntervalFastR
                  reports the current number of seconds during which
                  there have been fast retrains."
         ::= { adslAtucIntervalExtEntry 1 }

         adslAtucIntervalFailedFastR OBJECT-TYPE
             SYNTAX      PerfIntervalCount
             UNITS       "seconds"
             MAX-ACCESS  read-only
             STATUS      current


             DESCRIPTION
                 "For the each interval, adslAtucIntervalFailedFastR
                  reports the number of seconds during which
                  there have been failed fast retrains."
         ::= { adslAtucIntervalExtEntry 2 }

         adslAtucIntervalSesL OBJECT-TYPE
             SYNTAX      PerfIntervalCount
             UNITS       "seconds"
             MAX-ACCESS  read-only
             STATUS      current
             DESCRIPTION
                 "For the each interval, adslAtucIntervalSesL
                  reports the number of seconds during which
                  there have been severely errored seconds-line."
         ::= { adslAtucIntervalExtEntry 3 }

         adslAtucIntervalUasL OBJECT-TYPE
             SYNTAX      PerfIntervalCount
             UNITS       "seconds"
             MAX-ACCESS  read-only
             STATUS      current
             DESCRIPTION
                 "For the each interval, adslAtucIntervalUasL
                  reports the number of seconds during which
                  there have been unavailable seconds-line."
         ::= { adslAtucIntervalExtEntry 4 }

         adslAturPerfDataExtTable   OBJECT-TYPE
             SYNTAX          SEQUENCE OF AdslAturPerfDataExtEntry
             MAX-ACCESS      not-accessible
             STATUS          current
             DESCRIPTION
                 "This table contains ADSL physical line counters
                  not defined in the adslAturPerfDataTable
                  from the ADSL-LINE-MIB [RFC2662]."
         ::= { adslExtMibObjects 20 }

         adslAturPerfDataExtEntry   OBJECT-TYPE
             SYNTAX          AdslAturPerfDataExtEntry
             MAX-ACCESS      not-accessible
             STATUS          current
             DESCRIPTION
                 "An entry extends the adslAturPerfDataEntry defined
                  in [RFC2662].  Each entry corresponds to an ADSL
                  line."
             AUGMENTS { adslAturPerfDataEntry }
         ::= { adslAturPerfDataExtTable 1 }


         AdslAturPerfDataExtEntry ::=
             SEQUENCE {
             adslAturPerfStatSesL             Counter32,
             adslAturPerfStatUasL             Counter32,
             adslAturPerfCurr15MinSesL        PerfCurrentCount,
             adslAturPerfCurr15MinUasL        PerfCurrentCount,
             adslAturPerfCurr1DaySesL         AdslPerfCurrDayCount,
             adslAturPerfCurr1DayUasL         AdslPerfCurrDayCount,
             adslAturPerfPrev1DaySesL         AdslPerfPrevDayCount,
             adslAturPerfPrev1DayUasL         AdslPerfPrevDayCount
         }

         adslAturPerfStatSesL OBJECT-TYPE
             SYNTAX      Counter32
             UNITS       "seconds"
             MAX-ACCESS  read-only
             STATUS      current
             DESCRIPTION
                 "The value of this object reports the count of
                  severely errored second-line since the last agent
                  reset."
             REFERENCE "ITU G.997.1 Section 7.2.1.1.7 "
         ::= { adslAturPerfDataExtEntry 1 }

         adslAturPerfStatUasL OBJECT-TYPE
             SYNTAX      Counter32
             UNITS       "seconds"
             MAX-ACCESS  read-only
             STATUS      current
             DESCRIPTION
                 "The value of this object reports the count of
                  unavailable seconds-line since the last agent
                  reset."
             REFERENCE "ITU G.997.1 Section 7.2.1.2.9 "
         ::= { adslAturPerfDataExtEntry 2 }

         adslAturPerfCurr15MinSesL OBJECT-TYPE
             SYNTAX      PerfCurrentCount
             UNITS       "seconds"
             MAX-ACCESS  read-only
             STATUS      current
             DESCRIPTION
                 "For the current 15-minute interval,
                  adslAturPerfCurr15MinSesL reports the current
                  number of seconds during which there have been
                  severely errored seconds-line."

             REFERENCE "ITU G.997.1 Section 7.2.1.2.7 "


         ::= { adslAturPerfDataExtEntry 3 }

         adslAturPerfCurr15MinUasL   OBJECT-TYPE
             SYNTAX      PerfCurrentCount
             UNITS       "seconds"
             MAX-ACCESS  read-only
             STATUS      current
             DESCRIPTION
                 "For the current 15-minute interval,
                  adslAturPerfCurr15MinUasL reports the current
                  number of seconds during which there have been
                  available seconds-line."
             REFERENCE "ITU G.997.1 Section 7.2.1.2.9 "
         ::= { adslAturPerfDataExtEntry 4 }

         adslAturPerfCurr1DaySesL    OBJECT-TYPE
             SYNTAX      AdslPerfCurrDayCount
             UNITS       "seconds"
             MAX-ACCESS  read-only
             STATUS      current
             DESCRIPTION
                 "For the current day as measured by
                  adslAturPerfCurr1DayTimeElapsed [RFC2662],
                  adslAturPerfCurr1DaySesL reports the
                  number of seconds during which there have been
                  severely errored seconds-line."
             REFERENCE "ITU G.997.1 Section 7.2.1.2.7 "
         ::= { adslAturPerfDataExtEntry 5 }

         adslAturPerfCurr1DayUasL    OBJECT-TYPE
             SYNTAX      AdslPerfCurrDayCount
             UNITS       "seconds"
             MAX-ACCESS  read-only
             STATUS      current
             DESCRIPTION
                 "For the current day as measured by
                  adslAturPerfCurr1DayTimeElapsed [RFC2662],
                  adslAturPerfCurr1DayUasL reports the
                  number of seconds during which there have been
                  unavailable seconds-line."
             REFERENCE "ITU G.997.1 Section 7.2.1.2.9 "
         ::= { adslAturPerfDataExtEntry 6 }

         adslAturPerfPrev1DaySesL     OBJECT-TYPE
             SYNTAX      AdslPerfPrevDayCount
             UNITS       "seconds"
             MAX-ACCESS  read-only
             STATUS      current


             DESCRIPTION
                 "For the previous day, adslAturPerfPrev1DaySesL
                  reports the number of seconds during which there
                  were severely errored seconds-line."
             REFERENCE "ITU G.997.1 Section 7.2.1.2.7 "
         ::= { adslAturPerfDataExtEntry 7 }

         adslAturPerfPrev1DayUasL OBJECT-TYPE
             SYNTAX      AdslPerfPrevDayCount
             UNITS       "seconds"
             MAX-ACCESS  read-only
             STATUS      current
             DESCRIPTION
                 "For the previous day, adslAturPerfPrev1DayUasL
                  reports the number of seconds during which there
                  were severely errored seconds-line."
             REFERENCE "ITU G.997.1 Section 7.2.1.2.9 "
         ::= { adslAturPerfDataExtEntry 8 }

         adslAturIntervalExtTable   OBJECT-TYPE
             SYNTAX          SEQUENCE OF AdslAturIntervalExtEntry
             MAX-ACCESS      not-accessible
             STATUS          current
             DESCRIPTION
                 "This table provides one row for each ATU-R
                  performance data collection interval for
                  ADSL physical interfaces whose
                  IfEntries' ifType is equal to adsl(94)."
         ::= { adslExtMibObjects 21 }

         adslAturIntervalExtEntry   OBJECT-TYPE
             SYNTAX          AdslAturIntervalExtEntry
             MAX-ACCESS      not-accessible
             STATUS          current
             DESCRIPTION     "An entry in the
                              adslAturIntervalExtTable."
             AUGMENTS        { adslAturIntervalEntry }
         ::= { adslAturIntervalExtTable 1 }

         AdslAturIntervalExtEntry ::=
             SEQUENCE {
             adslAturIntervalSesL             PerfIntervalCount,
             adslAturIntervalUasL             PerfIntervalCount
             }

         adslAturIntervalSesL OBJECT-TYPE
             SYNTAX      PerfIntervalCount
             UNITS       "seconds"


             MAX-ACCESS  read-only
             STATUS      current
             DESCRIPTION
                 "For the each interval, adslAturIntervalSesL
                  reports the number of seconds during which
                  there have been severely errored seconds-line."
         ::= { adslAturIntervalExtEntry 1 }

         adslAturIntervalUasL OBJECT-TYPE
             SYNTAX      PerfIntervalCount
             UNITS       "seconds"
             MAX-ACCESS  read-only
             STATUS      current
             DESCRIPTION
                 "For the each interval, adslAturIntervalUasL
                  reports the number of seconds during which
                  there have been unavailable seconds-line."
         ::= { adslAturIntervalExtEntry 2 }

         adslConfProfileExtTable   OBJECT-TYPE
             SYNTAX          SEQUENCE OF AdslConfProfileExtEntry
             MAX-ACCESS      not-accessible
             STATUS          current
             DESCRIPTION
                 "The adslConfProfileExtTable extends the ADSL line
                  profile configuration information in the
                  adslLineConfProfileTable from the ADSL-LINE-MIB
                  [RFC2662] by adding the ability to configure the
                  ADSL physical line mode."
         ::= { adslExtMibObjects 22 }

         adslConfProfileExtEntry   OBJECT-TYPE
             SYNTAX          AdslConfProfileExtEntry
             MAX-ACCESS      not-accessible
             STATUS          current
             DESCRIPTION
                 "An entry extends the adslLineConfProfileEntry
                  defined in [RFC2662].  Each entry corresponds to an
                  ADSL line profile."
             AUGMENTS { adslLineConfProfileEntry }
         ::= { adslConfProfileExtTable 1 }

         AdslConfProfileExtEntry ::=
             SEQUENCE {
                 adslConfProfileLineType  INTEGER
             }

         adslConfProfileLineType OBJECT-TYPE


             SYNTAX      INTEGER {
                 noChannel (1),        -- no channels exist
                 fastOnly (2),         -- only fast channel exists
                 interleavedOnly (3),  -- only interleaved channel
                                       -- exist
                 fastOrInterleaved (4),-- either fast or interleaved
                                       -- channels can exist, but
                                       -- only one at any time
                 fastAndInterleaved (5)-- both the fast channel and
                                       -- the interleaved channel
                                       -- exist
                 }
             MAX-ACCESS  read-create
             STATUS      current
             DESCRIPTION
                 "This object is used to configure the ADSL physical
                  line mode.  It has following valid values:

                  noChannel(1), when no channels exist.
                  fastOnly(2), when only fast channel exists.
                  interleavedOnly(3), when only interleaved channel
                      exist.
                  fastOrInterleaved(4), when either fast or
                      interleaved channels can exist, but only one
                      at any time.
                  fastAndInterleaved(5), when both the fast channel
                      and the interleaved channel exist.

                  In the case when no value has been set, the default
                  Value is noChannel(1).
                  "
             DEFVAL { fastOnly }
         ::= { adslConfProfileExtEntry 1 }

         adslAlarmConfProfileExtTable   OBJECT-TYPE
             SYNTAX          SEQUENCE OF AdslAlarmConfProfileExtEntry
             MAX-ACCESS      not-accessible
             STATUS          current
             DESCRIPTION
                 "This table extends the
                  adslLineAlarmConfProfileTable and provides
                  threshold parameters for all the counters defined
                  in this MIB module."
         ::= { adslExtMibObjects 23 }

         adslAlarmConfProfileExtEntry   OBJECT-TYPE
             SYNTAX          AdslAlarmConfProfileExtEntry
             MAX-ACCESS      not-accessible


             STATUS          current
             DESCRIPTION
                 "An entry extends the adslLineAlarmConfProfileTable
                  defined in [RFC2662].  Each entry corresponds to
                  an ADSL alarm profile."
             AUGMENTS { adslLineAlarmConfProfileEntry }
         ::= { adslAlarmConfProfileExtTable 1 }

         AdslAlarmConfProfileExtEntry ::=
             SEQUENCE {
             adslAtucThreshold15MinFailedFastR     Integer32,
             adslAtucThreshold15MinSesL            Integer32,
             adslAtucThreshold15MinUasL            Integer32,
             adslAturThreshold15MinSesL            Integer32,
             adslAturThreshold15MinUasL            Integer32
         }

         adslAtucThreshold15MinFailedFastR   OBJECT-TYPE
             SYNTAX      Integer32(0..900)
             UNITS       "seconds"
             MAX-ACCESS  read-create
             STATUS      current
             DESCRIPTION
                 "The first time the value of the corresponding
                  instance of adslAtucPerfCurr15MinFailedFastR
                  reaches or exceeds this value within a given
                  15-minute performance data collection period,
                  an adslAtucFailedFastRThreshTrap  notification
                  will be generated. The value '0' will disable
                  the notification. The default value of this
                  object is '0'."
             DEFVAL { 0 }
         ::= { adslAlarmConfProfileExtEntry 1 }

         adslAtucThreshold15MinSesL OBJECT-TYPE
             SYNTAX      Integer32(0..900)
             UNITS       "seconds"
             MAX-ACCESS  read-create
             STATUS      current
             DESCRIPTION
                 "The first time the value of the corresponding
                  instance of adslAtucPerf15MinSesL reaches or
                  exceeds this value within a given 15-minute
                  performance data collection period, an
                  adslAtucSesLThreshTrap notification will be
                  generated. The value '0' will disable the
                  notification.  The default value of this
                  object is '0'."


             DEFVAL { 0 }

         ::= { adslAlarmConfProfileExtEntry 2 }

         adslAtucThreshold15MinUasL OBJECT-TYPE
             SYNTAX      Integer32(0..900)
             UNITS       "seconds"
             MAX-ACCESS  read-create
             STATUS      current
             DESCRIPTION
                 "The first time the value of the corresponding
                  instance of adslAtucPerf15MinUasL reaches or
                  exceeds this value within a given 15-minute
                  performance data collection period, an
                  adslAtucUasLThreshTrap notification will be
                  generated. The value '0' will disable the
                  notification.  The default value of this
                  object is '0'."
             DEFVAL { 0 }
         ::= { adslAlarmConfProfileExtEntry 3 }

         adslAturThreshold15MinSesL OBJECT-TYPE
             SYNTAX      Integer32(0..900)
             UNITS       "seconds"
             MAX-ACCESS  read-create
             STATUS      current
             DESCRIPTION
                 "The first time the value of the corresponding
                  instance of adslAturPerf15MinSesL reaches or
                  exceeds this value within a given 15-minute
                  performance data collection period, an
                  adslAturSesLThreshTrap notification will be
                  generated. The value '0' will disable the
                  notification.  The default value of this
                  object is '0'."
             DEFVAL { 0 }
         ::= { adslAlarmConfProfileExtEntry 4 }

         adslAturThreshold15MinUasL OBJECT-TYPE
             SYNTAX      Integer32(0..900)
             UNITS       "seconds"
             MAX-ACCESS  read-create
             STATUS      current
             DESCRIPTION
                 "The first time the value of the corresponding
                  instance of adslAturPerf15MinUasL reaches or
                  exceeds this value within a given 15-minute
                  performance data collection period, an


                  adslAturUasLThreshTrap notification will be
                  generated. The value '0' will disable the
                  notification.  The default value of this
                  object is '0'."
             DEFVAL { 0 }

         ::= { adslAlarmConfProfileExtEntry 5 }

  --   definitions

   adslExtTraps OBJECT IDENTIFIER ::= { adslExtMibObjects 24 }

   adslExtAtucTraps OBJECT IDENTIFIER ::= { adslExtTraps 1 }

   adslExtAtucTrapsPrefix OBJECT IDENTIFIER ::= { adslExtAtucTraps 0 }

         adslAtucFailedFastRThreshTrap      NOTIFICATION-TYPE
             OBJECTS { adslAtucPerfCurr15MinFailedFastR }
             STATUS  current
             DESCRIPTION
                 "Failed Fast Retrains 15-minute threshold reached."
         ::= { adslExtAtucTrapsPrefix 1 }

         adslAtucSesLThreshTrap      NOTIFICATION-TYPE
             OBJECTS { adslAtucPerfCurr15MinSesL }
             STATUS  current
             DESCRIPTION
                 "Severely errored seconds-line 15-minute threshold
                  reached."
         ::= { adslExtAtucTrapsPrefix 2 }

         adslAtucUasLThreshTrap      NOTIFICATION-TYPE
             OBJECTS { adslAtucPerfCurr15MinUasL }
             STATUS  current
             DESCRIPTION
                 "Unavailable seconds-line 15-minute threshold
                  reached."
         ::= { adslExtAtucTrapsPrefix 3 }

   adslExtAturTraps OBJECT IDENTIFIER ::= { adslExtTraps 2 }

   adslExtAturTrapsPrefix OBJECT IDENTIFIER ::= { adslExtAturTraps 0 }

         adslAturSesLThreshTrap      NOTIFICATION-TYPE
             OBJECTS { adslAturPerfCurr15MinSesL }
             STATUS  current
             DESCRIPTION


                 "Severely errored seconds-line 15-minute threshold
                  reached."
         ::= { adslExtAturTrapsPrefix 1 }

         adslAturUasLThreshTrap      NOTIFICATION-TYPE
             OBJECTS { adslAturPerfCurr15MinUasL }
             STATUS  current
             DESCRIPTION
                 "Unavailable seconds-line 15-minute threshold
                  reached."
         ::= { adslExtAturTrapsPrefix 2 }

   -- conformance information

   adslExtConformance OBJECT IDENTIFIER ::= { adslExtMIB 2 }

   adslExtGroups OBJECT IDENTIFIER ::= { adslExtConformance 1 }
   adslExtCompliances OBJECT IDENTIFIER ::= { adslExtConformance 2 }

         -- ATU-C agent compliance statements

         adslExtLineMibAtucCompliance MODULE-COMPLIANCE
             STATUS  current
             DESCRIPTION
                 "The compliance statement for SNMP entities which
                  represent ADSL ATU-C interfaces."

             MODULE  -- this module
             MANDATORY-GROUPS
                {
                adslExtLineGroup,
                adslExtLineConfProfileControlGroup,
                adslExtLineAlarmConfProfileGroup
                }

             GROUP       adslExtAtucPhysPerfCounterGroup
             DESCRIPTION
                 "This group is optional.  Implementations which
                  require continuous ATU-C physical event counters
                  should implement this group."

             GROUP       adslExtAturPhysPerfCounterGroup
             DESCRIPTION
                 "This group is optional.  Implementations which
                  require continuous ATU-R physical event counters
                  should implement this group."


             GROUP   adslExtNotificationsGroup
             DESCRIPTION
           "This group is optional.  Implementations which
                  support TCA (Threshold Crossing Alert) should
                  implement this group."

             OBJECT      adslAtucThreshold15MinFailedFastR
             MIN-ACCESS  read-write
             DESCRIPTION
                 "Read-write access is applicable only when
                  static profiles as defined in ADSL Line MIB
                  [RFC2662] are implemented."

             OBJECT      adslAtucThreshold15MinSesL
             MIN-ACCESS  read-write
             DESCRIPTION
                 "Read-write access is applicable only when
                  static profiles as defined in ADSL Line MIB
                  [RFC2662] are implemented."

             OBJECT      adslAtucThreshold15MinUasL
             MIN-ACCESS  read-write
             DESCRIPTION
                 "Read-write access is applicable only when
                  static profiles as defined in ADSL Line MIB
                  [RFC2662] are implemented."

             OBJECT      adslAturThreshold15MinSesL
             MIN-ACCESS  read-write
             DESCRIPTION
                 "Read-write access is applicable only when
                  static profiles as defined in ADSL Line MIB
                  [RFC2662] are implemented."

             OBJECT      adslAturThreshold15MinUasL
             MIN-ACCESS  read-write
             DESCRIPTION
                 "Read-write access is applicable only when
                  static profiles as defined in ADSL Line MIB
                  [RFC2662] are implemented."

             OBJECT      adslLineConfProfileDualLite
             MIN-ACCESS  read-only
             DESCRIPTION
                 "Read-only access is applicable only when
                  static profiles as defined in ADSL Line MIB
                  [RFC2662] are implemented."


         ::= { adslExtCompliances 1 }

         -- units of conformance
         adslExtLineGroup    OBJECT-GROUP
             OBJECTS {
                 adslLineConfProfileDualLite,
                 adslLineTransAtucCap,
                 adslLineTransAtucConfig,
                 adslLineTransAtucActual,
                 adslLineGlitePowerState
                }
             STATUS     current
             DESCRIPTION
                 "A collection of objects providing extended
                 configuration information about an ADSL Line."
         ::= { adslExtGroups 1 }

         adslExtAtucPhysPerfCounterGroup OBJECT-GROUP
             OBJECTS {
                 adslAtucPerfStatFastR,
                 adslAtucPerfStatFailedFastR,
                 adslAtucPerfCurr15MinFastR,
                 adslAtucPerfCurr15MinFailedFastR,
                 adslAtucPerfCurr1DayFastR,
                 adslAtucPerfCurr1DayFailedFastR,
                 adslAtucPerfPrev1DayFastR,
                 adslAtucPerfPrev1DayFailedFastR,
                 adslAtucPerfStatSesL,
                 adslAtucPerfStatUasL,
                 adslAtucPerfCurr15MinSesL,
                 adslAtucPerfCurr15MinUasL,
                 adslAtucPerfCurr1DaySesL,
                 adslAtucPerfCurr1DayUasL,
                 adslAtucPerfPrev1DaySesL,
                 adslAtucPerfPrev1DayUasL,
                 adslAtucIntervalFastR,
                 adslAtucIntervalFailedFastR,
                 adslAtucIntervalSesL,
                 adslAtucIntervalUasL
                }
             STATUS     current
             DESCRIPTION
                 "A collection of objects providing raw performance
                 counts on an ADSL Line (ATU-C end)."
         ::= { adslExtGroups 2 }

         adslExtAturPhysPerfCounterGroup OBJECT-GROUP
             OBJECTS {


                 adslAturPerfStatSesL,
                 adslAturPerfStatUasL,
                 adslAturPerfCurr15MinSesL,
                 adslAturPerfCurr15MinUasL,
                 adslAturPerfCurr1DaySesL,
                 adslAturPerfCurr1DayUasL,
                 adslAturPerfPrev1DaySesL,
                 adslAturPerfPrev1DayUasL,
                 adslAturIntervalSesL, adslAturIntervalUasL
                }
             STATUS     current
             DESCRIPTION
                 "A collection of objects providing raw performance
                 counts on an ADSL Line (ATU-C end)."
         ::= { adslExtGroups 3 }

         adslExtLineConfProfileControlGroup OBJECT-GROUP
             OBJECTS {
                 adslConfProfileLineType
                }
             STATUS     current
             DESCRIPTION
                 "A collection of objects providing profile
                 control for the ADSL system."
         ::= { adslExtGroups 4 }

         adslExtLineAlarmConfProfileGroup OBJECT-GROUP
             OBJECTS {
                    adslAtucThreshold15MinFailedFastR,
                    adslAtucThreshold15MinSesL,
                    adslAtucThreshold15MinUasL,
                    adslAturThreshold15MinSesL,
                    adslAturThreshold15MinUasL
                }
             STATUS     current
             DESCRIPTION
                 "A collection of objects providing alarm profile
                 control for the ADSL system."
         ::= { adslExtGroups 5 }

         adslExtNotificationsGroup NOTIFICATION-GROUP
             NOTIFICATIONS {
                 adslAtucFailedFastRThreshTrap,
                 adslAtucSesLThreshTrap,
                 adslAtucUasLThreshTrap,
                 adslAturSesLThreshTrap,
                 adslAturUasLThreshTrap
             }


             STATUS        current
             DESCRIPTION
                 "The collection of ADSL extension notifications."
            ::= { adslExtGroups 6 }

END

BRIDGE-MIB DEFINITIONS ::= BEGIN

IMPORTS
           Counter, TimeTicks
                   FROM RFC1155-SMI
           mib-2
                   FROM RFC1213-MIB
           OBJECT-TYPE
                   FROM RFC-1212
           TRAP-TYPE
                   FROM RFC-1215;

-- All representations of MAC addresses in this MIB Module
-- use, as a textual convention (i.e. this convention does
-- not affect their encoding), the data type:

MacAddress ::= OCTET STRING (SIZE (6))    -- a 6 octet address
                                          -- in the
                                          -- "canonical"
                                          -- order
-- defined by IEEE 802.1a, i.e., as if it were transmitted
-- least significant bit first, even though 802.5 (in
-- contrast to other n802.x protocols) requires MAC
-- addresses to be transmitted most significant bit first.
--
-- 16-bit addresses, if needed, are represented by setting
-- their upper 4 octets to all 0's, i.e., AAFF would be
-- represented as 00000000AAFF.


-- Similarly, all representations of Bridge-Id in this MIB
-- Module use, as a textual convention (i.e. this
-- convention does not affect their encoding), the data
-- type:

BridgeId ::= OCTET STRING (SIZE (8))   -- the
                                       -- Bridge-Identifier
                                       -- as used in the
                                       -- Spanning Tree
-- Protocol to uniquely identify a bridge.  Its first two
-- octets (in network byte order) contain a priority
-- value and its last 6 octets contain the MAC address
-- used to refer to a bridge in a unique fashion
-- (typically, the numerically smallest MAC address
-- of all ports on the bridge).

-- Several objects in this MIB module represent values of
-- timers used by the Spanning Tree Protocol.  In this
-- MIB, these timers have values in units of hundreths of
-- a second (i.e. 1/100 secs).
-- These timers, when stored in a Spanning Tree Protocol's
-- BPDU, are in units of 1/256 seconds.  Note, however,
-- that 802.1D-1990 specifies a settable granularity of
-- no more than 1 second for these timers.  To avoid
-- ambiguity, a data type is defined here as a textual
-- convention and all representation of these timers
-- in this MIB module are defined using this data type.  An
-- algorithm is also defined for converting between the
-- different units, to ensure a timer's value is not
-- distorted by multiple conversions.
-- The data type is:

Timeout ::= INTEGER -- a STP timer in units of 1/100 seconds

-- To convert a Timeout value into a value in units of
-- 1/256 seconds, the following algorithm should be used:
--
--      b  = floor( (n * 256) / 100)
--
-- where:
--      floor   =  quotient [ignore remainder]
--      n is the value in 1/100 second units
--      b is the value in 1/256 second units
--
-- To convert the value from 1/256 second units back to
-- 1/100 seconds, the following algorithm should be used:
--
--      n = ceiling( (b * 100) / 256)
--
-- where:
--      ceiling =  quotient [if remainder is 0], or
--                 quotient + 1 [if remainder is non-zero]
--      n is the value in 1/100 second units
--      b is the value in 1/256 second units
--
-- Note: it is important that the arithmetic operations are
-- done in the order specified (i.e., multiply first, divide
-- second).


   dot1dBridge   OBJECT IDENTIFIER ::= { mib-2 17 }



-- groups in the Bridge MIB

dot1dBase     OBJECT IDENTIFIER ::= { dot1dBridge 1 }

dot1dStp      OBJECT IDENTIFIER ::= { dot1dBridge 2 }

dot1dSr       OBJECT IDENTIFIER ::= { dot1dBridge 3 }
-- separately documented

dot1dTp       OBJECT IDENTIFIER ::= { dot1dBridge 4 }

dot1dStatic   OBJECT IDENTIFIER ::= { dot1dBridge 5 }


-- the dot1dBase group

-- Implementation of the dot1dBase group is mandatory for all
-- bridges.

dot1dBaseBridgeAddress OBJECT-TYPE
    SYNTAX  MacAddress
    ACCESS  read-only
    STATUS  mandatory
    DESCRIPTION
            "The MAC address used by this bridge when it must
            be referred to in a unique fashion.   It is
            recommended that this be the numerically smallest
            MAC address of all ports that belong to this
            bridge.  However it is only required to be unique.
            When concatenated with dot1dStpPriority a unique
            BridgeIdentifier is formed which is used in the
            Spanning Tree Protocol."
    REFERENCE
            "IEEE 802.1D-1990: Sections 6.4.1.1.3 and 3.12.5"
    ::= { dot1dBase 1 }

dot1dBaseNumPorts OBJECT-TYPE
    SYNTAX  INTEGER
    ACCESS  read-only
    STATUS  mandatory
    DESCRIPTION
            "The number of ports controlled by this bridging
            entity."
    REFERENCE
            "IEEE 802.1D-1990: Section 6.4.1.1.3"
    ::= { dot1dBase 2 }

dot1dBaseType OBJECT-TYPE
    SYNTAX  INTEGER {
                unknown(1),
                transparent-only(2),
                sourceroute-only(3),
                srt(4)
            }
    ACCESS  read-only
    STATUS  mandatory
    DESCRIPTION
            "Indicates what type of bridging this bridge can
            perform.  If a bridge is actually performing a
            certain type of bridging this will be indicated by
            entries in the port table for the given type."
    ::= { dot1dBase 3 }

-- The Generic Bridge Port Table

dot1dBasePortTable OBJECT-TYPE
    SYNTAX  SEQUENCE OF Dot1dBasePortEntry
    ACCESS  not-accessible
    STATUS  mandatory
    DESCRIPTION
            "A table that contains generic information about
            every port that is associated with this bridge.
            Transparent, source-route, and srt ports are
            included."
    ::= { dot1dBase 4 }

dot1dBasePortEntry OBJECT-TYPE
    SYNTAX  Dot1dBasePortEntry
    ACCESS  not-accessible
    STATUS  mandatory
    DESCRIPTION
            "A list of information for each port of the
            bridge."
    REFERENCE
            "IEEE 802.1D-1990: Section 6.4.2, 6.6.1"
    INDEX  { dot1dBasePort }
    ::= { dot1dBasePortTable 1 }


Dot1dBasePortEntry ::=
    SEQUENCE {
        dot1dBasePort
            INTEGER,
        dot1dBasePortIfIndex
            INTEGER,
        dot1dBasePortCircuit
            OBJECT IDENTIFIER,
        dot1dBasePortDelayExceededDiscards
            Counter,
        dot1dBasePortMtuExceededDiscards
            Counter
    }

dot1dBasePort OBJECT-TYPE
    SYNTAX  INTEGER (1..65535)
    ACCESS  read-only
    STATUS  mandatory
    DESCRIPTION
            "The port number of the port for which this entry
            contains bridge management information."
    ::= { dot1dBasePortEntry 1 }

dot1dBasePortIfIndex OBJECT-TYPE
    SYNTAX  INTEGER
    ACCESS  read-only
    STATUS  mandatory
    DESCRIPTION
            "The value of the instance of the ifIndex object,
            defined in MIB-II, for the interface corresponding
            to this port."
    ::= { dot1dBasePortEntry 2 }

dot1dBasePortCircuit OBJECT-TYPE
    SYNTAX  OBJECT IDENTIFIER
    ACCESS  read-only
    STATUS  mandatory
    DESCRIPTION
            "For a port which (potentially) has the same value
            of dot1dBasePortIfIndex as another port on the
            same bridge, this object contains the name of an
            object instance unique to this port.  For example,
            in the case where multiple ports correspond one-
            to-one with multiple X.25 virtual circuits, this
            value might identify an (e.g., the first) object
            instance associated with the X.25 virtual circuit
            corresponding to this port.

            For a port which has a unique value of
            dot1dBasePortIfIndex, this object can have the
            value { 0 0 }."
    ::= { dot1dBasePortEntry 3 }

dot1dBasePortDelayExceededDiscards OBJECT-TYPE
    SYNTAX  Counter
    ACCESS  read-only
    STATUS  mandatory
    DESCRIPTION
            "The number of frames discarded by this port due
            to excessive transit delay through the bridge.  It
            is incremented by both transparent and source
            route bridges."
    REFERENCE
             "IEEE 802.1D-1990: Section 6.6.1.1.3"
    ::= { dot1dBasePortEntry 4 }

dot1dBasePortMtuExceededDiscards OBJECT-TYPE
    SYNTAX  Counter
    ACCESS  read-only
    STATUS  mandatory
    DESCRIPTION
            "The number of frames discarded by this port due
            to an excessive size.  It is incremented by both
            transparent and source route bridges."
    REFERENCE
            "IEEE 802.1D-1990: Section 6.6.1.1.3"
    ::= { dot1dBasePortEntry 5 }


-- the dot1dStp group

-- Implementation of the dot1dStp group is optional.  It is
-- implemented by those bridges that support the Spanning Tree
-- Protocol.


dot1dStpProtocolSpecification OBJECT-TYPE
    SYNTAX  INTEGER {
                unknown(1),
                decLb100(2),
                ieee8021d(3)
            }
    ACCESS  read-only
    STATUS  mandatory
    DESCRIPTION
            "An indication of what version of the Spanning
            Tree Protocol is being run.  The value
            'decLb100(2)' indicates the DEC LANbridge 100
            Spanning Tree protocol.  IEEE 802.1d
            implementations will return 'ieee8021d(3)'.  If
            future versions of the IEEE Spanning Tree Protocol
            are released that are incompatible with the
            current version a new value will be defined."
    ::= { dot1dStp 1 }

dot1dStpPriority OBJECT-TYPE
    SYNTAX  INTEGER (0..65535)
    ACCESS  read-write
    STATUS  mandatory
    DESCRIPTION
            "The value of the write-able portion of the Bridge
            ID, i.e., the first two octets of the (8 octet
            long) Bridge ID.  The other (last) 6 octets of the
            Bridge ID are given by the value of
            dot1dBaseBridgeAddress."
    REFERENCE
            "IEEE 802.1D-1990: Section 4.5.3.7"
    ::= { dot1dStp 2 }

dot1dStpTimeSinceTopologyChange OBJECT-TYPE
    SYNTAX  TimeTicks
    ACCESS  read-only
    STATUS  mandatory
    DESCRIPTION
            "The time (in hundredths of a second) since the
            last time a topology change was detected by the
            bridge entity."
    REFERENCE
            "IEEE 802.1D-1990: Section 6.8.1.1.3"
    ::= { dot1dStp 3 }

dot1dStpTopChanges OBJECT-TYPE
    SYNTAX  Counter
    ACCESS  read-only
    STATUS  mandatory
    DESCRIPTION
            "The total number of topology changes detected by
            this bridge since the management entity was last
            reset or initialized."
    REFERENCE
            "IEEE 802.1D-1990: Section 6.8.1.1.3"
    ::= { dot1dStp 4 }

dot1dStpDesignatedRoot OBJECT-TYPE
    SYNTAX  BridgeId
    ACCESS  read-only
    STATUS  mandatory
    DESCRIPTION
            "The bridge identifier of the root of the spanning
            tree as determined by the Spanning Tree Protocol
            as executed by this node.  This value is used as
            the Root Identifier parameter in all Configuration
            Bridge PDUs originated by this node."
    REFERENCE
            "IEEE 802.1D-1990: Section 4.5.3.1"
    ::= { dot1dStp 5 }

dot1dStpRootCost OBJECT-TYPE
    SYNTAX  INTEGER
    ACCESS  read-only
    STATUS  mandatory
    DESCRIPTION
            "The cost of the path to the root as seen from
            this bridge."
    REFERENCE
            "IEEE 802.1D-1990: Section 4.5.3.2"
    ::= { dot1dStp 6 }

dot1dStpRootPort OBJECT-TYPE
    SYNTAX  INTEGER
    ACCESS  read-only
    STATUS  mandatory
    DESCRIPTION
            "The port number of the port which offers the
            lowest cost path from this bridge to the root
            bridge."
    REFERENCE
            "IEEE 802.1D-1990: Section 4.5.3.3"
    ::= { dot1dStp 7 }

dot1dStpMaxAge OBJECT-TYPE
    SYNTAX  Timeout
    ACCESS  read-only
    STATUS  mandatory
    DESCRIPTION
            "The maximum age of Spanning Tree Protocol
            information learned from the network on any port
            before it is discarded, in units of hundredths of
            a second.  This is the actual value that this
            bridge is currently using."
    REFERENCE
            "IEEE 802.1D-1990: Section 4.5.3.4"
    ::= { dot1dStp 8 }

dot1dStpHelloTime OBJECT-TYPE
    SYNTAX  Timeout
    ACCESS  read-only
    STATUS  mandatory
    DESCRIPTION
            "The amount of time between the transmission of
            Configuration bridge PDUs by this node on any port
            when it is the root of the spanning tree or trying
            to become so, in units of hundredths of a second.
            This is the actual value that this bridge is
            currently using."
    REFERENCE
            "IEEE 802.1D-1990: Section 4.5.3.5"
    ::= { dot1dStp 9 }

dot1dStpHoldTime OBJECT-TYPE
    SYNTAX  INTEGER
    ACCESS  read-only
    STATUS  mandatory
    DESCRIPTION
            "This time value determines the interval length
            during which no more than two Configuration bridge
            PDUs shall be transmitted by this node, in units
            of hundredths of a second."
    REFERENCE
            "IEEE 802.1D-1990: Section 4.5.3.14"
    ::= { dot1dStp 10 }

dot1dStpForwardDelay OBJECT-TYPE
    SYNTAX  Timeout
    ACCESS  read-only
    STATUS  mandatory
    DESCRIPTION
            "This time value, measured in units of hundredths
            of a second, controls how fast a port changes its
            spanning state when moving towards the Forwarding
            state.  The value determines how long the port
            stays in each of the Listening and Learning
            states, which precede the Forwarding state.  This
            value is also used, when a topology change has
            been detected and is underway, to age all dynamic
            entries in the Forwarding Database.  [Note that
            this value is the one that this bridge is
            currently using, in contrast to
            dot1dStpBridgeForwardDelay which is the value that
            this bridge and all others would start using
            if/when this bridge were to become the root.]"
    REFERENCE
            "IEEE 802.1D-1990: Section 4.5.3.6"
    ::= { dot1dStp 11 }

dot1dStpBridgeMaxAge OBJECT-TYPE
    SYNTAX  Timeout (600..4000)
    ACCESS  read-write
    STATUS  mandatory
    DESCRIPTION
            "The value that all bridges use for MaxAge when
            this bridge is acting as the root.  Note that
            802.1D-1990 specifies that the range for this
            parameter is related to the value of
            dot1dStpBridgeHelloTime. The granularity of this
            timer is specified by 802.1D-1990 to be 1 second.
            An agent may return a badValue error if a set is
            attempted to a value which is not a whole number
            of seconds."
    REFERENCE
            "IEEE 802.1D-1990: Section 4.5.3.8"
    ::= { dot1dStp 12 }

dot1dStpBridgeHelloTime OBJECT-TYPE
    SYNTAX  Timeout (100..1000)
    ACCESS  read-write
    STATUS  mandatory
    DESCRIPTION
            "The value that all bridges use for HelloTime when
            this bridge is acting as the root.  The
            granularity of this timer is specified by 802.1D-
            1990 to be 1 second.  An agent may return a
            badValue error if a set is attempted to a value
            which is not a whole number of seconds."
    REFERENCE
            "IEEE 802.1D-1990: Section 4.5.3.9"
    ::= { dot1dStp 13 }

dot1dStpBridgeForwardDelay OBJECT-TYPE
    SYNTAX  Timeout (400..3000)
    ACCESS  read-write
    STATUS  mandatory
    DESCRIPTION
            "The value that all bridges use for ForwardDelay
            when this bridge is acting as the root.  Note that
            802.1D-1990 specifies that the range for this
            parameter is related to the value of
            dot1dStpBridgeMaxAge.  The granularity of this
            timer is specified by 802.1D-1990 to be 1 second.
            An agent may return a badValue error if a set is
            attempted to a value which is not a whole number
            of seconds."
    REFERENCE
            "IEEE 802.1D-1990: Section 4.5.3.10"
    ::= { dot1dStp 14 }
-- The Spanning Tree Port Table

dot1dStpPortTable OBJECT-TYPE
    SYNTAX  SEQUENCE OF Dot1dStpPortEntry
    ACCESS  not-accessible
    STATUS  mandatory
    DESCRIPTION
            "A table that contains port-specific information
            for the Spanning Tree Protocol."
    ::= { dot1dStp 15 }

dot1dStpPortEntry OBJECT-TYPE
    SYNTAX  Dot1dStpPortEntry
    ACCESS  not-accessible
    STATUS  mandatory
    DESCRIPTION
            "A list of information maintained by every port
            about the Spanning Tree Protocol state for that
            port."
    INDEX   { dot1dStpPort }
    ::= { dot1dStpPortTable 1 }

Dot1dStpPortEntry ::=
    SEQUENCE {
        dot1dStpPort
            INTEGER,
        dot1dStpPortPriority
            INTEGER,
        dot1dStpPortState
            INTEGER,
        dot1dStpPortEnable
            INTEGER,
        dot1dStpPortPathCost
            INTEGER,
        dot1dStpPortDesignatedRoot
            BridgeId,
        dot1dStpPortDesignatedCost
            INTEGER,
        dot1dStpPortDesignatedBridge
            BridgeId,
        dot1dStpPortDesignatedPort
            OCTET STRING,
        dot1dStpPortForwardTransitions
            Counter
    }

dot1dStpPort OBJECT-TYPE
    SYNTAX  INTEGER (1..65535)
    ACCESS  read-only
    STATUS  mandatory
    DESCRIPTION
            "The port number of the port for which this entry
            contains Spanning Tree Protocol management
            information."
    REFERENCE
            "IEEE 802.1D-1990: Section 6.8.2.1.2"
    ::= { dot1dStpPortEntry 1 }

dot1dStpPortPriority OBJECT-TYPE
    SYNTAX  INTEGER (0..255)
    ACCESS  read-write
    STATUS  mandatory
    DESCRIPTION
            "The value of the priority field which is
            contained in the first (in network byte order)
            octet of the (2 octet long) Port ID.  The other
            octet of the Port ID is given by the value of
            dot1dStpPort."
    REFERENCE
            "IEEE 802.1D-1990: Section 4.5.5.1"
    ::= { dot1dStpPortEntry 2 }

dot1dStpPortState OBJECT-TYPE
    SYNTAX  INTEGER {
                disabled(1),
                blocking(2),
                listening(3),
                learning(4),
                forwarding(5),
                broken(6)
            }
    ACCESS  read-only
    STATUS  mandatory
    DESCRIPTION
            "The port's current state as defined by
            application of the Spanning Tree Protocol.  This
            state controls what action a port takes on
            reception of a frame.  If the bridge has detected
            a port that is malfunctioning it will place that
            port into the broken(6) state.  For ports which
            are disabled (see dot1dStpPortEnable), this object
            will have a value of disabled(1)."
    REFERENCE
            "IEEE 802.1D-1990: Section 4.5.5.2"
    ::= { dot1dStpPortEntry 3 }

dot1dStpPortEnable OBJECT-TYPE
    SYNTAX  INTEGER {
                enabled(1),
                disabled(2)
            }
    ACCESS  read-write
    STATUS  mandatory
    DESCRIPTION
            "The enabled/disabled status of the port."
    REFERENCE
            "IEEE 802.1D-1990: Section 4.5.5.2"
    ::= { dot1dStpPortEntry 4 }

dot1dStpPortPathCost OBJECT-TYPE
    SYNTAX  INTEGER (1..65535)
    ACCESS  read-write
    STATUS  mandatory
    DESCRIPTION
            "The contribution of this port to the path cost of
            paths towards the spanning tree root which include
            this port.  802.1D-1990 recommends that the
            default value of this parameter be in inverse
            proportion to the speed of the attached LAN."
    REFERENCE
            "IEEE 802.1D-1990: Section 4.5.5.3"
    ::= { dot1dStpPortEntry 5 }

dot1dStpPortDesignatedRoot OBJECT-TYPE
    SYNTAX  BridgeId
    ACCESS  read-only
    STATUS  mandatory
    DESCRIPTION
            "The unique Bridge Identifier of the Bridge
            recorded as the Root in the Configuration BPDUs
            transmitted by the Designated Bridge for the
            segment to which the port is attached."
    REFERENCE
            "IEEE 802.1D-1990: Section 4.5.5.4"
    ::= { dot1dStpPortEntry 6 }

dot1dStpPortDesignatedCost OBJECT-TYPE
    SYNTAX  INTEGER
    ACCESS  read-only
    STATUS  mandatory
    DESCRIPTION
            "The path cost of the Designated Port of the
            segment connected to this port.  This value is
            compared to the Root Path Cost field in received
            bridge PDUs."
    REFERENCE
            "IEEE 802.1D-1990: Section 4.5.5.5"
    ::= { dot1dStpPortEntry 7 }

dot1dStpPortDesignatedBridge OBJECT-TYPE
    SYNTAX  BridgeId
    ACCESS  read-only
    STATUS  mandatory
    DESCRIPTION
            "The Bridge Identifier of the bridge which this
            port considers to be the Designated Bridge for
            this port's segment."
    REFERENCE
            "IEEE 802.1D-1990: Section 4.5.5.6"
    ::= { dot1dStpPortEntry 8 }

dot1dStpPortDesignatedPort OBJECT-TYPE
    SYNTAX  OCTET STRING (SIZE (2))
    ACCESS  read-only
    STATUS  mandatory
    DESCRIPTION
            "The Port Identifier of the port on the Designated
            Bridge for this port's segment."
    REFERENCE
            "IEEE 802.1D-1990: Section 4.5.5.7"
    ::= { dot1dStpPortEntry 9 }

dot1dStpPortForwardTransitions OBJECT-TYPE
    SYNTAX  Counter
    ACCESS  read-only
    STATUS  mandatory
    DESCRIPTION
            "The number of times this port has transitioned
            from the Learning state to the Forwarding state."
    ::= { dot1dStpPortEntry 10 }


-- the dot1dTp group

-- Implementation of the dot1dTp group is optional.  It is
-- implemented by those bridges that support the transparent
-- bridging mode.  A transparent or SRT bridge will implement
-- this group.


dot1dTpLearnedEntryDiscards OBJECT-TYPE
    SYNTAX  Counter
    ACCESS  read-only
    STATUS  mandatory
    DESCRIPTION
            "The total number of Forwarding Database entries,
            which have been or would have been learnt, but
            have been discarded due to a lack of space to
            store them in the Forwarding Database.  If this
            counter is increasing, it indicates that the
            Forwarding Database is regularly becoming full (a
            condition which has unpleasant performance effects
            on the subnetwork).  If this counter has a
            significant value but is not presently increasing,
            it indicates that the problem has been occurring
            but is not persistent."
    REFERENCE
            "IEEE 802.1D-1990: Section 6.7.1.1.3"
    ::= { dot1dTp 1 }

dot1dTpAgingTime OBJECT-TYPE
    SYNTAX   INTEGER (10..1000000)
    ACCESS   read-write
    STATUS   mandatory
    DESCRIPTION
            "The timeout period in seconds for aging out
            dynamically learned forwarding information.
            802.1D-1990 recommends a default of 300 seconds."
    REFERENCE
            "IEEE 802.1D-1990: Section 6.7.1.1.3"
    ::= { dot1dTp 2 }


--  The Forwarding Database for Transparent Bridges

dot1dTpFdbTable OBJECT-TYPE
    SYNTAX  SEQUENCE OF Dot1dTpFdbEntry
    ACCESS  not-accessible
    STATUS  mandatory
    DESCRIPTION
            "A table that contains information about unicast
            entries for which the bridge has forwarding and/or
            filtering information.  This information is used
            by the transparent bridging function in
            determining how to propagate a received frame."
    ::= { dot1dTp 3 }

dot1dTpFdbEntry OBJECT-TYPE
    SYNTAX  Dot1dTpFdbEntry
    ACCESS  not-accessible
    STATUS  mandatory
    DESCRIPTION
            "Information about a specific unicast MAC address
            for which the bridge has some forwarding and/or
            filtering information."
    INDEX   { dot1dTpFdbAddress }
    ::= { dot1dTpFdbTable 1 }

Dot1dTpFdbEntry ::=
    SEQUENCE {
        dot1dTpFdbAddress
            MacAddress,
        dot1dTpFdbPort
            INTEGER,
        dot1dTpFdbStatus
            INTEGER
    }

dot1dTpFdbAddress OBJECT-TYPE
    SYNTAX  MacAddress
    ACCESS  read-only
    STATUS  mandatory
    DESCRIPTION
            "A unicast MAC address for which the bridge has
            forwarding and/or filtering information."
    REFERENCE
            "IEEE 802.1D-1990: Section 3.9.1, 3.9.2"
    ::= { dot1dTpFdbEntry 1 }

dot1dTpFdbPort OBJECT-TYPE
    SYNTAX  INTEGER
    ACCESS  read-only
    STATUS  mandatory
    DESCRIPTION
            "Either the value '0', or the port number of the
            port on which a frame having a source address
            equal to the value of the corresponding instance
            of dot1dTpFdbAddress has been seen.  A value of
            '0' indicates that the port number has not been
            learned but that the bridge does have some
            forwarding/filtering information about this
            address (e.g. in the dot1dStaticTable).
            Implementors are encouraged to assign the port
            value to this object whenever it is learned even
            for addresses for which the corresponding value of
            dot1dTpFdbStatus is not learned(3)."
    ::= { dot1dTpFdbEntry 2 }

dot1dTpFdbStatus OBJECT-TYPE
    SYNTAX  INTEGER {
                other(1),
                invalid(2),
                learned(3),
                self(4),
                mgmt(5)
            }
    ACCESS  read-only
    STATUS  mandatory
    DESCRIPTION
            "The status of this entry.  The meanings of the
            values are:

              other(1)   : none of the following.  This would
                           include the case where some other
                           MIB object (not the corresponding
                           instance of dot1dTpFdbPort, nor an
                           entry in the dot1dStaticTable) is
                           being used to determine if and how
                           frames addressed to the value of
                           the corresponding instance of
                           dot1dTpFdbAddress are being
                           forwarded.

              invalid(2) : this entry is not longer valid
                           (e.g., it was learned but has since
                           aged-out), but has not yet been
                           flushed from the table.

              learned(3) : the value of the corresponding
                           instance of dot1dTpFdbPort was
                           learned, and is being used.

              self(4)    : the value of the corresponding
                           instance of dot1dTpFdbAddress
                           represents one of the bridge's
                           addresses.  The corresponding
                           instance of dot1dTpFdbPort
                           indicates which of the bridge's
                           ports has this address.

              mgmt(5)    : the value of the corresponding
                           instance of dot1dTpFdbAddress is
                           also the value of an existing
                           instance of dot1dStaticAddress."
    ::= { dot1dTpFdbEntry 3 }

--  Port Table for Transparent Bridges

dot1dTpPortTable OBJECT-TYPE
    SYNTAX  SEQUENCE OF Dot1dTpPortEntry
    ACCESS  not-accessible
    STATUS  mandatory
    DESCRIPTION
            "A table that contains information about every
            port that is associated with this transparent
            bridge."
    ::= { dot1dTp 4 }

dot1dTpPortEntry OBJECT-TYPE
    SYNTAX  Dot1dTpPortEntry
    ACCESS  not-accessible
    STATUS  mandatory
    DESCRIPTION
            "A list of information for each port of a
            transparent bridge."
    INDEX   { dot1dTpPort }
    ::= { dot1dTpPortTable 1 }

Dot1dTpPortEntry ::=
    SEQUENCE {
        dot1dTpPort
            INTEGER,
        dot1dTpPortMaxInfo
            INTEGER,
        dot1dTpPortInFrames
            Counter,
        dot1dTpPortOutFrames
            Counter,
        dot1dTpPortInDiscards
            Counter
    }

dot1dTpPort OBJECT-TYPE
    SYNTAX  INTEGER (1..65535)
    ACCESS  read-only
    STATUS  mandatory
    DESCRIPTION
            "The port number of the port for which this entry
            contains Transparent bridging management
            information."
    ::= { dot1dTpPortEntry 1 }

-- It would be nice if we could use ifMtu as the size of the
-- largest INFO field, but we can't because ifMtu is defined
-- to be the size that the (inter-)network layer can use which
-- can differ from the MAC layer (especially if several layers
-- of encapsulation are used).

dot1dTpPortMaxInfo OBJECT-TYPE
    SYNTAX  INTEGER
    ACCESS  read-only
    STATUS  mandatory
    DESCRIPTION
            "The maximum size of the INFO (non-MAC) field that
            this port will receive or transmit."
    ::= { dot1dTpPortEntry 2 }

dot1dTpPortInFrames OBJECT-TYPE
    SYNTAX  Counter
    ACCESS  read-only
    STATUS  mandatory
    DESCRIPTION
            "The number of frames that have been received by
            this port from its segment. Note that a frame
            received on the interface corresponding to this
            port is only counted by this object if and only if
            it is for a protocol being processed by the local
            bridging function, including bridge management
            frames."
    REFERENCE
            "IEEE 802.1D-1990: Section 6.6.1.1.3"
    ::= { dot1dTpPortEntry 3 }

dot1dTpPortOutFrames OBJECT-TYPE
    SYNTAX  Counter
    ACCESS  read-only
    STATUS  mandatory
    DESCRIPTION
            "The number of frames that have been transmitted
            by this port to its segment.  Note that a frame
            transmitted on the interface corresponding to this
            port is only counted by this object if and only if
            it is for a protocol being processed by the local
            bridging function, including bridge management
            frames."
    REFERENCE
            "IEEE 802.1D-1990: Section 6.6.1.1.3"
    ::= { dot1dTpPortEntry 4 }

dot1dTpPortInDiscards OBJECT-TYPE
    SYNTAX   Counter
    ACCESS   read-only
    STATUS   mandatory
    DESCRIPTION
            "Count of valid frames received which were
            discarded (i.e., filtered) by the Forwarding
            Process."
    REFERENCE
            "IEEE 802.1D-1990: Section 6.6.1.1.3"
    ::= { dot1dTpPortEntry 5 }


-- The Static (Destination-Address Filtering) Database

-- Implementation of this group is optional.


dot1dStaticTable OBJECT-TYPE
    SYNTAX  SEQUENCE OF Dot1dStaticEntry
    ACCESS  not-accessible
    STATUS  mandatory
    DESCRIPTION
            "A table containing filtering information
            configured into the bridge by (local or network)
            management specifying the set of ports to which
            frames received from specific ports and containing
            specific destination addresses are allowed to be
            forwarded.  The value of zero in this table as the
            port number from which frames with a specific
            destination address are received, is used to
            specify all ports for which there is no specific
            entry in this table for that particular
            destination address.  Entries are valid for
            unicast and for group/broadcast addresses."
    REFERENCE
            "IEEE 802.1D-1990: Section 6.7.2"
    ::= { dot1dStatic 1 }

dot1dStaticEntry OBJECT-TYPE
    SYNTAX  Dot1dStaticEntry
    ACCESS  not-accessible
    STATUS  mandatory
    DESCRIPTION
            "Filtering information configured into the bridge
            by (local or network) management specifying the
            set of ports to which frames received from a
            specific port and containing a specific
            destination address are allowed to be forwarded."
    REFERENCE
            "IEEE 802.1D-1990: Section 6.7.2"
    INDEX   { dot1dStaticAddress, dot1dStaticReceivePort }
    ::= { dot1dStaticTable 1 }

Dot1dStaticEntry ::=
    SEQUENCE {
        dot1dStaticAddress
            MacAddress,
        dot1dStaticReceivePort
            INTEGER,
        dot1dStaticAllowedToGoTo
            OCTET STRING,
        dot1dStaticStatus
            INTEGER
    }

dot1dStaticAddress OBJECT-TYPE
    SYNTAX  MacAddress
    ACCESS  read-write
    STATUS  mandatory
    DESCRIPTION
            "The destination MAC address in a frame to which
            this entry's filtering information applies.  This
            object can take the value of a unicast address, a
            group address or the broadcast address."
    REFERENCE
            "IEEE 802.1D-1990: Section 3.9.1, 3.9.2"
    ::= { dot1dStaticEntry 1 }

dot1dStaticReceivePort OBJECT-TYPE
    SYNTAX  INTEGER
    ACCESS  read-write
    STATUS  mandatory
    DESCRIPTION
            "Either the value '0', or the port number of the
            port from which a frame must be received in order
            for this entry's filtering information to apply.
            A value of zero indicates that this entry applies
            on all ports of the bridge for which there is no
            other applicable entry."
    ::= { dot1dStaticEntry 2 }

dot1dStaticAllowedToGoTo OBJECT-TYPE
    SYNTAX  OCTET STRING
    ACCESS  read-write
    STATUS  mandatory
    DESCRIPTION
            "The set of ports to which frames received from a
            specific port and destined for a specific MAC
            address, are allowed to be forwarded.  Each octet
            within the value of this object specifies a set of
            eight ports, with the first octet specifying ports
            1 through 8, the second octet specifying ports 9
            through 16, etc.  Within each octet, the most
            significant bit represents the lowest numbered
            port, and the least significant bit represents the
            highest numbered port.  Thus, each port of the
            bridge is represented by a single bit within the
            value of this object.  If that bit has a value of
            '1' then that port is included in the set of
            ports; the port is not included if its bit has a
            value of '0'.  (Note that the setting of the bit
            corresponding to the port from which a frame is
            received is irrelevant.)  The default value of
            this object is a string of ones of appropriate
            length."
    ::= { dot1dStaticEntry 3 }

dot1dStaticStatus OBJECT-TYPE
    SYNTAX  INTEGER {
                other(1),
                invalid(2),
                permanent(3),
                deleteOnReset(4),
                deleteOnTimeout(5)
            }
    ACCESS  read-write
    STATUS  mandatory
    DESCRIPTION
            "This object indicates the status of this entry.
            The default value is permanent(3).

                 other(1) - this entry is currently in use but
                      the conditions under which it will
                      remain so are different from each of the
                      following values.
                 invalid(2) - writing this value to the object
                      removes the corresponding entry.
                 permanent(3) - this entry is currently in use
                      and will remain so after the next reset
                      of the bridge.
                 deleteOnReset(4) - this entry is currently in
                      use and will remain so until the next
                      reset of the bridge.
                 deleteOnTimeout(5) - this entry is currently
                      in use and will remain so until it is
                      aged out."
    ::= { dot1dStaticEntry 4 }


-- Traps for use by Bridges

-- Traps for the Spanning Tree Protocol

newRoot TRAP-TYPE
    ENTERPRISE  dot1dBridge
    DESCRIPTION
            "The newRoot trap indicates that the sending agent
            has become the new root of the Spanning Tree; the
            trap is sent by a bridge soon after its election
            as the new root, e.g., upon expiration of the
            Topology Change Timer immediately subsequent to
            its election.  Implementation of this trap is
            optional."
    ::= 1

topologyChange TRAP-TYPE
    ENTERPRISE  dot1dBridge
    DESCRIPTION
            "A topologyChange trap is sent by a bridge when
            any of its configured ports transitions from the
            Learning state to the Forwarding state, or from
            the Forwarding state to the Blocking state.  The
            trap is not sent if a newRoot trap is sent for the
            same transition.  Implementation of this trap is
            optional."
    ::= 2

END

-- Changed import of old RFC1271-MIB to new RMON-MIB (klb)

TOKEN-RING-RMON-MIB DEFINITIONS ::= BEGIN

          IMPORTS
              Counter, TimeTicks          FROM RFC1155-SMI
              OBJECT-TYPE                 FROM RFC-1212
              OwnerString, EntryStatus,   -- Textual Conventions
              rmon, statistics, history
                                          --FROM RFC1271-MIB;
                                          FROM RMON-MIB;

             -- All representations of MAC addresses in this MIB
             -- Module use, as a textual convention (i.e. this
             -- convention does not affect their encoding), the
             -- data type:

             MacAddress ::= OCTET STRING (SIZE (6)) -- a 6 octet
                                                    -- address in
                                                    -- the "canonical"
                                                    -- order
             -- defined by IEEE 802.1a, i.e., as if it were
             -- transmitted least significant bit first, even though
             -- 802.5 (in contrast to other 802.x protocols) requires
             -- MAC addresses to be transmitted most significant bit
             -- first.

              TimeInterval ::= INTEGER
              -- A period of time, measured in units of 0.01 seconds.

          --  This MIB module uses the extended OBJECT-TYPE macro as
          --  defined in [2].

          --  Token Ring Remote Network Monitoring MIB

              tokenRing             OBJECT IDENTIFIER ::= { rmon 10 }

          -- The Token Ring Mac-Layer Statistics Group
          --
          -- Implementation of this group is optional

          tokenRingMLStatsTable OBJECT-TYPE
              SYNTAX SEQUENCE OF TokenRingMLStatsEntry
              ACCESS not-accessible
              STATUS mandatory
              DESCRIPTION
                      "A list of Mac-Layer Token Ring statistics
                      entries."
              ::= { statistics 2 }

          tokenRingMLStatsEntry OBJECT-TYPE
              SYNTAX TokenRingMLStatsEntry
              ACCESS not-accessible
              STATUS mandatory
              DESCRIPTION
                      "A collection of Mac-Layer statistics kept for a
                      particular Token Ring interface."
              INDEX { tokenRingMLStatsIndex }
              ::= { tokenRingMLStatsTable 1 }

          -- As an example, an instance of the
          -- tokenRingMLStatsMacOctets object
          -- might be named tokenRingMLStatsMacOctets.1

          TokenRingMLStatsEntry ::= SEQUENCE {
              tokenRingMLStatsIndex                     INTEGER,
              tokenRingMLStatsDataSource            OBJECT IDENTIFIER,
              tokenRingMLStatsDropEvents                Counter,
              tokenRingMLStatsMacOctets                 Counter,
              tokenRingMLStatsMacPkts                   Counter,
              tokenRingMLStatsRingPurgeEvents           Counter,
              tokenRingMLStatsRingPurgePkts             Counter,
              tokenRingMLStatsBeaconEvents              Counter,
              tokenRingMLStatsBeaconTime                TimeInterval,
              tokenRingMLStatsBeaconPkts                Counter,
              tokenRingMLStatsClaimTokenEvents          Counter,
              tokenRingMLStatsClaimTokenPkts            Counter,
              tokenRingMLStatsNAUNChanges               Counter,
              tokenRingMLStatsLineErrors                Counter,
              tokenRingMLStatsInternalErrors            Counter,
              tokenRingMLStatsBurstErrors               Counter,
              tokenRingMLStatsACErrors                  Counter,
              tokenRingMLStatsAbortErrors               Counter,
              tokenRingMLStatsLostFrameErrors           Counter,
              tokenRingMLStatsCongestionErrors          Counter,
              tokenRingMLStatsFrameCopiedErrors         Counter,
              tokenRingMLStatsFrequencyErrors           Counter,
              tokenRingMLStatsTokenErrors               Counter,
              tokenRingMLStatsSoftErrorReports          Counter,
              tokenRingMLStatsRingPollEvents            Counter,
              tokenRingMLStatsOwner                     OwnerString,
              tokenRingMLStatsStatus                    EntryStatus
          }


          tokenRingMLStatsIndex OBJECT-TYPE
              SYNTAX INTEGER (1..65535)
              ACCESS read-only
              STATUS mandatory
              DESCRIPTION
                      "The value of this object uniquely identifies this
                      tokenRingMLStats entry."
              ::= { tokenRingMLStatsEntry 1 }

          tokenRingMLStatsDataSource OBJECT-TYPE
              SYNTAX OBJECT IDENTIFIER
              ACCESS read-write
              STATUS mandatory
              DESCRIPTION
                      "This object identifies the source of the data
                      that this tokenRingMLStats entry is configured to
                      analyze.  This source can be any tokenRing
                      interface on this device.  In order to identify a
                      particular interface, this object shall identify
                      the instance of the ifIndex object, defined in
                      MIB-II [3], for the desired interface.  For
                      example, if an entry were to receive data from
                      interface #1, this object would be set to
                      ifIndex.1.

                      The statistics in this group reflect all error
                      reports on the local network segment attached to
                      the identified interface.

                      This object may not be modified if the associated
                      tokenRingMLStatsStatus object is equal to
                      valid(1)."
              ::= { tokenRingMLStatsEntry 2 }

          tokenRingMLStatsDropEvents OBJECT-TYPE
              SYNTAX Counter
              ACCESS read-only
              STATUS mandatory
              DESCRIPTION
                      "The total number of events in which packets were
                      dropped by the probe due to lack of resources.
                      Note that this number is not necessarily the
                      number of packets dropped; it is just the number
                      of times this condition has been detected.  This
                      value is the same as the corresponding
                      tokenRingPStatsDropEvents."
              ::= { tokenRingMLStatsEntry 3 }

          tokenRingMLStatsMacOctets OBJECT-TYPE
              SYNTAX Counter
              ACCESS read-only
              STATUS mandatory
              DESCRIPTION
                      "The total number of octets of data in MAC packets
                      (excluding those that were not good frames)
                      received on the network (excluding framing bits
                      but including FCS octets)."
              ::= { tokenRingMLStatsEntry 4 }

          tokenRingMLStatsMacPkts OBJECT-TYPE
              SYNTAX Counter
              ACCESS read-only
              STATUS mandatory
              DESCRIPTION
                      "The total number of MAC packets (excluding
                      packets that were not good frames) received."
              ::= { tokenRingMLStatsEntry 5 }

          tokenRingMLStatsRingPurgeEvents OBJECT-TYPE
              SYNTAX Counter
              ACCESS read-only
              STATUS mandatory
              DESCRIPTION
                      "The total number of times that the ring enters
                      the ring purge state from normal ring state.  The
                      ring purge state that comes in response to the
                      claim token or beacon state is not counted."
              ::= { tokenRingMLStatsEntry 6 }

          tokenRingMLStatsRingPurgePkts OBJECT-TYPE
              SYNTAX Counter
              ACCESS read-only
              STATUS mandatory
              DESCRIPTION
                      "The total number of ring purge MAC packets
                      detected by probe."
              ::= { tokenRingMLStatsEntry 7 }

          tokenRingMLStatsBeaconEvents OBJECT-TYPE
              SYNTAX Counter
              ACCESS read-only
              STATUS mandatory
              DESCRIPTION
                      "The total number of times that the ring enters a
                      beaconing state (beaconFrameStreamingState,
                      beaconBitStreamingState,
                      beaconSetRecoveryModeState, or
                      beaconRingSignalLossState) from a non-beaconing
                      state.  Note that a change of the source address
                      of the beacon packet does not constitute a new
                      beacon event."
              ::= { tokenRingMLStatsEntry 8 }

          tokenRingMLStatsBeaconTime OBJECT-TYPE
              SYNTAX TimeInterval
              ACCESS read-only
              STATUS mandatory
              DESCRIPTION
                      "The total amount of time that the ring has been
                      in the beaconing state."
              ::= { tokenRingMLStatsEntry 9 }

          tokenRingMLStatsBeaconPkts OBJECT-TYPE
              SYNTAX Counter
              ACCESS read-only
              STATUS mandatory
              DESCRIPTION
                      "The total number of beacon MAC packets detected
                      by the probe."
              ::= { tokenRingMLStatsEntry 10 }

          tokenRingMLStatsClaimTokenEvents OBJECT-TYPE
              SYNTAX Counter
              ACCESS read-only
              STATUS mandatory
              DESCRIPTION
                      "The total number of times that the ring enters
                      the claim token state from normal ring state or
                      ring purge state.  The claim token state that
                      comes in response to a beacon state is not
                      counted."
              ::= { tokenRingMLStatsEntry 11 }

          tokenRingMLStatsClaimTokenPkts OBJECT-TYPE
              SYNTAX Counter
              ACCESS read-only
              STATUS mandatory
              DESCRIPTION
                      "The total number of claim token MAC packets
                      detected by the probe."
              ::= { tokenRingMLStatsEntry 12 }

          tokenRingMLStatsNAUNChanges OBJECT-TYPE
              SYNTAX Counter
              ACCESS read-only
              STATUS mandatory
              DESCRIPTION
                      "The total number of NAUN changes detected by the
                      probe."
              ::= { tokenRingMLStatsEntry 13 }

          tokenRingMLStatsLineErrors OBJECT-TYPE
              SYNTAX Counter
              ACCESS read-only
              STATUS mandatory
              DESCRIPTION
                      "The total number of line errors reported in error
                      reporting packets detected by the probe."
              ::= { tokenRingMLStatsEntry 14 }

          tokenRingMLStatsInternalErrors OBJECT-TYPE
              SYNTAX Counter
              ACCESS read-only
              STATUS mandatory
              DESCRIPTION
                      "The total number of adapter internal errors
                      reported in error reporting packets detected by
                      the probe."
              ::= { tokenRingMLStatsEntry 15 }

          tokenRingMLStatsBurstErrors OBJECT-TYPE
              SYNTAX Counter
              ACCESS read-only
              STATUS mandatory
              DESCRIPTION
                      "The total number of burst errors reported in
                      error reporting packets detected by the probe."
              ::= { tokenRingMLStatsEntry 16 }

          tokenRingMLStatsACErrors OBJECT-TYPE
              SYNTAX Counter
              ACCESS read-only
              STATUS mandatory
              DESCRIPTION
                      "The total number of AC (Address Copied)  errors
                      reported in error reporting packets detected by
                      the probe."
              ::= { tokenRingMLStatsEntry 17 }

          tokenRingMLStatsAbortErrors OBJECT-TYPE
              SYNTAX Counter
              ACCESS read-only
              STATUS mandatory
              DESCRIPTION
                      "The total number of abort delimiters reported in
                      error reporting packets detected by the probe."
              ::= { tokenRingMLStatsEntry 18 }

          tokenRingMLStatsLostFrameErrors OBJECT-TYPE
              SYNTAX Counter
              ACCESS read-only
              STATUS mandatory
              DESCRIPTION
                      "The total number of lost frame errors reported in
                      error reporting packets detected by the probe."
              ::= { tokenRingMLStatsEntry 19 }

          tokenRingMLStatsCongestionErrors OBJECT-TYPE
              SYNTAX Counter
              ACCESS read-only
              STATUS mandatory
              DESCRIPTION
                      "The total number of receive congestion errors
                      reported in error reporting packets detected by
                      the probe."
              ::= { tokenRingMLStatsEntry 20 }

          tokenRingMLStatsFrameCopiedErrors OBJECT-TYPE
              SYNTAX Counter
              ACCESS read-only
              STATUS mandatory
              DESCRIPTION
                      "The total number of frame copied errors reported
                      in error reporting packets detected by the probe."
              ::= { tokenRingMLStatsEntry 21 }

          tokenRingMLStatsFrequencyErrors OBJECT-TYPE
              SYNTAX Counter
              ACCESS read-only
              STATUS mandatory
              DESCRIPTION
                      "The total number of frequency errors reported in
                      error reporting packets detected by the probe."
              ::= { tokenRingMLStatsEntry 22 }

          tokenRingMLStatsTokenErrors OBJECT-TYPE
              SYNTAX Counter
              ACCESS read-only
              STATUS mandatory
              DESCRIPTION
                      "The total number of token errors reported in
                      error reporting packets detected by the probe."
              ::= { tokenRingMLStatsEntry 23 }

          tokenRingMLStatsSoftErrorReports OBJECT-TYPE
              SYNTAX Counter
              ACCESS read-only
              STATUS mandatory
              DESCRIPTION
                      "The total number of soft error report frames
                      detected by the probe."
              ::= { tokenRingMLStatsEntry 24 }

          tokenRingMLStatsRingPollEvents OBJECT-TYPE
              SYNTAX Counter
              ACCESS read-only
              STATUS mandatory
              DESCRIPTION
                      "The total number of ring poll events detected by
                      the probe (i.e. the number of ring polls initiated
                      by the active monitor that were detected)."
              ::= { tokenRingMLStatsEntry 25 }

          tokenRingMLStatsOwner OBJECT-TYPE
              SYNTAX OwnerString
              ACCESS read-write
              STATUS mandatory
              DESCRIPTION
                      "The entity that configured this entry and is
                      therefore using the resources assigned to it."
              ::= { tokenRingMLStatsEntry 26 }

          tokenRingMLStatsStatus OBJECT-TYPE
              SYNTAX EntryStatus
              ACCESS read-write
              STATUS mandatory
              DESCRIPTION
                      "The status of this tokenRingMLStats entry."
              ::= { tokenRingMLStatsEntry 27 }


          -- The Token Ring Promiscuous Statistics Group
          --
          -- Implementation of this group is optional

          tokenRingPStatsTable OBJECT-TYPE
              SYNTAX SEQUENCE OF TokenRingPStatsEntry
              ACCESS not-accessible
              STATUS mandatory
              DESCRIPTION
                      "A list of promiscuous Token Ring statistics
                      entries."
              ::= { statistics 3 }

          tokenRingPStatsEntry OBJECT-TYPE
              SYNTAX TokenRingPStatsEntry
              ACCESS not-accessible
              STATUS mandatory
              DESCRIPTION
                      "A collection of promiscuous statistics kept for
                      non-MAC packets on a particular Token Ring
                      interface."
              INDEX { tokenRingPStatsIndex }
              ::= { tokenRingPStatsTable 1 }

          -- As an example, an instance of the
          -- tokenRingPStatsDataOctets object
          -- might be named tokenRingPStatsDataOctets.1

          TokenRingPStatsEntry ::= SEQUENCE {
              tokenRingPStatsIndex                          INTEGER,
              tokenRingPStatsDataSource               OBJECT IDENTIFIER,
              tokenRingPStatsDropEvents                     Counter,
              tokenRingPStatsDataOctets                     Counter,
              tokenRingPStatsDataPkts                       Counter,
              tokenRingPStatsDataBroadcastPkts              Counter,
              tokenRingPStatsDataMulticastPkts              Counter,
              tokenRingPStatsDataPkts18to63Octets           Counter,
              tokenRingPStatsDataPkts64to127Octets          Counter,
              tokenRingPStatsDataPkts128to255Octets         Counter,
              tokenRingPStatsDataPkts256to511Octets         Counter,
              tokenRingPStatsDataPkts512to1023Octets        Counter,
              tokenRingPStatsDataPkts1024to2047Octets       Counter,
              tokenRingPStatsDataPkts2048to4095Octets       Counter,
              tokenRingPStatsDataPkts4096to8191Octets       Counter,
              tokenRingPStatsDataPkts8192to18000Octets      Counter,
              tokenRingPStatsDataPktsGreaterThan18000Octets Counter,
              tokenRingPStatsOwner                          OwnerString,
              tokenRingPStatsStatus                         EntryStatus
          }

          tokenRingPStatsIndex OBJECT-TYPE
              SYNTAX INTEGER (1..65535)
              ACCESS read-only
              STATUS mandatory
              DESCRIPTION
                      "The value of this object uniquely identifies this
                      tokenRingPStats entry."
              ::= { tokenRingPStatsEntry 1 }

          tokenRingPStatsDataSource OBJECT-TYPE
              SYNTAX OBJECT IDENTIFIER
              ACCESS read-write
              STATUS mandatory
              DESCRIPTION
                      "This object identifies the source of the data
                      that this tokenRingPStats entry is configured to
                      analyze.  This source can be any tokenRing
                      interface on this device.  In order to identify a
                      particular interface, this object shall identify
                      the instance of the ifIndex object, defined in
                      MIB-II [3], for the desired interface.  For
                      example, if an entry were to receive data from
                      interface #1, this object would be set to
                      ifIndex.1.

                      The statistics in this group reflect all non-MAC
                      packets on the local network segment attached to
                      the identified interface.

                      This object may not be modified if the associated
                      tokenRingPStatsStatus object is equal to
                      valid(1)."
              ::= { tokenRingPStatsEntry 2 }

          tokenRingPStatsDropEvents OBJECT-TYPE
              SYNTAX Counter
              ACCESS read-only
              STATUS mandatory
              DESCRIPTION
                      "The total number of events in which packets were
                      dropped by the probe due to lack of resources.
                      Note that this number is not necessarily the
                      number of packets dropped; it is just the number
                      of times this condition has been detected.  This
                      value is the same as the corresponding
                      tokenRingMLStatsDropEvents"
              ::= { tokenRingPStatsEntry 3 }

          tokenRingPStatsDataOctets OBJECT-TYPE
              SYNTAX Counter
              ACCESS read-only
              STATUS mandatory
              DESCRIPTION
                      "The total number of octets of data in good frames
                      received on the network (excluding framing bits
                      but including FCS octets) in non-MAC packets."
              ::= { tokenRingPStatsEntry 4 }

          tokenRingPStatsDataPkts OBJECT-TYPE
              SYNTAX Counter
              ACCESS read-only
              STATUS mandatory
              DESCRIPTION
                      "The total number of non-MAC packets in good
                      frames.  received."
              ::= { tokenRingPStatsEntry 5 }

          tokenRingPStatsDataBroadcastPkts OBJECT-TYPE
              SYNTAX Counter
              ACCESS read-only
              STATUS mandatory
              DESCRIPTION
                      "The total number of good non-MAC frames received
                      that were directed to an LLC broadcast address
                      (0xFFFFFFFFFFFF or 0xC000FFFFFFFF)."
              ::= { tokenRingPStatsEntry 6 }

          tokenRingPStatsDataMulticastPkts OBJECT-TYPE
              SYNTAX Counter
              ACCESS read-only
              STATUS mandatory
              DESCRIPTION
                      "The total number of good non-MAC frames received
                      that were directed to a local or global multicast
                      or functional address.  Note that this number does
                      not include packets directed to the broadcast
                      address."
              ::= { tokenRingPStatsEntry 7 }

          tokenRingPStatsDataPkts18to63Octets OBJECT-TYPE
              SYNTAX Counter
              ACCESS read-only
              STATUS mandatory
              DESCRIPTION
                      "The total number of good non-MAC frames received
                      that were between 18 and 63 octets in length
                      inclusive, excluding framing bits but including
                      FCS octets."
              ::= { tokenRingPStatsEntry 8 }

          tokenRingPStatsDataPkts64to127Octets OBJECT-TYPE
              SYNTAX Counter
              ACCESS read-only
              STATUS mandatory
              DESCRIPTION
                      "The total number of good non-MAC frames received
                      that were between 64 and 127 octets in length
                      inclusive, excluding framing bits but including
                      FCS octets."
              ::= { tokenRingPStatsEntry 9 }

          tokenRingPStatsDataPkts128to255Octets OBJECT-TYPE
              SYNTAX Counter
              ACCESS read-only
              STATUS mandatory
              DESCRIPTION
                      "The total number of good non-MAC frames received
                      that were between 128 and 255 octets in length
                      inclusive, excluding framing bits but including
                      FCS octets."
              ::= { tokenRingPStatsEntry 10 }

          tokenRingPStatsDataPkts256to511Octets OBJECT-TYPE
              SYNTAX Counter
              ACCESS read-only
              STATUS mandatory
              DESCRIPTION
                      "The total number of good non-MAC frames received
                      that were between 256 and 511 octets in length
                      inclusive, excluding framing bits but including
                      FCS octets."
              ::= { tokenRingPStatsEntry 11 }

          tokenRingPStatsDataPkts512to1023Octets OBJECT-TYPE
              SYNTAX Counter
              ACCESS read-only
              STATUS mandatory
              DESCRIPTION
                      "The total number of good non-MAC frames received
                      that were between 512 and 1023 octets in length
                      inclusive, excluding framing bits but including
                      FCS octets."
              ::= { tokenRingPStatsEntry 12 }

          tokenRingPStatsDataPkts1024to2047Octets OBJECT-TYPE
              SYNTAX Counter
              ACCESS read-only
              STATUS mandatory
              DESCRIPTION
                      "The total number of good non-MAC frames received
                      that were between 1024 and 2047 octets in length
                      inclusive, excluding framing bits but including
                      FCS octets."
              ::= { tokenRingPStatsEntry 13 }

          tokenRingPStatsDataPkts2048to4095Octets OBJECT-TYPE
              SYNTAX Counter
              ACCESS read-only
              STATUS mandatory
              DESCRIPTION
                      "The total number of good non-MAC frames received
                      that were between 2048 and 4095 octets in length
                      inclusive, excluding framing bits but including
                      FCS octets."
              ::= { tokenRingPStatsEntry 14 }

          tokenRingPStatsDataPkts4096to8191Octets OBJECT-TYPE
              SYNTAX Counter
              ACCESS read-only
              STATUS mandatory
              DESCRIPTION
                      "The total number of good non-MAC frames received
                      that were between 4096 and 8191 octets in length
                      inclusive, excluding framing bits but including
                      FCS octets."
              ::= { tokenRingPStatsEntry 15 }

          tokenRingPStatsDataPkts8192to18000Octets OBJECT-TYPE
              SYNTAX Counter
              ACCESS read-only
              STATUS mandatory
              DESCRIPTION
                      "The total number of good non-MAC frames received
                      that were between 8192 and 18000 octets in length
                      inclusive, excluding framing bits but including
                      FCS octets."
              ::= { tokenRingPStatsEntry 16 }

          tokenRingPStatsDataPktsGreaterThan18000Octets OBJECT-TYPE
              SYNTAX Counter
              ACCESS read-only
              STATUS mandatory
              DESCRIPTION
                      "The total number of good non-MAC frames received
                      that were greater than 18000 octets in length,
                      excluding framing bits but including FCS octets."
              ::= { tokenRingPStatsEntry 17 }

          tokenRingPStatsOwner OBJECT-TYPE
              SYNTAX OwnerString
              ACCESS read-write
              STATUS mandatory
              DESCRIPTION
                      "The entity that configured this entry and is
                      therefore using the resources assigned to it."
              ::= { tokenRingPStatsEntry 18 }

          tokenRingPStatsStatus OBJECT-TYPE
              SYNTAX EntryStatus
              ACCESS read-write
              STATUS mandatory
              DESCRIPTION
                      "The status of this tokenRingPStats entry."
              ::= { tokenRingPStatsEntry 19 }

          -- The Token Ring History Groups

          -- When an entry in the historyControlTable is created that
          -- identifies a token ring interface as its
          -- historyControlDataSource, the probe shall create
          -- corresponding entries in the tokenRingMLHistoryTable
          -- and/or the tokenRingPHistoryTable, depending on which
          -- groups it supports.

          -- The Token Ring Mac-Layer History Group
          --
          -- Implementation of this group is optional.
          -- Implementation of this group requires implementation of
          -- the historyControl group from RFC1271.

          tokenRingMLHistoryTable OBJECT-TYPE
              SYNTAX SEQUENCE OF TokenRingMLHistoryEntry
              ACCESS not-accessible
              STATUS mandatory
              DESCRIPTION
                      "A list of Mac-Layer Token Ring statistics
                      entries."
              ::= { history 3 }

          tokenRingMLHistoryEntry OBJECT-TYPE
              SYNTAX TokenRingMLHistoryEntry
              ACCESS not-accessible
              STATUS mandatory
              DESCRIPTION
                      "A collection of Mac-Layer statistics kept for a
                      particular Token Ring interface."
              INDEX { tokenRingMLHistoryIndex,
                      tokenRingMLHistorySampleIndex }
              ::= { tokenRingMLHistoryTable 1 }

          -- As an example, an instance of the
          -- tokenRingMLHistoryMacOctets
          -- object might be named tokenRingMLHistoryMacOctets.1.27

          TokenRingMLHistoryEntry ::= SEQUENCE {
              tokenRingMLHistoryIndex                     INTEGER,
              tokenRingMLHistorySampleIndex               INTEGER,
              tokenRingMLHistoryIntervalStart             TimeTicks,
              tokenRingMLHistoryDropEvents                Counter,
              tokenRingMLHistoryMacOctets                 Counter,
              tokenRingMLHistoryMacPkts                   Counter,
              tokenRingMLHistoryRingPurgeEvents           Counter,
              tokenRingMLHistoryRingPurgePkts             Counter,
              tokenRingMLHistoryBeaconEvents              Counter,
              tokenRingMLHistoryBeaconTime                TimeInterval,
              tokenRingMLHistoryBeaconPkts                Counter,
              tokenRingMLHistoryClaimTokenEvents          Counter,
              tokenRingMLHistoryClaimTokenPkts            Counter,
              tokenRingMLHistoryNAUNChanges               Counter,
              tokenRingMLHistoryLineErrors                Counter,
              tokenRingMLHistoryInternalErrors            Counter,
              tokenRingMLHistoryBurstErrors               Counter,
              tokenRingMLHistoryACErrors                  Counter,
              tokenRingMLHistoryAbortErrors               Counter,
              tokenRingMLHistoryLostFrameErrors           Counter,
              tokenRingMLHistoryCongestionErrors          Counter,
              tokenRingMLHistoryFrameCopiedErrors         Counter,
              tokenRingMLHistoryFrequencyErrors           Counter,
              tokenRingMLHistoryTokenErrors               Counter,
              tokenRingMLHistorySoftErrorReports          Counter,
              tokenRingMLHistoryRingPollEvents            Counter,
              tokenRingMLHistoryActiveStations            INTEGER
          }


          tokenRingMLHistoryIndex OBJECT-TYPE
              SYNTAX INTEGER (1..65535)
              ACCESS read-only
              STATUS mandatory
              DESCRIPTION
                      "The history of which this entry is a part.  The
                      history identified by a particular value of this
                      index is the same history as identified by the
                      same value of historyControlIndex."
              ::= { tokenRingMLHistoryEntry 1 }

          tokenRingMLHistorySampleIndex OBJECT-TYPE
              SYNTAX INTEGER
              ACCESS read-only
              STATUS mandatory
              DESCRIPTION
                      "An index that uniquely identifies the particular
                      Mac-Layer sample this entry represents among all
                      Mac-Layer samples associated with the same
                      historyControlEntry.  This index starts at 1 and
                      increases by one as each new sample is taken."
              ::= { tokenRingMLHistoryEntry 2 }

          tokenRingMLHistoryIntervalStart OBJECT-TYPE
              SYNTAX TimeTicks
              ACCESS read-only
              STATUS mandatory
              DESCRIPTION
                      "The value of sysUpTime at the start of the
                      interval over which this sample was measured.  If
                      the probe keeps track of the time of day, it
                      should start the first sample of the history at a
                      time such that when the next hour of the day
                      begins, a sample is started at that instant.  Note
                      that following this rule may require the probe to
                      delay collecting the first sample of the history,
                      as each sample must be of the same interval.  Also
                      note that the sample which is currently being
                      collected is not accessible in this table until
                      the end of its interval."
              ::= { tokenRingMLHistoryEntry 3 }

          tokenRingMLHistoryDropEvents OBJECT-TYPE
              SYNTAX Counter
              ACCESS read-only
              STATUS mandatory
              DESCRIPTION
                      "The total number of events in which packets were
                      dropped by the probe due to lack of resources
                      during this sampling interval.  Note that this
                      number is not necessarily the number of packets
                      dropped, it is just the number of times this
                      condition has been detected."
              ::= { tokenRingMLHistoryEntry 4 }

          tokenRingMLHistoryMacOctets OBJECT-TYPE
              SYNTAX Counter
              ACCESS read-only
              STATUS mandatory
              DESCRIPTION
                      "The total number of octets of data in MAC packets
                      (excluding those that were not good frames)
                      received on the network during this sampling
                      interval (excluding framing bits but including FCS
                      octets)."
              ::= { tokenRingMLHistoryEntry 5 }

          tokenRingMLHistoryMacPkts OBJECT-TYPE
              SYNTAX Counter
              ACCESS read-only
              STATUS mandatory
              DESCRIPTION
                      "The total number of MAC packets (excluding those
                      that were not good frames) received during this
                      sampling interval."
              ::= { tokenRingMLHistoryEntry 6 }

          tokenRingMLHistoryRingPurgeEvents OBJECT-TYPE
              SYNTAX Counter
              ACCESS read-only
              STATUS mandatory
              DESCRIPTION
                      "The total number of times that the ring entered
                      the ring purge state from normal ring state during
                      this sampling interval.  The ring purge state that
                      comes from the claim token or beacon state is not
                      counted."
              ::= { tokenRingMLHistoryEntry 7 }

          tokenRingMLHistoryRingPurgePkts OBJECT-TYPE
              SYNTAX Counter
              ACCESS read-only
              STATUS mandatory
              DESCRIPTION
                      "The total number of Ring Purge MAC packets
                      detected by the probe during this sampling
                      interval."
              ::= { tokenRingMLHistoryEntry 8 }

          tokenRingMLHistoryBeaconEvents OBJECT-TYPE
              SYNTAX Counter
              ACCESS read-only
              STATUS mandatory
              DESCRIPTION
                      "The total number of times that the ring enters a
                      beaconing state (beaconFrameStreamingState,
                      beaconBitStreamingState,
                      beaconSetRecoveryModeState, or
                      beaconRingSignalLossState) during this sampling
                      interval.  Note that a change of the source
                      address of the beacon packet does not constitute a
                      new beacon event."
              ::= { tokenRingMLHistoryEntry 9 }

          tokenRingMLHistoryBeaconTime OBJECT-TYPE
              SYNTAX TimeInterval
              ACCESS read-only
              STATUS mandatory
              DESCRIPTION
                      "The amount of time that the ring has been in the
                      beaconing state during this sampling interval."
              ::= { tokenRingMLHistoryEntry 10 }

          tokenRingMLHistoryBeaconPkts OBJECT-TYPE
              SYNTAX Counter
              ACCESS read-only
              STATUS mandatory
              DESCRIPTION
                      "The total number of beacon MAC packets detected
                      by the probe during this sampling interval."
              ::= { tokenRingMLHistoryEntry 11 }

          tokenRingMLHistoryClaimTokenEvents OBJECT-TYPE
              SYNTAX Counter
              ACCESS read-only
              STATUS mandatory
              DESCRIPTION
                      "The total number of times that the ring enters
                      the claim token state from normal ring state or
                      ring purge state during this sampling interval.
                      The claim token state that comes from the beacon
                      state is not counted."
              ::= { tokenRingMLHistoryEntry 12 }

          tokenRingMLHistoryClaimTokenPkts OBJECT-TYPE
              SYNTAX Counter
              ACCESS read-only
              STATUS mandatory
              DESCRIPTION
                      "The total number of claim token MAC packets
                      detected by the probe during this sampling
                      interval."
              ::= { tokenRingMLHistoryEntry 13 }

          tokenRingMLHistoryNAUNChanges OBJECT-TYPE
              SYNTAX Counter
              ACCESS read-only
              STATUS mandatory
              DESCRIPTION
                      "The total number of NAUN changes detected by the
                      probe during this sampling interval."
              ::= { tokenRingMLHistoryEntry 14 }

          tokenRingMLHistoryLineErrors OBJECT-TYPE
              SYNTAX Counter
              ACCESS read-only
              STATUS mandatory
              DESCRIPTION
                      "The total number of line errors reported in error
                      reporting packets detected by the probe during
                      this sampling interval."
              ::= { tokenRingMLHistoryEntry 15 }

          tokenRingMLHistoryInternalErrors OBJECT-TYPE
              SYNTAX Counter
              ACCESS read-only
              STATUS mandatory
              DESCRIPTION
                      "The total number of adapter internal errors
                      reported in error reporting packets detected by
                      the probe during this sampling interval."
              ::= { tokenRingMLHistoryEntry 16 }

          tokenRingMLHistoryBurstErrors OBJECT-TYPE
              SYNTAX Counter
              ACCESS read-only
              STATUS mandatory
              DESCRIPTION
                      "The total number of burst errors reported in
                      error reporting packets detected by the probe
                      during this sampling interval."
              ::= { tokenRingMLHistoryEntry 17 }

          tokenRingMLHistoryACErrors OBJECT-TYPE
              SYNTAX Counter
              ACCESS read-only
              STATUS mandatory
              DESCRIPTION
                      "The total number of AC (Address Copied) errors
                      reported in error reporting packets detected by
                      the probe during this sampling interval."
              ::= { tokenRingMLHistoryEntry 18 }

          tokenRingMLHistoryAbortErrors OBJECT-TYPE
              SYNTAX Counter
              ACCESS read-only
              STATUS mandatory
              DESCRIPTION
                      "The total number of abort delimiters reported in
                      error reporting packets detected by the probe
                      during this sampling interval."
              ::= { tokenRingMLHistoryEntry 19 }

          tokenRingMLHistoryLostFrameErrors OBJECT-TYPE
              SYNTAX Counter
              ACCESS read-only
              STATUS mandatory
              DESCRIPTION
                      "The total number of lost frame errors reported in
                      error reporting packets detected by the probe
                      during this sampling interval."
              ::= { tokenRingMLHistoryEntry 20 }

          tokenRingMLHistoryCongestionErrors OBJECT-TYPE
              SYNTAX Counter
              ACCESS read-only
              STATUS mandatory
              DESCRIPTION
                      "The total number of receive congestion errors
                      reported in error reporting packets detected by
                      the probe during this sampling interval."
              ::= { tokenRingMLHistoryEntry 21 }

          tokenRingMLHistoryFrameCopiedErrors OBJECT-TYPE
              SYNTAX Counter
              ACCESS read-only
              STATUS mandatory
              DESCRIPTION
                      "The total number of frame copied errors reported
                      in error reporting packets detected by the probe
                      during this sampling interval."
              ::= { tokenRingMLHistoryEntry 22 }

          tokenRingMLHistoryFrequencyErrors OBJECT-TYPE
              SYNTAX Counter
              ACCESS read-only
              STATUS mandatory
              DESCRIPTION
                      "The total number of frequency errors reported in
                      error reporting packets detected by the probe
                      during this sampling interval."
              ::= { tokenRingMLHistoryEntry 23 }

          tokenRingMLHistoryTokenErrors OBJECT-TYPE
              SYNTAX Counter
              ACCESS read-only
              STATUS mandatory
              DESCRIPTION
                      "The total number of token errors reported in
                      error reporting packets detected by the probe
                      during this sampling interval."
              ::= { tokenRingMLHistoryEntry 24 }

          tokenRingMLHistorySoftErrorReports OBJECT-TYPE
              SYNTAX Counter
              ACCESS read-only
              STATUS mandatory
              DESCRIPTION
                      "The total number of soft error report frames
                      detected by the probe during this sampling
                      interval."
              ::= { tokenRingMLHistoryEntry 25 }

          tokenRingMLHistoryRingPollEvents OBJECT-TYPE
              SYNTAX Counter
              ACCESS read-only
              STATUS mandatory
              DESCRIPTION
                      "The total number of ring poll events detected by
                      the probe during this sampling interval."
              ::= { tokenRingMLHistoryEntry 26 }

          tokenRingMLHistoryActiveStations OBJECT-TYPE
              SYNTAX INTEGER
              ACCESS read-only
              STATUS mandatory
              DESCRIPTION
                      "The maximum number of active stations on the ring
                      detected by the probe during this sampling
                      interval."
              ::= { tokenRingMLHistoryEntry 27}

          -- The Token Ring Promiscuous History Group
          --
          -- Implementation of this group is optional.
          -- Implementation of this group requires the implementation
          -- of the historyControl group from RFC1271.

          tokenRingPHistoryTable OBJECT-TYPE
              SYNTAX SEQUENCE OF TokenRingPHistoryEntry
              ACCESS not-accessible
              STATUS mandatory
              DESCRIPTION
                      "A list of promiscuous Token Ring statistics
                      entries."
              ::= { history 4 }

          tokenRingPHistoryEntry OBJECT-TYPE
              SYNTAX TokenRingPHistoryEntry
              ACCESS not-accessible
              STATUS mandatory
              DESCRIPTION
                      "A collection of promiscuous statistics kept for a
                      particular Token Ring interface."
              INDEX { tokenRingPHistoryIndex,
                      tokenRingPHistorySampleIndex }
              ::= { tokenRingPHistoryTable 1 }

          -- As an example, an instance of the
          -- tokenRingPHistoryDataPkts object
          -- might be named tokenRingPHistoryDataPkts.1.27

          TokenRingPHistoryEntry ::= SEQUENCE {
              tokenRingPHistoryIndex                          INTEGER,
              tokenRingPHistorySampleIndex                    INTEGER,
              tokenRingPHistoryIntervalStart                  TimeTicks,
              tokenRingPHistoryDropEvents                     Counter,
              tokenRingPHistoryDataOctets                     Counter,
              tokenRingPHistoryDataPkts                       Counter,
              tokenRingPHistoryDataBroadcastPkts              Counter,
              tokenRingPHistoryDataMulticastPkts              Counter,
              tokenRingPHistoryDataPkts18to63Octets           Counter,
              tokenRingPHistoryDataPkts64to127Octets          Counter,
              tokenRingPHistoryDataPkts128to255Octets         Counter,
              tokenRingPHistoryDataPkts256to511Octets         Counter,
              tokenRingPHistoryDataPkts512to1023Octets        Counter,
              tokenRingPHistoryDataPkts1024to2047Octets       Counter,
              tokenRingPHistoryDataPkts2048to4095Octets       Counter,
              tokenRingPHistoryDataPkts4096to8191Octets       Counter,
              tokenRingPHistoryDataPkts8192to18000Octets      Counter,
              tokenRingPHistoryDataPktsGreaterThan18000Octets Counter
          }

          tokenRingPHistoryIndex OBJECT-TYPE
              SYNTAX INTEGER (1..65535)
              ACCESS read-only
              STATUS mandatory
              DESCRIPTION
                      "The history of which this entry is a part.  The
                      history identified by a particular value of this
                      index is the same history as identified by the
                      same value of historyControlIndex."
              ::= { tokenRingPHistoryEntry 1 }

          tokenRingPHistorySampleIndex OBJECT-TYPE
              SYNTAX INTEGER
              ACCESS read-only
              STATUS mandatory
              DESCRIPTION
                      "An index that uniquely identifies the particular
                      sample this entry represents among all samples
                      associated with the same historyControlEntry.
                      This index starts at 1 and increases by one as
                      each new sample is taken."
              ::= { tokenRingPHistoryEntry 2 }

          tokenRingPHistoryIntervalStart OBJECT-TYPE
              SYNTAX TimeTicks
              ACCESS read-only
              STATUS mandatory
              DESCRIPTION
                      "The value of sysUpTime at the start of the
                      interval over which this sample was measured.  If
                      the probe keeps track of the time of day, it
                      should start the first sample of the history at a
                      time such that when the next hour of the day
                      begins, a sample is started at that instant.  Note
                      that following this rule may require the probe to
                      delay collecting the first sample of the history,
                      as each sample must be of the same interval.  Also
                      note that the sample which is currently being
                      collected is not accessible in this table until
                      the end of its interval."
              ::= { tokenRingPHistoryEntry 3 }

          tokenRingPHistoryDropEvents OBJECT-TYPE
              SYNTAX Counter
              ACCESS read-only
              STATUS mandatory
              DESCRIPTION
                      "The total number of events in which packets were
                      dropped by the probe due to lack of resources
                      during this sampling interval.  Note that this
                      number is not necessarily the number of packets
                      dropped, it is just the number of times this
                      condition has been detected."
              ::= { tokenRingPHistoryEntry 4 }

          tokenRingPHistoryDataOctets OBJECT-TYPE
              SYNTAX Counter
              ACCESS read-only
              STATUS mandatory
              DESCRIPTION
                      "The total number of octets of data in good frames
                      received on the network (excluding framing bits
                      but including FCS octets) in non-MAC packets
                      during this sampling interval."
              ::= { tokenRingPHistoryEntry 5 }

          tokenRingPHistoryDataPkts OBJECT-TYPE
              SYNTAX Counter
              ACCESS read-only
              STATUS mandatory
              DESCRIPTION
                      "The total number of good non-MAC frames received
                      during this sampling interval."
              ::= { tokenRingPHistoryEntry 6 }

          tokenRingPHistoryDataBroadcastPkts OBJECT-TYPE
              SYNTAX Counter
              ACCESS read-only
              STATUS mandatory
              DESCRIPTION
                      "The total number of good non-MAC frames received
                      during this sampling interval that were directed
                      to an LLC broadcast address (0xFFFFFFFFFFFF or
                      0xC000FFFFFFFF)."
              ::= { tokenRingPHistoryEntry 7 }

          tokenRingPHistoryDataMulticastPkts OBJECT-TYPE
              SYNTAX Counter
              ACCESS read-only
              STATUS mandatory
              DESCRIPTION
                      "The total number of good non-MAC frames received
                      during this sampling interval that were directed
                      to a local or global multicast or functional
                      address.  Note that this number does not include
                      packets directed to the broadcast address."
              ::= { tokenRingPHistoryEntry 8 }

          tokenRingPHistoryDataPkts18to63Octets OBJECT-TYPE
              SYNTAX Counter
              ACCESS read-only
              STATUS mandatory
              DESCRIPTION
                      "The total number of good non-MAC frames received
                      during this sampling interval that were between 18
                      and 63 octets in length inclusive, excluding
                      framing bits but including FCS octets."
              ::= { tokenRingPHistoryEntry 9 }

          tokenRingPHistoryDataPkts64to127Octets OBJECT-TYPE
              SYNTAX Counter
              ACCESS read-only
              STATUS mandatory
              DESCRIPTION
                      "The total number of good non-MAC frames received
                      during this sampling interval that were between 64
                      and 127 octets in length inclusive, excluding
                      framing bits but including FCS octets."
              ::= { tokenRingPHistoryEntry 10 }

          tokenRingPHistoryDataPkts128to255Octets OBJECT-TYPE
              SYNTAX Counter
              ACCESS read-only
              STATUS mandatory
              DESCRIPTION
                      "The total number of good non-MAC frames received
                      during this sampling interval that were between
                      128 and 255 octets in length inclusive, excluding
                      framing bits but including FCS octets."
              ::= { tokenRingPHistoryEntry 11 }

          tokenRingPHistoryDataPkts256to511Octets OBJECT-TYPE
              SYNTAX Counter
              ACCESS read-only
              STATUS mandatory
              DESCRIPTION
                      "The total number of good non-MAC frames received
                      during this sampling interval that were between
                      256 and 511 octets in length inclusive, excluding
                      framing bits but including FCS octets."
              ::= { tokenRingPHistoryEntry 12 }

          tokenRingPHistoryDataPkts512to1023Octets OBJECT-TYPE
              SYNTAX Counter
              ACCESS read-only
              STATUS mandatory
              DESCRIPTION
                      "The total number of good non-MAC frames received
                      during this sampling interval that were between
                      512 and 1023 octets in length inclusive, excluding
                      framing bits but including FCS octets."
              ::= { tokenRingPHistoryEntry 13 }

          tokenRingPHistoryDataPkts1024to2047Octets OBJECT-TYPE
              SYNTAX Counter
              ACCESS read-only
              STATUS mandatory
              DESCRIPTION
                      "The total number of good non-MAC frames received
                      during this sampling interval that were between
                      1024 and 2047 octets in length inclusive,
                      excluding framing bits but including FCS octets."
              ::= { tokenRingPHistoryEntry 14 }

          tokenRingPHistoryDataPkts2048to4095Octets OBJECT-TYPE
              SYNTAX Counter
              ACCESS read-only
              STATUS mandatory
              DESCRIPTION
                      "The total number of good non-MAC frames received
                      during this sampling interval that were between
                      2048 and 4095 octets in length inclusive,
                      excluding framing bits but including FCS octets."
              ::= { tokenRingPHistoryEntry 15 }

          tokenRingPHistoryDataPkts4096to8191Octets OBJECT-TYPE
              SYNTAX Counter
              ACCESS read-only
              STATUS mandatory
              DESCRIPTION
                      "The total number of good non-MAC frames received
                      during this sampling interval that were between
                      4096 and 8191 octets in length inclusive,
                      excluding framing bits but including FCS octets."
              ::= { tokenRingPHistoryEntry 16 }

          tokenRingPHistoryDataPkts8192to18000Octets OBJECT-TYPE
              SYNTAX Counter
              ACCESS read-only
              STATUS mandatory
              DESCRIPTION
                      "The total number of good non-MAC frames received
                      during this sampling interval that were between
                      8192 and 18000 octets in length inclusive,
                      excluding framing bits but including FCS octets."
              ::= { tokenRingPHistoryEntry 17 }

          tokenRingPHistoryDataPktsGreaterThan18000Octets OBJECT-TYPE
              SYNTAX Counter
              ACCESS read-only
              STATUS mandatory
              DESCRIPTION
                      "The total number of good non-MAC frames received
                      during this sampling interval that were greater
                      than 18000 octets in length, excluding framing
                      bits but including FCS octets."
              ::= { tokenRingPHistoryEntry 18 }

          -- The Token Ring Ring Station Group
          --
          -- Implementation of this group is optional
          --
          -- Although the ringStationTable stores entries only for
          -- those stations physically attached to the local ring and
          -- the number of stations attached to a ring is limited, a
          -- probe may still need to free resources when resources
          -- grow tight.  In such a situation, it is suggested that
          -- the probe free only inactive stations, and to
          -- first free the stations that have been inactive for the
          -- longest time.

          ringStationControlTable OBJECT-TYPE
              SYNTAX SEQUENCE OF RingStationControlEntry
              ACCESS not-accessible
              STATUS mandatory
              DESCRIPTION
                      "A list of ringStation table control entries."
              ::= { tokenRing 1 }

          ringStationControlEntry OBJECT-TYPE
              SYNTAX RingStationControlEntry
              ACCESS not-accessible
              STATUS mandatory
              DESCRIPTION
                      "A list of parameters that set up the discovery of
                      stations on a particular interface and the
                      collection of statistics about these stations."
              INDEX { ringStationControlIfIndex }
              ::= { ringStationControlTable 1 }

          -- As an example, an instance of the
          -- ringStationControlIfIndex object
          -- might be named ringStationControlIfIndex.1

          RingStationControlEntry ::= SEQUENCE {
              ringStationControlIfIndex          INTEGER,
              ringStationControlTableSize        INTEGER,
              ringStationControlActiveStations   INTEGER,
              ringStationControlRingState        INTEGER,
              ringStationControlBeaconSender     MacAddress,
              ringStationControlBeaconNAUN       MacAddress,
              ringStationControlActiveMonitor    MacAddress,
              ringStationControlOrderChanges     Counter,
              ringStationControlOwner            OwnerString,
              ringStationControlStatus           EntryStatus
          }

          ringStationControlIfIndex OBJECT-TYPE
              SYNTAX INTEGER (1..65535)
              ACCESS read-only
              STATUS mandatory
              DESCRIPTION
                      "The value of this object uniquely identifies the
                      interface on this remote network monitoring device
                      from which ringStation data is collected.  The
                      interface identified by a particular value of this
                      object is the same interface as identified by the
                      same value of the ifIndex object, defined in MIB-
                      II [3]."
              ::= { ringStationControlEntry 1 }

          ringStationControlTableSize OBJECT-TYPE
              SYNTAX INTEGER
              ACCESS read-only
              STATUS mandatory
              DESCRIPTION
                      "The number of ringStationEntries in the
                      ringStationTable associated with this
                      ringStationControlEntry."
              ::= { ringStationControlEntry 2 }


          ringStationControlActiveStations OBJECT-TYPE
              SYNTAX INTEGER
              ACCESS read-only
              STATUS mandatory
              DESCRIPTION
                      "The number of active ringStationEntries in the
                      ringStationTable associated with this
                      ringStationControlEntry."
              ::= { ringStationControlEntry 3 }

          ringStationControlRingState OBJECT-TYPE
              SYNTAX INTEGER {
                  normalOperation(1),
                  ringPurgeState(2),
                  claimTokenState(3),
                  beaconFrameStreamingState(4),
                  beaconBitStreamingState(5),
                  beaconRingSignalLossState(6),
                  beaconSetRecoveryModeState(7)
              }
              ACCESS read-only
              STATUS mandatory
              DESCRIPTION
                      "The current status of this ring."
              ::= { ringStationControlEntry 4 }

          ringStationControlBeaconSender OBJECT-TYPE
              SYNTAX MacAddress
              ACCESS read-only
              STATUS mandatory
              DESCRIPTION
                      "The address of the sender of the last beacon
                      frame received by the probe on this ring.  If no
                      beacon frames have been received, this object
                      shall be equal to six octets of zero."
              ::= { ringStationControlEntry 5 }

          ringStationControlBeaconNAUN OBJECT-TYPE
              SYNTAX MacAddress
              ACCESS read-only
              STATUS mandatory
              DESCRIPTION
                      "The address of the NAUN in the last beacon frame
                      received by the probe on this ring.  If no beacon
                      frames have been received, this object shall be
                      equal to six octets of zero."
              ::= { ringStationControlEntry 6 }

          ringStationControlActiveMonitor OBJECT-TYPE
              SYNTAX MacAddress
              ACCESS read-only
              STATUS mandatory
              DESCRIPTION
                      "The address of the Active Monitor on this
                      segment.  If this address is unknown, this object
                      shall be equal to six octets of zero."
              ::= { ringStationControlEntry 7 }

          ringStationControlOrderChanges OBJECT-TYPE
              SYNTAX Counter
              ACCESS read-only
              STATUS mandatory
              DESCRIPTION
                      "The number of add and delete events in the
                      ringStationOrderTable optionally associated with
                      this ringStationControlEntry."
              ::= { ringStationControlEntry 8 }

          ringStationControlOwner OBJECT-TYPE
              SYNTAX OwnerString
              ACCESS read-write
              STATUS mandatory
              DESCRIPTION
                      "The entity that configured this entry and is
                      therefore using the resources assigned to it."
              ::= { ringStationControlEntry 9 }

          ringStationControlStatus OBJECT-TYPE
              SYNTAX EntryStatus
              ACCESS read-write
              STATUS mandatory
              DESCRIPTION
                      "The status of this ringStationControl entry.

                      If this object is not equal to valid(1), all
                      associated entries in the ringStationTable shall
                      be deleted by the agent."
              ::= { ringStationControlEntry 10 }

          ringStationTable OBJECT-TYPE
              SYNTAX SEQUENCE OF RingStationEntry
              ACCESS not-accessible
              STATUS mandatory
              DESCRIPTION
                      "A list of ring station entries.  An entry will
                      exist for each station that is now or has
                      previously been detected as physically present on
                      this ring."
               ::= { tokenRing 2 }

          ringStationEntry OBJECT-TYPE
              SYNTAX RingStationEntry
              ACCESS not-accessible
              STATUS mandatory
              DESCRIPTION
                      "A collection of statistics for a particular
                      station that has been discovered on a ring
                      monitored by this device."
              INDEX { ringStationIfIndex, ringStationMacAddress }
              ::= { ringStationTable 1 }

          -- As an example, an instance of the
          -- ringStationStationStatus object might be named
          -- ringStationStationStatus.1.16.0.90.0.64.131

          RingStationEntry ::= SEQUENCE {
              ringStationIfIndex                INTEGER,
              ringStationMacAddress             MacAddress,
              ringStationLastNAUN               MacAddress,
              ringStationStationStatus          INTEGER,
              ringStationLastEnterTime          TimeTicks,
              ringStationLastExitTime           TimeTicks,
              ringStationDuplicateAddresses     Counter,
              ringStationInLineErrors           Counter,
              ringStationOutLineErrors          Counter,
              ringStationInternalErrors         Counter,
              ringStationInBurstErrors          Counter,
              ringStationOutBurstErrors         Counter,
              ringStationACErrors               Counter,
              ringStationAbortErrors            Counter,
              ringStationLostFrameErrors        Counter,
              ringStationCongestionErrors       Counter,
              ringStationFrameCopiedErrors      Counter,
              ringStationFrequencyErrors        Counter,
              ringStationTokenErrors            Counter,
              ringStationInBeaconErrors         Counter,
              ringStationOutBeaconErrors        Counter,
              ringStationInsertions             Counter
          }

          ringStationIfIndex OBJECT-TYPE
              SYNTAX INTEGER
              ACCESS read-only
              STATUS mandatory
              DESCRIPTION
                      "The value of this object uniquely identifies the
                      interface on this remote network monitoring device
                      on which this station was detected.  The interface
                      identified by a particular value of this object is
                      the same interface as identified by the same value
                      of the ifIndex object, defined in MIB-II [3]."
              ::= { ringStationEntry 1 }

          ringStationMacAddress OBJECT-TYPE
              SYNTAX MacAddress
              ACCESS read-only
              STATUS mandatory
              DESCRIPTION
                      "The physical address of this station."
              ::= { ringStationEntry 2 }

          ringStationLastNAUN OBJECT-TYPE
              SYNTAX MacAddress
              ACCESS read-only
              STATUS mandatory
              DESCRIPTION
                      "The physical address of last known NAUN of this
                      station."
              ::= { ringStationEntry 3 }

          ringStationStationStatus OBJECT-TYPE
              SYNTAX INTEGER {
                  active(1),    -- actively participating in ring poll.
                  inactive(2),  -- Not participating in ring poll
                  forcedRemoval(3) -- Forced off ring by network
                                   -- management.
              }
              ACCESS read-only
              STATUS mandatory
              DESCRIPTION
                      "The status of this station on the ring."
              ::= { ringStationEntry 4 }

          ringStationLastEnterTime OBJECT-TYPE
              SYNTAX TimeTicks
              ACCESS read-only
              STATUS mandatory
              DESCRIPTION
                      "The value of sysUpTime at the time this station
                      last entered the ring.  If the time is unknown,
                      this value shall be zero."
              ::= { ringStationEntry 5 }

          ringStationLastExitTime OBJECT-TYPE
              SYNTAX TimeTicks
              ACCESS read-only
              STATUS mandatory
              DESCRIPTION
                      "The value of sysUpTime at the time the probe
                      detected that this station last exited the ring.
                      If the time is unknown, this value shall be zero."
              ::= { ringStationEntry 6 }

          ringStationDuplicateAddresses OBJECT-TYPE
              SYNTAX Counter
              ACCESS read-only
              STATUS mandatory
              DESCRIPTION
                      "The number of times this station experienced a
                      duplicate address error."
              ::= { ringStationEntry 7 }

          ringStationInLineErrors OBJECT-TYPE
              SYNTAX Counter
              ACCESS read-only
              STATUS mandatory
              DESCRIPTION
                      "The total number of line errors reported by this
                      station in error reporting packets detected by the
                      probe."
              ::= { ringStationEntry 8 }

          ringStationOutLineErrors OBJECT-TYPE
              SYNTAX Counter
              ACCESS read-only
              STATUS mandatory
              DESCRIPTION
                      "The total number of line errors reported in error
                      reporting packets sent by the nearest active
                      downstream neighbor of this station and detected
                      by the probe."
              ::= { ringStationEntry 9 }

          ringStationInternalErrors OBJECT-TYPE
              SYNTAX Counter
              ACCESS read-only
              STATUS mandatory
              DESCRIPTION
                      "The total number of adapter internal errors
                      reported by this station in error reporting
                      packets detected by the probe."
              ::= { ringStationEntry 10 }

          ringStationInBurstErrors OBJECT-TYPE
              SYNTAX Counter
              ACCESS read-only
              STATUS mandatory
              DESCRIPTION
                      "The total number of burst errors reported by this
                      station in error reporting packets detected by the
                      probe."
              ::= { ringStationEntry 11 }

          ringStationOutBurstErrors OBJECT-TYPE
              SYNTAX Counter
              ACCESS read-only
              STATUS mandatory
              DESCRIPTION
                      "The total number of burst errors reported in
                      error reporting packets sent by the nearest active
                      downstream neighbor of this station and detected
                      by the probe."
              ::= { ringStationEntry 12 }

          ringStationACErrors OBJECT-TYPE
              SYNTAX Counter
              ACCESS read-only
              STATUS mandatory
              DESCRIPTION
                      "The total number of AC (Address Copied) errors
                      reported in error reporting packets sent by the
                      nearest active downstream neighbor of this station
                      and detected by the probe."
              ::= { ringStationEntry 13 }

          ringStationAbortErrors OBJECT-TYPE
              SYNTAX Counter
              ACCESS read-only
              STATUS mandatory
              DESCRIPTION
                      "The total number of abort delimiters reported by
                      this station in error reporting packets detected
                      by the probe."
              ::= { ringStationEntry 14 }

          ringStationLostFrameErrors OBJECT-TYPE
              SYNTAX Counter
              ACCESS read-only
              STATUS mandatory
              DESCRIPTION
                      "The total number of lost frame errors reported by
                      this station in error reporting packets detected
                      by the probe."
              ::= { ringStationEntry 15 }

          ringStationCongestionErrors OBJECT-TYPE
              SYNTAX Counter
              ACCESS read-only
              STATUS mandatory
              DESCRIPTION
                      "The total number of receive congestion errors
                      reported by this station in error reporting
                      packets detected by the probe."
              ::= { ringStationEntry 16 }

          ringStationFrameCopiedErrors OBJECT-TYPE
              SYNTAX Counter
              ACCESS read-only
              STATUS mandatory
              DESCRIPTION
                      "The total number of frame copied errors reported
                      by this station in error reporting packets
                      detected by the probe."
              ::= { ringStationEntry 17 }

          ringStationFrequencyErrors OBJECT-TYPE
              SYNTAX Counter
              ACCESS read-only
              STATUS mandatory
              DESCRIPTION
                      "The total number of frequency errors reported by
                      this station in error reporting packets detected
                      by the probe."
              ::= { ringStationEntry 18 }

          ringStationTokenErrors OBJECT-TYPE
              SYNTAX Counter
              ACCESS read-only
              STATUS mandatory
              DESCRIPTION
                      "The total number of token errors reported by this
                      station in error reporting frames detected by the
                      probe."
              ::= { ringStationEntry 19 }

          ringStationInBeaconErrors OBJECT-TYPE
              SYNTAX Counter
              ACCESS read-only
              STATUS mandatory
              DESCRIPTION
                      "The total number of beacon frames sent by this
                      station and detected by the probe."
              ::= { ringStationEntry 20 }

          ringStationOutBeaconErrors OBJECT-TYPE
              SYNTAX Counter
              ACCESS read-only
              STATUS mandatory
              DESCRIPTION
                      "The total number of beacon frames detected by the
                      probe that name this station as the NAUN."
              ::= { ringStationEntry 21 }

          ringStationInsertions OBJECT-TYPE
              SYNTAX Counter
              ACCESS read-only
              STATUS mandatory
              DESCRIPTION
                      "The number of times the probe detected this
                      station inserting onto the ring."
              ::= { ringStationEntry 22 }

          -- The Token Ring Ring Station Order Group
          --
          -- Implementation of this group is optional
          --

          -- The ringStationOrderTable

          ringStationOrderTable OBJECT-TYPE
              SYNTAX SEQUENCE OF RingStationOrderEntry
              ACCESS not-accessible
              STATUS mandatory
              DESCRIPTION
                      "A list of ring station entries for stations in
                      the ring poll, ordered by their ring-order."
              ::= { tokenRing 3 }

          ringStationOrderEntry OBJECT-TYPE
              SYNTAX RingStationOrderEntry
              ACCESS not-accessible
              STATUS mandatory
              DESCRIPTION
                      "A collection of statistics for a particular
                      station that is active on a ring monitored by this
                      device.  This table will contain information for
                      every interface that has a
                      ringStationControlStatus equal to valid."
              INDEX { ringStationOrderIfIndex,
                      ringStationOrderOrderIndex }
              ::= { ringStationOrderTable 1 }

          -- As an example, an instance of the
          -- ringStationOrderMacAddress object might be named
          -- ringStationOrderMacAddress.1.14

          RingStationOrderEntry ::= SEQUENCE {
              ringStationOrderIfIndex             INTEGER,
              ringStationOrderOrderIndex          INTEGER,
              ringStationOrderMacAddress          MacAddress
          }

          ringStationOrderIfIndex OBJECT-TYPE
              SYNTAX INTEGER
              ACCESS read-only
              STATUS mandatory
              DESCRIPTION
                      "The value of this object uniquely identifies the
                      interface on this remote network monitoring device
                      on which this station was detected.  The interface
                      identified by a particular value of this object is
                      the same interface as identified by the same value
                      of the ifIndex object, defined in MIB-II [3]."
              ::= { ringStationOrderEntry 1 }

          ringStationOrderOrderIndex OBJECT-TYPE
              SYNTAX INTEGER
              ACCESS read-only
              STATUS mandatory
              DESCRIPTION
                      "This index denotes the location of this station
                      with respect to other stations on the ring.  This
                      index is one more than the number of hops
                      downstream that this station is from the rmon
                      probe.  The rmon probe itself gets the value one."
              ::= { ringStationOrderEntry 2 }

          ringStationOrderMacAddress OBJECT-TYPE
              SYNTAX MacAddress
              ACCESS read-only
              STATUS mandatory
              DESCRIPTION
                      "The physical address of this station."
              ::= { ringStationOrderEntry 3 }

          -- The Token Ring Ring Station Config Group
          --
          -- Implementation of this group is optional.
          -- The ring station config group manages token ring nodes
          -- through active means.

          ringStationConfigControlTable OBJECT-TYPE
              SYNTAX SEQUENCE OF RingStationConfigControlEntry
              ACCESS not-accessible
              STATUS mandatory
              DESCRIPTION
                      "A list of ring station configuration control
                      entries."
              ::= { tokenRing 4 }

          ringStationConfigControlEntry OBJECT-TYPE
              SYNTAX RingStationConfigControlEntry
              ACCESS not-accessible
              STATUS mandatory
              DESCRIPTION
                      "This entry controls active management of stations
                      by the probe.  One entry exists in this table for
                      each active station in the ringStationTable."
              INDEX { ringStationConfigControlIfIndex,
                      ringStationConfigControlMacAddress }
              ::= { ringStationConfigControlTable 1 }

          -- As an example, an instance of the
          -- ringStationConfigControlRemove object might be named
          -- ringStationConfigControlRemove.1.16.0.90.0.64.131

          RingStationConfigControlEntry ::= SEQUENCE {
              ringStationConfigControlIfIndex         INTEGER,
              ringStationConfigControlMacAddress      MacAddress,
              ringStationConfigControlRemove          INTEGER,
              ringStationConfigControlUpdateStats     INTEGER
          }

          ringStationConfigControlIfIndex OBJECT-TYPE
              SYNTAX INTEGER
              ACCESS read-only
              STATUS mandatory
              DESCRIPTION
                      "The value of this object uniquely identifies the
                      interface on this remote network monitoring device
                      on which this station was detected.  The interface
                      identified by a particular value of this object is
                      the same interface as identified by the same value
                      of the ifIndex object, defined in MIB-II [3]."
              ::= { ringStationConfigControlEntry 1 }

          ringStationConfigControlMacAddress OBJECT-TYPE
              SYNTAX MacAddress
              ACCESS read-only
              STATUS mandatory
              DESCRIPTION
                      "The physical address of this station."
              ::= { ringStationConfigControlEntry 2 }

          ringStationConfigControlRemove OBJECT-TYPE
              SYNTAX INTEGER {
                  stable(1),
                  removing(2)
              }
              ACCESS read-write
              STATUS mandatory
              DESCRIPTION
                      "Setting this object to `removing(2)' causes a
                      Remove Station MAC frame to be sent.  The agent
                      will set this object to `stable(1)' after
                      processing the request."
              ::= { ringStationConfigControlEntry 3 }

          ringStationConfigControlUpdateStats OBJECT-TYPE
              SYNTAX INTEGER {
                  stable(1),
                  updating(2)
              }
              ACCESS read-write
              STATUS mandatory
              DESCRIPTION
                      "Setting this object to `updating(2)' causes the
                      configuration information associate with this
                      entry to be updated.  The agent will set this
                      object to `stable(1)' after processing the
                      request."
              ::= { ringStationConfigControlEntry 4 }

          --  The ringStationConfig Table
          --
          --  Entries exist in this table after an active
          --  configuration query has completed successfully for
          --  a station.  This query is initiated by the associated
          --  ringStationConfigControlUpdateStats variable.

          ringStationConfigTable OBJECT-TYPE
              SYNTAX SEQUENCE OF RingStationConfigEntry
              ACCESS not-accessible
              STATUS mandatory
              DESCRIPTION
                      "A list of configuration entries for stations on a
                      ring monitored by this probe."
              ::= { tokenRing 5 }

          ringStationConfigEntry OBJECT-TYPE
              SYNTAX RingStationConfigEntry
              ACCESS not-accessible
              STATUS mandatory
              DESCRIPTION
                      "A collection of statistics for a particular
                      station that has been discovered on a ring
                      monitored by this probe."
              INDEX { ringStationConfigIfIndex,
                      ringStationConfigMacAddress }
              ::= { ringStationConfigTable 1 }

          -- As an example, an instance of the
          -- ringStationConfigLocation object might be named
          -- ringStationConfigLocation.1.16.0.90.0.64.131

          RingStationConfigEntry ::= SEQUENCE {
              ringStationConfigIfIndex            INTEGER,
              ringStationConfigMacAddress         MacAddress,
              ringStationConfigUpdateTime         TimeTicks,
              ringStationConfigLocation           OCTET STRING,
              ringStationConfigMicrocode          OCTET STRING,
              ringStationConfigGroupAddress       OCTET STRING,
              ringStationConfigFunctionalAddress  OCTET STRING
          }

          ringStationConfigIfIndex OBJECT-TYPE
              SYNTAX INTEGER
              ACCESS read-only
              STATUS mandatory
              DESCRIPTION
                      "The value of this object uniquely identifies the
                      interface on this remote network monitoring device
                      on which this station was detected.  The interface
                      identified by a particular value of this object is
                      the same interface as identified by the same value
                      of the ifIndex object, defined in MIB-II [3]."
              ::= { ringStationConfigEntry 1 }

          ringStationConfigMacAddress OBJECT-TYPE
              SYNTAX MacAddress
              ACCESS read-only
              STATUS mandatory
              DESCRIPTION
                      "The physical address of this station."
              ::= { ringStationConfigEntry 2 }

          ringStationConfigUpdateTime OBJECT-TYPE
              SYNTAX TimeTicks
              ACCESS read-only
              STATUS mandatory
              DESCRIPTION
                      "The value of sysUpTime at the time this
                      configuration information was last updated
                      (completely)."
              ::= { ringStationConfigEntry 3 }

          ringStationConfigLocation OBJECT-TYPE
              SYNTAX OCTET STRING (SIZE(4))
              ACCESS read-only
              STATUS mandatory
              DESCRIPTION
                      "The assigned physical location of this station."
              ::= { ringStationConfigEntry 4 }

          ringStationConfigMicrocode OBJECT-TYPE
              SYNTAX OCTET STRING (SIZE(10))
              ACCESS read-only
              STATUS mandatory
              DESCRIPTION
                      "The microcode EC level of this station."
              ::= { ringStationConfigEntry 5 }

          ringStationConfigGroupAddress OBJECT-TYPE
              SYNTAX OCTET STRING (SIZE(4))
              ACCESS read-only
              STATUS mandatory
              DESCRIPTION
                      "The low-order 4 octets of the group address
                      recognized by this station."
              ::= { ringStationConfigEntry 6 }

          ringStationConfigFunctionalAddress OBJECT-TYPE
              SYNTAX OCTET STRING (SIZE(4))
              ACCESS read-only
              STATUS mandatory
              DESCRIPTION
                      "the functional addresses recognized by this
                      station."
              ::= { ringStationConfigEntry 7 }

          -- The Token Ring Source Routing group
          --
          -- Implementation of this group is optional.
          -- The data in this group is collected from the source
          -- routing information potentially present in any token ring
          -- packet.  This information will be valid only in a pure
          -- source route bridging environment.  In a transparent
          -- bridging or a mixed bridging environment, this
          -- information may not be accurate.

          sourceRoutingStatsTable OBJECT-TYPE
              SYNTAX SEQUENCE OF SourceRoutingStatsEntry
              ACCESS not-accessible
              STATUS mandatory
              DESCRIPTION
                      "A list of source routing statistics entries."
              ::= { tokenRing 6 }

          sourceRoutingStatsEntry OBJECT-TYPE
              SYNTAX SourceRoutingStatsEntry
              ACCESS not-accessible
              STATUS mandatory
              DESCRIPTION
                      "A collection of source routing statistics kept
                      for a particular Token Ring interface."
              INDEX { sourceRoutingStatsIfIndex }
              ::= { sourceRoutingStatsTable 1 }

          -- As an example, an instance of the
          -- sourceRoutingStatsInFrames object might be named
          -- sourceRoutingStatsInFrames.1

          SourceRoutingStatsEntry ::= SEQUENCE {
              sourceRoutingStatsIfIndex                     INTEGER,
              sourceRoutingStatsRingNumber                  INTEGER,
              sourceRoutingStatsInFrames                    Counter,
                  -- in to our net
              sourceRoutingStatsOutFrames                   Counter,
                  -- out from our net
              sourceRoutingStatsThroughFrames               Counter,
                  -- through our net
              sourceRoutingStatsAllRoutesBroadcastFrames    Counter,
              sourceRoutingStatsSingleRouteBroadcastFrames  Counter,
              sourceRoutingStatsInOctets                    Counter,
              sourceRoutingStatsOutOctets                   Counter,
              sourceRoutingStatsThroughOctets               Counter,
              sourceRoutingStatsAllRoutesBroadcastOctets    Counter,
              sourceRoutingStatsSingleRoutesBroadcastOctets Counter,
              sourceRoutingStatsLocalLLCFrames              Counter,
              sourceRoutingStats1HopFrames                  Counter,
              sourceRoutingStats2HopsFrames                 Counter,
              sourceRoutingStats3HopsFrames                 Counter,
              sourceRoutingStats4HopsFrames                 Counter,
              sourceRoutingStats5HopsFrames                 Counter,
              sourceRoutingStats6HopsFrames                 Counter,
              sourceRoutingStats7HopsFrames                 Counter,
              sourceRoutingStats8HopsFrames                 Counter,
              sourceRoutingStatsMoreThan8HopsFrames         Counter,
              sourceRoutingStatsOwner                       OwnerString,
              sourceRoutingStatsStatus                      EntryStatus
          }

          sourceRoutingStatsIfIndex OBJECT-TYPE
              SYNTAX INTEGER
              ACCESS read-only
              STATUS mandatory
              DESCRIPTION
                      "The value of this object uniquely identifies the
                      interface on this remote network monitoring device
                      on which source routing statistics will be
                      detected.  The interface identified by a
                      particular value of this object is the same
                      interface as identified by the same value of the
                      ifIndex object, defined in MIB-II [3]."
              ::= { sourceRoutingStatsEntry 1 }

          sourceRoutingStatsRingNumber OBJECT-TYPE
              SYNTAX INTEGER
              ACCESS read-only
              STATUS mandatory
              DESCRIPTION
                      "The ring number of the ring monitored by this
                      entry.  When any object in this entry is created,
                      the probe will attempt to discover the ring
                      number.  Only after the ring number is discovered
                      will this object be created.  After creating an
                      object in this entry, the management station
                      should poll this object to detect when it is
                      created.  Only after this object is created can
                      the management station set the
                      sourceRoutingStatsStatus entry to valid(1)."
              ::= { sourceRoutingStatsEntry 2 }

          sourceRoutingStatsInFrames OBJECT-TYPE
              SYNTAX Counter
              ACCESS read-only
              STATUS mandatory
              DESCRIPTION
                      "The count of frames sent into this ring from
                      another ring."
              ::= { sourceRoutingStatsEntry 3 }

          sourceRoutingStatsOutFrames OBJECT-TYPE
              SYNTAX Counter
              ACCESS read-only
              STATUS mandatory
              DESCRIPTION
                      "The count of frames sent from this ring to
                      another ring."
              ::= { sourceRoutingStatsEntry 4 }

          sourceRoutingStatsThroughFrames OBJECT-TYPE
              SYNTAX Counter
              ACCESS read-only
              STATUS mandatory
              DESCRIPTION
                      "The count of frames sent from another ring,
                      through this ring, to another ring."
              ::= { sourceRoutingStatsEntry 5 }

          sourceRoutingStatsAllRoutesBroadcastFrames OBJECT-TYPE
              SYNTAX Counter
              ACCESS read-only
              STATUS mandatory
              DESCRIPTION
                      "The total number of good frames received that
                      were All Routes Broadcast."
              ::= { sourceRoutingStatsEntry 6 }

          sourceRoutingStatsSingleRouteBroadcastFrames OBJECT-TYPE
              SYNTAX Counter
              ACCESS read-only
              STATUS mandatory
              DESCRIPTION
                      "The total number of good frames received that
                      were Single Route Broadcast."
              ::= { sourceRoutingStatsEntry 7 }

          sourceRoutingStatsInOctets OBJECT-TYPE
              SYNTAX Counter
              ACCESS read-only
              STATUS mandatory
              DESCRIPTION
                      "The count of octets in good frames sent into this
                      ring from another ring."
              ::= { sourceRoutingStatsEntry 8 }

          sourceRoutingStatsOutOctets OBJECT-TYPE
              SYNTAX Counter
              ACCESS read-only
              STATUS mandatory
              DESCRIPTION
                      "The count of octets in good frames sent from this
                      ring to another ring."
              ::= { sourceRoutingStatsEntry 9 }

          sourceRoutingStatsThroughOctets OBJECT-TYPE
              SYNTAX Counter
              ACCESS read-only
              STATUS mandatory
              DESCRIPTION
                      "The count of octets in good frames sent another
                      ring, through this ring, to another ring."
              ::= { sourceRoutingStatsEntry 10 }

          sourceRoutingStatsAllRoutesBroadcastOctets OBJECT-TYPE
              SYNTAX Counter
              ACCESS read-only
              STATUS mandatory
              DESCRIPTION
                      "The total number of octets in good frames
                      received that were All Routes Broadcast."
              ::= { sourceRoutingStatsEntry 11 }

          sourceRoutingStatsSingleRoutesBroadcastOctets OBJECT-TYPE
              SYNTAX Counter
              ACCESS read-only
              STATUS mandatory
              DESCRIPTION
                      "The total number of octets in good frames
                      received that were Single Route Broadcast."
              ::= { sourceRoutingStatsEntry 12 }

          sourceRoutingStatsLocalLLCFrames OBJECT-TYPE
              SYNTAX Counter
              ACCESS read-only
              STATUS mandatory
              DESCRIPTION
                      "The total number of frames received who had no
                      RIF field (or had a RIF field that only included
                      the local ring's number) and were not All Route
                      Broadcast Frames."
              ::= { sourceRoutingStatsEntry 13 }

          sourceRoutingStats1HopFrames OBJECT-TYPE
              SYNTAX Counter
              ACCESS read-only
              STATUS mandatory
              DESCRIPTION
                      "The total number of frames received whose route
                      had 1 hop, were not All Route Broadcast Frames,
                      and whose source or destination were on this ring
                      (i.e. frames that had a RIF field and had this
                      ring number in the first or last entry of the RIF
                      field)."
              ::= { sourceRoutingStatsEntry 14 }

          sourceRoutingStats2HopsFrames OBJECT-TYPE
              SYNTAX Counter
              ACCESS read-only
              STATUS mandatory
              DESCRIPTION
                      "The total number of frames received whose route
                      had 2 hops, were not All Route Broadcast Frames,
                      and whose source or destination were on this ring
                      (i.e. frames that had a RIF field and had this
                      ring number in the first or last entry of the RIF
                      field)."
              ::= { sourceRoutingStatsEntry 15 }

          sourceRoutingStats3HopsFrames OBJECT-TYPE
              SYNTAX Counter
              ACCESS read-only
              STATUS mandatory
              DESCRIPTION
                      "The total number of frames received whose route
                      had 3 hops, were not All Route Broadcast Frames,
                      and whose source or destination were on this ring
                      (i.e. frames that had a RIF field and had this
                      ring number in the first or last entry of the RIF
                      field)."
              ::= { sourceRoutingStatsEntry 16 }

          sourceRoutingStats4HopsFrames OBJECT-TYPE
              SYNTAX Counter
              ACCESS read-only
              STATUS mandatory
              DESCRIPTION
                      "The total number of frames received whose route
                      had 4 hops, were not All Route Broadcast Frames,
                      and whose source or destination were on this ring
                      (i.e. frames that had a RIF field and had this
                      ring number in the first or last entry of the RIF
                      field)."
              ::= { sourceRoutingStatsEntry 17 }

          sourceRoutingStats5HopsFrames OBJECT-TYPE
              SYNTAX Counter
              ACCESS read-only
              STATUS mandatory
              DESCRIPTION
                      "The total number of frames received whose route
                      had 5 hops, were not All Route Broadcast Frames,
                      and whose source or destination were on this ring
                      (i.e. frames that had a RIF field and had this
                      ring number in the first or last entry of the RIF
                      field)."
              ::= { sourceRoutingStatsEntry 18 }

          sourceRoutingStats6HopsFrames OBJECT-TYPE
              SYNTAX Counter
              ACCESS read-only
              STATUS mandatory
              DESCRIPTION
                      "The total number of frames received whose route
                      had 6 hops, were not All Route Broadcast Frames,
                      and whose source or destination were on this ring
                      (i.e. frames that had a RIF field and had this
                      ring number in the first or last entry of the RIF
                      field)."
              ::= { sourceRoutingStatsEntry 19 }

          sourceRoutingStats7HopsFrames OBJECT-TYPE
              SYNTAX Counter
              ACCESS read-only
              STATUS mandatory
              DESCRIPTION
                      "The total number of frames received whose route
                      had 7 hops, were not All Route Broadcast Frames,
                      and whose source or destination were on this ring
                      (i.e. frames that had a RIF field and had this
                      ring number in the first or last entry of the RIF
                      field)."
              ::= { sourceRoutingStatsEntry 20 }

          sourceRoutingStats8HopsFrames OBJECT-TYPE
              SYNTAX Counter
              ACCESS read-only
              STATUS mandatory
              DESCRIPTION
                      "The total number of frames received whose route
                      had 8 hops, were not All Route Broadcast Frames,
                      and whose source or destination were on this ring
                      (i.e. frames that had a RIF field and had this
                      ring number in the first or last entry of the RIF
                      field)."
              ::= { sourceRoutingStatsEntry 21 }

          sourceRoutingStatsMoreThan8HopsFrames OBJECT-TYPE
              SYNTAX Counter
              ACCESS read-only
              STATUS mandatory
              DESCRIPTION
                      "The total number of frames received whose route
                      had more than 8 hops, were not All Route Broadcast
                      Frames, and whose source or destination were on
                      this ring (i.e. frames that had a RIF field and
                      had this ring number in the first or last entry of
                      the RIF field)."
              ::= { sourceRoutingStatsEntry 22 }

          sourceRoutingStatsOwner OBJECT-TYPE
              SYNTAX OwnerString
              ACCESS read-write
              STATUS mandatory
              DESCRIPTION
                      "The entity that configured this entry and is
                      therefore using the resources assigned to it."
              ::= { sourceRoutingStatsEntry 23 }

          sourceRoutingStatsStatus OBJECT-TYPE
              SYNTAX EntryStatus
              ACCESS read-write
              STATUS mandatory
              DESCRIPTION
                      "The status of this sourceRoutingStats entry."
              ::= { sourceRoutingStatsEntry 24 }

END

RMON-MIB DEFINITIONS ::= BEGIN

     IMPORTS
         MODULE-IDENTITY, OBJECT-TYPE, OBJECT-IDENTITY,
         NOTIFICATION-TYPE, mib-2, Counter32,
         Integer32, TimeTicks                   FROM SNMPv2-SMI

         TEXTUAL-CONVENTION, DisplayString      FROM SNMPv2-TC

         MODULE-COMPLIANCE, OBJECT-GROUP,
         NOTIFICATION-GROUP                     FROM SNMPv2-CONF;

 --  Remote Network Monitoring MIB

 rmonMibModule MODULE-IDENTITY
     LAST-UPDATED "200005110000Z"  -- 11 May, 2000
     ORGANIZATION "IETF RMON MIB Working Group"
     CONTACT-INFO
         "Steve Waldbusser
         Phone: +1-650-948-6500
         Fax:   +1-650-745-0671
         Email: waldbusser@nextbeacon.com"
     DESCRIPTION
         "Remote network monitoring devices, often called
         monitors or probes, are instruments that exist for
         the purpose of managing a network. This MIB defines
         objects for managing remote network monitoring devices."

     REVISION "200005110000Z"    -- 11 May, 2000
     DESCRIPTION
         "Reformatted into SMIv2 format.

         This version published as RFC 2819."

     REVISION "199502010000Z" -- 1 Feb, 1995
     DESCRIPTION
         "Bug fixes, clarifications and minor changes based on
         implementation experience, published as RFC1757 [18].

         Two changes were made to object definitions:

         1) A new status bit has been defined for the
         captureBufferPacketStatus object, indicating that the
         packet order within the capture buffer may not be identical to
         the packet order as received off the wire.  This bit may only


         be used for packets transmitted by the probe.  Older NMS
         applications can safely ignore this status bit, which might be
         used by newer agents.

         2) The packetMatch trap has been removed.  This trap was never
         actually 'approved' and was not added to this document along
         with the risingAlarm and fallingAlarm traps. The packetMatch
         trap could not be throttled, which could cause disruption of
         normal network traffic under some circumstances. An NMS should
         configure a risingAlarm threshold on the appropriate
         channelMatches instance if a trap is desired for a packetMatch
         event. Note that logging of packetMatch events is still
         supported--only trap generation for such events has been
         removed.

         In addition, several clarifications to individual object
         definitions have been added to assist agent and NMS
         implementors:

         - global definition of 'good packets' and 'bad packets'

         - more detailed text governing conceptual row creation and
           modification

         - instructions for probes relating to interface changes and
           disruptions

         - clarification of some ethernet counter definitions

         - recommended formula for calculating network utilization

         - clarification of channel and captureBuffer behavior for some
           unusual conditions

         - examples of proper instance naming for each table"

     REVISION "199111010000Z"    -- 1 Nov, 1991
     DESCRIPTION
         "The original version of this MIB, published as RFC1271."
     ::= { rmonConformance 8 }

     rmon    OBJECT IDENTIFIER ::= { mib-2 16 }

     -- textual conventions

 OwnerString ::= TEXTUAL-CONVENTION
     STATUS current


     DESCRIPTION
         "This data type is used to model an administratively
         assigned name of the owner of a resource. Implementations
         must accept values composed of well-formed NVT ASCII
         sequences. In addition, implementations should accept
         values composed of well-formed UTF-8 sequences.

         It is suggested that this name contain one or more of
         the following: IP address, management station name,
         network manager's name, location, or phone number.
         In some cases the agent itself will be the owner of
         an entry.  In these cases, this string shall be set
         to a string starting with 'monitor'.

         SNMP access control is articulated entirely in terms
         of the contents of MIB views; access to a particular
         SNMP object instance depends only upon its presence
         or absence in a particular MIB view and never upon
         its value or the value of related object instances.
         Thus, objects of this type afford resolution of
         resource contention only among cooperating
         managers; they realize no access control function
         with respect to uncooperative parties."
     SYNTAX OCTET STRING (SIZE (0..127))

 EntryStatus ::= TEXTUAL-CONVENTION
     STATUS current
     DESCRIPTION
         "The status of a table entry.

         Setting this object to the value invalid(4) has the
         effect of invalidating the corresponding entry.
         That is, it effectively disassociates the mapping
         identified with said entry.
         It is an implementation-specific matter as to whether
         the agent removes an invalidated entry from the table.
         Accordingly, management stations must be prepared to
         receive tabular information from agents that corresponds
         to entries currently not in use.  Proper
         interpretation of such entries requires examination
         of the relevant EntryStatus object.

         An existing instance of this object cannot be set to
         createRequest(2).  This object may only be set to
         createRequest(2) when this instance is created.  When
         this object is created, the agent may wish to create
         supplemental object instances with default values
         to complete a conceptual row in this table.  Because the


         creation of these default objects is entirely at the option
         of the agent, the manager must not assume that any will be
         created, but may make use of any that are created.
         Immediately after completing the create operation, the agent
         must set this object to underCreation(3).

         When in the underCreation(3) state, an entry is allowed to
         exist in a possibly incomplete, possibly inconsistent state,
         usually to allow it to be modified in multiple PDUs.  When in
         this state, an entry is not fully active.
         Entries shall exist in the underCreation(3) state until
         the management station is finished configuring the entry
         and sets this object to valid(1) or aborts, setting this
         object to invalid(4).  If the agent determines that an
         entry has been in the underCreation(3) state for an
         abnormally long time, it may decide that the management
         station has crashed.  If the agent makes this decision,
         it may set this object to invalid(4) to reclaim the
         entry.  A prudent agent will understand that the
         management station may need to wait for human input
         and will allow for that possibility in its
         determination of this abnormally long period.

         An entry in the valid(1) state is fully configured and
         consistent and fully represents the configuration or
         operation such a row is intended to represent.  For
         example, it could be a statistical function that is
         configured and active, or a filter that is available
         in the list of filters processed by the packet capture
         process.

         A manager is restricted to changing the state of an entry in
         the following ways:

              To:       valid  createRequest  underCreation  invalid
         From:
         valid             OK             NO             OK       OK
         createRequest    N/A            N/A            N/A      N/A
         underCreation     OK             NO             OK       OK
         invalid           NO             NO             NO       OK
         nonExistent       NO             OK             NO       OK

         In the table above, it is not applicable to move the state
         from the createRequest state to any other state because the
         manager will never find the variable in that state.  The
         nonExistent state is not a value of the enumeration, rather
         it means that the entryStatus variable does not exist at all.


         An agent may allow an entryStatus variable to change state in
         additional ways, so long as the semantics of the states are
         followed.  This allowance is made to ease the implementation of
         the agent and is made despite the fact that managers should
         never exercise these additional state transitions."
     SYNTAX INTEGER {
                valid(1),
                createRequest(2),
                underCreation(3),
                invalid(4)
            }

     statistics        OBJECT IDENTIFIER ::= { rmon 1 }
     history           OBJECT IDENTIFIER ::= { rmon 2 }
     alarm             OBJECT IDENTIFIER ::= { rmon 3 }
     hosts             OBJECT IDENTIFIER ::= { rmon 4 }
     hostTopN          OBJECT IDENTIFIER ::= { rmon 5 }
     matrix            OBJECT IDENTIFIER ::= { rmon 6 }
     filter            OBJECT IDENTIFIER ::= { rmon 7 }
     capture           OBJECT IDENTIFIER ::= { rmon 8 }
     event             OBJECT IDENTIFIER ::= { rmon 9 }
     rmonConformance   OBJECT IDENTIFIER ::= { rmon 20 }

 -- The Ethernet Statistics Group
 --
 -- Implementation of the Ethernet Statistics group is optional.
 -- Consult the MODULE-COMPLIANCE macro for the authoritative
 -- conformance information for this MIB.
 --
 -- The ethernet statistics group contains statistics measured by the
 -- probe for each monitored interface on this device.  These
 -- statistics take the form of free running counters that start from
 -- zero when a valid entry is created.
 --
 -- This group currently has statistics defined only for
 -- Ethernet interfaces.  Each etherStatsEntry contains statistics
 -- for one Ethernet interface.  The probe must create one
 -- etherStats entry for each monitored Ethernet interface
 -- on the device.

 etherStatsTable OBJECT-TYPE
     SYNTAX     SEQUENCE OF EtherStatsEntry
     MAX-ACCESS not-accessible
     STATUS     current
     DESCRIPTION
         "A list of Ethernet statistics entries."
     ::= { statistics 1 }


 etherStatsEntry OBJECT-TYPE
     SYNTAX     EtherStatsEntry
     MAX-ACCESS not-accessible
     STATUS     current
     DESCRIPTION
         "A collection of statistics kept for a particular
         Ethernet interface.  As an example, an instance of the
         etherStatsPkts object might be named etherStatsPkts.1"
     INDEX { etherStatsIndex }
     ::= { etherStatsTable 1 }

 EtherStatsEntry ::= SEQUENCE {
     etherStatsIndex                    Integer32,
     etherStatsDataSource               OBJECT IDENTIFIER,
     etherStatsDropEvents               Counter32,
     etherStatsOctets                   Counter32,
     etherStatsPkts                     Counter32,
     etherStatsBroadcastPkts            Counter32,
     etherStatsMulticastPkts            Counter32,
     etherStatsCRCAlignErrors           Counter32,
     etherStatsUndersizePkts            Counter32,
     etherStatsOversizePkts             Counter32,
     etherStatsFragments                Counter32,
     etherStatsJabbers                  Counter32,
     etherStatsCollisions               Counter32,
     etherStatsPkts64Octets             Counter32,
     etherStatsPkts65to127Octets        Counter32,
     etherStatsPkts128to255Octets       Counter32,
     etherStatsPkts256to511Octets       Counter32,
     etherStatsPkts512to1023Octets      Counter32,
     etherStatsPkts1024to1518Octets     Counter32,
     etherStatsOwner                    OwnerString,
     etherStatsStatus                   EntryStatus
 }

 etherStatsIndex OBJECT-TYPE
     SYNTAX     Integer32 (1..65535)
     MAX-ACCESS read-only
     STATUS     current
     DESCRIPTION
         "The value of this object uniquely identifies this
         etherStats entry."
     ::= { etherStatsEntry 1 }

 etherStatsDataSource OBJECT-TYPE
     SYNTAX     OBJECT IDENTIFIER
     MAX-ACCESS read-create
     STATUS     current


     DESCRIPTION
         "This object identifies the source of the data that
         this etherStats entry is configured to analyze.  This
         source can be any ethernet interface on this device.
         In order to identify a particular interface, this object
         shall identify the instance of the ifIndex object,
         defined in RFC 2233 [17], for the desired interface.
         For example, if an entry were to receive data from
         interface #1, this object would be set to ifIndex.1.

         The statistics in this group reflect all packets
         on the local network segment attached to the identified
         interface.

         An agent may or may not be able to tell if fundamental
         changes to the media of the interface have occurred and
         necessitate an invalidation of this entry.  For example, a
         hot-pluggable ethernet card could be pulled out and replaced
         by a token-ring card.  In such a case, if the agent has such
         knowledge of the change, it is recommended that it
         invalidate this entry.

         This object may not be modified if the associated
         etherStatsStatus object is equal to valid(1)."
     ::= { etherStatsEntry 2 }

 etherStatsDropEvents OBJECT-TYPE
     SYNTAX     Counter32
     MAX-ACCESS read-only
     STATUS     current
     DESCRIPTION
         "The total number of events in which packets
         were dropped by the probe due to lack of resources.
         Note that this number is not necessarily the number of
         packets dropped; it is just the number of times this
         condition has been detected."
     ::= { etherStatsEntry 3 }

 etherStatsOctets OBJECT-TYPE
     SYNTAX     Counter32
     UNITS      "Octets"
     MAX-ACCESS read-only
     STATUS     current
     DESCRIPTION
         "The total number of octets of data (including
         those in bad packets) received on the
         network (excluding framing bits but including
         FCS octets).


         This object can be used as a reasonable estimate of
         10-Megabit ethernet utilization.  If greater precision is
         desired, the etherStatsPkts and etherStatsOctets objects
         should be sampled before and after a common interval.  The
         differences in the sampled values are Pkts and Octets,
         respectively, and the number of seconds in the interval is
         Interval.  These values are used to calculate the Utilization
         as follows:

                          Pkts * (9.6 + 6.4) + (Octets * .8)
          Utilization = -------------------------------------
                                  Interval * 10,000

         The result of this equation is the value Utilization which
         is the percent utilization of the ethernet segment on a
         scale of 0 to 100 percent."
     ::= { etherStatsEntry 4 }

 etherStatsPkts OBJECT-TYPE
     SYNTAX     Counter32
     UNITS      "Packets"
     MAX-ACCESS read-only
     STATUS     current
     DESCRIPTION
         "The total number of packets (including bad packets,
         broadcast packets, and multicast packets) received."
     ::= { etherStatsEntry 5 }

 etherStatsBroadcastPkts OBJECT-TYPE
     SYNTAX     Counter32
     UNITS      "Packets"
     MAX-ACCESS read-only
     STATUS     current
     DESCRIPTION
         "The total number of good packets received that were
         directed to the broadcast address.  Note that this
         does not include multicast packets."
     ::= { etherStatsEntry 6 }

 etherStatsMulticastPkts OBJECT-TYPE
     SYNTAX     Counter32
     UNITS      "Packets"
     MAX-ACCESS read-only
     STATUS     current
     DESCRIPTION
         "The total number of good packets received that were
         directed to a multicast address.  Note that this number
         does not include packets directed to the broadcast


         address."
     ::= { etherStatsEntry 7 }

 etherStatsCRCAlignErrors OBJECT-TYPE
     SYNTAX     Counter32
     UNITS      "Packets"
     MAX-ACCESS read-only
     STATUS     current
     DESCRIPTION
         "The total number of packets received that
         had a length (excluding framing bits, but
         including FCS octets) of between 64 and 1518
         octets, inclusive, but had either a bad
         Frame Check Sequence (FCS) with an integral
         number of octets (FCS Error) or a bad FCS with
         a non-integral number of octets (Alignment Error)."
     ::= { etherStatsEntry 8 }

 etherStatsUndersizePkts OBJECT-TYPE
     SYNTAX     Counter32
     UNITS      "Packets"
     MAX-ACCESS read-only
     STATUS     current
     DESCRIPTION
         "The total number of packets received that were
         less than 64 octets long (excluding framing bits,
         but including FCS octets) and were otherwise well
         formed."
     ::= { etherStatsEntry 9 }

 etherStatsOversizePkts OBJECT-TYPE
     SYNTAX     Counter32
     UNITS      "Packets"
     MAX-ACCESS read-only
     STATUS     current
     DESCRIPTION
         "The total number of packets received that were
         longer than 1518 octets (excluding framing bits,
         but including FCS octets) and were otherwise
         well formed."
     ::= { etherStatsEntry 10 }

 etherStatsFragments OBJECT-TYPE
     SYNTAX     Counter32
     UNITS      "Packets"
     MAX-ACCESS read-only
     STATUS     current
     DESCRIPTION


         "The total number of packets received that were less than
         64 octets in length (excluding framing bits but including
         FCS octets) and had either a bad Frame Check Sequence
         (FCS) with an integral number of octets (FCS Error) or a
         bad FCS with a non-integral number of octets (Alignment
         Error).

         Note that it is entirely normal for etherStatsFragments to
         increment.  This is because it counts both runts (which are
         normal occurrences due to collisions) and noise hits."
     ::= { etherStatsEntry 11 }

 etherStatsJabbers OBJECT-TYPE
     SYNTAX     Counter32
     UNITS      "Packets"
     MAX-ACCESS read-only
     STATUS     current
     DESCRIPTION
         "The total number of packets received that were
         longer than 1518 octets (excluding framing bits,
         but including FCS octets), and had either a bad
         Frame Check Sequence (FCS) with an integral number
         of octets (FCS Error) or a bad FCS with a non-integral
         number of octets (Alignment Error).

         Note that this definition of jabber is different
         than the definition in IEEE-802.3 section 8.2.1.5
         (10BASE5) and section 10.3.1.4 (10BASE2).  These
         documents define jabber as the condition where any
         packet exceeds 20 ms.  The allowed range to detect
         jabber is between 20 ms and 150 ms."
     ::= { etherStatsEntry 12 }

 etherStatsCollisions OBJECT-TYPE
     SYNTAX     Counter32
     UNITS      "Collisions"
     MAX-ACCESS read-only
     STATUS     current
     DESCRIPTION
         "The best estimate of the total number of collisions
         on this Ethernet segment.

         The value returned will depend on the location of the
         RMON probe. Section 8.2.1.3 (10BASE-5) and section
         10.3.1.3 (10BASE-2) of IEEE standard 802.3 states that a
         station must detect a collision, in the receive mode, if
         three or more stations are transmitting simultaneously.  A
         repeater port must detect a collision when two or more


         stations are transmitting simultaneously.  Thus a probe
         placed on a repeater port could record more collisions
         than a probe connected to a station on the same segment
         would.

         Probe location plays a much smaller role when considering
         10BASE-T.  14.2.1.4 (10BASE-T) of IEEE standard 802.3
         defines a collision as the simultaneous presence of signals
         on the DO and RD circuits (transmitting and receiving
         at the same time).  A 10BASE-T station can only detect
         collisions when it is transmitting.  Thus probes placed on
         a station and a repeater, should report the same number of
         collisions.

         Note also that an RMON probe inside a repeater should
         ideally report collisions between the repeater and one or
         more other hosts (transmit collisions as defined by IEEE
         802.3k) plus receiver collisions observed on any coax
         segments to which the repeater is connected."
     ::= { etherStatsEntry 13 }

 etherStatsPkts64Octets OBJECT-TYPE
     SYNTAX     Counter32
     UNITS      "Packets"
     MAX-ACCESS read-only
     STATUS     current
     DESCRIPTION
         "The total number of packets (including bad
         packets) received that were 64 octets in length
         (excluding framing bits but including FCS octets)."
     ::= { etherStatsEntry 14 }

 etherStatsPkts65to127Octets OBJECT-TYPE
     SYNTAX     Counter32
     UNITS      "Packets"
     MAX-ACCESS read-only
     STATUS     current
     DESCRIPTION
         "The total number of packets (including bad
         packets) received that were between
         65 and 127 octets in length inclusive
         (excluding framing bits but including FCS octets)."
     ::= { etherStatsEntry 15 }

 etherStatsPkts128to255Octets OBJECT-TYPE
     SYNTAX     Counter32
     UNITS      "Packets"
     MAX-ACCESS read-only


     STATUS     current
     DESCRIPTION
         "The total number of packets (including bad
         packets) received that were between
         128 and 255 octets in length inclusive
         (excluding framing bits but including FCS octets)."
     ::= { etherStatsEntry 16 }

 etherStatsPkts256to511Octets OBJECT-TYPE
     SYNTAX     Counter32
     UNITS      "Packets"
     MAX-ACCESS read-only
     STATUS     current
     DESCRIPTION
         "The total number of packets (including bad
         packets) received that were between
         256 and 511 octets in length inclusive
         (excluding framing bits but including FCS octets)."
     ::= { etherStatsEntry 17 }

 etherStatsPkts512to1023Octets OBJECT-TYPE
     SYNTAX     Counter32
     UNITS      "Packets"
     MAX-ACCESS read-only
     STATUS     current
     DESCRIPTION
         "The total number of packets (including bad
         packets) received that were between
         512 and 1023 octets in length inclusive
         (excluding framing bits but including FCS octets)."
     ::= { etherStatsEntry 18 }

 etherStatsPkts1024to1518Octets OBJECT-TYPE
     SYNTAX     Counter32
     UNITS      "Packets"
     MAX-ACCESS read-only
     STATUS     current
     DESCRIPTION
         "The total number of packets (including bad
         packets) received that were between
         1024 and 1518 octets in length inclusive
         (excluding framing bits but including FCS octets)."
     ::= { etherStatsEntry 19 }

 etherStatsOwner OBJECT-TYPE
     SYNTAX     OwnerString
     MAX-ACCESS read-create
     STATUS     current


     DESCRIPTION
         "The entity that configured this entry and is therefore
         using the resources assigned to it."
     ::= { etherStatsEntry 20 }

 etherStatsStatus OBJECT-TYPE
     SYNTAX     EntryStatus
     MAX-ACCESS read-create
     STATUS     current
     DESCRIPTION
         "The status of this etherStats entry."
     ::= { etherStatsEntry 21 }

 -- The History Control Group

 -- Implementation of the History Control group is optional.
 -- Consult the MODULE-COMPLIANCE macro for the authoritative
 -- conformance information for this MIB.
 --
 -- The history control group controls the periodic statistical
 -- sampling of data from various types of networks.  The
 -- historyControlTable stores configuration entries that each
 -- define an interface, polling period, and other parameters.
 -- Once samples are taken, their data is stored in an entry
 -- in a media-specific table.  Each such entry defines one
 -- sample, and is associated with the historyControlEntry that
 -- caused the sample to be taken.  Each counter in the
 -- etherHistoryEntry counts the same event as its similarly-named
 -- counterpart in the etherStatsEntry, except that each value here
 -- is a cumulative sum during a sampling period.
 --
 -- If the probe keeps track of the time of day, it should start
 -- the first sample of the history at a time such that
 -- when the next hour of the day begins, a sample is
 -- started at that instant.  This tends to make more
 -- user-friendly reports, and enables comparison of reports
 -- from different probes that have relatively accurate time
 -- of day.
 --
 -- The probe is encouraged to add two history control entries
 -- per monitored interface upon initialization that describe a short
 -- term and a long term polling period.  Suggested parameters are 30
 -- seconds for the short term polling period and 30 minutes for
 -- the long term period.

 historyControlTable OBJECT-TYPE
     SYNTAX     SEQUENCE OF HistoryControlEntry
     MAX-ACCESS not-accessible


     STATUS     current
     DESCRIPTION
         "A list of history control entries."
     ::= { history 1 }

 historyControlEntry OBJECT-TYPE
     SYNTAX     HistoryControlEntry
     MAX-ACCESS not-accessible
     STATUS     current
     DESCRIPTION
         "A list of parameters that set up a periodic sampling of
         statistics.  As an example, an instance of the
         historyControlInterval object might be named
         historyControlInterval.2"
     INDEX { historyControlIndex }
     ::= { historyControlTable 1 }

 HistoryControlEntry ::= SEQUENCE {
     historyControlIndex             Integer32,
     historyControlDataSource        OBJECT IDENTIFIER,
     historyControlBucketsRequested  Integer32,
     historyControlBucketsGranted    Integer32,
     historyControlInterval          Integer32,
     historyControlOwner             OwnerString,
     historyControlStatus            EntryStatus
 }

 historyControlIndex OBJECT-TYPE
     SYNTAX     Integer32 (1..65535)
     MAX-ACCESS read-only
     STATUS     current
     DESCRIPTION
         "An index that uniquely identifies an entry in the
         historyControl table.  Each such entry defines a
         set of samples at a particular interval for an
         interface on the device."
     ::= { historyControlEntry 1 }

 historyControlDataSource OBJECT-TYPE
     SYNTAX     OBJECT IDENTIFIER
     MAX-ACCESS read-create
     STATUS     current
     DESCRIPTION
         "This object identifies the source of the data for
         which historical data was collected and
         placed in a media-specific table on behalf of this
         historyControlEntry.  This source can be any
         interface on this device.  In order to identify


         a particular interface, this object shall identify
         the instance of the ifIndex object, defined
         in  RFC 2233 [17], for the desired interface.
         For example, if an entry were to receive data from
         interface #1, this object would be set to ifIndex.1.

         The statistics in this group reflect all packets
         on the local network segment attached to the identified
         interface.

         An agent may or may not be able to tell if fundamental
         changes to the media of the interface have occurred and
         necessitate an invalidation of this entry.  For example, a
         hot-pluggable ethernet card could be pulled out and replaced
         by a token-ring card.  In such a case, if the agent has such
         knowledge of the change, it is recommended that it
         invalidate this entry.

         This object may not be modified if the associated
         historyControlStatus object is equal to valid(1)."
     ::= { historyControlEntry 2 }

 historyControlBucketsRequested OBJECT-TYPE
     SYNTAX     Integer32 (1..65535)
     MAX-ACCESS read-create
     STATUS     current
     DESCRIPTION
         "The requested number of discrete time intervals
         over which data is to be saved in the part of the
         media-specific table associated with this
         historyControlEntry.

         When this object is created or modified, the probe
         should set historyControlBucketsGranted as closely to
         this object as is possible for the particular probe
         implementation and available resources."
     DEFVAL { 50 }
     ::= { historyControlEntry 3 }

 historyControlBucketsGranted OBJECT-TYPE
     SYNTAX     Integer32 (1..65535)
     MAX-ACCESS read-only
     STATUS     current
     DESCRIPTION
         "The number of discrete sampling intervals
         over which data shall be saved in the part of
         the media-specific table associated with this
         historyControlEntry.


         When the associated historyControlBucketsRequested
         object is created or modified, the probe
         should set this object as closely to the requested
         value as is possible for the particular
         probe implementation and available resources.  The
         probe must not lower this value except as a result
         of a modification to the associated
         historyControlBucketsRequested object.

         There will be times when the actual number of
         buckets associated with this entry is less than
         the value of this object.  In this case, at the
         end of each sampling interval, a new bucket will
         be added to the media-specific table.

         When the number of buckets reaches the value of
         this object and a new bucket is to be added to the
         media-specific table, the oldest bucket associated
         with this historyControlEntry shall be deleted by
         the agent so that the new bucket can be added.

         When the value of this object changes to a value less
         than the current value, entries are deleted
         from the media-specific table associated with this
         historyControlEntry.  Enough of the oldest of these
         entries shall be deleted by the agent so that their
         number remains less than or equal to the new value of
         this object.

         When the value of this object changes to a value greater
         than the current value, the number of associated media-
         specific entries may be allowed to grow."
     ::= { historyControlEntry 4 }

 historyControlInterval OBJECT-TYPE
     SYNTAX     Integer32 (1..3600)
     UNITS      "Seconds"
     MAX-ACCESS read-create
     STATUS     current
     DESCRIPTION
         "The interval in seconds over which the data is
         sampled for each bucket in the part of the
         media-specific table associated with this
         historyControlEntry.  This interval can
         be set to any number of seconds between 1 and
         3600 (1 hour).

         Because the counters in a bucket may overflow at their


         maximum value with no indication, a prudent manager will
         take into account the possibility of overflow in any of
         the associated counters.  It is important to consider the
         minimum time in which any counter could overflow on a
         particular media type and set the historyControlInterval
         object to a value less than this interval.  This is
         typically most important for the 'octets' counter in any
         media-specific table.  For example, on an Ethernet
         network, the etherHistoryOctets counter could overflow
         in about one hour at the Ethernet's maximum
         utilization.

         This object may not be modified if the associated
         historyControlStatus object is equal to valid(1)."
     DEFVAL { 1800 }
     ::= { historyControlEntry 5 }

 historyControlOwner OBJECT-TYPE
     SYNTAX     OwnerString
     MAX-ACCESS read-create
     STATUS     current
     DESCRIPTION
         "The entity that configured this entry and is therefore
         using the resources assigned to it."
     ::= { historyControlEntry 6 }

 historyControlStatus OBJECT-TYPE
     SYNTAX     EntryStatus
     MAX-ACCESS read-create
     STATUS     current
     DESCRIPTION
         "The status of this historyControl entry.

         Each instance of the media-specific table associated
         with this historyControlEntry will be deleted by the agent
         if this historyControlEntry is not equal to valid(1)."
     ::= { historyControlEntry 7 }

 -- The Ethernet History Group

 -- Implementation of the Ethernet History group is optional.
 -- Consult the MODULE-COMPLIANCE macro for the authoritative
 -- conformance information for this MIB.
 --
 -- The Ethernet History group records periodic statistical samples
 -- from a network and stores them for later retrieval.
 -- Once samples are taken, their data is stored in an entry
 -- in a media-specific table.  Each such entry defines one


 -- sample, and is associated with the historyControlEntry that
 -- caused the sample to be taken.  This group defines the
 -- etherHistoryTable, for Ethernet networks.
 --

 etherHistoryTable OBJECT-TYPE
     SYNTAX     SEQUENCE OF EtherHistoryEntry
     MAX-ACCESS not-accessible
     STATUS     current
     DESCRIPTION
         "A list of Ethernet history entries."
     ::= { history 2 }

 etherHistoryEntry OBJECT-TYPE
     SYNTAX     EtherHistoryEntry
     MAX-ACCESS not-accessible
     STATUS     current
     DESCRIPTION
         "An historical sample of Ethernet statistics on a particular
         Ethernet interface.  This sample is associated with the
         historyControlEntry which set up the parameters for
         a regular collection of these samples.  As an example, an
         instance of the etherHistoryPkts object might be named
         etherHistoryPkts.2.89"
     INDEX { etherHistoryIndex , etherHistorySampleIndex }
     ::= { etherHistoryTable 1 }

 EtherHistoryEntry ::= SEQUENCE {
     etherHistoryIndex                 Integer32,
     etherHistorySampleIndex           Integer32,
     etherHistoryIntervalStart         TimeTicks,
     etherHistoryDropEvents            Counter32,
     etherHistoryOctets                Counter32,
     etherHistoryPkts                  Counter32,
     etherHistoryBroadcastPkts         Counter32,
     etherHistoryMulticastPkts         Counter32,
     etherHistoryCRCAlignErrors        Counter32,
     etherHistoryUndersizePkts         Counter32,
     etherHistoryOversizePkts          Counter32,
     etherHistoryFragments             Counter32,
     etherHistoryJabbers               Counter32,
     etherHistoryCollisions            Counter32,
     etherHistoryUtilization           Integer32
 }

 etherHistoryIndex OBJECT-TYPE
     SYNTAX     Integer32 (1..65535)
     MAX-ACCESS read-only


     STATUS     current
     DESCRIPTION
         "The history of which this entry is a part.  The
         history identified by a particular value of this
         index is the same history as identified
         by the same value of historyControlIndex."
     ::= { etherHistoryEntry 1 }

 etherHistorySampleIndex OBJECT-TYPE
     SYNTAX     Integer32 (1..2147483647)
     MAX-ACCESS read-only
     STATUS     current
     DESCRIPTION
         "An index that uniquely identifies the particular
         sample this entry represents among all samples
         associated with the same historyControlEntry.
         This index starts at 1 and increases by one
         as each new sample is taken."
     ::= { etherHistoryEntry 2 }

 etherHistoryIntervalStart OBJECT-TYPE
     SYNTAX     TimeTicks
     MAX-ACCESS read-only
     STATUS     current
     DESCRIPTION
         "The value of sysUpTime at the start of the interval
         over which this sample was measured.  If the probe
         keeps track of the time of day, it should start
         the first sample of the history at a time such that
         when the next hour of the day begins, a sample is
         started at that instant.  Note that following this
         rule may require the probe to delay collecting the
         first sample of the history, as each sample must be
         of the same interval.  Also note that the sample which
         is currently being collected is not accessible in this
         table until the end of its interval."
     ::= { etherHistoryEntry 3 }

 etherHistoryDropEvents OBJECT-TYPE
     SYNTAX     Counter32
     MAX-ACCESS read-only
     STATUS     current
     DESCRIPTION
         "The total number of events in which packets
         were dropped by the probe due to lack of resources
         during this sampling interval.  Note that this number
         is not necessarily the number of packets dropped, it
         is just the number of times this condition has been


         detected."
     ::= { etherHistoryEntry 4 }

 etherHistoryOctets OBJECT-TYPE
     SYNTAX     Counter32
     UNITS      "Octets"
     MAX-ACCESS read-only
     STATUS     current
     DESCRIPTION
         "The total number of octets of data (including
         those in bad packets) received on the
         network (excluding framing bits but including
         FCS octets)."
     ::= { etherHistoryEntry 5 }

 etherHistoryPkts OBJECT-TYPE
     SYNTAX     Counter32
     UNITS      "Packets"
     MAX-ACCESS read-only
     STATUS     current
     DESCRIPTION
         "The number of packets (including bad packets)
         received during this sampling interval."
     ::= { etherHistoryEntry 6 }

 etherHistoryBroadcastPkts OBJECT-TYPE
     SYNTAX     Counter32
     UNITS      "Packets"
     MAX-ACCESS read-only
     STATUS     current
     DESCRIPTION
         "The number of good packets received during this
         sampling interval that were directed to the
         broadcast address."
     ::= { etherHistoryEntry 7 }

 etherHistoryMulticastPkts OBJECT-TYPE
     SYNTAX     Counter32
     UNITS      "Packets"
     MAX-ACCESS read-only
     STATUS     current
     DESCRIPTION
         "The number of good packets received during this
         sampling interval that were directed to a
         multicast address.  Note that this number does not
         include packets addressed to the broadcast address."
     ::= { etherHistoryEntry 8 }


 etherHistoryCRCAlignErrors OBJECT-TYPE
     SYNTAX     Counter32
     UNITS      "Packets"
     MAX-ACCESS read-only
     STATUS     current
     DESCRIPTION
         "The number of packets received during this
         sampling interval that had a length (excluding
         framing bits but including FCS octets) between
         64 and 1518 octets, inclusive, but had either a bad Frame
         Check Sequence (FCS) with an integral number of octets
         (FCS Error) or a bad FCS with a non-integral number
         of octets (Alignment Error)."
     ::= { etherHistoryEntry 9 }

 etherHistoryUndersizePkts OBJECT-TYPE
     SYNTAX     Counter32
     UNITS      "Packets"
     MAX-ACCESS read-only
     STATUS     current
     DESCRIPTION
         "The number of packets received during this
         sampling interval that were less than 64 octets
         long (excluding framing bits but including FCS
         octets) and were otherwise well formed."
     ::= { etherHistoryEntry 10 }

 etherHistoryOversizePkts OBJECT-TYPE
     SYNTAX     Counter32
     UNITS      "Packets"
     MAX-ACCESS read-only
     STATUS     current
     DESCRIPTION
         "The number of packets received during this
         sampling interval that were longer than 1518
         octets (excluding framing bits but including
         FCS octets) but were otherwise well formed."
     ::= { etherHistoryEntry 11 }

 etherHistoryFragments OBJECT-TYPE
     SYNTAX     Counter32
     UNITS      "Packets"
     MAX-ACCESS read-only
     STATUS     current
     DESCRIPTION
         "The total number of packets received during this
         sampling interval that were less than 64 octets in
         length (excluding framing bits but including FCS


         octets) had either a bad Frame Check Sequence (FCS)
         with an integral number of octets (FCS Error) or a bad
         FCS with a non-integral number of octets (Alignment
         Error).

         Note that it is entirely normal for etherHistoryFragments to
         increment.  This is because it counts both runts (which are
         normal occurrences due to collisions) and noise hits."
     ::= { etherHistoryEntry 12 }

 etherHistoryJabbers OBJECT-TYPE
     SYNTAX     Counter32
     UNITS      "Packets"
     MAX-ACCESS read-only
     STATUS     current
     DESCRIPTION
         "The number of packets received during this
         sampling interval that were longer than 1518 octets
         (excluding framing bits but including FCS octets),
         and  had either a bad Frame Check Sequence (FCS)
         with an integral number of octets (FCS Error) or
         a bad FCS with a non-integral number of octets
         (Alignment Error).

         Note that this definition of jabber is different
         than the definition in IEEE-802.3 section 8.2.1.5
         (10BASE5) and section 10.3.1.4 (10BASE2).  These
         documents define jabber as the condition where any
         packet exceeds 20 ms.  The allowed range to detect
         jabber is between 20 ms and 150 ms."
     ::= { etherHistoryEntry 13 }

 etherHistoryCollisions OBJECT-TYPE
     SYNTAX     Counter32
     UNITS      "Collisions"
     MAX-ACCESS read-only
     STATUS     current
     DESCRIPTION
         "The best estimate of the total number of collisions
         on this Ethernet segment during this sampling
         interval.

         The value returned will depend on the location of the
         RMON probe. Section 8.2.1.3 (10BASE-5) and section
         10.3.1.3 (10BASE-2) of IEEE standard 802.3 states that a
         station must detect a collision, in the receive mode, if
         three or more stations are transmitting simultaneously.  A
         repeater port must detect a collision when two or more


         stations are transmitting simultaneously.  Thus a probe
         placed on a repeater port could record more collisions
         than a probe connected to a station on the same segment
         would.

         Probe location plays a much smaller role when considering
         10BASE-T.  14.2.1.4 (10BASE-T) of IEEE standard 802.3
         defines a collision as the simultaneous presence of signals
         on the DO and RD circuits (transmitting and receiving
         at the same time).  A 10BASE-T station can only detect
         collisions when it is transmitting.  Thus probes placed on
         a station and a repeater, should report the same number of
         collisions.

         Note also that an RMON probe inside a repeater should
         ideally report collisions between the repeater and one or
         more other hosts (transmit collisions as defined by IEEE
         802.3k) plus receiver collisions observed on any coax
         segments to which the repeater is connected."
     ::= { etherHistoryEntry 14 }

 etherHistoryUtilization OBJECT-TYPE
     SYNTAX     Integer32 (0..10000)
     MAX-ACCESS read-only
     STATUS     current
     DESCRIPTION
         "The best estimate of the mean physical layer
         network utilization on this interface during this
         sampling interval, in hundredths of a percent."
     ::= { etherHistoryEntry 15 }

 -- The Alarm Group

 -- Implementation of the Alarm group is optional. The Alarm Group
 -- requires the implementation of the Event group.
 -- Consult the MODULE-COMPLIANCE macro for the authoritative
 -- conformance information for this MIB.
 --
 -- The Alarm group periodically takes statistical samples from
 -- variables in the probe and compares them to thresholds that have
 -- been configured.  The alarm table stores configuration
 -- entries that each define a variable, polling period, and
 -- threshold parameters.  If a sample is found to cross the
 -- threshold values, an event is generated.  Only variables that
 -- resolve to an ASN.1 primitive type of INTEGER (INTEGER, Integer32,
 -- Counter32, Counter64, Gauge32, or TimeTicks) may be monitored in
 -- this way.
 --


 -- This function has a hysteresis mechanism to limit the generation
 -- of events.  This mechanism generates one event as a threshold
 -- is crossed in the appropriate direction.  No more events are
 -- generated for that threshold until the opposite threshold is
 -- crossed.
 --
 -- In the case of a sampling a deltaValue, a probe may implement
 -- this mechanism with more precision if it takes a delta sample
 -- twice per period, each time comparing the sum of the latest two
 -- samples to the threshold.  This allows the detection of threshold
 -- crossings that span the sampling boundary.  Note that this does
 -- not require any special configuration of the threshold value.
 -- It is suggested that probes implement this more precise algorithm.

 alarmTable OBJECT-TYPE
     SYNTAX     SEQUENCE OF AlarmEntry
     MAX-ACCESS not-accessible
     STATUS     current
     DESCRIPTION
         "A list of alarm entries."
     ::= { alarm 1 }

 alarmEntry OBJECT-TYPE
     SYNTAX     AlarmEntry
     MAX-ACCESS not-accessible
     STATUS     current
     DESCRIPTION
         "A list of parameters that set up a periodic checking
         for alarm conditions.  For example, an instance of the
         alarmValue object might be named alarmValue.8"
     INDEX { alarmIndex }
     ::= { alarmTable 1 }

 AlarmEntry ::= SEQUENCE {
     alarmIndex                    Integer32,
     alarmInterval                 Integer32,
     alarmVariable                 OBJECT IDENTIFIER,
     alarmSampleType               INTEGER,
     alarmValue                    Integer32,
     alarmStartupAlarm             INTEGER,
     alarmRisingThreshold          Integer32,
     alarmFallingThreshold         Integer32,
     alarmRisingEventIndex         Integer32,
     alarmFallingEventIndex        Integer32,
     alarmOwner                    OwnerString,
     alarmStatus                   EntryStatus
 }


 alarmIndex OBJECT-TYPE
     SYNTAX     Integer32 (1..65535)
     MAX-ACCESS read-only
     STATUS     current
     DESCRIPTION
         "An index that uniquely identifies an entry in the
         alarm table.  Each such entry defines a
         diagnostic sample at a particular interval
         for an object on the device."
     ::= { alarmEntry 1 }

 alarmInterval OBJECT-TYPE
     SYNTAX     Integer32
     UNITS      "Seconds"
     MAX-ACCESS read-create
     STATUS     current
     DESCRIPTION
         "The interval in seconds over which the data is
         sampled and compared with the rising and falling
         thresholds.  When setting this variable, care
         should be taken in the case of deltaValue
         sampling - the interval should be set short enough
         that the sampled variable is very unlikely to
         increase or decrease by more than 2^31 - 1 during
         a single sampling interval.

         This object may not be modified if the associated
         alarmStatus object is equal to valid(1)."
     ::= { alarmEntry 2 }

 alarmVariable OBJECT-TYPE
     SYNTAX     OBJECT IDENTIFIER
     MAX-ACCESS read-create
     STATUS     current
     DESCRIPTION
         "The object identifier of the particular variable to be
         sampled.  Only variables that resolve to an ASN.1 primitive
         type of INTEGER (INTEGER, Integer32, Counter32, Counter64,
         Gauge, or TimeTicks) may be sampled.

         Because SNMP access control is articulated entirely
         in terms of the contents of MIB views, no access
         control mechanism exists that can restrict the value of
         this object to identify only those objects that exist
         in a particular MIB view.  Because there is thus no
         acceptable means of restricting the read access that
         could be obtained through the alarm mechanism, the
         probe must only grant write access to this object in


         those views that have read access to all objects on
         the probe.

         During a set operation, if the supplied variable name is
         not available in the selected MIB view, a badValue error
         must be returned.  If at any time the variable name of
         an established alarmEntry is no longer available in the
         selected MIB view, the probe must change the status of
         this alarmEntry to invalid(4).

         This object may not be modified if the associated
         alarmStatus object is equal to valid(1)."
     ::= { alarmEntry 3 }

 alarmSampleType OBJECT-TYPE
     SYNTAX     INTEGER {
                  absoluteValue(1),
                  deltaValue(2)
                }
     MAX-ACCESS read-create
     STATUS     current
     DESCRIPTION
         "The method of sampling the selected variable and
         calculating the value to be compared against the
         thresholds.  If the value of this object is
         absoluteValue(1), the value of the selected variable
         will be compared directly with the thresholds at the
         end of the sampling interval.  If the value of this
         object is deltaValue(2), the value of the selected
         variable at the last sample will be subtracted from
         the current value, and the difference compared with
         the thresholds.

         This object may not be modified if the associated
         alarmStatus object is equal to valid(1)."
     ::= { alarmEntry 4 }

 alarmValue OBJECT-TYPE
     SYNTAX     Integer32
     MAX-ACCESS read-only
     STATUS     current
     DESCRIPTION
         "The value of the statistic during the last sampling
         period.  For example, if the sample type is deltaValue,
         this value will be the difference between the samples
         at the beginning and end of the period.  If the sample
         type is absoluteValue, this value will be the sampled
         value at the end of the period.


         This is the value that is compared with the rising and
         falling thresholds.

         The value during the current sampling period is not
         made available until the period is completed and will
         remain available until the next period completes."
     ::= { alarmEntry 5 }

 alarmStartupAlarm OBJECT-TYPE
     SYNTAX     INTEGER {
                  risingAlarm(1),
                  fallingAlarm(2),
                  risingOrFallingAlarm(3)
                }
     MAX-ACCESS read-create
     STATUS     current
     DESCRIPTION
         "The alarm that may be sent when this entry is first
         set to valid.  If the first sample after this entry
         becomes valid is greater than or equal to the
         risingThreshold and alarmStartupAlarm is equal to
         risingAlarm(1) or risingOrFallingAlarm(3), then a single
         rising alarm will be generated.  If the first sample
         after this entry becomes valid is less than or equal
         to the fallingThreshold and alarmStartupAlarm is equal
         to fallingAlarm(2) or risingOrFallingAlarm(3), then a
         single falling alarm will be generated.

         This object may not be modified if the associated
         alarmStatus object is equal to valid(1)."
     ::= { alarmEntry 6 }

 alarmRisingThreshold OBJECT-TYPE
     SYNTAX     Integer32
     MAX-ACCESS read-create
     STATUS     current
     DESCRIPTION
         "A threshold for the sampled statistic.  When the current
         sampled value is greater than or equal to this threshold,
         and the value at the last sampling interval was less than
         this threshold, a single event will be generated.
         A single event will also be generated if the first
         sample after this entry becomes valid is greater than or
         equal to this threshold and the associated
         alarmStartupAlarm is equal to risingAlarm(1) or
         risingOrFallingAlarm(3).

         After a rising event is generated, another such event


         will not be generated until the sampled value
         falls below this threshold and reaches the
         alarmFallingThreshold.

         This object may not be modified if the associated
         alarmStatus object is equal to valid(1)."
     ::= { alarmEntry 7 }

 alarmFallingThreshold OBJECT-TYPE
     SYNTAX     Integer32
     MAX-ACCESS read-create
     STATUS     current
     DESCRIPTION
         "A threshold for the sampled statistic.  When the current
         sampled value is less than or equal to this threshold,
         and the value at the last sampling interval was greater than
         this threshold, a single event will be generated.
         A single event will also be generated if the first
         sample after this entry becomes valid is less than or
         equal to this threshold and the associated
         alarmStartupAlarm is equal to fallingAlarm(2) or
         risingOrFallingAlarm(3).

         After a falling event is generated, another such event
         will not be generated until the sampled value
         rises above this threshold and reaches the
         alarmRisingThreshold.

         This object may not be modified if the associated
         alarmStatus object is equal to valid(1)."
     ::= { alarmEntry 8 }

 alarmRisingEventIndex OBJECT-TYPE
     SYNTAX     Integer32 (0..65535)
     MAX-ACCESS read-create
     STATUS     current
     DESCRIPTION
         "The index of the eventEntry that is
         used when a rising threshold is crossed.  The
         eventEntry identified by a particular value of
         this index is the same as identified by the same value
         of the eventIndex object.  If there is no
         corresponding entry in the eventTable, then
         no association exists.  In particular, if this value
         is zero, no associated event will be generated, as
         zero is not a valid event index.

         This object may not be modified if the associated


         alarmStatus object is equal to valid(1)."
     ::= { alarmEntry 9 }

 alarmFallingEventIndex OBJECT-TYPE
     SYNTAX     Integer32 (0..65535)
     MAX-ACCESS read-create
     STATUS     current
     DESCRIPTION
         "The index of the eventEntry that is
         used when a falling threshold is crossed.  The
         eventEntry identified by a particular value of
         this index is the same as identified by the same value
         of the eventIndex object.  If there is no
         corresponding entry in the eventTable, then
         no association exists.  In particular, if this value
         is zero, no associated event will be generated, as
         zero is not a valid event index.

         This object may not be modified if the associated
         alarmStatus object is equal to valid(1)."
     ::= { alarmEntry 10 }

 alarmOwner OBJECT-TYPE
     SYNTAX     OwnerString
     MAX-ACCESS read-create
     STATUS     current
     DESCRIPTION
         "The entity that configured this entry and is therefore
         using the resources assigned to it."
     ::= { alarmEntry 11 }

 alarmStatus OBJECT-TYPE
     SYNTAX     EntryStatus
     MAX-ACCESS read-create
     STATUS     current
     DESCRIPTION
         "The status of this alarm entry."
     ::= { alarmEntry 12 }

 -- The Host Group

 -- Implementation of the Host group is optional.
 -- Consult the MODULE-COMPLIANCE macro for the authoritative
 -- conformance information for this MIB.
 --
 -- The host group discovers new hosts on the network by
 -- keeping a list of source and destination MAC Addresses seen
 -- in good packets.  For each of these addresses, the host group


 -- keeps a set of statistics.  The hostControlTable controls
 -- which interfaces this function is performed on, and contains
 -- some information about the process.  On behalf of each
 -- hostControlEntry, data is collected on an interface and placed
 -- in both the hostTable and the hostTimeTable.  If the
 -- monitoring device finds itself short of resources, it may
 -- delete entries as needed.  It is suggested that the device
 -- delete the least recently used entries first.

 -- The hostTable contains entries for each address discovered on
 -- a particular interface.  Each entry contains statistical
 -- data about that host.  This table is indexed by the
 -- MAC address of the host, through which a random access
 -- may be achieved.

 -- The hostTimeTable contains data in the same format as the
 -- hostTable, and must contain the same set of hosts, but is
 -- indexed using hostTimeCreationOrder rather than hostAddress.
 -- The hostTimeCreationOrder is an integer which reflects
 -- the relative order in which a particular entry was discovered
 -- and thus inserted into the table.  As this order, and thus
 -- the index, is among those entries currently in the table,
 -- the index for a particular entry may change if an
 -- (earlier) entry is deleted.  Thus the association between
 -- hostTimeCreationOrder and hostTimeEntry may be broken at
 -- any time.

 -- The hostTimeTable has two important uses.  The first is the
 -- fast download of this potentially large table.  Because the
 -- index of this table runs from 1 to the size of the table,
 -- inclusive, its values are predictable.  This allows very
 -- efficient packing of variables into SNMP PDU's and allows
 -- a table transfer to have multiple packets outstanding.
 -- These benefits increase transfer rates tremendously.

 -- The second use of the hostTimeTable is the efficient discovery
 -- by the management station of new entries added to the table.
 -- After the management station has downloaded the entire table,
 -- it knows that new entries will be added immediately after the
 -- end of the current table.  It can thus detect new entries there
 -- and retrieve them easily.

 -- Because the association between hostTimeCreationOrder and
 -- hostTimeEntry may be broken at any time, the management
 -- station must monitor the related hostControlLastDeleteTime
 -- object.  When the management station thus detects a deletion,
 -- it must assume that any such associations have been broken,
 -- and invalidate any it has stored locally.  This includes


 -- restarting any download of the hostTimeTable that may have been
 -- in progress, as well as rediscovering the end of the
 -- hostTimeTable so that it may detect new entries.  If the
 -- management station does not detect the broken association,
 -- it may continue to refer to a particular host by its
 -- creationOrder while unwittingly retrieving the data associated
 -- with another host entirely.  If this happens while downloading
 -- the host table, the management station may fail to download
 -- all of the entries in the table.

 hostControlTable OBJECT-TYPE
     SYNTAX     SEQUENCE OF HostControlEntry
     MAX-ACCESS not-accessible
     STATUS     current
     DESCRIPTION
         "A list of host table control entries."
     ::= { hosts 1 }

 hostControlEntry OBJECT-TYPE
     SYNTAX     HostControlEntry
     MAX-ACCESS not-accessible
     STATUS     current
     DESCRIPTION
         "A list of parameters that set up the discovery of hosts
         on a particular interface and the collection of statistics
         about these hosts.  For example, an instance of the
         hostControlTableSize object might be named
         hostControlTableSize.1"
     INDEX { hostControlIndex }
     ::= { hostControlTable 1 }

 HostControlEntry ::= SEQUENCE {

     hostControlIndex            Integer32,
     hostControlDataSource       OBJECT IDENTIFIER,
     hostControlTableSize        Integer32,
     hostControlLastDeleteTime   TimeTicks,
     hostControlOwner            OwnerString,
     hostControlStatus           EntryStatus
 }

 hostControlIndex OBJECT-TYPE
     SYNTAX     Integer32 (1..65535)
     MAX-ACCESS read-only
     STATUS     current
     DESCRIPTION
         "An index that uniquely identifies an entry in the


         hostControl table.  Each such entry defines
         a function that discovers hosts on a particular interface
         and places statistics about them in the hostTable and
         the hostTimeTable on behalf of this hostControlEntry."
     ::= { hostControlEntry 1 }

 hostControlDataSource OBJECT-TYPE
     SYNTAX     OBJECT IDENTIFIER
     MAX-ACCESS read-create
     STATUS     current
     DESCRIPTION
         "This object identifies the source of the data for
         this instance of the host function.  This source
         can be any interface on this device.  In order
         to identify a particular interface, this object shall
         identify the instance of the ifIndex object, defined
         in RFC 2233 [17], for the desired interface.
         For example, if an entry were to receive data from
         interface #1, this object would be set to ifIndex.1.

         The statistics in this group reflect all packets
         on the local network segment attached to the identified
         interface.

         An agent may or may not be able to tell if fundamental
         changes to the media of the interface have occurred and
         necessitate an invalidation of this entry.  For example, a
         hot-pluggable ethernet card could be pulled out and replaced
         by a token-ring card.  In such a case, if the agent has such
         knowledge of the change, it is recommended that it
         invalidate this entry.

         This object may not be modified if the associated
         hostControlStatus object is equal to valid(1)."
     ::= { hostControlEntry 2 }

 hostControlTableSize OBJECT-TYPE
     SYNTAX     Integer32
     MAX-ACCESS read-only
     STATUS     current
     DESCRIPTION
         "The number of hostEntries in the hostTable and the
         hostTimeTable associated with this hostControlEntry."
     ::= { hostControlEntry 3 }

 hostControlLastDeleteTime OBJECT-TYPE
     SYNTAX     TimeTicks
     MAX-ACCESS read-only


     STATUS     current
     DESCRIPTION
         "The value of sysUpTime when the last entry
         was deleted from the portion of the hostTable
         associated with this hostControlEntry.  If no
         deletions have occurred, this value shall be zero."
     ::= { hostControlEntry 4 }

 hostControlOwner OBJECT-TYPE
     SYNTAX     OwnerString
     MAX-ACCESS read-create
     STATUS     current
     DESCRIPTION
         "The entity that configured this entry and is therefore
         using the resources assigned to it."
     ::= { hostControlEntry 5 }

 hostControlStatus OBJECT-TYPE
     SYNTAX     EntryStatus
     MAX-ACCESS read-create
     STATUS     current
     DESCRIPTION
         "The status of this hostControl entry.

         If this object is not equal to valid(1), all associated
         entries in the hostTable, hostTimeTable, and the
         hostTopNTable shall be deleted by the agent."
     ::= { hostControlEntry 6 }

 hostTable OBJECT-TYPE
     SYNTAX     SEQUENCE OF HostEntry
     MAX-ACCESS not-accessible
     STATUS     current
     DESCRIPTION
         "A list of host entries."
     ::= { hosts 2 }

 hostEntry OBJECT-TYPE
     SYNTAX     HostEntry
     MAX-ACCESS not-accessible
     STATUS     current
     DESCRIPTION
         "A collection of statistics for a particular host that has
         been discovered on an interface of this device.  For example,
         an instance of the hostOutBroadcastPkts object might be
         named hostOutBroadcastPkts.1.6.8.0.32.27.3.176"
     INDEX { hostIndex, hostAddress }
     ::= { hostTable 1 }


 HostEntry ::= SEQUENCE {
     hostAddress             OCTET STRING,
     hostCreationOrder       Integer32,
     hostIndex               Integer32,
     hostInPkts              Counter32,
     hostOutPkts             Counter32,
     hostInOctets            Counter32,
     hostOutOctets           Counter32,
     hostOutErrors           Counter32,
     hostOutBroadcastPkts    Counter32,
     hostOutMulticastPkts    Counter32
 }

 hostAddress OBJECT-TYPE
     SYNTAX     OCTET STRING
     MAX-ACCESS read-only
     STATUS     current
     DESCRIPTION
         "The physical address of this host."
     ::= { hostEntry 1 }

 hostCreationOrder OBJECT-TYPE
     SYNTAX     Integer32 (1..65535)
     MAX-ACCESS read-only
     STATUS     current
     DESCRIPTION
         "An index that defines the relative ordering of
         the creation time of hosts captured for a
         particular hostControlEntry.  This index shall
         be between 1 and N, where N is the value of
         the associated hostControlTableSize.  The ordering
         of the indexes is based on the order of each entry's
         insertion into the table, in which entries added earlier
         have a lower index value than entries added later.

         It is important to note that the order for a
         particular entry may change as an (earlier) entry
         is deleted from the table.  Because this order may
         change, management stations should make use of the
         hostControlLastDeleteTime variable in the
         hostControlEntry associated with the relevant
         portion of the hostTable.  By observing
         this variable, the management station may detect
         the circumstances where a previous association
         between a value of hostCreationOrder
         and a hostEntry may no longer hold."
     ::= { hostEntry 2 }


 hostIndex OBJECT-TYPE
     SYNTAX     Integer32 (1..65535)
     MAX-ACCESS read-only
     STATUS     current
     DESCRIPTION
         "The set of collected host statistics of which
         this entry is a part.  The set of hosts
         identified by a particular value of this
         index is associated with the hostControlEntry
         as identified by the same value of hostControlIndex."
     ::= { hostEntry 3 }

 hostInPkts OBJECT-TYPE
     SYNTAX     Counter32
     UNITS      "Packets"
     MAX-ACCESS read-only
     STATUS     current
     DESCRIPTION
         "The number of good packets transmitted to this
         address since it was added to the hostTable."
     ::= { hostEntry 4 }

 hostOutPkts OBJECT-TYPE
     SYNTAX     Counter32
     UNITS      "Packets"
     MAX-ACCESS read-only
     STATUS     current
     DESCRIPTION
         "The number of packets, including bad packets, transmitted
         by this address since it was added to the hostTable."
     ::= { hostEntry 5 }

 hostInOctets OBJECT-TYPE
     SYNTAX     Counter32
     UNITS      "Octets"
     MAX-ACCESS read-only
     STATUS     current
     DESCRIPTION
         "The number of octets transmitted to this address since
         it was added to the hostTable (excluding framing
         bits but including FCS octets), except for those
         octets in bad packets."
     ::= { hostEntry 6 }

 hostOutOctets OBJECT-TYPE
     SYNTAX     Counter32
     UNITS      "Octets"
     MAX-ACCESS read-only


     STATUS     current
     DESCRIPTION
         "The number of octets transmitted by this address since
         it was added to the hostTable (excluding framing
         bits but including FCS octets), including those
         octets in bad packets."
     ::= { hostEntry 7 }

 hostOutErrors OBJECT-TYPE
     SYNTAX     Counter32
     UNITS      "Packets"
     MAX-ACCESS read-only
     STATUS     current
     DESCRIPTION
         "The number of bad packets transmitted by this address
         since this host was added to the hostTable."
     ::= { hostEntry 8 }

 hostOutBroadcastPkts OBJECT-TYPE
     SYNTAX     Counter32
     UNITS      "Packets"
     MAX-ACCESS read-only
     STATUS     current
     DESCRIPTION
         "The number of good packets transmitted by this
         address that were directed to the broadcast address
         since this host was added to the hostTable."
     ::= { hostEntry 9 }

 hostOutMulticastPkts OBJECT-TYPE
     SYNTAX     Counter32
     UNITS      "Packets"
     MAX-ACCESS read-only
     STATUS     current
     DESCRIPTION
         "The number of good packets transmitted by this
         address that were directed to a multicast address
         since this host was added to the hostTable.
         Note that this number does not include packets
         directed to the broadcast address."
     ::= { hostEntry 10 }

 -- host Time Table

 hostTimeTable OBJECT-TYPE
     SYNTAX     SEQUENCE OF HostTimeEntry
     MAX-ACCESS not-accessible
     STATUS     current


     DESCRIPTION
         "A list of time-ordered host table entries."
     ::= { hosts 3 }

 hostTimeEntry OBJECT-TYPE
     SYNTAX     HostTimeEntry
     MAX-ACCESS not-accessible
     STATUS     current
     DESCRIPTION
         "A collection of statistics for a particular host that has
         been discovered on an interface of this device.  This
         collection includes the relative ordering of the creation
         time of this object.  For example, an instance of the
         hostTimeOutBroadcastPkts object might be named
         hostTimeOutBroadcastPkts.1.687"
     INDEX { hostTimeIndex, hostTimeCreationOrder }
     ::= { hostTimeTable 1 }

 HostTimeEntry ::= SEQUENCE {
     hostTimeAddress              OCTET STRING,
     hostTimeCreationOrder        Integer32,
     hostTimeIndex                Integer32,
     hostTimeInPkts               Counter32,
     hostTimeOutPkts              Counter32,
     hostTimeInOctets             Counter32,
     hostTimeOutOctets            Counter32,
     hostTimeOutErrors            Counter32,
     hostTimeOutBroadcastPkts     Counter32,
     hostTimeOutMulticastPkts     Counter32
 }

 hostTimeAddress OBJECT-TYPE
     SYNTAX     OCTET STRING
     MAX-ACCESS read-only
     STATUS     current
     DESCRIPTION
         "The physical address of this host."
     ::= { hostTimeEntry 1 }

 hostTimeCreationOrder OBJECT-TYPE
     SYNTAX     Integer32 (1..65535)
     MAX-ACCESS read-only
     STATUS     current
     DESCRIPTION
         "An index that uniquely identifies an entry in
         the hostTime table among those entries associated
         with the same hostControlEntry.  This index shall
         be between 1 and N, where N is the value of


         the associated hostControlTableSize.  The ordering
         of the indexes is based on the order of each entry's
         insertion into the table, in which entries added earlier
         have a lower index value than entries added later.
         Thus the management station has the ability to
         learn of new entries added to this table without
         downloading the entire table.

         It is important to note that the index for a
         particular entry may change as an (earlier) entry
         is deleted from the table.  Because this order may
         change, management stations should make use of the
         hostControlLastDeleteTime variable in the
         hostControlEntry associated with the relevant
         portion of the hostTimeTable.  By observing
         this variable, the management station may detect
         the circumstances where a download of the table
         may have missed entries, and where a previous
         association between a value of hostTimeCreationOrder
         and a hostTimeEntry may no longer hold."
     ::= { hostTimeEntry 2 }

 hostTimeIndex OBJECT-TYPE
     SYNTAX     Integer32 (1..65535)
     MAX-ACCESS read-only
     STATUS     current
     DESCRIPTION
         "The set of collected host statistics of which
         this entry is a part.  The set of hosts
         identified by a particular value of this
         index is associated with the hostControlEntry
         as identified by the same value of hostControlIndex."
     ::= { hostTimeEntry 3 }

 hostTimeInPkts OBJECT-TYPE
     SYNTAX     Counter32
     UNITS      "Packets"
     MAX-ACCESS read-only
     STATUS     current
     DESCRIPTION
         "The number of good packets transmitted to this
         address since it was added to the hostTimeTable."
     ::= { hostTimeEntry 4 }

 hostTimeOutPkts OBJECT-TYPE
     SYNTAX     Counter32
     UNITS      "Packets"
     MAX-ACCESS read-only


     STATUS     current
     DESCRIPTION
         "The number of packets, including bad packets, transmitted
         by this address since it was added to the hostTimeTable."
     ::= { hostTimeEntry 5 }

 hostTimeInOctets OBJECT-TYPE
     SYNTAX     Counter32
     UNITS      "Octets"
     MAX-ACCESS read-only
     STATUS     current
     DESCRIPTION
         "The number of octets transmitted to this address since
         it was added to the hostTimeTable (excluding framing
         bits but including FCS octets), except for those
         octets in bad packets."
     ::= { hostTimeEntry 6 }

 hostTimeOutOctets OBJECT-TYPE
     SYNTAX     Counter32
     UNITS      "Octets"
     MAX-ACCESS read-only
     STATUS     current
     DESCRIPTION
         "The number of octets transmitted by this address since
         it was added to the hostTimeTable (excluding framing
         bits but including FCS octets), including those
         octets in bad packets."
     ::= { hostTimeEntry 7 }

 hostTimeOutErrors OBJECT-TYPE
     SYNTAX     Counter32
     UNITS      "Packets"
     MAX-ACCESS read-only
     STATUS     current
     DESCRIPTION
         "The number of bad packets transmitted by this address
         since this host was added to the hostTimeTable."
     ::= { hostTimeEntry 8 }

 hostTimeOutBroadcastPkts OBJECT-TYPE
     SYNTAX     Counter32
     UNITS      "Packets"
     MAX-ACCESS read-only
     STATUS     current
     DESCRIPTION
         "The number of good packets transmitted by this
         address that were directed to the broadcast address


         since this host was added to the hostTimeTable."
     ::= { hostTimeEntry 9 }

 hostTimeOutMulticastPkts OBJECT-TYPE
     SYNTAX     Counter32
     UNITS      "Packets"
     MAX-ACCESS read-only
     STATUS     current
     DESCRIPTION
         "The number of good packets transmitted by this
         address that were directed to a multicast address
         since this host was added to the hostTimeTable.
         Note that this number does not include packets directed
         to the broadcast address."
     ::= { hostTimeEntry 10 }

 -- The Host Top "N" Group

 -- Implementation of the Host Top N group is optional. The Host Top N
 -- group requires the implementation of the host group.
 -- Consult the MODULE-COMPLIANCE macro for the authoritative
 -- conformance information for this MIB.
 --
 -- The Host Top N group is used to prepare reports that describe
 -- the hosts that top a list ordered by one of their statistics.
 -- The available statistics are samples of one of their
 -- base statistics, over an interval specified by the management
 -- station.  Thus, these statistics are rate based.  The management
 -- station also selects how many such hosts are reported.

 -- The hostTopNControlTable is used to initiate the generation of
 -- such a report.  The management station may select the parameters
 -- of such a report, such as which interface, which statistic,
 -- how many hosts, and the start and stop times of the sampling.
 -- When the report is prepared, entries are created in the
 -- hostTopNTable associated with the relevant hostTopNControlEntry.
 -- These entries are static for each report after it has been
 -- prepared.

 hostTopNControlTable OBJECT-TYPE
     SYNTAX     SEQUENCE OF HostTopNControlEntry
     MAX-ACCESS not-accessible
     STATUS     current
     DESCRIPTION
         "A list of top N host control entries."
     ::= { hostTopN 1 }

 hostTopNControlEntry OBJECT-TYPE


     SYNTAX     HostTopNControlEntry
     MAX-ACCESS not-accessible
     STATUS     current
     DESCRIPTION
         "A set of parameters that control the creation of a report
         of the top N hosts according to several metrics.  For
         example, an instance of the hostTopNDuration object might
         be named hostTopNDuration.3"
     INDEX { hostTopNControlIndex }
     ::= { hostTopNControlTable 1 }

 HostTopNControlEntry ::= SEQUENCE {
     hostTopNControlIndex    Integer32,
     hostTopNHostIndex       Integer32,
     hostTopNRateBase        INTEGER,
     hostTopNTimeRemaining   Integer32,
     hostTopNDuration        Integer32,
     hostTopNRequestedSize   Integer32,
     hostTopNGrantedSize     Integer32,
     hostTopNStartTime       TimeTicks,
     hostTopNOwner           OwnerString,
     hostTopNStatus          EntryStatus
 }

 hostTopNControlIndex OBJECT-TYPE
     SYNTAX     Integer32 (1..65535)
     MAX-ACCESS read-only
     STATUS     current
     DESCRIPTION
         "An index that uniquely identifies an entry
         in the hostTopNControl table.  Each such
         entry defines one top N report prepared for
         one interface."
     ::= { hostTopNControlEntry 1 }

 hostTopNHostIndex OBJECT-TYPE
     SYNTAX     Integer32 (1..65535)
     MAX-ACCESS read-create
     STATUS     current
     DESCRIPTION
         "The host table for which a top N report will be prepared
         on behalf of this entry.  The host table identified by a
         particular value of this index is associated with the same
         host table as identified by the same value of
         hostIndex.

         This object may not be modified if the associated
         hostTopNStatus object is equal to valid(1)."


     ::= { hostTopNControlEntry 2 }

 hostTopNRateBase OBJECT-TYPE
     SYNTAX     INTEGER {
                  hostTopNInPkts(1),
                  hostTopNOutPkts(2),
                  hostTopNInOctets(3),
                  hostTopNOutOctets(4),
                  hostTopNOutErrors(5),
                  hostTopNOutBroadcastPkts(6),
                  hostTopNOutMulticastPkts(7)
                }
     MAX-ACCESS read-create
     STATUS     current
     DESCRIPTION
         "The variable for each host that the hostTopNRate
         variable is based upon.

         This object may not be modified if the associated
         hostTopNStatus object is equal to valid(1)."
     ::= { hostTopNControlEntry 3 }

 hostTopNTimeRemaining OBJECT-TYPE
     SYNTAX     Integer32
     UNITS      "Seconds"
     MAX-ACCESS read-create
     STATUS     current
     DESCRIPTION
         "The number of seconds left in the report currently being
         collected.  When this object is modified by the management
         station, a new collection is started, possibly aborting
         a currently running report.  The new value is used
         as the requested duration of this report, which is
         loaded into the associated hostTopNDuration object.

         When this object is set to a non-zero value, any
         associated hostTopNEntries shall be made
         inaccessible by the monitor.  While the value of this
         object is non-zero, it decrements by one per second until
         it reaches zero.  During this time, all associated
         hostTopNEntries shall remain inaccessible.  At the time
         that this object decrements to zero, the report is made
         accessible in the hostTopNTable.  Thus, the hostTopN
         table needs to be created only at the end of the collection
         interval."
     DEFVAL { 0 }
     ::= { hostTopNControlEntry 4 }


 hostTopNDuration OBJECT-TYPE
     SYNTAX     Integer32
     UNITS      "Seconds"
     MAX-ACCESS read-only
     STATUS     current
     DESCRIPTION
         "The number of seconds that this report has collected
         during the last sampling interval, or if this
         report is currently being collected, the number
         of seconds that this report is being collected
         during this sampling interval.

         When the associated hostTopNTimeRemaining object is set,
         this object shall be set by the probe to the same value
         and shall not be modified until the next time
         the hostTopNTimeRemaining is set.

         This value shall be zero if no reports have been
         requested for this hostTopNControlEntry."
     DEFVAL { 0 }
     ::= { hostTopNControlEntry 5 }

 hostTopNRequestedSize OBJECT-TYPE
     SYNTAX     Integer32
     MAX-ACCESS read-create
     STATUS     current
     DESCRIPTION
         "The maximum number of hosts requested for the top N
         table.

         When this object is created or modified, the probe
         should set hostTopNGrantedSize as closely to this
         object as is possible for the particular probe
         implementation and available resources."
     DEFVAL { 10 }
     ::= { hostTopNControlEntry 6 }

 hostTopNGrantedSize OBJECT-TYPE
     SYNTAX     Integer32
     MAX-ACCESS read-only
     STATUS     current
     DESCRIPTION
         "The maximum number of hosts in the top N table.

         When the associated hostTopNRequestedSize object is
         created or modified, the probe should set this
         object as closely to the requested value as is possible
         for the particular implementation and available


         resources. The probe must not lower this value except
         as a result of a set to the associated
         hostTopNRequestedSize object.

         Hosts with the highest value of hostTopNRate shall be
         placed in this table in decreasing order of this rate
         until there is no more room or until there are no more
         hosts."
     ::= { hostTopNControlEntry 7 }

 hostTopNStartTime OBJECT-TYPE
     SYNTAX     TimeTicks
     MAX-ACCESS read-only
     STATUS     current
     DESCRIPTION
         "The value of sysUpTime when this top N report was
         last started.  In other words, this is the time that
         the associated hostTopNTimeRemaining object was
         modified to start the requested report."
     ::= { hostTopNControlEntry 8 }

 hostTopNOwner OBJECT-TYPE
     SYNTAX     OwnerString
     MAX-ACCESS read-create
     STATUS     current
     DESCRIPTION
         "The entity that configured this entry and is therefore
         using the resources assigned to it."
     ::= { hostTopNControlEntry 9 }

 hostTopNStatus OBJECT-TYPE
     SYNTAX     EntryStatus
     MAX-ACCESS read-create
     STATUS     current
     DESCRIPTION
         "The status of this hostTopNControl entry.

         If this object is not equal to valid(1), all associated
         hostTopNEntries shall be deleted by the agent."
     ::= { hostTopNControlEntry 10 }

 hostTopNTable OBJECT-TYPE
     SYNTAX     SEQUENCE OF HostTopNEntry
     MAX-ACCESS not-accessible
     STATUS     current
     DESCRIPTION
         "A list of top N host entries."
     ::= { hostTopN 2 }


 hostTopNEntry OBJECT-TYPE
     SYNTAX     HostTopNEntry
     MAX-ACCESS not-accessible
     STATUS     current
     DESCRIPTION
         "A set of statistics for a host that is part of a top N
         report.  For example, an instance of the hostTopNRate
         object might be named hostTopNRate.3.10"
     INDEX { hostTopNReport, hostTopNIndex }
     ::= { hostTopNTable 1 }

 HostTopNEntry ::= SEQUENCE {
     hostTopNReport                Integer32,
     hostTopNIndex                 Integer32,
     hostTopNAddress               OCTET STRING,
     hostTopNRate                  Integer32
 }

 hostTopNReport OBJECT-TYPE
     SYNTAX     Integer32 (1..65535)
     MAX-ACCESS read-only
     STATUS     current
     DESCRIPTION
         "This object identifies the top N report of which
         this entry is a part.  The set of hosts
         identified by a particular value of this
         object is part of the same report as identified
         by the same value of the hostTopNControlIndex object."
     ::= { hostTopNEntry 1 }

 hostTopNIndex OBJECT-TYPE
     SYNTAX     Integer32 (1..65535)
     MAX-ACCESS read-only
     STATUS     current
     DESCRIPTION
         "An index that uniquely identifies an entry in
         the hostTopN table among those in the same report.
         This index is between 1 and N, where N is the
         number of entries in this table.  Increasing values
         of hostTopNIndex shall be assigned to entries with
         decreasing values of hostTopNRate until index N
         is assigned to the entry with the lowest value of
         hostTopNRate or there are no more hostTopNEntries."
     ::= { hostTopNEntry 2 }

 hostTopNAddress OBJECT-TYPE
     SYNTAX     OCTET STRING
     MAX-ACCESS read-only


     STATUS     current
     DESCRIPTION
         "The physical address of this host."
     ::= { hostTopNEntry 3 }

 hostTopNRate OBJECT-TYPE
     SYNTAX     Integer32
     MAX-ACCESS read-only
     STATUS     current
     DESCRIPTION
         "The amount of change in the selected variable
         during this sampling interval.  The selected
         variable is this host's instance of the object
         selected by hostTopNRateBase."
     ::= { hostTopNEntry 4 }

 -- The Matrix Group

 -- Implementation of the Matrix group is optional.
 -- Consult the MODULE-COMPLIANCE macro for the authoritative
 -- conformance information for this MIB.
 --
 -- The Matrix group consists of the matrixControlTable, matrixSDTable
 -- and the matrixDSTable.  These tables store statistics for a
 -- particular conversation between two addresses.  As the device
 -- detects a new conversation, including those to a non-unicast
 -- address, it creates a new entry in both of the matrix tables.
 -- It must only create new entries based on information
 -- received in good packets.  If the monitoring device finds
 -- itself short of resources, it may delete entries as needed.
 -- It is suggested that the device delete the least recently used
 -- entries first.

 matrixControlTable OBJECT-TYPE
     SYNTAX     SEQUENCE OF MatrixControlEntry
     MAX-ACCESS not-accessible
     STATUS     current
     DESCRIPTION
         "A list of information entries for the
         traffic matrix on each interface."
     ::= { matrix 1 }

 matrixControlEntry OBJECT-TYPE
     SYNTAX     MatrixControlEntry
     MAX-ACCESS not-accessible
     STATUS     current
     DESCRIPTION
         "Information about a traffic matrix on a particular


         interface.  For example, an instance of the
         matrixControlLastDeleteTime object might be named
         matrixControlLastDeleteTime.1"
     INDEX { matrixControlIndex }
     ::= { matrixControlTable 1 }

 MatrixControlEntry ::= SEQUENCE {
     matrixControlIndex           Integer32,
     matrixControlDataSource      OBJECT IDENTIFIER,
     matrixControlTableSize       Integer32,
     matrixControlLastDeleteTime  TimeTicks,
     matrixControlOwner           OwnerString,
     matrixControlStatus          EntryStatus
 }

 matrixControlIndex OBJECT-TYPE
     SYNTAX     Integer32 (1..65535)
     MAX-ACCESS read-only
     STATUS     current
     DESCRIPTION
         "An index that uniquely identifies an entry in the
         matrixControl table.  Each such entry defines
         a function that discovers conversations on a particular
         interface and places statistics about them in the
         matrixSDTable and the matrixDSTable on behalf of this
         matrixControlEntry."
     ::= { matrixControlEntry 1 }

 matrixControlDataSource OBJECT-TYPE
     SYNTAX     OBJECT IDENTIFIER
     MAX-ACCESS read-create
     STATUS     current
     DESCRIPTION
         "This object identifies the source of
         the data from which this entry creates a traffic matrix.
         This source can be any interface on this device.  In
         order to identify a particular interface, this object
         shall identify the instance of the ifIndex object,
         defined in RFC 2233 [17], for the desired
         interface.  For example, if an entry were to receive data
         from interface #1, this object would be set to ifIndex.1.

         The statistics in this group reflect all packets
         on the local network segment attached to the identified
         interface.

         An agent may or may not be able to tell if fundamental
         changes to the media of the interface have occurred and


         necessitate an invalidation of this entry.  For example, a
         hot-pluggable ethernet card could be pulled out and replaced
         by a token-ring card.  In such a case, if the agent has such
         knowledge of the change, it is recommended that it
         invalidate this entry.

         This object may not be modified if the associated
         matrixControlStatus object is equal to valid(1)."
     ::= { matrixControlEntry 2 }

 matrixControlTableSize OBJECT-TYPE
     SYNTAX     Integer32
     MAX-ACCESS read-only
     STATUS     current
     DESCRIPTION
         "The number of matrixSDEntries in the matrixSDTable
         for this interface.  This must also be the value of
         the number of entries in the matrixDSTable for this
         interface."
     ::= { matrixControlEntry 3 }

 matrixControlLastDeleteTime OBJECT-TYPE
     SYNTAX     TimeTicks
     MAX-ACCESS read-only
     STATUS     current
     DESCRIPTION
         "The value of sysUpTime when the last entry
         was deleted from the portion of the matrixSDTable
         or matrixDSTable associated with this matrixControlEntry.
         If no deletions have occurred, this value shall be
         zero."
     ::= { matrixControlEntry 4 }

 matrixControlOwner OBJECT-TYPE
     SYNTAX     OwnerString
     MAX-ACCESS read-create
     STATUS     current
     DESCRIPTION
         "The entity that configured this entry and is therefore
         using the resources assigned to it."
     ::= { matrixControlEntry 5 }

 matrixControlStatus OBJECT-TYPE
     SYNTAX     EntryStatus
     MAX-ACCESS read-create
     STATUS     current
     DESCRIPTION
         "The status of this matrixControl entry.


         If this object is not equal to valid(1), all associated
         entries in the matrixSDTable and the matrixDSTable
         shall be deleted by the agent."
     ::= { matrixControlEntry 6 }

 matrixSDTable OBJECT-TYPE
     SYNTAX     SEQUENCE OF MatrixSDEntry
     MAX-ACCESS not-accessible
     STATUS     current
     DESCRIPTION
         "A list of traffic matrix entries indexed by
         source and destination MAC address."
     ::= { matrix 2 }

 matrixSDEntry OBJECT-TYPE
     SYNTAX     MatrixSDEntry
     MAX-ACCESS not-accessible
     STATUS     current
     DESCRIPTION
         "A collection of statistics for communications between
         two addresses on a particular interface.  For example,
         an instance of the matrixSDPkts object might be named
         matrixSDPkts.1.6.8.0.32.27.3.176.6.8.0.32.10.8.113"
     INDEX { matrixSDIndex,
             matrixSDSourceAddress, matrixSDDestAddress }
     ::= { matrixSDTable 1 }

 MatrixSDEntry ::= SEQUENCE {
     matrixSDSourceAddress       OCTET STRING,
     matrixSDDestAddress         OCTET STRING,
     matrixSDIndex               Integer32,
     matrixSDPkts                Counter32,
     matrixSDOctets              Counter32,
     matrixSDErrors              Counter32
 }

 matrixSDSourceAddress OBJECT-TYPE
     SYNTAX     OCTET STRING
     MAX-ACCESS read-only
     STATUS     current
     DESCRIPTION
         "The source physical address."
     ::= { matrixSDEntry 1 }

 matrixSDDestAddress OBJECT-TYPE
     SYNTAX     OCTET STRING
     MAX-ACCESS read-only
     STATUS     current


     DESCRIPTION
         "The destination physical address."
     ::= { matrixSDEntry 2 }

 matrixSDIndex OBJECT-TYPE
     SYNTAX     Integer32 (1..65535)
     MAX-ACCESS read-only
     STATUS     current
     DESCRIPTION
         "The set of collected matrix statistics of which
         this entry is a part.  The set of matrix statistics
         identified by a particular value of this index
         is associated with the same matrixControlEntry
         as identified by the same value of matrixControlIndex."
     ::= { matrixSDEntry 3 }

 matrixSDPkts OBJECT-TYPE
     SYNTAX     Counter32
     UNITS      "Packets"
     MAX-ACCESS read-only
     STATUS     current
     DESCRIPTION
         "The number of packets transmitted from the source
         address to the destination address (this number includes
         bad packets)."
     ::= { matrixSDEntry 4 }

 matrixSDOctets OBJECT-TYPE
     SYNTAX     Counter32
     UNITS      "Octets"
     MAX-ACCESS read-only
     STATUS     current
     DESCRIPTION
         "The number of octets (excluding framing bits but
         including FCS octets) contained in all packets
         transmitted from the source address to the
         destination address."
     ::= { matrixSDEntry 5 }

 matrixSDErrors OBJECT-TYPE
     SYNTAX     Counter32
     UNITS      "Packets"
     MAX-ACCESS read-only
     STATUS     current
     DESCRIPTION
         "The number of bad packets transmitted from
         the source address to the destination address."
     ::= { matrixSDEntry 6 }


 -- Traffic matrix tables from destination to source

 matrixDSTable OBJECT-TYPE
     SYNTAX     SEQUENCE OF MatrixDSEntry
     MAX-ACCESS not-accessible
     STATUS     current
     DESCRIPTION
         "A list of traffic matrix entries indexed by
         destination and source MAC address."
     ::= { matrix 3 }

 matrixDSEntry OBJECT-TYPE
     SYNTAX     MatrixDSEntry
     MAX-ACCESS not-accessible
     STATUS     current
     DESCRIPTION
         "A collection of statistics for communications between
         two addresses on a particular interface.  For example,
         an instance of the matrixSDPkts object might be named
         matrixSDPkts.1.6.8.0.32.10.8.113.6.8.0.32.27.3.176"
     INDEX { matrixDSIndex,
             matrixDSDestAddress, matrixDSSourceAddress }
     ::= { matrixDSTable 1 }

 MatrixDSEntry ::= SEQUENCE {
     matrixDSSourceAddress       OCTET STRING,
     matrixDSDestAddress         OCTET STRING,
     matrixDSIndex               Integer32,
     matrixDSPkts                Counter32,
     matrixDSOctets              Counter32,
     matrixDSErrors              Counter32
 }

 matrixDSSourceAddress OBJECT-TYPE
     SYNTAX     OCTET STRING
     MAX-ACCESS read-only
     STATUS     current
     DESCRIPTION
         "The source physical address."
     ::= { matrixDSEntry 1 }

 matrixDSDestAddress OBJECT-TYPE
     SYNTAX     OCTET STRING
     MAX-ACCESS read-only
     STATUS     current
     DESCRIPTION
         "The destination physical address."
     ::= { matrixDSEntry 2 }


 matrixDSIndex OBJECT-TYPE
     SYNTAX     Integer32 (1..65535)
     MAX-ACCESS read-only
     STATUS     current
     DESCRIPTION
         "The set of collected matrix statistics of which
         this entry is a part.  The set of matrix statistics
         identified by a particular value of this index
         is associated with the same matrixControlEntry
         as identified by the same value of matrixControlIndex."
     ::= { matrixDSEntry 3 }

 matrixDSPkts OBJECT-TYPE
     SYNTAX     Counter32
     UNITS      "Packets"
     MAX-ACCESS read-only
     STATUS     current
     DESCRIPTION
         "The number of packets transmitted from the source
         address to the destination address (this number includes
         bad packets)."
     ::= { matrixDSEntry 4 }

 matrixDSOctets OBJECT-TYPE
     SYNTAX     Counter32
     UNITS      "Octets"
     MAX-ACCESS read-only
     STATUS     current
     DESCRIPTION
         "The number of octets (excluding framing bits
         but including FCS octets) contained in all packets
         transmitted from the source address to the
         destination address."
     ::= { matrixDSEntry 5 }

 matrixDSErrors OBJECT-TYPE
     SYNTAX     Counter32
     UNITS      "Packets"
     MAX-ACCESS read-only
     STATUS     current
     DESCRIPTION
         "The number of bad packets transmitted from
         the source address to the destination address."
     ::= { matrixDSEntry 6 }

 -- The Filter Group

 -- Implementation of the Filter group is optional.


 -- Consult the MODULE-COMPLIANCE macro for the authoritative
 -- conformance information for this MIB.
 --
 -- The Filter group allows packets to be captured with an
 -- arbitrary filter expression.  A logical data and
 -- event stream or "channel" is formed by the packets
 -- that match the filter expression.
 --
 -- This filter mechanism allows the creation of an arbitrary
 -- logical expression with which to filter packets.  Each
 -- filter associated with a channel is OR'ed with the others.
 -- Within a filter, any bits checked in the data and status are
 -- AND'ed with respect to other bits in the same filter.  The
 -- NotMask also allows for checking for inequality.  Finally,
 -- the channelAcceptType object allows for inversion of the
 -- whole equation.
 --
 -- If a management station wishes to receive a trap to alert it
 -- that new packets have been captured and are available for
 -- download, it is recommended that it set up an alarm entry that
 -- monitors the value of the relevant channelMatches instance.
 --
 -- The channel can be turned on or off, and can also
 -- generate events when packets pass through it.

 filterTable OBJECT-TYPE
     SYNTAX     SEQUENCE OF FilterEntry
     MAX-ACCESS not-accessible
     STATUS     current
     DESCRIPTION
         "A list of packet filter entries."
     ::= { filter 1 }

 filterEntry OBJECT-TYPE
     SYNTAX     FilterEntry
     MAX-ACCESS not-accessible
     STATUS     current
     DESCRIPTION
         "A set of parameters for a packet filter applied on a
         particular interface.  As an example, an instance of the
         filterPktData object might be named filterPktData.12"
     INDEX { filterIndex }
     ::= { filterTable 1 }

 FilterEntry ::= SEQUENCE {
     filterIndex                 Integer32,
     filterChannelIndex          Integer32,
     filterPktDataOffset         Integer32,


     filterPktData               OCTET STRING,
     filterPktDataMask           OCTET STRING,
     filterPktDataNotMask        OCTET STRING,
     filterPktStatus             Integer32,
     filterPktStatusMask         Integer32,
     filterPktStatusNotMask      Integer32,
     filterOwner                 OwnerString,
     filterStatus                EntryStatus
 }

 filterIndex OBJECT-TYPE
     SYNTAX     Integer32 (1..65535)
     MAX-ACCESS read-only
     STATUS     current
     DESCRIPTION
         "An index that uniquely identifies an entry
         in the filter table.  Each such entry defines
         one filter that is to be applied to every packet
         received on an interface."
     ::= { filterEntry 1 }

 filterChannelIndex OBJECT-TYPE
     SYNTAX     Integer32 (1..65535)
     MAX-ACCESS read-create
     STATUS     current
     DESCRIPTION
         "This object identifies the channel of which this filter
         is a part.  The filters identified by a particular value
         of this object are associated with the same channel as
         identified by the same value of the channelIndex object."
     ::= { filterEntry 2 }

 filterPktDataOffset OBJECT-TYPE
     SYNTAX     Integer32
     UNITS      "Octets"
     MAX-ACCESS read-create
     STATUS     current
     DESCRIPTION
         "The offset from the beginning of each packet where
         a match of packet data will be attempted.  This offset
         is measured from the point in the physical layer
         packet after the framing bits, if any.  For example,
         in an Ethernet frame, this point is at the beginning of
         the destination MAC address.

         This object may not be modified if the associated
         filterStatus object is equal to valid(1)."
     DEFVAL { 0 }


     ::= { filterEntry 3 }

 filterPktData OBJECT-TYPE
     SYNTAX     OCTET STRING
     MAX-ACCESS read-create
     STATUS     current
     DESCRIPTION
         "The data that is to be matched with the input packet.
         For each packet received, this filter and the accompanying
         filterPktDataMask and filterPktDataNotMask will be
         adjusted for the offset.  The only bits relevant to this
         match algorithm are those that have the corresponding
         filterPktDataMask bit equal to one.  The following three
         rules are then applied to every packet:

         (1) If the packet is too short and does not have data
             corresponding to part of the filterPktData, the packet
             will fail this data match.

         (2) For each relevant bit from the packet with the
             corresponding filterPktDataNotMask bit set to zero, if
             the bit from the packet is not equal to the corresponding
             bit from the filterPktData, then the packet will fail
             this data match.

         (3) If for every relevant bit from the packet with the
             corresponding filterPktDataNotMask bit set to one, the
             bit from the packet is equal to the corresponding bit
             from the filterPktData, then the packet will fail this
             data match.

         Any packets that have not failed any of the three matches
         above have passed this data match.  In particular, a zero
         length filter will match any packet.

         This object may not be modified if the associated
         filterStatus object is equal to valid(1)."
     ::= { filterEntry 4 }

 filterPktDataMask OBJECT-TYPE
     SYNTAX     OCTET STRING
     MAX-ACCESS read-create
     STATUS     current
     DESCRIPTION
         "The mask that is applied to the match process.
         After adjusting this mask for the offset, only those
         bits in the received packet that correspond to bits set
         in this mask are relevant for further processing by the


         match algorithm.  The offset is applied to filterPktDataMask
         in the same way it is applied to the filter.  For the
         purposes of the matching algorithm, if the associated
         filterPktData object is longer than this mask, this mask is
         conceptually extended with '1' bits until it reaches the
         length of the filterPktData object.

         This object may not be modified if the associated
         filterStatus object is equal to valid(1)."
     ::= { filterEntry 5 }

 filterPktDataNotMask OBJECT-TYPE
     SYNTAX     OCTET STRING
     MAX-ACCESS read-create
     STATUS     current
     DESCRIPTION
         "The inversion mask that is applied to the match
         process.  After adjusting this mask for the offset,
         those relevant bits in the received packet that correspond
         to bits cleared in this mask must all be equal to their
         corresponding bits in the filterPktData object for the packet
         to be accepted.  In addition, at least one of those relevant
         bits in the received packet that correspond to bits set in
         this mask must be different to its corresponding bit in the
         filterPktData object.

         For the purposes of the matching algorithm, if the associated
         filterPktData object is longer than this mask, this mask is
         conceptually extended with '0' bits until it reaches the
         length of the filterPktData object.

         This object may not be modified if the associated
         filterStatus object is equal to valid(1)."
     ::= { filterEntry 6 }

 filterPktStatus OBJECT-TYPE
     SYNTAX     Integer32
     MAX-ACCESS read-create
     STATUS     current
     DESCRIPTION
         "The status that is to be matched with the input packet.
         The only bits relevant to this match algorithm are those that
         have the corresponding filterPktStatusMask bit equal to one.
         The following two rules are then applied to every packet:

         (1) For each relevant bit from the packet status with the
             corresponding filterPktStatusNotMask bit set to zero, if
             the bit from the packet status is not equal to the


             corresponding bit from the filterPktStatus, then the
             packet will fail this status match.

         (2) If for every relevant bit from the packet status with the
             corresponding filterPktStatusNotMask bit set to one, the
             bit from the packet status is equal to the corresponding
             bit from the filterPktStatus, then the packet will fail
             this status match.

         Any packets that have not failed either of the two matches
         above have passed this status match.  In particular, a zero
         length status filter will match any packet's status.

         The value of the packet status is a sum.  This sum
         initially takes the value zero.  Then, for each
         error, E, that has been discovered in this packet,
         2 raised to a value representing E is added to the sum.
         The errors and the bits that represent them are dependent
         on the media type of the interface that this channel
         is receiving packets from.

         The errors defined for a packet captured off of an
         Ethernet interface are as follows:

             bit #    Error
                 0    Packet is longer than 1518 octets
                 1    Packet is shorter than 64 octets
                 2    Packet experienced a CRC or Alignment error

         For example, an Ethernet fragment would have a
         value of 6 (2^1 + 2^2).

         As this MIB is expanded to new media types, this object
         will have other media-specific errors defined.

         For the purposes of this status matching algorithm, if the
         packet status is longer than this filterPktStatus object,
         this object is conceptually extended with '0' bits until it
         reaches the size of the packet status.

         This object may not be modified if the associated
         filterStatus object is equal to valid(1)."
     ::= { filterEntry 7 }

 filterPktStatusMask OBJECT-TYPE
     SYNTAX     Integer32
     MAX-ACCESS read-create
     STATUS     current


     DESCRIPTION
         "The mask that is applied to the status match process.
         Only those bits in the received packet that correspond to
         bits set in this mask are relevant for further processing
         by the status match algorithm.  For the purposes
         of the matching algorithm, if the associated filterPktStatus
         object is longer than this mask, this mask is conceptually
         extended with '1' bits until it reaches the size of the
         filterPktStatus.  In addition, if a packet status is longer
         than this mask, this mask is conceptually extended with '0'
         bits until it reaches the size of the packet status.

         This object may not be modified if the associated
         filterStatus object is equal to valid(1)."
     ::= { filterEntry 8 }

 filterPktStatusNotMask OBJECT-TYPE
     SYNTAX     Integer32
     MAX-ACCESS read-create
     STATUS     current
     DESCRIPTION
         "The inversion mask that is applied to the status match
         process.  Those relevant bits in the received packet status
         that correspond to bits cleared in this mask must all be
         equal to their corresponding bits in the filterPktStatus
         object for the packet to be accepted.  In addition, at least
         one of those relevant bits in the received packet status
         that correspond to bits set in this mask must be different
         to its corresponding bit in the filterPktStatus object for
         the packet to be accepted.

         For the purposes of the matching algorithm, if the associated
         filterPktStatus object or a packet status is longer than this
         mask, this mask is conceptually extended with '0' bits until
         it reaches the longer of the lengths of the filterPktStatus
         object and the packet status.

         This object may not be modified if the associated
         filterStatus object is equal to valid(1)."
     ::= { filterEntry 9 }

 filterOwner OBJECT-TYPE
     SYNTAX     OwnerString
     MAX-ACCESS read-create
     STATUS     current
     DESCRIPTION
         "The entity that configured this entry and is therefore
         using the resources assigned to it."


     ::= { filterEntry 10 }

 filterStatus OBJECT-TYPE
     SYNTAX     EntryStatus
     MAX-ACCESS read-create
     STATUS     current
     DESCRIPTION
         "The status of this filter entry."
     ::= { filterEntry 11 }

 channelTable OBJECT-TYPE
     SYNTAX     SEQUENCE OF ChannelEntry
     MAX-ACCESS not-accessible
     STATUS     current
     DESCRIPTION
         "A list of packet channel entries."
     ::= { filter 2 }

 channelEntry OBJECT-TYPE
     SYNTAX     ChannelEntry
     MAX-ACCESS not-accessible
     STATUS     current
     DESCRIPTION
         "A set of parameters for a packet channel applied on a
         particular interface.  As an example, an instance of the
         channelMatches object might be named channelMatches.3"
     INDEX { channelIndex }
     ::= { channelTable 1 }

 ChannelEntry ::= SEQUENCE {
     channelIndex                 Integer32,
     channelIfIndex               Integer32,
     channelAcceptType            INTEGER,
     channelDataControl           INTEGER,
     channelTurnOnEventIndex      Integer32,
     channelTurnOffEventIndex     Integer32,
     channelEventIndex            Integer32,
     channelEventStatus           INTEGER,
     channelMatches               Counter32,
     channelDescription           DisplayString,
     channelOwner                 OwnerString,
     channelStatus                EntryStatus
 }

 channelIndex OBJECT-TYPE
     SYNTAX     Integer32 (1..65535)
     MAX-ACCESS read-only
     STATUS     current


     DESCRIPTION
         "An index that uniquely identifies an entry in the channel
         table.  Each such entry defines one channel, a logical
         data and event stream.

         It is suggested that before creating a channel, an
         application should scan all instances of the
         filterChannelIndex object to make sure that there are no
         pre-existing filters that would be inadvertently be linked
         to the channel."
     ::= { channelEntry 1 }

 channelIfIndex OBJECT-TYPE
     SYNTAX     Integer32 (1..65535)
     MAX-ACCESS read-create
     STATUS     current
     DESCRIPTION
         "The value of this object uniquely identifies the
         interface on this remote network monitoring device to which
         the associated filters are applied to allow data into this
         channel.  The interface identified by a particular value
         of this object is the same interface as identified by the
         same value of the ifIndex object, defined in RFC 2233 [17].

         The filters in this group are applied to all packets on
         the local network segment attached to the identified
         interface.

         An agent may or may not be able to tell if fundamental
         changes to the media of the interface have occurred and
         necessitate an invalidation of this entry.  For example, a
         hot-pluggable ethernet card could be pulled out and replaced
         by a token-ring card.  In such a case, if the agent has such
         knowledge of the change, it is recommended that it
         invalidate this entry.

         This object may not be modified if the associated
         channelStatus object is equal to valid(1)."
     ::= { channelEntry 2 }

 channelAcceptType OBJECT-TYPE
     SYNTAX     INTEGER {
                  acceptMatched(1),
                  acceptFailed(2)
                }
     MAX-ACCESS read-create
     STATUS     current
     DESCRIPTION


         "This object controls the action of the filters
         associated with this channel.  If this object is equal
         to acceptMatched(1), packets will be accepted to this
         channel if they are accepted by both the packet data and
         packet status matches of an associated filter.  If
         this object is equal to acceptFailed(2), packets will
         be accepted to this channel only if they fail either
         the packet data match or the packet status match of
         each of the associated filters.

         In particular, a channel with no associated filters will
         match no packets if set to acceptMatched(1) case and will
         match all packets in the acceptFailed(2) case.

         This object may not be modified if the associated
         channelStatus object is equal to valid(1)."
     ::= { channelEntry 3 }

 channelDataControl OBJECT-TYPE
     SYNTAX     INTEGER {
                  on(1),
                  off(2)
                }
     MAX-ACCESS read-create
     STATUS     current
     DESCRIPTION
         "This object controls the flow of data through this channel.
         If this object is on(1), data, status and events flow
         through this channel.  If this object is off(2), data,
         status and events will not flow through this channel."
     DEFVAL { off }
     ::= { channelEntry 4 }

 channelTurnOnEventIndex OBJECT-TYPE
     SYNTAX     Integer32 (0..65535)
     MAX-ACCESS read-create
     STATUS     current
     DESCRIPTION
         "The value of this object identifies the event
         that is configured to turn the associated
         channelDataControl from off to on when the event is
         generated.  The event identified by a particular value
         of this object is the same event as identified by the
         same value of the eventIndex object.  If there is no
         corresponding entry in the eventTable, then no
         association exists.  In fact, if no event is intended
         for this channel, channelTurnOnEventIndex must be
         set to zero, a non-existent event index.


         This object may not be modified if the associated
         channelStatus object is equal to valid(1)."
     ::= { channelEntry 5 }

 channelTurnOffEventIndex OBJECT-TYPE
     SYNTAX     Integer32 (0..65535)
     MAX-ACCESS read-create
     STATUS     current
     DESCRIPTION
         "The value of this object identifies the event
         that is configured to turn the associated
         channelDataControl from on to off when the event is
         generated.  The event identified by a particular value
         of this object is the same event as identified by the
         same value of the eventIndex object.  If there is no
         corresponding entry in the eventTable, then no
         association exists.  In fact, if no event is intended
         for this channel, channelTurnOffEventIndex must be
         set to zero, a non-existent event index.

         This object may not be modified if the associated
         channelStatus object is equal to valid(1)."
     ::= { channelEntry 6 }

 channelEventIndex OBJECT-TYPE
     SYNTAX     Integer32 (0..65535)
     MAX-ACCESS read-create
     STATUS     current
     DESCRIPTION
         "The value of this object identifies the event
         that is configured to be generated when the
         associated channelDataControl is on and a packet
         is matched.  The event identified by a particular value
         of this object is the same event as identified by the
         same value of the eventIndex object.  If there is no
         corresponding entry in the eventTable, then no
         association exists.  In fact, if no event is intended
         for this channel, channelEventIndex must be
         set to zero, a non-existent event index.

         This object may not be modified if the associated
         channelStatus object is equal to valid(1)."
     ::= { channelEntry 7 }

 channelEventStatus OBJECT-TYPE
     SYNTAX     INTEGER {
                  eventReady(1),
                  eventFired(2),


                  eventAlwaysReady(3)
                }
     MAX-ACCESS read-create
     STATUS     current
     DESCRIPTION
         "The event status of this channel.

         If this channel is configured to generate events
         when packets are matched, a means of controlling
         the flow of those events is often needed.  When
         this object is equal to eventReady(1), a single
         event may be generated, after which this object
         will be set by the probe to eventFired(2).  While
         in the eventFired(2) state, no events will be
         generated until the object is modified to
         eventReady(1) (or eventAlwaysReady(3)).  The
         management station can thus easily respond to a
         notification of an event by re-enabling this object.

         If the management station wishes to disable this
         flow control and allow events to be generated
         at will, this object may be set to
         eventAlwaysReady(3).  Disabling the flow control
         is discouraged as it can result in high network
         traffic or other performance problems."
     DEFVAL { eventReady }
     ::= { channelEntry 8 }

 channelMatches OBJECT-TYPE
     SYNTAX     Counter32
     UNITS      "Packets"
     MAX-ACCESS read-only
     STATUS     current
     DESCRIPTION
         "The number of times this channel has matched a packet.
         Note that this object is updated even when
         channelDataControl is set to off."
     ::= { channelEntry 9 }

 channelDescription OBJECT-TYPE
     SYNTAX     DisplayString (SIZE (0..127))
     MAX-ACCESS read-create
     STATUS     current
     DESCRIPTION
         "A comment describing this channel."
     ::= { channelEntry 10 }

 channelOwner OBJECT-TYPE


     SYNTAX     OwnerString
     MAX-ACCESS read-create
     STATUS     current
     DESCRIPTION
         "The entity that configured this entry and is therefore
         using the resources assigned to it."
     ::= { channelEntry 11 }

 channelStatus OBJECT-TYPE
     SYNTAX     EntryStatus
     MAX-ACCESS read-create
     STATUS     current
     DESCRIPTION
         "The status of this channel entry."
     ::= { channelEntry 12 }

 -- The Packet Capture Group

 -- Implementation of the Packet Capture group is optional. The Packet
 -- Capture Group requires implementation of the Filter Group.
 -- Consult the MODULE-COMPLIANCE macro for the authoritative
 -- conformance information for this MIB.
 --
 -- The Packet Capture group allows packets to be captured
 -- upon a filter match.  The bufferControlTable controls
 -- the captured packets output from a channel that is
 -- associated with it.  The captured packets are placed
 -- in entries in the captureBufferTable.  These entries are
 -- associated with the bufferControlEntry on whose behalf they
 -- were stored.

 bufferControlTable OBJECT-TYPE
     SYNTAX     SEQUENCE OF BufferControlEntry
     MAX-ACCESS not-accessible
     STATUS     current
     DESCRIPTION
         "A list of buffers control entries."
     ::= { capture 1 }

 bufferControlEntry OBJECT-TYPE
     SYNTAX     BufferControlEntry
     MAX-ACCESS not-accessible
     STATUS     current
     DESCRIPTION
         "A set of parameters that control the collection of a stream
         of packets that have matched filters.  As an example, an
         instance of the bufferControlCaptureSliceSize object might
         be named bufferControlCaptureSliceSize.3"


     INDEX { bufferControlIndex }
     ::= { bufferControlTable 1 }

 BufferControlEntry ::= SEQUENCE {
     bufferControlIndex                Integer32,
     bufferControlChannelIndex         Integer32,
     bufferControlFullStatus           INTEGER,
     bufferControlFullAction           INTEGER,
     bufferControlCaptureSliceSize     Integer32,
     bufferControlDownloadSliceSize    Integer32,
     bufferControlDownloadOffset       Integer32,
     bufferControlMaxOctetsRequested   Integer32,
     bufferControlMaxOctetsGranted     Integer32,
     bufferControlCapturedPackets      Integer32,
     bufferControlTurnOnTime           TimeTicks,
     bufferControlOwner                OwnerString,
     bufferControlStatus               EntryStatus
 }

 bufferControlIndex OBJECT-TYPE
     SYNTAX     Integer32 (1..65535)
     MAX-ACCESS read-only
     STATUS     current
     DESCRIPTION
         "An index that uniquely identifies an entry
         in the bufferControl table.  The value of this
         index shall never be zero.  Each such
         entry defines one set of packets that is
         captured and controlled by one or more filters."
     ::= { bufferControlEntry 1 }

 bufferControlChannelIndex OBJECT-TYPE
     SYNTAX     Integer32 (1..65535)
     MAX-ACCESS read-create
     STATUS     current
     DESCRIPTION
         "An index that identifies the channel that is the
         source of packets for this bufferControl table.
         The channel identified by a particular value of this
         index is the same as identified by the same value of
         the channelIndex object.

         This object may not be modified if the associated
         bufferControlStatus object is equal to valid(1)."
     ::= { bufferControlEntry 2 }

 bufferControlFullStatus OBJECT-TYPE
     SYNTAX     INTEGER {


                  spaceAvailable(1),
                  full(2)
                }
     MAX-ACCESS read-only
     STATUS     current
     DESCRIPTION
         "This object shows whether the buffer has room to
         accept new packets or if it is full.

         If the status is spaceAvailable(1), the buffer is
         accepting new packets normally.  If the status is
         full(2) and the associated bufferControlFullAction
         object is wrapWhenFull, the buffer is accepting new
         packets by deleting enough of the oldest packets
         to make room for new ones as they arrive.  Otherwise,
         if the status is full(2) and the
         bufferControlFullAction object is lockWhenFull,
         then the buffer has stopped collecting packets.

         When this object is set to full(2) the probe must
         not later set it to spaceAvailable(1) except in the
         case of a significant gain in resources such as
         an increase of bufferControlOctetsGranted.  In
         particular, the wrap-mode action of deleting old
         packets to make room for newly arrived packets
         must not affect the value of this object."
     ::= { bufferControlEntry 3 }

 bufferControlFullAction OBJECT-TYPE
     SYNTAX     INTEGER {
                  lockWhenFull(1),
                  wrapWhenFull(2)    -- FIFO
                }
     MAX-ACCESS read-create
     STATUS     current
     DESCRIPTION
         "Controls the action of the buffer when it
         reaches the full status.  When in the lockWhenFull(1)
         state and a packet is added to the buffer that
         fills the buffer, the bufferControlFullStatus will
         be set to full(2) and this buffer will stop capturing
         packets."
     ::= { bufferControlEntry 4 }

 bufferControlCaptureSliceSize OBJECT-TYPE
     SYNTAX     Integer32
     UNITS      "Octets"
     MAX-ACCESS read-create


     STATUS     current
     DESCRIPTION
         "The maximum number of octets of each packet
         that will be saved in this capture buffer.
         For example, if a 1500 octet packet is received by
         the probe and this object is set to 500, then only
         500 octets of the packet will be stored in the
         associated capture buffer.  If this variable is set
         to 0, the capture buffer will save as many octets
         as is possible.

         This object may not be modified if the associated
         bufferControlStatus object is equal to valid(1)."
     DEFVAL { 100 }
     ::= { bufferControlEntry 5 }

 bufferControlDownloadSliceSize OBJECT-TYPE
     SYNTAX     Integer32
     UNITS      "Octets"
     MAX-ACCESS read-create
     STATUS     current
     DESCRIPTION
         "The maximum number of octets of each packet
         in this capture buffer that will be returned in
         an SNMP retrieval of that packet.  For example,
         if 500 octets of a packet have been stored in the
         associated capture buffer, the associated
         bufferControlDownloadOffset is 0, and this
         object is set to 100, then the captureBufferPacket
         object that contains the packet will contain only
         the first 100 octets of the packet.

         A prudent manager will take into account possible
         interoperability or fragmentation problems that may
         occur if the download slice size is set too large.
         In particular, conformant SNMP implementations are not
         required to accept messages whose length exceeds 484
         octets, although they are encouraged to support larger
         datagrams whenever feasible."
     DEFVAL { 100 }
     ::= { bufferControlEntry 6 }

 bufferControlDownloadOffset OBJECT-TYPE
     SYNTAX     Integer32
     UNITS      "Octets"
     MAX-ACCESS read-create
     STATUS     current
     DESCRIPTION


         "The offset of the first octet of each packet
         in this capture buffer that will be returned in
         an SNMP retrieval of that packet.  For example,
         if 500 octets of a packet have been stored in the
         associated capture buffer and this object is set to
         100, then the captureBufferPacket object that
         contains the packet will contain bytes starting
         100 octets into the packet."
     DEFVAL { 0 }
     ::= { bufferControlEntry 7 }

 bufferControlMaxOctetsRequested OBJECT-TYPE
     SYNTAX     Integer32
     UNITS      "Octets"
     MAX-ACCESS read-create
     STATUS     current
     DESCRIPTION
         "The requested maximum number of octets to be
         saved in this captureBuffer, including any
         implementation-specific overhead. If this variable
         is set to -1, the capture buffer will save as many
         octets as is possible.

         When this object is created or modified, the probe
         should set bufferControlMaxOctetsGranted as closely
         to this object as is possible for the particular probe
         implementation and available resources.  However, if
         the object has the special value of -1, the probe
         must set bufferControlMaxOctetsGranted to -1."
     DEFVAL { -1 }
     ::= { bufferControlEntry 8 }

 bufferControlMaxOctetsGranted OBJECT-TYPE
     SYNTAX     Integer32
     UNITS      "Octets"
     MAX-ACCESS read-only
     STATUS     current
     DESCRIPTION
         "The maximum number of octets that can be
         saved in this captureBuffer, including overhead.
         If this variable is -1, the capture buffer will save
         as many octets as possible.

         When the bufferControlMaxOctetsRequested object is
         created or modified, the probe should set this object
         as closely to the requested value as is possible for the
         particular probe implementation and available resources.
         However, if the request object has the special value


         of -1, the probe must set this object to -1.

         The probe must not lower this value except as a result of
         a modification to the associated
         bufferControlMaxOctetsRequested object.

         When this maximum number of octets is reached
         and a new packet is to be added to this
         capture buffer and the corresponding
         bufferControlFullAction is set to wrapWhenFull(2),
         enough of the oldest packets associated with this
         capture buffer shall be deleted by the agent so
         that the new packet can be added.  If the corresponding
         bufferControlFullAction is set to lockWhenFull(1),
         the new packet shall be discarded.  In either case,
         the probe must set bufferControlFullStatus to
         full(2).

         When the value of this object changes to a value less
         than the current value, entries are deleted from
         the captureBufferTable associated with this
         bufferControlEntry.  Enough of the
         oldest of these captureBufferEntries shall be
         deleted by the agent so that the number of octets
         used remains less than or equal to the new value of
         this object.

         When the value of this object changes to a value greater
         than the current value, the number of associated
         captureBufferEntries may be allowed to grow."
     ::= { bufferControlEntry 9 }

 bufferControlCapturedPackets OBJECT-TYPE
     SYNTAX     Integer32
     UNITS      "Packets"
     MAX-ACCESS read-only
     STATUS     current
     DESCRIPTION
         "The number of packets currently in this captureBuffer."
     ::= { bufferControlEntry 10 }

 bufferControlTurnOnTime OBJECT-TYPE
     SYNTAX     TimeTicks
     MAX-ACCESS read-only
     STATUS     current
     DESCRIPTION
         "The value of sysUpTime when this capture buffer was
         first turned on."


     ::= { bufferControlEntry 11 }

 bufferControlOwner OBJECT-TYPE
     SYNTAX     OwnerString
     MAX-ACCESS read-create
     STATUS     current
     DESCRIPTION
         "The entity that configured this entry and is therefore
         using the resources assigned to it."
     ::= { bufferControlEntry 12 }

 bufferControlStatus OBJECT-TYPE
     SYNTAX     EntryStatus
     MAX-ACCESS read-create
     STATUS     current
     DESCRIPTION
         "The status of this buffer Control Entry."
     ::= { bufferControlEntry 13 }

 captureBufferTable OBJECT-TYPE
     SYNTAX     SEQUENCE OF CaptureBufferEntry
     MAX-ACCESS not-accessible
     STATUS     current
     DESCRIPTION
         "A list of packets captured off of a channel."
     ::= { capture 2 }

 captureBufferEntry OBJECT-TYPE
     SYNTAX     CaptureBufferEntry
     MAX-ACCESS not-accessible
     STATUS     current
     DESCRIPTION
         "A packet captured off of an attached network.  As an
         example, an instance of the captureBufferPacketData
         object might be named captureBufferPacketData.3.1783"
     INDEX { captureBufferControlIndex, captureBufferIndex }
     ::= { captureBufferTable 1 }

 CaptureBufferEntry ::= SEQUENCE {
     captureBufferControlIndex   Integer32,
     captureBufferIndex          Integer32,
     captureBufferPacketID       Integer32,
     captureBufferPacketData     OCTET STRING,
     captureBufferPacketLength   Integer32,
     captureBufferPacketTime     Integer32,
     captureBufferPacketStatus   Integer32
 }


 captureBufferControlIndex OBJECT-TYPE
     SYNTAX     Integer32 (1..65535)
     MAX-ACCESS read-only
     STATUS     current
     DESCRIPTION
         "The index of the bufferControlEntry with which
         this packet is associated."
     ::= { captureBufferEntry 1 }

 captureBufferIndex OBJECT-TYPE
     SYNTAX     Integer32 (1..2147483647)
     MAX-ACCESS read-only
     STATUS     current
     DESCRIPTION
         "An index that uniquely identifies an entry
         in the captureBuffer table associated with a
         particular bufferControlEntry.  This index will
         start at 1 and increase by one for each new packet
         added with the same captureBufferControlIndex.

         Should this value reach 2147483647, the next packet
         added with the same captureBufferControlIndex shall
         cause this value to wrap around to 1."
     ::= { captureBufferEntry 2 }

 captureBufferPacketID OBJECT-TYPE
     SYNTAX     Integer32
     MAX-ACCESS read-only
     STATUS     current
     DESCRIPTION
         "An index that describes the order of packets
         that are received on a particular interface.
         The packetID of a packet captured on an
         interface is defined to be greater than the
         packetID's of all packets captured previously on
         the same interface.  As the captureBufferPacketID
         object has a maximum positive value of 2^31 - 1,
         any captureBufferPacketID object shall have the
         value of the associated packet's packetID mod 2^31."
     ::= { captureBufferEntry 3 }

 captureBufferPacketData OBJECT-TYPE
     SYNTAX     OCTET STRING
     MAX-ACCESS read-only
     STATUS     current
     DESCRIPTION
         "The data inside the packet, starting at the beginning
         of the packet plus any offset specified in the


         associated bufferControlDownloadOffset, including any
         link level headers.  The length of the data in this object
         is the minimum of the length of the captured packet minus
         the offset, the length of the associated
         bufferControlCaptureSliceSize minus the offset, and the
         associated bufferControlDownloadSliceSize.  If this minimum
         is less than zero, this object shall have a length of zero."
     ::= { captureBufferEntry 4 }

 captureBufferPacketLength OBJECT-TYPE
     SYNTAX     Integer32
     UNITS      "Octets"
     MAX-ACCESS read-only
     STATUS     current
     DESCRIPTION
         "The actual length (off the wire) of the packet stored
         in this entry, including FCS octets."
     ::= { captureBufferEntry 5 }

 captureBufferPacketTime OBJECT-TYPE
     SYNTAX     Integer32
     UNITS      "Milliseconds"
     MAX-ACCESS read-only
     STATUS     current
     DESCRIPTION
         "The number of milliseconds that had passed since
         this capture buffer was first turned on when this
         packet was captured."
     ::= { captureBufferEntry 6 }

 captureBufferPacketStatus OBJECT-TYPE
     SYNTAX     Integer32
     MAX-ACCESS read-only
     STATUS     current
     DESCRIPTION
         "A value which indicates the error status of this packet.

         The value of this object is defined in the same way as
         filterPktStatus.  The value is a sum.  This sum
         initially takes the value zero.  Then, for each
         error, E, that has been discovered in this packet,
         2 raised to a value representing E is added to the sum.

         The errors defined for a packet captured off of an
         Ethernet interface are as follows:

             bit #    Error
                 0    Packet is longer than 1518 octets


                 1    Packet is shorter than 64 octets
                 2    Packet experienced a CRC or Alignment error
                 3    First packet in this capture buffer after
                      it was detected that some packets were
                      not processed correctly.
                 4    Packet's order in buffer is only approximate
                      (May only be set for packets sent from
                      the probe)

         For example, an Ethernet fragment would have a
         value of 6 (2^1 + 2^2).

         As this MIB is expanded to new media types, this object
         will have other media-specific errors defined."
     ::= { captureBufferEntry 7 }

 -- The Event Group

 -- Implementation of the Event group is optional.
 -- Consult the MODULE-COMPLIANCE macro for the authoritative
 -- conformance information for this MIB.
 --
 -- The Event group controls the generation and notification
 -- of events from this device.  Each entry in the eventTable
 -- describes the parameters of the event that can be triggered.
 -- Each event entry is fired by an associated condition located
 -- elsewhere in the MIB.  An event entry may also be associated
 -- with a function elsewhere in the MIB that will be executed
 -- when the event is generated.  For example, a channel may
 -- be turned on or off by the firing of an event.
 --
 -- Each eventEntry may optionally specify that a log entry
 -- be created on its behalf whenever the event occurs.
 -- Each entry may also specify that notification should
 -- occur by way of SNMP trap messages.  In this case, the
 -- community for the trap message is given in the associated
 -- eventCommunity object.  The enterprise and specific trap
 -- fields of the trap are determined by the condition that
 -- triggered the event.  Two traps are defined: risingAlarm and
 -- fallingAlarm.  If the eventTable is triggered by a condition
 -- specified elsewhere, the enterprise and specific trap fields
 -- must be specified for traps generated for that condition.

 eventTable OBJECT-TYPE
     SYNTAX     SEQUENCE OF EventEntry
     MAX-ACCESS not-accessible
     STATUS     current
     DESCRIPTION


         "A list of events to be generated."
     ::= { event 1 }

 eventEntry OBJECT-TYPE
     SYNTAX     EventEntry
     MAX-ACCESS not-accessible
     STATUS     current
     DESCRIPTION
         "A set of parameters that describe an event to be generated
         when certain conditions are met.  As an example, an instance
         of the eventLastTimeSent object might be named
         eventLastTimeSent.6"
     INDEX { eventIndex }
     ::= { eventTable 1 }

 EventEntry ::= SEQUENCE {
     eventIndex          Integer32,
     eventDescription    DisplayString,
     eventType           INTEGER,
     eventCommunity      OCTET STRING,
     eventLastTimeSent   TimeTicks,
     eventOwner          OwnerString,
     eventStatus         EntryStatus
 }

 eventIndex OBJECT-TYPE
     SYNTAX     Integer32 (1..65535)
     MAX-ACCESS read-only
     STATUS     current
     DESCRIPTION
         "An index that uniquely identifies an entry in the
         event table.  Each such entry defines one event that
         is to be generated when the appropriate conditions
         occur."
     ::= { eventEntry 1 }

 eventDescription OBJECT-TYPE
     SYNTAX     DisplayString (SIZE (0..127))
     MAX-ACCESS read-create
     STATUS     current
     DESCRIPTION
         "A comment describing this event entry."
     ::= { eventEntry 2 }

 eventType OBJECT-TYPE
     SYNTAX     INTEGER {
                  none(1),
                  log(2),


                  snmptrap(3),    -- send an SNMP trap
                  logandtrap(4)
                }
     MAX-ACCESS read-create
     STATUS     current
     DESCRIPTION
         "The type of notification that the probe will make
         about this event.  In the case of log, an entry is
         made in the log table for each event.  In the case of
         snmp-trap, an SNMP trap is sent to one or more
         management stations."
     ::= { eventEntry 3 }

 eventCommunity OBJECT-TYPE
     SYNTAX     OCTET STRING (SIZE (0..127))
     MAX-ACCESS read-create
     STATUS     current
     DESCRIPTION
         "If an SNMP trap is to be sent, it will be sent to
         the SNMP community specified by this octet string."
     ::= { eventEntry 4 }

 eventLastTimeSent OBJECT-TYPE
     SYNTAX     TimeTicks
     MAX-ACCESS read-only
     STATUS     current
     DESCRIPTION
         "The value of sysUpTime at the time this event
         entry last generated an event.  If this entry has
         not generated any events, this value will be
         zero."
     ::= { eventEntry 5 }

 eventOwner OBJECT-TYPE
     SYNTAX     OwnerString
     MAX-ACCESS read-create
     STATUS     current
     DESCRIPTION
         "The entity that configured this entry and is therefore
         using the resources assigned to it.

         If this object contains a string starting with 'monitor'
         and has associated entries in the log table, all connected
         management stations should retrieve those log entries,
         as they may have significance to all management stations
         connected to this device"
     ::= { eventEntry 6 }


 eventStatus OBJECT-TYPE
     SYNTAX     EntryStatus
     MAX-ACCESS read-create
     STATUS     current
     DESCRIPTION
         "The status of this event entry.

         If this object is not equal to valid(1), all associated
         log entries shall be deleted by the agent."
     ::= { eventEntry 7 }

 --
 logTable OBJECT-TYPE
     SYNTAX     SEQUENCE OF LogEntry
     MAX-ACCESS not-accessible
     STATUS     current
     DESCRIPTION
         "A list of events that have been logged."
     ::= { event 2 }

 logEntry OBJECT-TYPE
     SYNTAX     LogEntry
     MAX-ACCESS not-accessible
     STATUS     current
     DESCRIPTION
         "A set of data describing an event that has been
         logged.  For example, an instance of the logDescription
         object might be named logDescription.6.47"
     INDEX { logEventIndex, logIndex }
     ::= { logTable 1 }

 LogEntry ::= SEQUENCE {
     logEventIndex           Integer32,
     logIndex                Integer32,
     logTime                 TimeTicks,
     logDescription          DisplayString
 }

 logEventIndex OBJECT-TYPE
     SYNTAX     Integer32 (1..65535)
     MAX-ACCESS read-only
     STATUS     current
     DESCRIPTION
         "The event entry that generated this log
         entry.  The log identified by a particular
         value of this index is associated with the same
         eventEntry as identified by the same value
         of eventIndex."


     ::= { logEntry 1 }

 logIndex OBJECT-TYPE
     SYNTAX     Integer32 (1..2147483647)
     MAX-ACCESS read-only
     STATUS     current
     DESCRIPTION
         "An index that uniquely identifies an entry
         in the log table amongst those generated by the
         same eventEntries.  These indexes are
         assigned beginning with 1 and increase by one
         with each new log entry.  The association
         between values of logIndex and logEntries
         is fixed for the lifetime of each logEntry.
         The agent may choose to delete the oldest
         instances of logEntry as required because of
         lack of memory.  It is an implementation-specific
         matter as to when this deletion may occur."
     ::= { logEntry 2 }

 logTime OBJECT-TYPE
     SYNTAX     TimeTicks
     MAX-ACCESS read-only
     STATUS     current
     DESCRIPTION
         "The value of sysUpTime when this log entry was created."
     ::= { logEntry 3 }

 logDescription OBJECT-TYPE
     SYNTAX     DisplayString (SIZE (0..255))
     MAX-ACCESS read-only
     STATUS     current
     DESCRIPTION
         "An implementation dependent description of the
         event that activated this log entry."
     ::= { logEntry 4 }

 --  Remote Network Monitoring Traps

 rmonEventsV2 OBJECT-IDENTITY
     STATUS      current
     DESCRIPTION "Definition point for RMON notifications."
     ::= { rmon 0 }

 risingAlarm NOTIFICATION-TYPE
     OBJECTS  { alarmIndex, alarmVariable, alarmSampleType,
                alarmValue, alarmRisingThreshold }
     STATUS   current


     DESCRIPTION
         "The SNMP trap that is generated when an alarm
         entry crosses its rising threshold and generates
         an event that is configured for sending SNMP
         traps."
     ::= { rmonEventsV2 1 }

 fallingAlarm NOTIFICATION-TYPE
     OBJECTS { alarmIndex, alarmVariable, alarmSampleType,
               alarmValue, alarmFallingThreshold }
     STATUS    current
     DESCRIPTION
         "The SNMP trap that is generated when an alarm
         entry crosses its falling threshold and generates
         an event that is configured for sending SNMP
         traps."
     ::= { rmonEventsV2 2 }

 -- Conformance information

 rmonCompliances OBJECT IDENTIFIER ::= { rmonConformance 9 }
 rmonGroups      OBJECT IDENTIFIER ::= { rmonConformance 10 }

 -- Compliance Statements
 rmonCompliance MODULE-COMPLIANCE
     STATUS current
     DESCRIPTION
         "The requirements for conformance to the RMON MIB. At least
         one of the groups in this module must be implemented to
         conform to the RMON MIB. Implementations of this MIB
         must also implement the system group of MIB-II [16] and the
         IF-MIB [17]."
     MODULE -- this module

       GROUP rmonEtherStatsGroup
           DESCRIPTION
               "The RMON Ethernet Statistics Group is optional."

       GROUP rmonHistoryControlGroup
           DESCRIPTION
               "The RMON History Control Group is optional."

       GROUP rmonEthernetHistoryGroup
           DESCRIPTION
               "The RMON Ethernet History Group is optional."

       GROUP rmonAlarmGroup
           DESCRIPTION


               "The RMON Alarm Group is optional."

       GROUP rmonHostGroup
           DESCRIPTION
               "The RMON Host Group is mandatory when the
               rmonHostTopNGroup is implemented."

       GROUP rmonHostTopNGroup
           DESCRIPTION
               "The RMON Host Top N Group is optional."

       GROUP rmonMatrixGroup
           DESCRIPTION
               "The RMON Matrix Group is optional."

       GROUP rmonFilterGroup
           DESCRIPTION
               "The RMON Filter Group is mandatory when the
               rmonPacketCaptureGroup is implemented."

       GROUP rmonPacketCaptureGroup
           DESCRIPTION
               "The RMON Packet Capture Group is optional."

       GROUP rmonEventGroup
           DESCRIPTION
               "The RMON Event Group is mandatory when the
               rmonAlarmGroup is implemented."
     ::= { rmonCompliances 1 }

     rmonEtherStatsGroup OBJECT-GROUP
         OBJECTS {
             etherStatsIndex, etherStatsDataSource,
             etherStatsDropEvents, etherStatsOctets, etherStatsPkts,
             etherStatsBroadcastPkts, etherStatsMulticastPkts,
             etherStatsCRCAlignErrors, etherStatsUndersizePkts,
             etherStatsOversizePkts, etherStatsFragments,
             etherStatsJabbers, etherStatsCollisions,
             etherStatsPkts64Octets, etherStatsPkts65to127Octets,
             etherStatsPkts128to255Octets,
             etherStatsPkts256to511Octets,
             etherStatsPkts512to1023Octets,
             etherStatsPkts1024to1518Octets,
             etherStatsOwner, etherStatsStatus
         }
         STATUS current
         DESCRIPTION
             "The RMON Ethernet Statistics Group."


         ::= { rmonGroups 1 }

     rmonHistoryControlGroup OBJECT-GROUP
         OBJECTS {
             historyControlIndex, historyControlDataSource,
             historyControlBucketsRequested,
             historyControlBucketsGranted, historyControlInterval,
             historyControlOwner, historyControlStatus
         }
         STATUS current
         DESCRIPTION
             "The RMON History Control Group."
         ::= { rmonGroups 2 }

     rmonEthernetHistoryGroup OBJECT-GROUP
         OBJECTS {
             etherHistoryIndex, etherHistorySampleIndex,
             etherHistoryIntervalStart, etherHistoryDropEvents,
             etherHistoryOctets, etherHistoryPkts,
             etherHistoryBroadcastPkts, etherHistoryMulticastPkts,
             etherHistoryCRCAlignErrors, etherHistoryUndersizePkts,
             etherHistoryOversizePkts, etherHistoryFragments,
             etherHistoryJabbers, etherHistoryCollisions,
             etherHistoryUtilization
         }
         STATUS current
         DESCRIPTION
             "The RMON Ethernet History Group."
         ::= { rmonGroups 3 }

     rmonAlarmGroup OBJECT-GROUP
         OBJECTS {
             alarmIndex, alarmInterval, alarmVariable,
             alarmSampleType, alarmValue, alarmStartupAlarm,
             alarmRisingThreshold, alarmFallingThreshold,
             alarmRisingEventIndex, alarmFallingEventIndex,
             alarmOwner, alarmStatus
         }
         STATUS current
         DESCRIPTION
             "The RMON Alarm Group."
         ::= { rmonGroups 4 }

     rmonHostGroup OBJECT-GROUP
         OBJECTS {
             hostControlIndex, hostControlDataSource,
             hostControlTableSize, hostControlLastDeleteTime,
             hostControlOwner, hostControlStatus,


             hostAddress, hostCreationOrder, hostIndex,
             hostInPkts, hostOutPkts, hostInOctets,
             hostOutOctets, hostOutErrors, hostOutBroadcastPkts,
             hostOutMulticastPkts, hostTimeAddress,
             hostTimeCreationOrder, hostTimeIndex,
             hostTimeInPkts, hostTimeOutPkts, hostTimeInOctets,
             hostTimeOutOctets, hostTimeOutErrors,
             hostTimeOutBroadcastPkts, hostTimeOutMulticastPkts
         }
         STATUS current
         DESCRIPTION
             "The RMON Host Group."
         ::= { rmonGroups 5 }

     rmonHostTopNGroup OBJECT-GROUP
         OBJECTS {
             hostTopNControlIndex, hostTopNHostIndex,
             hostTopNRateBase, hostTopNTimeRemaining,
             hostTopNDuration, hostTopNRequestedSize,
             hostTopNGrantedSize, hostTopNStartTime,
             hostTopNOwner, hostTopNStatus,
             hostTopNReport, hostTopNIndex,
             hostTopNAddress, hostTopNRate
         }
         STATUS current
         DESCRIPTION
             "The RMON Host Top 'N' Group."
         ::= { rmonGroups 6 }

     rmonMatrixGroup OBJECT-GROUP
         OBJECTS {
             matrixControlIndex, matrixControlDataSource,
             matrixControlTableSize, matrixControlLastDeleteTime,
             matrixControlOwner, matrixControlStatus,
             matrixSDSourceAddress, matrixSDDestAddress,
             matrixSDIndex, matrixSDPkts,
             matrixSDOctets, matrixSDErrors,
             matrixDSSourceAddress, matrixDSDestAddress,
             matrixDSIndex, matrixDSPkts,
             matrixDSOctets, matrixDSErrors
         }
         STATUS current
         DESCRIPTION
             "The RMON Matrix Group."
         ::= { rmonGroups 7 }

     rmonFilterGroup OBJECT-GROUP
         OBJECTS {


             filterIndex, filterChannelIndex, filterPktDataOffset,
             filterPktData, filterPktDataMask,
             filterPktDataNotMask, filterPktStatus,
             filterPktStatusMask, filterPktStatusNotMask,
             filterOwner, filterStatus,
             channelIndex, channelIfIndex, channelAcceptType,
             channelDataControl, channelTurnOnEventIndex,
             channelTurnOffEventIndex, channelEventIndex,
             channelEventStatus, channelMatches,
             channelDescription, channelOwner, channelStatus
         }
         STATUS current
         DESCRIPTION
             "The RMON Filter Group."
         ::= { rmonGroups 8 }

     rmonPacketCaptureGroup OBJECT-GROUP
         OBJECTS {
             bufferControlIndex, bufferControlChannelIndex,
             bufferControlFullStatus, bufferControlFullAction,
             bufferControlCaptureSliceSize,
             bufferControlDownloadSliceSize,
             bufferControlDownloadOffset,
             bufferControlMaxOctetsRequested,
             bufferControlMaxOctetsGranted,
             bufferControlCapturedPackets,
             bufferControlTurnOnTime,
             bufferControlOwner, bufferControlStatus,
             captureBufferControlIndex, captureBufferIndex,
             captureBufferPacketID, captureBufferPacketData,
             captureBufferPacketLength, captureBufferPacketTime,
             captureBufferPacketStatus
         }
         STATUS current
         DESCRIPTION
             "The RMON Packet Capture Group."
         ::= { rmonGroups 9 }

     rmonEventGroup OBJECT-GROUP
         OBJECTS {
             eventIndex, eventDescription, eventType,
             eventCommunity, eventLastTimeSent,
             eventOwner, eventStatus,
             logEventIndex, logIndex, logTime,
             logDescription
         }
         STATUS current
         DESCRIPTION


             "The RMON Event Group."
         ::= { rmonGroups 10 }

     rmonNotificationGroup NOTIFICATION-GROUP
         NOTIFICATIONS { risingAlarm, fallingAlarm }
         STATUS        current
         DESCRIPTION
             "The RMON Notification Group."
         ::= { rmonGroups 11 }
END

RMON2-MIB DEFINITIONS ::= BEGIN

IMPORTS
    MODULE-IDENTITY, OBJECT-TYPE, Counter32, Integer32,
        Gauge32, IpAddress, TimeTicks            FROM SNMPv2-SMI
    TEXTUAL-CONVENTION, RowStatus, DisplayString, TimeStamp
                                                 FROM SNMPv2-TC
    MODULE-COMPLIANCE, OBJECT-GROUP FROM SNMPv2-CONF
    mib-2, ifIndex                  FROM RFC1213-MIB
    OwnerString, statistics, history, hosts,
    matrix, filter, etherStatsEntry, historyControlEntry,
    hostControlEntry, matrixControlEntry, filterEntry,
    channelEntry                    FROM RMON-MIB
    tokenRing, tokenRingMLStatsEntry, tokenRingPStatsEntry,
    ringStationControlEntry, sourceRoutingStatsEntry
                                    FROM TOKEN-RING-RMON-MIB;
--  Remote Network Monitoring MIB

rmon MODULE-IDENTITY
    LAST-UPDATED "9605270000Z"
    ORGANIZATION "IETF RMON MIB Working Group"
    CONTACT-INFO
        "Steve Waldbusser   (WG Editor)
         Postal: International Network Services
         650 Castro Street, Suite 260
         Mountain View, CA 94041
         Phone:  +1 415 254 4251
         Email:  waldbusser@ins.com

         Andy Bierman   (WG Chair)
         Phone:  +1 805 648 2028
         Email:  abierman@west.net"
    DESCRIPTION
        "The MIB module for managing remote monitoring
         device implementations. This MIB module
         augments the original RMON MIB as specified in
         RFC 1757."
    ::= { mib-2 16 }

-- { rmon 1 } through { rmon 10 } are defined in RMON and
-- the Token Ring RMON MIB [RFC 1513]


    protocolDir     OBJECT IDENTIFIER ::= { rmon 11 }
    protocolDist    OBJECT IDENTIFIER ::= { rmon 12 }
    addressMap      OBJECT IDENTIFIER ::= { rmon 13 }
    nlHost          OBJECT IDENTIFIER ::= { rmon 14 }
    nlMatrix        OBJECT IDENTIFIER ::= { rmon 15 }
    alHost          OBJECT IDENTIFIER ::= { rmon 16 }
    alMatrix        OBJECT IDENTIFIER ::= { rmon 17 }
    usrHistory      OBJECT IDENTIFIER ::= { rmon 18 }
    probeConfig     OBJECT IDENTIFIER ::= { rmon 19 }
    rmonConformance OBJECT IDENTIFIER ::= { rmon 20 }

-- Textual Conventions

ZeroBasedCounter32 ::= TEXTUAL-CONVENTION
    STATUS current
    DESCRIPTION
        "This TC describes an object which counts events with the
        following semantics: objects of this type will be set to
        zero(0) on creation and will thereafter count appropriate
        events, wrapping back to zero(0) when the value 2^32 is
        reached.

        Provided that an application discovers the new object within
        the minimum time to wrap it can use the initial value as a
        delta since it last polled the table of which this object is
        part.  It is important for a management station to be aware of
        this minimum time and the actual time between polls, and to
        discard data if the actual time is too long or there is no
        defined minimum time.

        Typically this TC is used in tables where the INDEX space is
        constantly changing and/or the TimeFilter mechanism is in use."
    SYNTAX Gauge32

-- HPOV Compiler Bug!
--LastCreatTime ::= TEXTUAL-CONVENTION
--    STATUS current
--    DESCRIPTION
--        "This TC describes an object that stores the last time its
--        entry was created.
--
--        This can be used for polling applications to determine that an
--        entry has been deleted and re-created between polls, causing
--        an otherwise undetectable discontinuity in the data."
--    SYNTAX TimeStamp

TimeFilter ::= TEXTUAL-CONVENTION
    STATUS        current
    DESCRIPTION
        "To be used for the index to a table.  Allows an application
        to download only those rows changed since a particular time.
        A row is considered changed if the value of any object in the
        row changes or if the row is created or deleted.

        When sysUpTime is equal to zero, this table shall be empty.

        One entry exists for each past value of sysUpTime, except that
        the whole table is purged should sysUpTime wrap.

        As this basic row is updated new conceptual rows are created
        (which still share the now updated object values with all
        other instances).  The number of instances which are created
        is determined by the value of sysUpTime at which the basic row
        was last updated.  One instance will exist for each value of
        sysUpTime at the last update time for the row.  A new
        timeMark instance is created for each new sysUpTime value.
        Each new conceptual row will be associated with the timeMark
        instance which was created at the value of sysUpTime with
        which the conceptual row is to be associated.

        By definition all conceptual rows were updated at or after
        time zero and so at least one conceptual row (associated with
        timeMark.0) must exist for each underlying (basic) row.

        See the appendix for further discussion of this variable.

        Consider the following fooTable:

        fooTable ...
        INDEX { fooTimeMark, fooIndex }

        FooEntry {
           fooTimeMark  TimeFilter
           fooIndex     INTEGER,
           fooCounts    Counter
        }

        Should there be two basic rows in this table (fooIndex == 1,
        fooIndex == 2) and row 1 was updated most recently at time 6,
        while row 2 was updated most recently at time 8, and both rows
        had been updated on several earlier occasions such that the
        current values were 5 and 9 respectively then the following
        fooCounts instances would exist.

        fooCounts.0.1  5
        fooCounts.0.2  9
        fooCounts.1.1  5


        fooCounts.1.2  9
        fooCounts.2.1  5
        fooCounts.2.2  9
        fooCounts.3.1  5
        fooCounts.3.2  9
        fooCounts.4.1  5
        fooCounts.4.2  9
        fooCounts.5.1  5
        fooCounts.5.2  9
        fooCounts.6.1  5
        fooCounts.6.2  9
        fooCounts.7.2  9    -- note that row 1 doesn't exist for
        fooCounts.8.2  9    -- times 7 and 8"
    SYNTAX    TimeTicks

DataSource ::= TEXTUAL-CONVENTION
    STATUS        current
    DESCRIPTION
        "Identifies the source of the data that the associated
        function is configured to analyze. This source can be any
        interface on this device.

        In order to identify a particular interface, this
        object shall identify the instance of the ifIndex
        object, defined in [3,5], for the desired interface.

        For example, if an entry were to receive data from
        interface #1, this object would be set to ifIndex.1."
    SYNTAX      OBJECT IDENTIFIER
--
-- Protocol Directory Group
--
-- Lists the inventory of protocols the probe has the capability of
-- monitoring and allows the addition, deletion, and configuration of
-- entries in this list.

protocolDirLastChange OBJECT-TYPE
    SYNTAX      TimeStamp
    MAX-ACCESS  read-only
    STATUS      current
    DESCRIPTION
        "The value of sysUpTime at the time the protocol directory
        was last modified, either through insertions or deletions,
        or through modifications of either the
        protocolDirAddressMapConfig, protocolDirHostConfig, or
        protocolDirMatrixConfig."
    ::= { protocolDir 1 }


protocolDirTable OBJECT-TYPE
    SYNTAX      SEQUENCE OF ProtocolDirEntry
    MAX-ACCESS  not-accessible
    STATUS      current
    DESCRIPTION
        "This table lists the protocols that this agent has the
        capability to decode and count.  There is one entry in this
        table for each such protocol.  These protocols represent
        different network layer, transport layer, and higher-layer
        protocols.  The agent should boot up with this table
        preconfigured with those protocols that it knows about and
        wishes to monitor.  Implementations are strongly encouraged to
        support protocols higher than the network layer (at least for
        the protocol distribution group), even for implementations
        that don't support the application layer groups."
    ::= { protocolDir 2 }

protocolDirEntry OBJECT-TYPE
    SYNTAX      ProtocolDirEntry
    MAX-ACCESS  not-accessible
    STATUS      current
    DESCRIPTION
        "A conceptual row in the protocolDirTable.

         An example of the indexing of this entry is
         protocolDirLocalIndex.8.0.0.0.1.0.0.8.0.2.0.0, which is the
         encoding of a length of 8, followed by 8 subids encoding the
         protocolDirID of 1.2048, followed by a length of 2 and the
         2 subids encoding zero-valued parameters."
    INDEX { protocolDirID, protocolDirParameters }
    ::= { protocolDirTable  1 }

ProtocolDirEntry ::= SEQUENCE {
    protocolDirID                   OCTET STRING,
    protocolDirParameters           OCTET STRING,
    protocolDirLocalIndex           Integer32,
    protocolDirDescr                DisplayString,
    protocolDirType                 BITS,
    protocolDirAddressMapConfig     INTEGER,
    protocolDirHostConfig           INTEGER,
    protocolDirMatrixConfig         INTEGER,
    protocolDirOwner                OwnerString,
    protocolDirStatus               RowStatus
}

protocolDirID OBJECT-TYPE
    SYNTAX      OCTET STRING
    MAX-ACCESS  not-accessible


    STATUS      current
    DESCRIPTION
        "A unique identifier for a particular protocol.  Standard
        identifiers will be defined in a manner such that they
        can often be used as specifications for new protocols - i.e.
        a tree-structured assignment mechanism that matches the
        protocol encapsulation `tree' and which has algorithmic
        assignment mechanisms for certain subtrees. See RFC XXX for
        more details.

        Despite the algorithmic mechanism, the probe will only place
        entries in here for those protocols it chooses to collect.  In
        other words, it need not populate this table with all of the
        possible ethernet protocol types, nor need it create them on
        the fly when it sees them.  Whether or not it does these
        things is a matter of product definition (cost/benefit,
        usability), and is up to the designer of the product.

        If an entry is written to this table with a protocolDirID that
        the agent doesn't understand, either directly or
        algorithmically, the SET request will be rejected with an
        inconsistentName or badValue (for SNMPv1) error."
    ::= { protocolDirEntry 1 }

protocolDirParameters OBJECT-TYPE
    SYNTAX      OCTET STRING
    MAX-ACCESS  not-accessible
    STATUS      current
    DESCRIPTION
        "A set of parameters for the associated protocolDirID.
        See the associated RMON2 Protocol Identifiers document
        for a description of the possible parameters. There
        will be one octet in this string for each sub-identifier in
        the protocolDirID, and the parameters will appear here in the
        same order as the associated sub-identifiers appear in the
        protocolDirID.

        Every node in the protocolDirID tree has a different, optional
        set of parameters defined (that is, the definition of
        parameters for a node is optional).  The proper parameter
        value for each node is included in this string.  Note that the
        inclusion of a parameter value in this string for each node is
        not optional - what is optional is that a node may have no
        parameters defined, in which case the parameter field for that
        node will be zero."
    ::= { protocolDirEntry 2 }

protocolDirLocalIndex OBJECT-TYPE


    SYNTAX      Integer32 (1..2147483647)
    MAX-ACCESS  read-only
    STATUS      current
    DESCRIPTION
        "The locally arbitrary, but unique identifier associated
        with this protocolDir entry.

        The value for each supported protocol must remain constant at
        least from one re-initialization of the entity's network
        management system to the next re-initialization, except that
        if a protocol is deleted and re-created, it must be re-created
        with a new value that has not been used since the last
        re-initialization.

        The specific value is meaningful only within a given SNMP
        entity. A protocolDirLocalIndex must not be re-used until the
        next agent-restart in the event the protocol directory entry
        is deleted."
    ::= { protocolDirEntry 3 }

protocolDirDescr OBJECT-TYPE
    SYNTAX      DisplayString (SIZE (1..64))
    MAX-ACCESS  read-create
    STATUS      current
    DESCRIPTION
        "A textual description of the protocol encapsulation.
        A probe may choose to describe only a subset of the
        entire encapsulation (e.g. only the highest layer).

        This object is intended for human consumption only.

        This object may not be modified if the associated
        protocolDirStatus object is equal to active(1)."
    ::= { protocolDirEntry 4 }

protocolDirType OBJECT-TYPE
    SYNTAX      BITS {
                    extensible(0),
                    addressRecognitionCapable(1)
                }
    MAX-ACCESS  read-only
    STATUS      current
    DESCRIPTION
        "This object describes 2 attributes of this protocol
         directory entry.

         The presence or absence of the `extensible' bit describes
         whether or not this protocol directory entry can be extended


         by the user by creating protocol directory entries which are
         children of this protocol.

         An example of an entry that will often allow extensibility is
         `ip.udp'.  The probe may automatically populate some children
         of this node such as `ip.udp.snmp' and `ip.udp.dns'.
         A probe administrator or user may also populate additional
         children via remote SNMP requests that create entries in this
         table.  When a child node is added for a protocol for which the
         probe has no built in support, extending a parent node (for
         which the probe does have built in support),
         that child node is not extendible.  This is termed `limited
         extensibility'.

         When a child node is added through this extensibility
         mechanism, the values of protocolDirLocalIndex and
         protocolDirType shall be assigned by the agent.

         The other objects in the entry will be assigned by the
         manager who is creating the new entry.

         This object also describes whether or not this agent can
         recognize addresses for this protocol, should it be a network
         level protocol.  That is, while a probe may be able to
         recognize packets of a particular network layer protocol and
         count them, it takes additional logic to be able to recognize
         the addresses in this protocol and to populate network layer
         or application layer tables with the addresses in this
         protocol.  If this bit is set, the agent will recognize
         network layer addresses for this protoocl and populate the
         network and application layer host and matrix tables with
         these protocols.

         Note that when an entry is created, the agent will supply
         values for the bits that match the capabilities of the agent
         with respect to this protocol.  Note that since row creations
         usually exercise the limited extensibility feature, these
         bits will usually be set to zero."
    ::= { protocolDirEntry 5 }

protocolDirAddressMapConfig OBJECT-TYPE
    SYNTAX      INTEGER {
                    notSupported(1),
                    supportedOff(2),
                    supportedOn(3)
                }
    MAX-ACCESS  read-create
    STATUS      current


    DESCRIPTION
        "This object describes and configures the probe's support for
        address mapping for this protocol.  When the probe creates
        entries in this table for all protocols that it understands,
        it will set the entry to notSupported(1) if it doesn't have
        the capability to perform address mapping for the protocol or
        if this protocol is not a network-layer protocol.  When
        an entry is created in this table by a management operation as
        part of the limited extensibility feature, the probe must set
        this value to notSupported(1), because limited extensibility
        of the protocolDirTable does not extend to interpreting
        addresses of the extended protocols.

        If the value of this object is notSupported(1), the probe
        will not perform address mapping for this protocol and
        shall not allow this object to be changed to any other value.
        If the value of this object is supportedOn(3), the probe
        supports address mapping for this protocol and is configured
        to perform address mapping for this protocol for all
        addressMappingControlEntries and all interfaces.
        If the value of this object is supportedOff(2), the probe
        supports address mapping for this protocol but is configured
        to not perform address mapping for this protocol for any
        addressMappingControlEntries and all interfaces.
        Whenever this value changes from supportedOn(3) to
        supportedOff(2), the probe shall delete all related entries in
        the addressMappingTable."
    ::= { protocolDirEntry 6 }

protocolDirHostConfig OBJECT-TYPE
    SYNTAX      INTEGER {
                    notSupported(1),
                    supportedOff(2),
                    supportedOn(3)
                }
    MAX-ACCESS  read-create
    STATUS      current
    DESCRIPTION
        "This object describes and configures the probe's support for
        the network layer and application layer host tables for this
        protocol.  When the probe creates entries in this table for
        all protocols that it understands, it will set the entry to
        notSupported(1) if it doesn't have the capability to track the
        nlHostTable for this protocol or if the alHostTable is
        implemented but doesn't have the capability to track this
        protocol.  Note that if the alHostTable is implemented, the
        probe may only support a protocol if it is supported in both
        the nlHostTable and the alHostTable.


        If the associated protocolDirType object has the
        addressRecognitionCapable bit set, then this is a network
        layer protocol for which the probe recognizes addresses, and
        thus the probe will populate the nlHostTable and alHostTable
        with addresses it discovers for this protocol.

        If the value of this object is notSupported(1), the probe
        will not track the nlHostTable or alHostTable for this
        protocol and shall not allow this object to be changed to any
        other value. If the value of this object is supportedOn(3),
        the probe supports tracking of the nlHostTable and alHostTable
        for this protocol and is configured to track both tables
        for this protocol for all control entries and all interfaces.
        If the value of this object is supportedOff(2), the probe
        supports tracking of the nlHostTable and alHostTable for this
        protocol but is configured to not track these tables
        for any control entries or interfaces.
        Whenever this value changes from supportedOn(3) to
        supportedOff(2), the probe shall delete all related entries in
        the nlHostTable and alHostTable.

        Note that since each alHostEntry references 2 protocol
        directory entries, one for the network address and one for the
        type of the highest protocol recognized, that an entry will
        only be created in that table if this value is supportedOn(3)
        for both protocols."
    ::= { protocolDirEntry 7 }

protocolDirMatrixConfig OBJECT-TYPE
    SYNTAX      INTEGER {
                    notSupported(1),
                    supportedOff(2),
                    supportedOn(3)
                }
    MAX-ACCESS  read-create
    STATUS      current
    DESCRIPTION
        "This object describes and configures the probe's support for
        the network layer and application layer matrix tables for this
        protocol.  When the probe creates entries in this table for
        all protocols that it understands, it will set the entry to
        notSupported(1) if it doesn't have the capability to track the
        nlMatrixTables for this protocol or if the alMatrixTables are
        implemented but don't have the capability to track this
        protocol.  Note that if the alMatrix tables are implemented,
        the probe may only support a protocol if it is supported in
        the the both of the nlMatrixTables and both of the
        alMatrixTables.


        If the associated protocolDirType object has the
        addressRecognitionCapable bit set, then this is a network
        layer protocol for which the probe recognizes addresses, and
        thus the probe will populate both of the nlMatrixTables and
        both of the alMatrixTables with addresses it discovers for
        this protocol.

        If the value of this object is notSupported(1), the probe
        will not track either of the nlMatrixTables or the
        alMatrixTables for this protocol and shall not allow this
        object to be changed to any other value. If the value of this
        object is supportedOn(3), the probe supports tracking of both
        of the nlMatrixTables and (if implemented) both of the
        alMatrixTables for this protocol and is configured to track
        these tables for this protocol for all control entries and all
        interfaces. If the value of this object is supportedOff(2),
        the probe supports tracking of both of the nlMatrixTables and
        (if implemented) both of the alMatrixTables for this protocol
        but is configured to not track these tables for this
        protocol for any control entries or interfaces.
        Whenever this value changes from supportedOn(3) to
        supportedOff(2), the probe shall delete all related entries in
        the nlMatrixTables and the alMatrixTables.

        Note that since each alMatrixEntry references 2 protocol
        directory entries, one for the network address and one for the
        type of the highest protocol recognized, that an entry will
        only be created in that table if this value is supportedOn(3)
        for both protocols."
    ::= { protocolDirEntry 8 }

protocolDirOwner OBJECT-TYPE
    SYNTAX      OwnerString
    MAX-ACCESS  read-create
    STATUS      current
    DESCRIPTION
        "The entity that configured this entry and is
        therefore using the resources assigned to it."
    ::= { protocolDirEntry 9 }

protocolDirStatus OBJECT-TYPE
    SYNTAX      RowStatus
    MAX-ACCESS  read-create
    STATUS      current
    DESCRIPTION
        "The status of this protocol directory entry.

        An entry may not exist in the active state unless all


        objects in the entry have an appropriate value.

        If this object is not equal to active(1), all associated
        entries in the nlHostTable, nlMatrixSDTable, nlMatrixDSTable,
        alHostTable, alMatrixSDTable, and alMatrixDSTable shall be
        deleted."
    ::= { protocolDirEntry 10 }

--
-- Protocol Distribution Group  (protocolDist)
--
-- Collects the relative amounts of octets and packets for the
-- different protocols detected on a network segment.
--    protocolDistControlTable,
--    protocolDistStatsTable

protocolDistControlTable OBJECT-TYPE
    SYNTAX      SEQUENCE OF ProtocolDistControlEntry
    MAX-ACCESS  not-accessible
    STATUS      current
    DESCRIPTION
        "Controls the setup of protocol type distribution statistics
        tables.

        Implementations are encouraged to add an entry per monitored
        interface upon initialization so that a default collection
        of protocol statistics is available.

        Rationale:
        This table controls collection of very basic statistics
        for any or all of the protocols detected on a given interface.
        An NMS can use this table to quickly determine bandwidth
        allocation utilized by different protocols.

        A media-specific statistics collection could also
        be configured (e.g. etherStats, trPStats) to easily obtain
        total frame, octet, and droppedEvents for the same
        interface."
    ::= { protocolDist 1 }

protocolDistControlEntry OBJECT-TYPE
    SYNTAX      ProtocolDistControlEntry
    MAX-ACCESS  not-accessible
    STATUS      current
    DESCRIPTION
        "A conceptual row in the protocolDistControlTable.

         An example of the indexing of this entry is


         protocolDistControlDroppedFrames.7"
    INDEX { protocolDistControlIndex }
    ::= { protocolDistControlTable 1 }

ProtocolDistControlEntry ::= SEQUENCE {
    protocolDistControlIndex                Integer32,
    protocolDistControlDataSource           DataSource,
    protocolDistControlDroppedFrames        Counter32,
    protocolDistControlCreateTime           TimeStamp,
    protocolDistControlOwner                OwnerString,
    protocolDistControlStatus               RowStatus
}

protocolDistControlIndex OBJECT-TYPE
    SYNTAX      Integer32 (1..65535)
    MAX-ACCESS  not-accessible
    STATUS      current
    DESCRIPTION
        "A unique index for this protocolDistControlEntry."
    ::= { protocolDistControlEntry 1 }

protocolDistControlDataSource OBJECT-TYPE
    SYNTAX      DataSource
    MAX-ACCESS  read-create
    STATUS      current
    DESCRIPTION
        "The source of data for the this protocol distribution.

        The statistics in this group reflect all packets
        on the local network segment attached to the
        identified interface.

        This object may not be modified if the associated
        protocolDistControlStatus object is equal to active(1)."
    ::= { protocolDistControlEntry 2 }

protocolDistControlDroppedFrames OBJECT-TYPE
    SYNTAX     Counter32
    MAX-ACCESS read-only
    STATUS     current
    DESCRIPTION
       "The total number of frames which were received by the probe
        and therefore not accounted for in the *StatsDropEvents, but
        for which the probe chose not to count for this entry for
        whatever reason.  Most often, this event occurs when the probe
        is out of some resources and decides to shed load from this
        collection.


        This count does not include packets that were not counted
        because they had MAC-layer errors.

        Note that, unlike the dropEvents counter, this number is the
        exact number of frames dropped."
    ::= { protocolDistControlEntry 3 }

protocolDistControlCreateTime OBJECT-TYPE
    SYNTAX     TimeStamp
    MAX-ACCESS read-only
    STATUS     current
    DESCRIPTION
        "The value of sysUpTime when this control entry was last
        activated. This can be used by the management station to
        ensure that the table has not been deleted and recreated
        between polls."
    ::= { protocolDistControlEntry 4 }

protocolDistControlOwner OBJECT-TYPE
    SYNTAX      OwnerString
    MAX-ACCESS  read-create
    STATUS      current
    DESCRIPTION
        "The entity that configured this entry and is
        therefore using the resources assigned to it."
    ::= { protocolDistControlEntry 5 }

protocolDistControlStatus OBJECT-TYPE
    SYNTAX      RowStatus
    MAX-ACCESS  read-create
    STATUS      current
    DESCRIPTION
        "The status of this row.

        An entry may not exist in the active state unless all
        objects in the entry have an appropriate value.

        If this object is not equal to active(1), all associated
        entries in the protocolDistStatsTable shall be deleted."
    ::= { protocolDistControlEntry 6 }

-- per interface protocol distribution statistics table
protocolDistStatsTable OBJECT-TYPE
    SYNTAX      SEQUENCE OF ProtocolDistStatsEntry
    MAX-ACCESS  not-accessible
    STATUS      current
    DESCRIPTION
        "An entry is made in this table for every protocol in the


        protocolDirTable which has been seen in at least one packet.
        Counters are updated in this table for every protocol type
        that is encountered when parsing a packet, but no counters are
        updated for packets with MAC-layer errors.

        Note that if a protocolDirEntry is deleted, all associated
        entries in this table are removed."
    ::= { protocolDist 2 }

protocolDistStatsEntry OBJECT-TYPE
    SYNTAX      ProtocolDistStatsEntry
    MAX-ACCESS  not-accessible
    STATUS      current
    DESCRIPTION
        "A conceptual row in the protocolDistStatsTable.

        The index is composed of the protocolDistControlIndex of the
        associated protocolDistControlEntry followed by the
        protocolDirLocalIndex of the associated protocol that this
        entry represents.  In other words, the index identifies the
        protocol distribution an entry is a part of as well as the
        particular protocol that it represents.

        An example of the indexing of this entry is
        protocolDistStatsPkts.1.18"
    INDEX { protocolDistControlIndex, protocolDirLocalIndex }
    ::= { protocolDistStatsTable 1 }

ProtocolDistStatsEntry ::= SEQUENCE {
    protocolDistStatsPkts                    ZeroBasedCounter32,
    protocolDistStatsOctets                  ZeroBasedCounter32
}

protocolDistStatsPkts OBJECT-TYPE
    SYNTAX      ZeroBasedCounter32
    MAX-ACCESS  read-only
    STATUS      current
    DESCRIPTION
        "The number of packets without errors received of this
        protocol type.  Note that this is the number of link-layer
        packets, so if a single network-layer packet is fragmented
        into several link-layer frames, this counter is incremented
        several times."
    ::= { protocolDistStatsEntry 1 }

protocolDistStatsOctets OBJECT-TYPE
    SYNTAX      ZeroBasedCounter32
    MAX-ACCESS  read-only


    STATUS      current
    DESCRIPTION
        "The number of octets in packets received of this protocol
        type since it was added to the protocolDistStatsTable
        (excluding framing bits but including FCS octets), except for
        those octets in packets that contained errors.

        Note this doesn't count just those octets in the particular
        protocol frames, but includes the entire packet that contained
        the protocol."
    ::= { protocolDistStatsEntry 2 }

--
-- Address Map Group   (addressMap)
--
-- Lists MAC address to network address bindings discovered by the
-- probe and what interface they were last seen on.
--    addressMapControlTable
--    addressMapTable

addressMapInserts OBJECT-TYPE
    SYNTAX     Counter32
    MAX-ACCESS read-only
    STATUS     current
    DESCRIPTION
        "The number of times an address mapping entry has been
        inserted into the addressMapTable.  If an entry is inserted,
        then deleted, and then inserted, this counter will be
        incremented by 2.

        Note that the table size can be determined by subtracting
        addressMapDeletes from addressMapInserts."
    ::= { addressMap 1 }

addressMapDeletes OBJECT-TYPE
    SYNTAX     Counter32
    MAX-ACCESS read-only
    STATUS     current
    DESCRIPTION
        "The number of times an address mapping entry has been
        deleted from the addressMapTable (for any reason).  If
        an entry is deleted, then inserted, and then deleted, this
        counter will be incremented by 2.

        Note that the table size can be determined by subtracting
        addressMapDeletes from addressMapInserts."
    ::= { addressMap 2 }


addressMapMaxDesiredEntries OBJECT-TYPE
    SYNTAX      Integer32 (-1..2147483647)
    MAX-ACCESS  read-write
    STATUS      current
    DESCRIPTION
        "The maximum number of entries that are desired in the
        addressMapTable. The probe will not create more than
        this number of entries in the table, but may choose to create
        fewer entries in this table for any reason including the lack
        of resources.

        If this object is set to a value less than the current number
        of entries, enough entries are chosen in an
        implementation-dependent manner and deleted so that the number
        of entries in the table equals the value of this object.

        If this value is set to -1, the probe may create any number
        of entries in this table.

        This object may be used to control how resources are allocated
        on the probe for the various RMON functions."
    ::= { addressMap 3 }

addressMapControlTable OBJECT-TYPE
    SYNTAX      SEQUENCE OF AddressMapControlEntry
    MAX-ACCESS  not-accessible
    STATUS      current
    DESCRIPTION
        "A table to control the collection of network layer address to
        physical address to interface mappings.

        Note that this is not like the typical RMON
        controlTable and dataTable in which each entry creates
        its own data table.  Each entry in this table enables the
        discovery of addresses on a new interface and the placement
        of address mappings into the central addressMapTable.

        Implementations are encouraged to add an entry per monitored
        interface upon initialization so that a default collection
        of address mappings is available."
    ::= { addressMap 4 }

addressMapControlEntry OBJECT-TYPE
    SYNTAX      AddressMapControlEntry
    MAX-ACCESS  not-accessible
    STATUS      current
    DESCRIPTION
        "A conceptual row in the addressMapControlTable.


        An example of the indexing of this entry is
        addressMapControlDroppedFrames.1"
    INDEX { addressMapControlIndex }
    ::= { addressMapControlTable 1 }

AddressMapControlEntry ::= SEQUENCE {
    addressMapControlIndex              Integer32,
    addressMapControlDataSource         DataSource,
    addressMapControlDroppedFrames      Counter32,
    addressMapControlOwner              OwnerString,
    addressMapControlStatus             RowStatus
}

addressMapControlIndex OBJECT-TYPE
    SYNTAX      Integer32 (1..65535)
    MAX-ACCESS  not-accessible
    STATUS      current
    DESCRIPTION
        "A unique index for this entry in the addressMapControlTable."
    ::= { addressMapControlEntry 1 }

addressMapControlDataSource OBJECT-TYPE
    SYNTAX      DataSource
    MAX-ACCESS  read-create
    STATUS      current
    DESCRIPTION
        "The source of data for this addressMapControlEntry."
    ::= { addressMapControlEntry 2 }

addressMapControlDroppedFrames OBJECT-TYPE
    SYNTAX     Counter32
    MAX-ACCESS read-only
    STATUS     current
    DESCRIPTION
       "The total number of frames which were received by the probe
        and therefore not accounted for in the *StatsDropEvents, but
        for which the probe chose not to count for this entry for
        whatever reason.  Most often, this event occurs when the probe
        is out of some resources and decides to shed load from this
        collection.

        This count does not include packets that were not counted
        because they had MAC-layer errors.

        Note that, unlike the dropEvents counter, this number is the
        exact number of frames dropped."
    ::= { addressMapControlEntry 3 }


addressMapControlOwner OBJECT-TYPE
    SYNTAX      OwnerString
    MAX-ACCESS  read-create
    STATUS      current
    DESCRIPTION
        "The entity that configured this entry and is
        therefore using the resources assigned to it."
    ::= { addressMapControlEntry 4 }

addressMapControlStatus OBJECT-TYPE
    SYNTAX      RowStatus
    MAX-ACCESS  read-create
    STATUS      current
    DESCRIPTION
        "The status of this addressMap control entry.

        An entry may not exist in the active state unless all
        objects in the entry have an appropriate value.

        If this object is not equal to active(1), all associated
        entries in the addressMapTable shall be deleted."
    ::= { addressMapControlEntry 5 }

addressMapTable OBJECT-TYPE
    SYNTAX      SEQUENCE OF AddressMapEntry
    MAX-ACCESS  not-accessible
    STATUS      current
    DESCRIPTION
        "A table of network layer address to physical address to
        interface mappings.

        The probe will add entries to this table based on the source
        MAC and network addresses seen in packets without MAC-level
        errors. The probe will populate this table for all protocols
        in the protocol directory table whose value of
        protocolDirAddressMapConfig is equal to supportedOn(3), and
        will delete any entries whose protocolDirEntry is deleted or
        has a protocolDirAddressMapConfig value of supportedOff(2)."
    ::= { addressMap 5 }

addressMapEntry OBJECT-TYPE
    SYNTAX      AddressMapEntry
    MAX-ACCESS  not-accessible
    STATUS      current
    DESCRIPTION
        "A conceptual row in the addressMapTable.
        The protocolDirLocalIndex in the index identifies the network
        layer protocol of the addressMapNetworkAddress.


        An example of the indexing of this entry is
        addressMapSource.783495.18.4.128.2.6.6.11.1.3.6.1.2.1.2.2.1.1.1"
    INDEX { addressMapTimeMark, protocolDirLocalIndex,
            addressMapNetworkAddress, addressMapSource }
    ::= { addressMapTable 1 }

AddressMapEntry ::= SEQUENCE {
    addressMapTimeMark                 TimeFilter,
    addressMapNetworkAddress           OCTET STRING,
    addressMapSource                   OBJECT IDENTIFIER,
    addressMapPhysicalAddress          OCTET STRING,
    addressMapLastChange               TimeStamp
}

addressMapTimeMark OBJECT-TYPE
    SYNTAX      TimeFilter
    MAX-ACCESS  not-accessible
    STATUS      current
    DESCRIPTION
        "A TimeFilter for this entry.  See the TimeFilter textual
        convention to see how this works."
    ::= { addressMapEntry 1 }

addressMapNetworkAddress OBJECT-TYPE
    SYNTAX      OCTET STRING
    MAX-ACCESS  not-accessible
    STATUS      current
    DESCRIPTION
        "The network address for this relation.

        This is represented as an octet string with
        specific semantics and length as identified
        by the protocolDirLocalIndex component of the
        index.

        For example, if the protocolDirLocalIndex indicates an
        encapsulation of ip, this object is encoded as a length
        octet of 4, followed by the 4 octets of the ip address,
        in network byte order."
    ::= { addressMapEntry 2 }

addressMapSource OBJECT-TYPE
    SYNTAX      OBJECT IDENTIFIER
    MAX-ACCESS  not-accessible
    STATUS      current
    DESCRIPTION
        "The interface or port on which the associated network
         address was most recently seen.


        If this address mapping was discovered on an interface, this
        object shall identify the instance of the ifIndex
        object, defined in [3,5], for the desired interface.
        For example, if an entry were to receive data from
        interface #1, this object would be set to ifIndex.1.

        If this address mapping was discovered on a port, this
        object shall identify the instance of the rptrGroupPortIndex
        object, defined in [RFC1516], for the desired port.
        For example, if an entry were to receive data from
        group #1, port #1, this object would be set to
        rptrGroupPortIndex.1.1.

        Note that while the dataSource associated with this entry
        may only point to index objects, this object may at times
        point to repeater port objects. This situation occurs when
        the dataSource points to an interface which is a locally
        attached repeater and the agent has additional information
        about the source port of traffic seen on that repeater."
    ::= { addressMapEntry 3 }

addressMapPhysicalAddress OBJECT-TYPE
    SYNTAX      OCTET STRING
    MAX-ACCESS  read-only
    STATUS      current
    DESCRIPTION
        "The last source physical address on which the associated
        network address was seen.  If the protocol of the associated
        network address was encapsulated inside of a network-level or
        higher protocol, this will be the address of the next-lower
        protocol with the addressRecognitionCapable bit enabled and
        will be formatted as specified for that protocol."
    ::= { addressMapEntry 4 }

addressMapLastChange OBJECT-TYPE
    SYNTAX      TimeStamp
    MAX-ACCESS  read-only
    STATUS      current
    DESCRIPTION
        "The value of sysUpTime at the time this entry was last
        created or the values of the physical address changed.

        This can be used to help detect duplicate address problems, in
        which case this object will be updated frequently."
    ::= { addressMapEntry 5 }

--
-- Network Layer Host Group


--
-- Counts the amount of traffic sent from and to each network address
-- discovered by the probe.
-- Note that while the hlHostControlTable also has objects that
-- control an optional alHostTable, implementation of the alHostTable is
-- not required to fully implement this group.

hlHostControlTable OBJECT-TYPE
    SYNTAX      SEQUENCE OF HlHostControlEntry
    MAX-ACCESS  not-accessible
    STATUS      current
    DESCRIPTION
        "A list of higher layer (i.e. non-MAC) host table control entries.

        These entries will enable the collection of the network and
        application level host tables indexed by network addresses.
        Both the network and application level host tables are
        controlled by this table is so that they will both be created
        and deleted at the same time, further increasing the ease with
        which they can be implemented as a single datastore (note that
        if an implementation stores application layer host records in
        memory, it can derive network layer host records from them).

        Entries in the nlHostTable will be created on behalf of each
        entry in this table. Additionally, if this probe implements
        the alHostTable, entries in the alHostTable will be created on
        behalf of each entry in this table.

        Implementations are encouraged to add an entry per monitored
        interface upon initialization so that a default collection
        of host statistics is available."
    ::= { nlHost 1 }

hlHostControlEntry OBJECT-TYPE
    SYNTAX      HlHostControlEntry
    MAX-ACCESS  not-accessible
    STATUS      current
    DESCRIPTION
        "A conceptual row in the hlHostControlTable.

        An example of the indexing of this entry is
        hlHostControlNlDroppedFrames.1"
    INDEX { hlHostControlIndex }
    ::= { hlHostControlTable 1 }

HlHostControlEntry ::= SEQUENCE {
    hlHostControlIndex               Integer32,
    hlHostControlDataSource          DataSource,


    hlHostControlNlDroppedFrames     Counter32,
    hlHostControlNlInserts           Counter32,
    hlHostControlNlDeletes           Counter32,
    hlHostControlNlMaxDesiredEntries Integer32,
    hlHostControlAlDroppedFrames     Counter32,
    hlHostControlAlInserts           Counter32,
    hlHostControlAlDeletes           Counter32,
    hlHostControlAlMaxDesiredEntries Integer32,
    hlHostControlOwner               OwnerString,
    hlHostControlStatus              RowStatus
}

hlHostControlIndex OBJECT-TYPE
    SYNTAX      Integer32 (1..65535)
    MAX-ACCESS  not-accessible
    STATUS      current
    DESCRIPTION
        "An index that uniquely identifies an entry in the
        hlHostControlTable.  Each such entry defines
        a function that discovers hosts on a particular
        interface and places statistics about them in the
        nlHostTable, and optionally in the alHostTable, on
        behalf of this hlHostControlEntry."
    ::= { hlHostControlEntry 1 }

hlHostControlDataSource OBJECT-TYPE
    SYNTAX      DataSource
    MAX-ACCESS  read-create
    STATUS      current
    DESCRIPTION
        "The source of data for the associated host tables.

        The statistics in this group reflect all packets
        on the local network segment attached to the
        identified interface.

        This object may not be modified if the associated
        hlHostControlStatus object is equal to active(1)."
    ::= { hlHostControlEntry 2 }

hlHostControlNlDroppedFrames OBJECT-TYPE
    SYNTAX     Counter32
    MAX-ACCESS read-only
    STATUS     current
    DESCRIPTION
       "The total number of frames which were received by the probe
        and therefore not accounted for in the *StatsDropEvents, but
        for which the probe chose not to count for the associated


        nlHost entries for whatever reason.  Most often, this event
        occurs when the probe is out of some resources and decides to
        shed load from this collection.

        This count does not include packets that were not counted
        because they had MAC-layer errors.

        Note that if the nlHostTable is inactive because no protocols
        are enabled in the protocol directory, this value should be 0.

        Note that, unlike the dropEvents counter, this number is the
        exact number of frames dropped."
    ::= { hlHostControlEntry 3 }

hlHostControlNlInserts OBJECT-TYPE
    SYNTAX     Counter32
    MAX-ACCESS read-only
    STATUS     current
    DESCRIPTION
        "The number of times an nlHost entry has been
        inserted into the nlHost table.  If an entry is inserted, then
        deleted, and then inserted, this counter will be incremented
        by 2.

        To allow for efficient implementation strategies, agents may
        delay updating this object for short periods of time.  For
        example, an implementation strategy may allow internal
        data structures to differ from those visible via SNMP for
        short periods of time.  This counter may reflect the internal
        data structures for those short periods of time.

        Note that the table size can be determined by subtracting
        hlHostControlNlDeletes from hlHostControlNlInserts."
    ::= { hlHostControlEntry 4 }

hlHostControlNlDeletes OBJECT-TYPE
    SYNTAX     Counter32
    MAX-ACCESS read-only
    STATUS     current
    DESCRIPTION
        "The number of times an nlHost entry has been
        deleted from the nlHost table (for any reason).  If an entry
        is deleted, then inserted, and then deleted, this counter will
        be incremented by 2.

        To allow for efficient implementation strategies, agents may
        delay updating this object for short periods of time.  For
        example, an implementation strategy may allow internal


        data structures to differ from those visible via SNMP for
        short periods of time.  This counter may reflect the internal
        data structures for those short periods of time.

        Note that the table size can be determined by subtracting
        hlHostControlNlDeletes from hlHostControlNlInserts."
    ::= { hlHostControlEntry 5 }

hlHostControlNlMaxDesiredEntries OBJECT-TYPE
    SYNTAX      Integer32 (-1..2147483647)
    MAX-ACCESS  read-create
    STATUS      current
    DESCRIPTION
        "The maximum number of entries that are desired in the
        nlHostTable on behalf of this control entry. The probe will
        not create more than this number of associated entries in the
        table, but may choose to create fewer entries in this table
        for any reason including the lack of resources.

        If this object is set to a value less than the current number
        of entries, enough entries are chosen in an
        implementation-dependent manner and deleted so that the number
        of entries in the table equals the value of this object.

        If this value is set to -1, the probe may create any number
        of entries in this table.  If the associated
        hlHostControlStatus object is equal to `active', this
        object may not be modified.

        This object may be used to control how resources are allocated
        on the probe for the various RMON functions."
    ::= { hlHostControlEntry 6 }

hlHostControlAlDroppedFrames OBJECT-TYPE
    SYNTAX     Counter32
    MAX-ACCESS read-only
    STATUS     current
    DESCRIPTION
       "The total number of frames which were received by the probe
        and therefore not accounted for in the *StatsDropEvents, but
        for which the probe chose not to count for the associated
        alHost entries for whatever reason.  Most often, this event
        occurs when the probe is out of some resources and decides to
        shed load from this collection.

        This count does not include packets that were not counted
        because they had MAC-layer errors.


        Note that if the alHostTable is not implemented or is inactive
        because no protocols are enabled in the protocol directory,
        this value should be 0.

        Note that, unlike the dropEvents counter, this number is the
        exact number of frames dropped."
    ::= { hlHostControlEntry 7 }

hlHostControlAlInserts OBJECT-TYPE
    SYNTAX     Counter32
    MAX-ACCESS read-only
    STATUS     current
    DESCRIPTION
        "The number of times an alHost entry has been
        inserted into the alHost table.  If an entry is inserted, then
        deleted, and then inserted, this counter will be incremented
        by 2.

        To allow for efficient implementation strategies, agents may
        delay updating this object for short periods of time.  For
        example, an implementation strategy may allow internal
        data structures to differ from those visible via SNMP for
        short periods of time.  This counter may reflect the internal
        data structures for those short periods of time.

        Note that the table size can be determined by subtracting
        hlHostControlAlDeletes from hlHostControlAlInserts."
    ::= { hlHostControlEntry 8 }

hlHostControlAlDeletes OBJECT-TYPE
    SYNTAX     Counter32
    MAX-ACCESS read-only
    STATUS     current
    DESCRIPTION
        "The number of times an alHost entry has been
        deleted from the alHost table (for any reason).  If an entry
        is deleted, then inserted, and then deleted, this counter will
        be incremented by 2.

        To allow for efficient implementation strategies, agents may
        delay updating this object for short periods of time.  For
        example, an implementation strategy may allow internal
        data structures to differ from those visible via SNMP for
        short periods of time.  This counter may reflect the internal
        data structures for those short periods of time.

        Note that the table size can be determined by subtracting
        hlHostControlAlDeletes from hlHostControlAlInserts."


    ::= { hlHostControlEntry 9 }

hlHostControlAlMaxDesiredEntries OBJECT-TYPE
    SYNTAX      Integer32 (-1..2147483647)
    MAX-ACCESS  read-create
    STATUS      current
    DESCRIPTION
        "The maximum number of entries that are desired in the alHost
        table on behalf of this control entry. The probe will not
        create more than this number of associated entries in the
        table, but may choose to create fewer entries in this table
        for any reason including the lack of resources.

        If this object is set to a value less than the current number
        of entries, enough entries are chosen in an
        implementation-dependent manner and deleted so that the number
        of entries in the table equals the value of this object.

        If this value is set to -1, the probe may create any number
        of entries in this table.  If the associated
        hlHostControlStatus object is equal to `active', this
        object may not be modified.

        This object may be used to control how resources are allocated
        on the probe for the various RMON functions."
    ::= { hlHostControlEntry 10 }

hlHostControlOwner OBJECT-TYPE
    SYNTAX      OwnerString
    MAX-ACCESS  read-create
    STATUS      current
    DESCRIPTION
        "The entity that configured this entry and is
        therefore using the resources assigned to it."
    ::= { hlHostControlEntry 11 }

hlHostControlStatus OBJECT-TYPE
    SYNTAX      RowStatus
    MAX-ACCESS  read-create
    STATUS      current
    DESCRIPTION
        "The status of this hlHostControlEntry.

        An entry may not exist in the active state unless all
        objects in the entry have an appropriate value.

        If this object is not equal to active(1), all associated
        entries in the nlHostTable and alHostTable shall be deleted."


    ::= { hlHostControlEntry 12 }

nlHostTable OBJECT-TYPE
    SYNTAX      SEQUENCE OF NlHostEntry
    MAX-ACCESS  not-accessible
    STATUS      current
    DESCRIPTION
        "A collection of statistics for a particular network layer
        address that has been discovered on an interface of this
        device.

        The probe will populate this table for all network layer
        protocols in the protocol directory table whose value of
        protocolDirHostConfig is equal to supportedOn(3), and
        will delete any entries whose protocolDirEntry is deleted or
        has a protocolDirHostConfig value of supportedOff(2).

        The probe will add to this table all addresses seen
        as the source or destination address in all packets with no
        MAC errors, and will increment octet and packet counts in the
        table for all packets with no MAC errors."
::= { nlHost 2 }

nlHostEntry OBJECT-TYPE
    SYNTAX      NlHostEntry
    MAX-ACCESS  not-accessible
    STATUS      current
    DESCRIPTION
        "A conceptual row in the nlHostTable.

        The hlHostControlIndex value in the index identifies the
        hlHostControlEntry on whose behalf this entry was created.
        The protocolDirLocalIndex value in the index identifies the
        network layer protocol of the nlHostAddress.

        An example of the indexing of this entry is
        nlHostOutPkts.1.783495.18.4.128.2.6.6."
    INDEX { hlHostControlIndex, nlHostTimeMark,
            protocolDirLocalIndex, nlHostAddress }
    ::= { nlHostTable 1 }

NlHostEntry ::= SEQUENCE {
    nlHostTimeMark              TimeFilter,
    nlHostAddress               OCTET STRING,
    nlHostInPkts                ZeroBasedCounter32,
    nlHostOutPkts               ZeroBasedCounter32,
    nlHostInOctets              ZeroBasedCounter32,
    nlHostOutOctets             ZeroBasedCounter32,


    nlHostOutMacNonUnicastPkts  ZeroBasedCounter32,
    nlHostCreateTime            TimeStamp
}

nlHostTimeMark OBJECT-TYPE
    SYNTAX      TimeFilter
    MAX-ACCESS  not-accessible
    STATUS      current
    DESCRIPTION
        "A TimeFilter for this entry.  See the TimeFilter textual
        convention to see how this works."
    ::= { nlHostEntry 1 }

nlHostAddress OBJECT-TYPE
    SYNTAX      OCTET STRING
    MAX-ACCESS  not-accessible
    STATUS      current
    DESCRIPTION
        "The network address for this nlHostEntry.

        This is represented as an octet string with
        specific semantics and length as identified
        by the protocolDirLocalIndex component of the index.

        For example, if the protocolDirLocalIndex indicates an
        encapsulation of ip, this object is encoded as a length
        octet of 4, followed by the 4 octets of the ip address,
        in network byte order."
    ::= { nlHostEntry 2 }

nlHostInPkts OBJECT-TYPE
    SYNTAX      ZeroBasedCounter32
    MAX-ACCESS  read-only
    STATUS      current
    DESCRIPTION
        "The number of packets without errors transmitted to
        this address since it was added to the nlHostTable.  Note that
        this is the number of link-layer packets, so if a single
        network-layer packet is fragmented into several link-layer
        frames, this counter is incremented several times."
    ::= { nlHostEntry 3 }

nlHostOutPkts OBJECT-TYPE
    SYNTAX      ZeroBasedCounter32
    MAX-ACCESS  read-only
    STATUS      current
    DESCRIPTION
        "The number of packets without errors transmitted by


        this address since it was added to the nlHostTable.  Note that
        this is the number of link-layer packets, so if a single
        network-layer packet is fragmented into several link-layer
        frames, this counter is incremented several times."
    ::= { nlHostEntry 4 }

nlHostInOctets OBJECT-TYPE
    SYNTAX      ZeroBasedCounter32
    MAX-ACCESS  read-only
    STATUS      current
    DESCRIPTION
        "The number of octets transmitted to this address
        since it was added to the nlHostTable (excluding
        framing bits but including FCS octets), excluding
        those octets in packets that contained errors.

        Note this doesn't count just those octets in the particular
        protocol frames, but includes the entire packet that contained
        the protocol."
    ::= { nlHostEntry 5 }

nlHostOutOctets OBJECT-TYPE
    SYNTAX      ZeroBasedCounter32
    MAX-ACCESS  read-only
    STATUS      current
    DESCRIPTION
        "The number of octets transmitted by this address
        since it was added to the nlHostTable (excluding
        framing bits but including FCS octets), excluding
        those octets in packets that contained errors.

        Note this doesn't count just those octets in the particular
        protocol frames, but includes the entire packet that contained
        the protocol."
    ::= { nlHostEntry 6 }

nlHostOutMacNonUnicastPkts OBJECT-TYPE
    SYNTAX      ZeroBasedCounter32
    MAX-ACCESS  read-only
    STATUS      current
    DESCRIPTION
        "The number of packets without errors transmitted by this
        address that were directed to any MAC broadcast addresses
        or to any MAC multicast addresses since this host was
        added to the nlHostTable. Note that this is the number of
        link-layer packets, so if a single network-layer packet is
        fragmented into several link-layer frames, this counter is
        incremented several times."


    ::= { nlHostEntry 7 }

nlHostCreateTime OBJECT-TYPE
    SYNTAX     TimeStamp
    MAX-ACCESS read-only
    STATUS     current
    DESCRIPTION
        "The value of sysUpTime when this entry was last activated.
        This can be used by the management station to ensure that the
        entry has not been deleted and recreated between polls."
    ::= { nlHostEntry 8 }

--
-- Network Layer Matrix Group
--
-- Counts the amount of traffic sent between each pair of network
-- addresses discovered by the probe.
-- Note that while the hlMatrixControlTable also has objects that
-- control optional alMatrixTables, implementation of the
-- alMatrixTables is not required to fully implement this group.

hlMatrixControlTable OBJECT-TYPE
    SYNTAX      SEQUENCE OF HlMatrixControlEntry
    MAX-ACCESS  not-accessible
    STATUS      current
    DESCRIPTION
        "A list of higher layer (i.e. non-MAC) matrix control entries.

        These entries will enable the collection of the network and
        application level matrix tables containing conversation
        statistics indexed by pairs of network addresses.
        Both the network and application level matrix tables are
        controlled by this table is so that they will both be created
        and deleted at the same time, further increasing the ease with
        which they can be implemented as a single datastore (note that
        if an implementation stores application layer matrix records
        in memory, it can derive network layer matrix records from
        them).

        Entries in the nlMatrixSDTable and nlMatrixDSTable will be
        created on behalf of each entry in this table.  Additionally,
        if this probe implements the alMatrix tables, entries in the
        alMatrix tables will be created on behalf of each entry in
        this table."
    ::= { nlMatrix 1 }

hlMatrixControlEntry OBJECT-TYPE
    SYNTAX      HlMatrixControlEntry


    MAX-ACCESS  not-accessible
    STATUS      current
    DESCRIPTION
        "A conceptual row in the hlMatrixControlTable.

        An example of indexing of this entry is
        hlMatrixControlNlDroppedFrames.1"
    INDEX { hlMatrixControlIndex }
    ::= { hlMatrixControlTable 1 }

HlMatrixControlEntry ::= SEQUENCE {
    hlMatrixControlIndex                  Integer32,
    hlMatrixControlDataSource             DataSource,
    hlMatrixControlNlDroppedFrames        Counter32,
    hlMatrixControlNlInserts              Counter32,
    hlMatrixControlNlDeletes              Counter32,
    hlMatrixControlNlMaxDesiredEntries    Integer32,
    hlMatrixControlAlDroppedFrames        Counter32,
    hlMatrixControlAlInserts              Counter32,
    hlMatrixControlAlDeletes              Counter32,
    hlMatrixControlAlMaxDesiredEntries    Integer32,
    hlMatrixControlOwner                  OwnerString,
    hlMatrixControlStatus                 RowStatus
}

hlMatrixControlIndex OBJECT-TYPE
    SYNTAX      Integer32 (1..65535)
    MAX-ACCESS  not-accessible
    STATUS      current
    DESCRIPTION
        "An index that uniquely identifies an entry in the
        hlMatrixControlTable.  Each such entry defines
        a function that discovers conversations on a particular
        interface and places statistics about them in the
        nlMatrixSDTable and the nlMatrixDSTable, and optionally the
        alMatrixSDTable and alMatrixDSTable, on behalf of this
        hlMatrixControlEntry."
    ::= { hlMatrixControlEntry 1 }

hlMatrixControlDataSource OBJECT-TYPE
    SYNTAX      DataSource
    MAX-ACCESS  read-create
    STATUS      current
    DESCRIPTION
        "The source of the data for the associated matrix tables.

        The statistics in this group reflect all packets
        on the local network segment attached to the


        identified interface.

        This object may not be modified if the associated
        hlMatrixControlStatus object is equal to active(1)."
    ::= { hlMatrixControlEntry 2 }

hlMatrixControlNlDroppedFrames OBJECT-TYPE
    SYNTAX     Counter32
    MAX-ACCESS read-only
    STATUS     current
    DESCRIPTION
       "The total number of frames which were received by the probe
        and therefore not accounted for in the *StatsDropEvents, but
        for which the probe chose not to count for this entry for
        whatever reason.  Most often, this event occurs when the probe
        is out of some resources and decides to shed load from this
        collection.

        This count does not include packets that were not counted
        because they had MAC-layer errors.

        Note that if the nlMatrixTables are inactive because no
        protocols are enabled in the protocol directory, this value
        should be 0.

        Note that, unlike the dropEvents counter, this number is the
        exact number of frames dropped."
    ::= { hlMatrixControlEntry 3 }

hlMatrixControlNlInserts OBJECT-TYPE
    SYNTAX     Counter32
    MAX-ACCESS read-only
    STATUS     current
    DESCRIPTION
        "The number of times an nlMatrix entry has been
        inserted into the nlMatrix tables.  If an entry is inserted,
        then deleted, and then inserted, this counter will be
        incremented by 2.  The addition of a conversation into both
        the nlMatrixSDTable and nlMatrixDSTable shall be counted as
        two insertions (even though every addition into one table must
        be accompanied by an insertion into the other).

        To allow for efficient implementation strategies, agents may
        delay updating this object for short periods of time.  For
        example, an implementation strategy may allow internal
        data structures to differ from those visible via SNMP for
        short periods of time.  This counter may reflect the internal
        data structures for those short periods of time.


        Note that the sum of then nlMatrixSDTable and nlMatrixDSTable
        sizes can be determined by subtracting
        hlMatrixControlNlDeletes from hlMatrixControlNlInserts."
    ::= { hlMatrixControlEntry 4 }

hlMatrixControlNlDeletes OBJECT-TYPE
    SYNTAX     Counter32
    MAX-ACCESS read-only
    STATUS     current
    DESCRIPTION
        "The number of times an nlMatrix entry has been
        deleted from the nlMatrix tables (for any reason).  If an
        entry is deleted, then inserted, and then deleted, this
        counter will be incremented by 2.  The deletion of a
        conversation from both the nlMatrixSDTable and nlMatrixDSTable
        shall be counted as two deletions (even though every deletion
        from one table must be accompanied by a deletion from the
        other).

        To allow for efficient implementation strategies, agents may
        delay updating this object for short periods of time.  For
        example, an implementation strategy may allow internal
        data structures to differ from those visible via SNMP for
        short periods of time.  This counter may reflect the internal
        data structures for those short periods of time.

        Note that the table size can be determined by subtracting
        hlMatrixControlNlDeletes from hlMatrixControlNlInserts."
    ::= { hlMatrixControlEntry 5 }

hlMatrixControlNlMaxDesiredEntries OBJECT-TYPE
    SYNTAX      Integer32 (-1..2147483647)
    MAX-ACCESS  read-create
    STATUS      current
    DESCRIPTION
        "The maximum number of entries that are desired in the
        nlMatrix tables on behalf of this control entry. The probe
        will not create more than this number of associated entries in
        the table, but may choose to create fewer entries in this
        table for any reason including the lack of resources.

        If this object is set to a value less than the current number
        of entries, enough entries are chosen in an
        implementation-dependent manner and deleted so that the number
        of entries in the table equals the value of this object.

        If this value is set to -1, the probe may create any number
        of entries in this table.  If the associated


        hlMatrixControlStatus object is equal to `active', this
        object may not be modified.

        This object may be used to control how resources are allocated
        on the probe for the various RMON functions."
    ::= { hlMatrixControlEntry 6 }

hlMatrixControlAlDroppedFrames OBJECT-TYPE
    SYNTAX     Counter32
    MAX-ACCESS read-only
    STATUS     current
    DESCRIPTION
       "The total number of frames which were received by the probe
        and therefore not accounted for in the *StatsDropEvents, but
        for which the probe chose not to count for this entry for
        whatever reason.  Most often, this event occurs when the probe
        is out of some resources and decides to shed load from this
        collection.

        This count does not include packets that were not counted
        because they had MAC-layer errors.

        Note that if the alMatrixTables are not implemented or are
        inactive because no protocols are enabled in the protocol
        directory, this value should be 0.

        Note that, unlike the dropEvents counter, this number is the
        exact number of frames dropped."
    ::= { hlMatrixControlEntry 7 }

hlMatrixControlAlInserts OBJECT-TYPE
    SYNTAX     Counter32
    MAX-ACCESS read-only
    STATUS     current
    DESCRIPTION
        "The number of times an alMatrix entry has been
        inserted into the alMatrix tables.  If an entry is inserted,
        then deleted, and then inserted, this counter will be
        incremented by 2.  The addition of a conversation into both
        the alMatrixSDTable and alMatrixDSTable shall be counted as
        two insertions (even though every addition into one table must
        be accompanied by an insertion into the other).

        To allow for efficient implementation strategies, agents may
        delay updating this object for short periods of time.  For
        example, an implementation strategy may allow internal
        data structures to differ from those visible via SNMP for
        short periods of time.  This counter may reflect the internal


        data structures for those short periods of time.

        Note that the table size can be determined by subtracting
        hlMatrixControlAlDeletes from hlMatrixControlAlInserts."
    ::= { hlMatrixControlEntry 8 }

hlMatrixControlAlDeletes OBJECT-TYPE
    SYNTAX     Counter32
    MAX-ACCESS read-only
    STATUS     current
    DESCRIPTION
        "The number of times an alMatrix entry has been
        deleted from the alMatrix tables.  If an entry is deleted,
        then inserted, and then deleted, this counter will be
        incremented by 2.  The deletion of a conversation from both
        the alMatrixSDTable and alMatrixDSTable shall be counted as
        two deletions (even though every deletion from one table must
        be accompanied by a deletion from the other).

        To allow for efficient implementation strategies, agents may
        delay updating this object for short periods of time.  For
        example, an implementation strategy may allow internal
        data structures to differ from those visible via SNMP for
        short periods of time.  This counter may reflect the internal
        data structures for those short periods of time.

        Note that the table size can be determined by subtracting
        hlMatrixControlAlDeletes from hlMatrixControlAlInserts."
    ::= { hlMatrixControlEntry 9 }

hlMatrixControlAlMaxDesiredEntries OBJECT-TYPE
    SYNTAX      Integer32 (-1..2147483647)
    MAX-ACCESS  read-create
    STATUS      current
    DESCRIPTION
        "The maximum number of entries that are desired in the
        alMatrix tables on behalf of this control entry. The probe
        will not create more than this number of associated entries in
        the table, but may choose to create fewer entries in this
        table for any reason including the lack of resources.

        If this object is set to a value less than the current number
        of entries, enough entries are chosen in an
        implementation-dependent manner and deleted so that the number
        of entries in the table equals the value of this object.

        If this value is set to -1, the probe may create any number
        of entries in this table.  If the associated


        hlMatrixControlStatus object is equal to `active', this
        object may not be modified.

        This object may be used to control how resources are allocated
        on the probe for the various RMON functions."
    ::= { hlMatrixControlEntry 10 }

hlMatrixControlOwner OBJECT-TYPE
    SYNTAX      OwnerString
    MAX-ACCESS  read-create
    STATUS      current
    DESCRIPTION
        "The entity that configured this entry and is
        therefore using the resources assigned to it."
    ::= { hlMatrixControlEntry 11 }

hlMatrixControlStatus OBJECT-TYPE
    SYNTAX      RowStatus
    MAX-ACCESS  read-create
    STATUS      current
    DESCRIPTION
        "The status of this hlMatrixControlEntry.

        An entry may not exist in the active state unless all
        objects in the entry have an appropriate value.

        If this object is not equal to active(1), all
        associated entries in the nlMatrixSDTable,
        nlMatrixDSTable, alMatrixSDTable, and the alMatrixDSTable
        shall be deleted by the agent."
    ::= { hlMatrixControlEntry 12 }

nlMatrixSDTable OBJECT-TYPE
    SYNTAX      SEQUENCE OF NlMatrixSDEntry
    MAX-ACCESS  not-accessible
    STATUS      current
    DESCRIPTION
        "A list of traffic matrix entries which collect statistics for
        conversations between two network-level addresses.  This table
        is indexed first by the source address and then by the
        destination address to make it convenient to collect all
        conversations from a particular address.

        The probe will populate this table for all network layer
        protocols in the protocol directory table whose value of
        protocolDirMatrixConfig is equal to supportedOn(3), and
        will delete any entries whose protocolDirEntry is deleted or
        has a protocolDirMatrixConfig value of supportedOff(2).


        The probe will add to this table all pairs of addresses
        seen in all packets with no MAC errors, and will increment
        octet and packet counts in the table for all packets with no
        MAC errors.

        Further, this table will only contain entries that have a
        corresponding entry in the nlMatrixDSTable with the same
        source address and destination address."
    ::= { nlMatrix 2 }

nlMatrixSDEntry OBJECT-TYPE
    SYNTAX      NlMatrixSDEntry
    MAX-ACCESS  not-accessible
    STATUS      current
    DESCRIPTION
        "A conceptual row in the nlMatrixSDTable.

        The hlMatrixControlIndex value in the index identifies the
        hlMatrixControlEntry on whose behalf this entry was created.
        The protocolDirLocalIndex value in the index identifies the
        network layer protocol of the nlMatrixSDSourceAddress and
        nlMatrixSDDestAddress.

        An example of the indexing of this table is
        nlMatrixSDPkts.1.783495.18.4.128.2.6.6.4.128.2.6.7"
    INDEX { hlMatrixControlIndex, nlMatrixSDTimeMark,
            protocolDirLocalIndex,
            nlMatrixSDSourceAddress, nlMatrixSDDestAddress }
    ::= { nlMatrixSDTable 1 }

NlMatrixSDEntry ::= SEQUENCE {
    nlMatrixSDTimeMark              TimeFilter,
    nlMatrixSDSourceAddress         OCTET STRING,
    nlMatrixSDDestAddress           OCTET STRING,
    nlMatrixSDPkts                  ZeroBasedCounter32,
    nlMatrixSDOctets                ZeroBasedCounter32,
    nlMatrixSDCreateTime            TimeStamp
}

nlMatrixSDTimeMark OBJECT-TYPE
    SYNTAX      TimeFilter
    MAX-ACCESS  not-accessible
    STATUS      current
    DESCRIPTION
        "A TimeFilter for this entry.  See the TimeFilter textual
        convention to see how this works."
    ::= { nlMatrixSDEntry 1 }


nlMatrixSDSourceAddress OBJECT-TYPE
    SYNTAX      OCTET STRING
    MAX-ACCESS  not-accessible
    STATUS      current
    DESCRIPTION
        "The network source address for this nlMatrixSDEntry.

        This is represented as an octet string with
        specific semantics and length as identified
        by the protocolDirLocalIndex component of the index.

        For example, if the protocolDirLocalIndex indicates an
        encapsulation of ip, this object is encoded as a length
        octet of 4, followed by the 4 octets of the ip address,
        in network byte order."
    ::= { nlMatrixSDEntry 2 }

nlMatrixSDDestAddress OBJECT-TYPE
    SYNTAX      OCTET STRING
    MAX-ACCESS  not-accessible
    STATUS      current
    DESCRIPTION
        "The network destination address for this
        nlMatrixSDEntry.

        This is represented as an octet string with
        specific semantics and length as identified
        by the protocolDirLocalIndex component of the index.

        For example, if the protocolDirLocalIndex indicates an
        encapsulation of ip, this object is encoded as a length
        octet of 4, followed by the 4 octets of the ip address,
        in network byte order."
    ::= { nlMatrixSDEntry 3 }

nlMatrixSDPkts OBJECT-TYPE
    SYNTAX      ZeroBasedCounter32
    MAX-ACCESS  read-only
    STATUS      current
    DESCRIPTION
        "The number of packets without errors transmitted from the
        source address to the destination address since this entry was
        added to the nlMatrixSDTable.  Note that this is the number of
        link-layer packets, so if a single network-layer packet is
        fragmented into several link-layer frames, this counter is
        incremented several times."
    ::= { nlMatrixSDEntry 4 }


nlMatrixSDOctets OBJECT-TYPE
    SYNTAX      ZeroBasedCounter32
    MAX-ACCESS  read-only
    STATUS      current
    DESCRIPTION
        "The number of octets transmitted from the source address to
        the destination address since this entry was added to the
        nlMatrixSDTable (excluding framing bits but
        including FCS octets), excluding those octets in packets that
        contained errors.

        Note this doesn't count just those octets in the particular
        protocol frames, but includes the entire packet that contained
        the protocol."
    ::= { nlMatrixSDEntry 5 }

nlMatrixSDCreateTime OBJECT-TYPE
    SYNTAX     TimeStamp
    MAX-ACCESS read-only
    STATUS     current
    DESCRIPTION
        "The value of sysUpTime when this entry was last activated.
        This can be used by the management station to ensure that the
        entry has not been deleted and recreated between polls."
    ::= { nlMatrixSDEntry 6 }

-- Traffic matrix tables from destination to source

nlMatrixDSTable OBJECT-TYPE
    SYNTAX      SEQUENCE OF NlMatrixDSEntry
    MAX-ACCESS  not-accessible
    STATUS      current
    DESCRIPTION
        "A list of traffic matrix entries which collect statistics for
        conversations between two network-level addresses.  This table
        is indexed first by the destination address and then by the
        source address to make it convenient to collect all
        conversations to a particular address.

        The probe will populate this table for all network layer
        protocols in the protocol directory table whose value of
        protocolDirMatrixConfig is equal to supportedOn(3), and
        will delete any entries whose protocolDirEntry is deleted or
        has a protocolDirMatrixConfig value of supportedOff(2).

        The probe will add to this table all pairs of addresses
        seen in all packets with no MAC errors, and will increment


        octet and packet counts in the table for all packets with no
        MAC errors.

        Further, this table will only contain entries that have a
        corresponding entry in the nlMatrixSDTable with the same
        source address and destination address."
    ::= { nlMatrix 3 }

nlMatrixDSEntry OBJECT-TYPE
    SYNTAX      NlMatrixDSEntry
    MAX-ACCESS  not-accessible
    STATUS      current
    DESCRIPTION
        "A conceptual row in the nlMatrixDSTable.

        The hlMatrixControlIndex value in the index identifies the
        hlMatrixControlEntry on whose behalf this entry was created.
        The protocolDirLocalIndex value in the index identifies the
        network layer protocol of the nlMatrixDSSourceAddress and
        nlMatrixDSDestAddress.

        An example of the indexing of this table is
        nlMatrixDSPkts.1.783495.18.4.128.2.6.7.4.128.2.6.6"
    INDEX { hlMatrixControlIndex, nlMatrixDSTimeMark,
            protocolDirLocalIndex,
            nlMatrixDSDestAddress, nlMatrixDSSourceAddress }
    ::= { nlMatrixDSTable 1 }

NlMatrixDSEntry ::= SEQUENCE {
    nlMatrixDSTimeMark                 TimeFilter,
    nlMatrixDSSourceAddress            OCTET STRING,
    nlMatrixDSDestAddress              OCTET STRING,
    nlMatrixDSPkts                     ZeroBasedCounter32,
    nlMatrixDSOctets                   ZeroBasedCounter32,
    nlMatrixDSCreateTime               TimeStamp
}

nlMatrixDSTimeMark OBJECT-TYPE
    SYNTAX      TimeFilter
    MAX-ACCESS  not-accessible
    STATUS      current
    DESCRIPTION
        "A TimeFilter for this entry.  See the TimeFilter textual
        convention to see how this works."
    ::= { nlMatrixDSEntry 1 }

nlMatrixDSSourceAddress OBJECT-TYPE
    SYNTAX      OCTET STRING


    MAX-ACCESS  not-accessible
    STATUS      current
    DESCRIPTION
        "The network source address for this nlMatrixDSEntry.

        This is represented as an octet string with
        specific semantics and length as identified
        by the protocolDirLocalIndex component of the index.

        For example, if the protocolDirLocalIndex indicates an
        encapsulation of ip, this object is encoded as a length
        octet of 4, followed by the 4 octets of the ip address,
        in network byte order."
    ::= { nlMatrixDSEntry 2 }

nlMatrixDSDestAddress OBJECT-TYPE
    SYNTAX      OCTET STRING
    MAX-ACCESS  not-accessible
    STATUS      current
    DESCRIPTION
        "The network destination address for this
        nlMatrixDSEntry.

        This is represented as an octet string with
        specific semantics and length as identified
        by the protocolDirLocalIndex component of the index.

        For example, if the protocolDirLocalIndex indicates an
        encapsulation of ip, this object is encoded as a length
        octet of 4, followed by the 4 octets of the ip address,
        in network byte order."
    ::= { nlMatrixDSEntry 3 }

nlMatrixDSPkts OBJECT-TYPE
    SYNTAX      ZeroBasedCounter32
    MAX-ACCESS  read-only
    STATUS      current
    DESCRIPTION
        "The number of packets without errors transmitted from the
        source address to the destination address since this entry was
        added to the nlMatrixDSTable.  Note that this is the number of
        link-layer packets, so if a single network-layer packet is
        fragmented into several link-layer frames, this counter is
        incremented several times."
    ::= { nlMatrixDSEntry 4 }

nlMatrixDSOctets OBJECT-TYPE
    SYNTAX      ZeroBasedCounter32


    MAX-ACCESS  read-only
    STATUS      current
    DESCRIPTION
        "The number of octets transmitted from the source address
        to the destination address since this entry was added to the
        nlMatrixDSTable (excluding framing bits but
        including FCS octets), excluding those octets in packets that
        contained errors.

        Note this doesn't count just those octets in the particular
        protocol frames, but includes the entire packet that contained
        the protocol."
    ::= { nlMatrixDSEntry 5 }

nlMatrixDSCreateTime OBJECT-TYPE
    SYNTAX     TimeStamp
    MAX-ACCESS read-only
    STATUS     current
    DESCRIPTION
        "The value of sysUpTime when this entry was last activated.
        This can be used by the management station to ensure that the
        entry has not been deleted and recreated between polls."
    ::= { nlMatrixDSEntry 6 }

nlMatrixTopNControlTable OBJECT-TYPE
    SYNTAX      SEQUENCE OF NlMatrixTopNControlEntry
    MAX-ACCESS  not-accessible
    STATUS      current
    DESCRIPTION
        "A set of parameters that control the creation of a
        report of the top N matrix entries according to
        a selected metric."
    ::= { nlMatrix 4 }

nlMatrixTopNControlEntry OBJECT-TYPE
    SYNTAX      NlMatrixTopNControlEntry
    MAX-ACCESS  not-accessible
    STATUS      current
    DESCRIPTION
        "A conceptual row in the nlMatrixTopNControlTable.

        An example of the indexing of this table is
        nlMatrixTopNControlDuration.3"
    INDEX { nlMatrixTopNControlIndex }
    ::= { nlMatrixTopNControlTable 1 }

NlMatrixTopNControlEntry ::= SEQUENCE {
    nlMatrixTopNControlIndex            Integer32,


    nlMatrixTopNControlMatrixIndex      Integer32,
    nlMatrixTopNControlRateBase         INTEGER,
    nlMatrixTopNControlTimeRemaining    Integer32,
    nlMatrixTopNControlGeneratedReports Counter32,
    nlMatrixTopNControlDuration         Integer32,
    nlMatrixTopNControlRequestedSize    Integer32,
    nlMatrixTopNControlGrantedSize      Integer32,
    nlMatrixTopNControlStartTime        TimeStamp,
    nlMatrixTopNControlOwner            OwnerString,
    nlMatrixTopNControlStatus           RowStatus
}

nlMatrixTopNControlIndex OBJECT-TYPE
    SYNTAX     Integer32 (1..65535)
    MAX-ACCESS not-accessible
    STATUS     current
    DESCRIPTION
        "An index that uniquely identifies an entry
        in the nlMatrixTopNControlTable.  Each such
        entry defines one top N report prepared for
        one interface."
    ::= { nlMatrixTopNControlEntry 1 }

nlMatrixTopNControlMatrixIndex OBJECT-TYPE
    SYNTAX     Integer32 (1..65535)
    MAX-ACCESS read-create
    STATUS     current
    DESCRIPTION
        "The nlMatrix[SD/DS] table for which a top N report will be
        prepared on behalf of this entry.  The nlMatrix[SD/DS] table
        is identified by the value of the hlMatrixControlIndex
        for that table - that value is used here to identify the
        particular table.

        This object may not be modified if the associated
        nlMatrixTopNControlStatus object is equal to active(1)."
    ::= { nlMatrixTopNControlEntry 2 }

nlMatrixTopNControlRateBase OBJECT-TYPE
    SYNTAX      INTEGER {
                    nlMatrixTopNPkts(1),
                    nlMatrixTopNOctets(2)
                }
    MAX-ACCESS read-create
    STATUS     current
    DESCRIPTION
        "The variable for each nlMatrix[SD/DS] entry that the
        nlMatrixTopNEntries are sorted by.


        This object may not be modified if the associated
        nlMatrixTopNControlStatus object is equal to active(1)."
    ::= { nlMatrixTopNControlEntry 3 }

nlMatrixTopNControlTimeRemaining OBJECT-TYPE
    SYNTAX     Integer32 (0..2147483647)
    MAX-ACCESS read-create
    STATUS     current
    DESCRIPTION
        "The number of seconds left in the report currently
        being collected.  When this object is modified by
        the management station, a new collection is started,
        possibly aborting a currently running report.  The
        new value is used as the requested duration of this
        report, and is immediately loaded into the associated
        nlMatrixTopNControlDuration object.
        When the report finishes, the probe will automatically
        start another collection with the same initial value
        of nlMatrixTopNControlTimeRemaining.  Thus the management
        station may simply read the resulting reports repeatedly,
        checking the startTime and duration each time to ensure that a
        report was not missed or that the report parameters were not
        changed.

        While the value of this object is non-zero, it decrements
        by one per second until it reaches zero.  At the time
        that this object decrements to zero, the report is made
        accessible in the nlMatrixTopNTable, overwriting any report
        that may be there.

        When this object is modified by the management station, any
        associated entries in the nlMatrixTopNTable shall be deleted.

        (Note that this is a different algorithm than the one used in
        the hostTopNTable)."
    DEFVAL { 1800 }
    ::= { nlMatrixTopNControlEntry 4 }

nlMatrixTopNControlGeneratedReports OBJECT-TYPE
    SYNTAX     Counter32
    MAX-ACCESS read-only
    STATUS     current
    DESCRIPTION
        "The number of reports that have been generated by this entry."
    ::= { nlMatrixTopNControlEntry 5 }

nlMatrixTopNControlDuration OBJECT-TYPE
    SYNTAX     Integer32


    MAX-ACCESS read-only
    STATUS     current
    DESCRIPTION
        "The number of seconds that this report has collected
        during the last sampling interval.

        When the associated nlMatrixTopNControlTimeRemaining object is
        set, this object shall be set by the probe to the
        same value and shall not be modified until the next
        time the nlMatrixTopNControlTimeRemaining is set.
        This value shall be zero if no reports have been
        requested for this nlMatrixTopNControlEntry."
    ::= { nlMatrixTopNControlEntry 6 }

nlMatrixTopNControlRequestedSize OBJECT-TYPE
    SYNTAX     Integer32 (0..2147483647)
    MAX-ACCESS read-create
    STATUS     current
    DESCRIPTION
        "The maximum number of matrix entries requested for this report.

        When this object is created or modified, the probe
        should set nlMatrixTopNControlGrantedSize as closely to this
        object as is possible for the particular probe
        implementation and available resources."
    DEFVAL { 150 }
    ::= { nlMatrixTopNControlEntry 7 }

nlMatrixTopNControlGrantedSize OBJECT-TYPE
    SYNTAX     Integer32 (0..2147483647)
    MAX-ACCESS read-only
    STATUS     current
    DESCRIPTION
        "The maximum number of matrix entries in this report.

        When the associated nlMatrixTopNControlRequestedSize object is
        created or modified, the probe should set this
        object as closely to the requested value as is
        possible for the particular implementation and
        available resources. The probe must not lower this
        value except as a result of a set to the associated
        nlMatrixTopNControlRequestedSize object.

        If the value of nlMatrixTopNControlRateBase is equal to
        nlMatrixTopNPkts, when the next topN report is generated,
        matrix entries with the highest value of nlMatrixTopNPktRate
        shall be placed in this table in decreasing order of this rate
        until there is no more room or until there are no more


        matrix entries.

        If the value of nlMatrixTopNControlRateBase is equal to
        nlMatrixTopNOctets, when the next topN report is generated,
        matrix entries with the highest value of nlMatrixTopNOctetRate
        shall be placed in this table in decreasing order of this rate
        until there is no more room or until there are no more
        matrix entries.

        It is an implementation-specific matter how entries with the
        same value of nlMatrixTopNPktRate or nlMatrixTopNOctetRate are
        sorted.  It is also an implementation-specific matter as to
        whether or not zero-valued entries are available."
    ::= { nlMatrixTopNControlEntry 8 }

nlMatrixTopNControlStartTime OBJECT-TYPE
    SYNTAX     TimeStamp
    MAX-ACCESS read-only
    STATUS     current
    DESCRIPTION
        "The value of sysUpTime when this top N report was
        last started.  In other words, this is the time that
        the associated nlMatrixTopNControlTimeRemaining object was
        modified to start the requested report or the time
        the report was last automatically (re)started.

        This object may be used by the management station to
        determine if a report was missed or not."
    ::= { nlMatrixTopNControlEntry 9 }

nlMatrixTopNControlOwner OBJECT-TYPE
    SYNTAX     OwnerString
    MAX-ACCESS read-create
    STATUS     current
    DESCRIPTION
        "The entity that configured this entry and is
        therefore using the resources assigned to it."
    ::= { nlMatrixTopNControlEntry 10 }

nlMatrixTopNControlStatus OBJECT-TYPE
    SYNTAX     RowStatus
    MAX-ACCESS read-create
    STATUS     current
    DESCRIPTION
        "The status of this nlMatrixTopNControlEntry.

        An entry may not exist in the active state unless all
        objects in the entry have an appropriate value.


        If this object is not equal to active(1), all
        associated entries in the nlMatrixTopNTable shall be deleted
        by the agent."
    ::= { nlMatrixTopNControlEntry 11 }

nlMatrixTopNTable OBJECT-TYPE
    SYNTAX     SEQUENCE OF NlMatrixTopNEntry
    MAX-ACCESS not-accessible
    STATUS     current
    DESCRIPTION
        "A set of statistics for those network layer matrix entries
        that have counted the highest number of octets or packets."
    ::= { nlMatrix 5 }

nlMatrixTopNEntry OBJECT-TYPE
    SYNTAX     NlMatrixTopNEntry
    MAX-ACCESS not-accessible
    STATUS     current
    DESCRIPTION
        "A conceptual row in the nlMatrixTopNTable.

        The nlMatrixTopNControlIndex value in the index identifies the
        nlMatrixTopNControlEntry on whose behalf this entry was
        created.

        An example of the indexing of this table is
        nlMatrixTopNPktRate.3.10"
    INDEX { nlMatrixTopNControlIndex, nlMatrixTopNIndex }
    ::= { nlMatrixTopNTable 1 }

NlMatrixTopNEntry ::= SEQUENCE {
    nlMatrixTopNIndex                 Integer32,
    nlMatrixTopNProtocolDirLocalIndex Integer32,
    nlMatrixTopNSourceAddress         OCTET STRING,
    nlMatrixTopNDestAddress           OCTET STRING,
    nlMatrixTopNPktRate               Gauge32,
    nlMatrixTopNReversePktRate        Gauge32,
    nlMatrixTopNOctetRate             Gauge32,
    nlMatrixTopNReverseOctetRate      Gauge32
}

nlMatrixTopNIndex OBJECT-TYPE
    SYNTAX     Integer32 (1..65535)
    MAX-ACCESS not-accessible
    STATUS     current
    DESCRIPTION
        "An index that uniquely identifies an entry in
        the nlMatrixTopNTable among those in the same report.


        This index is between 1 and N, where N is the
        number of entries in this report.

        If the value of nlMatrixTopNControlRateBase is equal to
        nlMatrixTopNPkts, increasing values of nlMatrixTopNIndex shall
        be assigned to entries with decreasing values of
        nlMatrixTopNPktRate until index N is assigned or there are no
        more nlMatrixTopNEntries.

        If the value of nlMatrixTopNControlRateBase is equal to
        nlMatrixTopNOctets, increasing values of nlMatrixTopNIndex
        shall be assigned to entries with decreasing values of
        nlMatrixTopNOctetRate until index N is assigned or there are
        no more nlMatrixTopNEntries."
    ::= { nlMatrixTopNEntry 1 }

nlMatrixTopNProtocolDirLocalIndex OBJECT-TYPE
    SYNTAX     Integer32 (1..2147483647)
    MAX-ACCESS read-only
    STATUS     current
    DESCRIPTION
        "The protocolDirLocalIndex of the network layer protocol of
        this entry's network address."
    ::= { nlMatrixTopNEntry 2 }

nlMatrixTopNSourceAddress OBJECT-TYPE
    SYNTAX     OCTET STRING
    MAX-ACCESS read-only
    STATUS     current
    DESCRIPTION
        "The network layer address of the source host in this
        conversation.

        This is represented as an octet string with
        specific semantics and length as identified
        by the associated nlMatrixTopNProtocolDirLocalIndex.

        For example, if the protocolDirLocalIndex indicates an
        encapsulation of ip, this object is encoded as a length
        octet of 4, followed by the 4 octets of the ip address,
        in network byte order."
    ::= { nlMatrixTopNEntry 3 }

nlMatrixTopNDestAddress OBJECT-TYPE
    SYNTAX     OCTET STRING
    MAX-ACCESS read-only
    STATUS     current
    DESCRIPTION


        "The network layer address of the destination host in this
        conversation.

        This is represented as an octet string with
        specific semantics and length as identified
        by the associated nlMatrixTopNProtocolDirLocalIndex.

        For example, if the nlMatrixTopNProtocolDirLocalIndex
        indicates an encapsulation of ip, this object is encoded as a
        length octet of 4, followed by the 4 octets of the ip address,
        in network byte order."
    ::= { nlMatrixTopNEntry 4 }

nlMatrixTopNPktRate OBJECT-TYPE
    SYNTAX     Gauge32
    MAX-ACCESS read-only
    STATUS     current
    DESCRIPTION
        "The number of packets seen from the source host
        to the destination host during this sampling interval, counted
        using the rules for counting the nlMatrixSDPkts object.
        If the value of nlMatrixTopNControlRateBase is
        nlMatrixTopNPkts, this variable will be used to sort this
        report."
    ::= { nlMatrixTopNEntry 5 }

nlMatrixTopNReversePktRate OBJECT-TYPE
    SYNTAX     Gauge32
    MAX-ACCESS read-only
    STATUS     current
    DESCRIPTION
        "The number of packets seen from the destination host to the
        source host during this sampling interval, counted
        using the rules for counting the nlMatrixSDPkts object (note
        that the corresponding nlMatrixSDPkts object selected is the
        one whose source address is equal to nlMatrixTopNDestAddress
        and whose destination address is equal to
        nlMatrixTopNSourceAddress.)

        Note that if the value of nlMatrixTopNControlRateBase is equal
        to nlMatrixTopNPkts, the sort of topN entries is based
        entirely on nlMatrixTopNPktRate, and not on the value of this
        object."
    ::= { nlMatrixTopNEntry 6 }

nlMatrixTopNOctetRate OBJECT-TYPE
    SYNTAX     Gauge32
    MAX-ACCESS read-only


    STATUS     current
    DESCRIPTION
        "The number of octets seen from the source host
        to the destination host during this sampling interval, counted
        using the rules for counting the nlMatrixSDOctets object.  If
        the value of nlMatrixTopNControlRateBase is
        nlMatrixTopNOctets, this variable will be used to sort this
        report."
    ::= { nlMatrixTopNEntry 7 }

nlMatrixTopNReverseOctetRate OBJECT-TYPE
    SYNTAX     Gauge32
    MAX-ACCESS read-only
    STATUS     current
    DESCRIPTION
        "The number of octets seen from the destination host to the
        source host during this sampling interval, counted
        using the rules for counting the nlMatrixDSOctets object (note
        that the corresponding nlMatrixSDOctets object selected is the
        one whose source address is equal to nlMatrixTopNDestAddress
        and whose destination address is equal to
        nlMatrixTopNSourceAddress.)

        Note that if the value of nlMatrixTopNControlRateBase is equal
        to nlMatrixTopNOctets, the sort of topN entries is based
        entirely on nlMatrixTopNOctetRate, and not on the value of
        this object."
    ::= { nlMatrixTopNEntry 8 }

-- Application Layer Functions
--
-- The application layer host, matrix, and matrixTopN functions report
-- on protocol usage at the network layer or higher.  Note that the
-- use of the term application layer does not imply that only
-- application-layer protocols are counted, rather it means that
-- protocols up to and including the application layer are supported.

--
-- Application Layer Host Group
--
-- Counts the amount of traffic, by protocol, sent from and to each
-- network address discovered by the probe.
-- Implementation of this group requires implementation of the Network
-- Layer Host Group.

alHostTable OBJECT-TYPE
    SYNTAX      SEQUENCE OF AlHostEntry
    MAX-ACCESS  not-accessible


    STATUS      current
    DESCRIPTION
        "A collection of statistics for a particular protocol from a
        particular network address that has been discovered on an
        interface of this device.

        The probe will populate this table for all protocols in the
        protocol directory table whose value of
        protocolDirHostConfig is equal to supportedOn(3), and
        will delete any entries whose protocolDirEntry is deleted or
        has a protocolDirHostConfig value of supportedOff(2).

        The probe will add to this table all addresses
        seen as the source or destination address in all packets with
        no MAC errors, and will increment octet and packet counts in
        the table for all packets with no MAC errors.  Further,
        entries will only be added to this table if their address
        exists in the nlHostTable and will be deleted from this table
        if their address is deleted from the nlHostTable."
    ::= { alHost 1 }

alHostEntry OBJECT-TYPE
    SYNTAX      AlHostEntry
    MAX-ACCESS  not-accessible
    STATUS      current
    DESCRIPTION
        "A conceptual row in the alHostTable.

        The hlHostControlIndex value in the index identifies the
        hlHostControlEntry on whose behalf this entry was created.
        The first protocolDirLocalIndex value in the index identifies
        the network layer protocol of the address.
        The nlHostAddress value in the index identifies the network
        layer address of this entry.
        The second protocolDirLocalIndex value in the index identifies
        the protocol that is counted by this entry.

        An example of the indexing in this entry is
        alHostOutPkts.1.783495.18.4.128.2.6.6.34"
    INDEX { hlHostControlIndex, alHostTimeMark,
            protocolDirLocalIndex, nlHostAddress,
            protocolDirLocalIndex }
    ::= { alHostTable 1 }

AlHostEntry ::= SEQUENCE {
    alHostTimeMark                 TimeFilter,
    alHostInPkts                   ZeroBasedCounter32,
    alHostOutPkts                  ZeroBasedCounter32,


    alHostInOctets                 ZeroBasedCounter32,
    alHostOutOctets                ZeroBasedCounter32,
    alHostCreateTime               TimeStamp
}

alHostTimeMark OBJECT-TYPE
    SYNTAX      TimeFilter
    MAX-ACCESS  not-accessible
    STATUS      current
    DESCRIPTION
        "A TimeFilter for this entry.  See the TimeFilter textual
        convention to see how this works."
    ::= { alHostEntry 1 }

alHostInPkts OBJECT-TYPE
    SYNTAX      ZeroBasedCounter32
    MAX-ACCESS  read-only
    STATUS      current
    DESCRIPTION
        "The number of packets of this protocol type without errors
        transmitted to this address since it was added to the
        alHostTable.  Note that this is the number of link-layer
        packets, so if a single network-layer packet is fragmented
        into several link-layer frames, this counter is incremented
        several times."
    ::= { alHostEntry 2 }

alHostOutPkts OBJECT-TYPE
    SYNTAX      ZeroBasedCounter32
    MAX-ACCESS  read-only
    STATUS      current
    DESCRIPTION
        "The number of packets of this protocol type without errors
        transmitted by this address since it was added to the
        alHostTable.  Note that this is the number of link-layer
        packets, so if a single network-layer packet is fragmented
        into several link-layer frames, this counter is incremented
        several times."
     ::= { alHostEntry 3 }

alHostInOctets OBJECT-TYPE
    SYNTAX      ZeroBasedCounter32
    MAX-ACCESS  read-only
    STATUS      current
    DESCRIPTION
        "The number of octets transmitted to this address
        of this protocol type since it was added to the
        alHostTable (excluding framing bits but including


        FCS octets), excluding those octets in packets that
        contained errors.

        Note this doesn't count just those octets in the particular
        protocol frames, but includes the entire packet that contained
        the protocol."
    ::= { alHostEntry 4 }

alHostOutOctets OBJECT-TYPE
    SYNTAX      ZeroBasedCounter32
    MAX-ACCESS  read-only
    STATUS      current
    DESCRIPTION
        "The number of octets transmitted by this address
        of this protocol type since it was added to the
        alHostTable (excluding framing bits but including
        FCS octets), excluding those octets in packets that
        contained errors.

        Note this doesn't count just those octets in the particular
        protocol frames, but includes the entire packet that contained
        the protocol."
    ::= { alHostEntry 5 }

alHostCreateTime OBJECT-TYPE
    SYNTAX     TimeStamp
    MAX-ACCESS read-only
    STATUS     current
    DESCRIPTION
        "The value of sysUpTime when this entry was last activated.
        This can be used by the management station to ensure that the
        entry has not been deleted and recreated between polls."
    ::= { alHostEntry 6 }

--
-- Application Layer Matrix Group
--
-- Counts the amount of traffic, by protocol, sent between each pair
-- of network addresses discovered by the probe.
-- Implementation of this group requires implementation of the Network
-- Layer Matrix Group.

alMatrixSDTable OBJECT-TYPE
    SYNTAX      SEQUENCE OF AlMatrixSDEntry
    MAX-ACCESS  not-accessible
    STATUS      current
    DESCRIPTION
        "A list of application traffic matrix entries which collect


        statistics for conversations of a particular protocol between
        two network-level addresses.  This table is indexed first by
        the source address and then by the destination address to make
        it convenient to collect all statistics from a particular
        address.

        The probe will populate this table for all protocols in the
        protocol directory table whose value of
        protocolDirMatrixConfig is equal to supportedOn(3), and
        will delete any entries whose protocolDirEntry is deleted or
        has a protocolDirMatrixConfig value of supportedOff(2).

        The probe will add to this table all pairs of addresses for
        all protocols seen in all packets with no MAC errors, and will
        increment octet and packet counts in the table for all packets
        with no MAC errors.  Further, entries will only be added to
        this table if their address pair exists in the nlMatrixSDTable
        and will be deleted from this table if the address pair is
        deleted from the nlMatrixSDTable."
    ::= { alMatrix 1 }

alMatrixSDEntry OBJECT-TYPE
    SYNTAX      AlMatrixSDEntry
    MAX-ACCESS  not-accessible
    STATUS      current
    DESCRIPTION
        "A conceptual row in the alMatrixSDTable.

        The hlMatrixControlIndex value in the index identifies the
        hlMatrixControlEntry on whose behalf this entry was created.
        The first protocolDirLocalIndex value in the index identifies
        the network layer protocol of the nlMatrixSDSourceAddress and
        nlMatrixSDDestAddress.
        The nlMatrixSDSourceAddress value in the index identifies the
        network layer address of the source host in this conversation.
        The nlMatrixSDDestAddress value in the index identifies the
        network layer address of the destination host in this
        conversation.
        The second protocolDirLocalIndex value in the index identifies
        the protocol that is counted by this entry.

        An example of the indexing of this entry is
        alMatrixSDPkts.1.783495.18.4.128.2.6.6.4.128.2.6.7.34"
    INDEX { hlMatrixControlIndex, alMatrixSDTimeMark,
            protocolDirLocalIndex,
            nlMatrixSDSourceAddress, nlMatrixSDDestAddress,
            protocolDirLocalIndex }
    ::= { alMatrixSDTable 1 }


AlMatrixSDEntry ::= SEQUENCE {
    alMatrixSDTimeMark                 TimeFilter,
    alMatrixSDPkts                     ZeroBasedCounter32,
    alMatrixSDOctets                   ZeroBasedCounter32,
    alMatrixSDCreateTime               TimeStamp
}

alMatrixSDTimeMark OBJECT-TYPE
    SYNTAX      TimeFilter
    MAX-ACCESS  not-accessible
    STATUS      current
    DESCRIPTION
        "A TimeFilter for this entry.  See the TimeFilter textual
        convention to see how this works."
    ::= { alMatrixSDEntry 1 }

alMatrixSDPkts OBJECT-TYPE
    SYNTAX      ZeroBasedCounter32
    MAX-ACCESS  read-only
    STATUS      current
    DESCRIPTION
        "The number of packets of this protocol type without errors
        transmitted from the source address to the destination address
        since this entry was added to the alMatrixSDTable.  Note that
        this is the number of link-layer packets, so if a single
        network-layer packet is fragmented into several link-layer
        frames, this counter is incremented several times."
    ::= { alMatrixSDEntry 2 }

alMatrixSDOctets OBJECT-TYPE
    SYNTAX      ZeroBasedCounter32
    MAX-ACCESS  read-only
    STATUS      current
    DESCRIPTION
        "The number of octets in packets of this protocol type
        transmitted from the source address to the destination address
        since this entry was added to the alMatrixSDTable (excluding
        framing bits but including FCS octets), excluding those octets
        in packets that contained errors.

        Note this doesn't count just those octets in the particular
        protocol frames, but includes the entire packet that contained
        the protocol."
    ::= { alMatrixSDEntry 3 }

alMatrixSDCreateTime OBJECT-TYPE
    SYNTAX     TimeStamp
    MAX-ACCESS read-only


    STATUS     current
    DESCRIPTION
        "The value of sysUpTime when this entry was last activated.
        This can be used by the management station to ensure that the
        entry has not been deleted and recreated between polls."
    ::= { alMatrixSDEntry 4 }

-- Traffic matrix tables from destination to source

alMatrixDSTable OBJECT-TYPE
    SYNTAX      SEQUENCE OF AlMatrixDSEntry
    MAX-ACCESS  not-accessible
    STATUS      current
    DESCRIPTION
        "A list of application traffic matrix entries which collect
        statistics for conversations of a particular protocol between
        two network-level addresses.  This table is indexed first by
        the destination address and then by the source address to make
        it convenient to collect all statistics to a particular
        address.

        The probe will populate this table for all protocols in the
        protocol directory table whose value of
        protocolDirMatrixConfig is equal to supportedOn(3), and
        will delete any entries whose protocolDirEntry is deleted or
        has a protocolDirMatrixConfig value of supportedOff(2).

        The probe will add to this table all pairs of addresses for
        all protocols seen in all packets with no MAC errors, and will
        increment octet and packet counts in the table for all packets
        with no MAC errors.  Further, entries will only be added to
        this table if their address pair exists in the nlMatrixDSTable
        and will be deleted from this table if the address pair is
        deleted from the nlMatrixDSTable."
    ::= { alMatrix 2 }

alMatrixDSEntry OBJECT-TYPE
    SYNTAX      AlMatrixDSEntry
    MAX-ACCESS  not-accessible
    STATUS      current
    DESCRIPTION
        "A conceptual row in the alMatrixDSTable.

        The hlMatrixControlIndex value in the index identifies the
        hlMatrixControlEntry on whose behalf this entry was created.
        The first protocolDirLocalIndex value in the index identifies
        the network layer protocol of the alMatrixDSSourceAddress and
        alMatrixDSDestAddress.


        The nlMatrixDSDestAddress value in the index identifies the
        network layer address of the destination host in this
        conversation.
        The nlMatrixDSSourceAddress value in the index identifies the
        network layer address of the source host in this conversation.
        The second protocolDirLocalIndex value in the index identifies
        the protocol that is counted by this entry.

        An example of the indexing of this entry is
        alMatrixDSPkts.1.783495.18.4.128.2.6.7.4.128.2.6.6.34"
    INDEX { hlMatrixControlIndex, alMatrixDSTimeMark,
            protocolDirLocalIndex,
            nlMatrixDSDestAddress, nlMatrixDSSourceAddress,
            protocolDirLocalIndex }
    ::= { alMatrixDSTable 1 }

AlMatrixDSEntry ::= SEQUENCE {
    alMatrixDSTimeMark                 TimeFilter,
    alMatrixDSPkts                     ZeroBasedCounter32,
    alMatrixDSOctets                   ZeroBasedCounter32,
    alMatrixDSCreateTime               TimeStamp
}

alMatrixDSTimeMark OBJECT-TYPE
    SYNTAX      TimeFilter
    MAX-ACCESS  not-accessible
    STATUS      current
    DESCRIPTION
        "A TimeFilter for this entry.  See the TimeFilter textual
        convention to see how this works."
    ::= { alMatrixDSEntry 1 }

alMatrixDSPkts OBJECT-TYPE
    SYNTAX      ZeroBasedCounter32
    MAX-ACCESS  read-only
    STATUS      current
    DESCRIPTION
        "The number of packets of this protocol type without errors
        transmitted from the source address to the destination address
        since this entry was added to the alMatrixDSTable.  Note that
        this is the number of link-layer packets, so if a single
        network-layer packet is fragmented into several link-layer
        frames, this counter is incremented several times."
    ::= { alMatrixDSEntry 2 }

alMatrixDSOctets OBJECT-TYPE
    SYNTAX      ZeroBasedCounter32
    MAX-ACCESS  read-only


    STATUS      current
    DESCRIPTION
        "The number of octets in packets of this protocol type
        transmitted from the source address to the destination address
        since this entry was added to the alMatrixDSTable (excluding
        framing bits but including FCS octets), excluding those octets
        in packets that contained errors.

        Note this doesn't count just those octets in the particular
        protocol frames, but includes the entire packet that contained
        the protocol."
    ::= { alMatrixDSEntry 3 }

alMatrixDSCreateTime OBJECT-TYPE
    SYNTAX     TimeStamp
    MAX-ACCESS read-only
    STATUS     current
    DESCRIPTION
        "The value of sysUpTime when this entry was last activated.
        This can be used by the management station to ensure that the
        entry has not been deleted and recreated between polls."
    ::= { alMatrixDSEntry 4 }

alMatrixTopNControlTable OBJECT-TYPE
    SYNTAX      SEQUENCE OF AlMatrixTopNControlEntry
    MAX-ACCESS  not-accessible
    STATUS      current
    DESCRIPTION
        "A set of parameters that control the creation of a
        report of the top N matrix entries according to
        a selected metric."
    ::= { alMatrix 3 }

alMatrixTopNControlEntry OBJECT-TYPE
    SYNTAX      AlMatrixTopNControlEntry
    MAX-ACCESS  not-accessible
    STATUS      current
    DESCRIPTION
        "A conceptual row in the alMatrixTopNControlTable.

        An example of the indexing of this table is
        alMatrixTopNControlDuration.3"
    INDEX { alMatrixTopNControlIndex }
    ::= { alMatrixTopNControlTable 1 }

AlMatrixTopNControlEntry ::= SEQUENCE {
    alMatrixTopNControlIndex            Integer32,
    alMatrixTopNControlMatrixIndex      Integer32,


    alMatrixTopNControlRateBase         INTEGER,
    alMatrixTopNControlTimeRemaining    Integer32,
    alMatrixTopNControlGeneratedReports Counter32,
    alMatrixTopNControlDuration         Integer32,
    alMatrixTopNControlRequestedSize    Integer32,
    alMatrixTopNControlGrantedSize      Integer32,
    alMatrixTopNControlStartTime        TimeStamp,
    alMatrixTopNControlOwner            OwnerString,
    alMatrixTopNControlStatus           RowStatus
}

alMatrixTopNControlIndex OBJECT-TYPE
    SYNTAX     Integer32 (1..65535)
    MAX-ACCESS not-accessible
    STATUS     current
    DESCRIPTION
        "An index that uniquely identifies an entry
        in the alMatrixTopNControlTable.  Each such
        entry defines one top N report prepared for
        one interface."
    ::= { alMatrixTopNControlEntry 1 }

alMatrixTopNControlMatrixIndex OBJECT-TYPE
    SYNTAX     Integer32 (1..65535)
    MAX-ACCESS read-create
    STATUS     current
    DESCRIPTION
        "The alMatrix[SD/DS] table for which a top N report will be
        prepared on behalf of this entry.  The alMatrix[SD/DS] table
        is identified by the value of the hlMatrixControlIndex
        for that table - that value is used here to identify the
        particular table.

        This object may not be modified if the associated
        alMatrixTopNControlStatus object is equal to active(1)."
    ::= { alMatrixTopNControlEntry 2 }

alMatrixTopNControlRateBase OBJECT-TYPE
    SYNTAX     INTEGER {
                  alMatrixTopNTerminalsPkts(1),
                  alMatrixTopNTerminalsOctets(2),
                  alMatrixTopNAllPkts(3),
                  alMatrixTopNAllOctets(4)
               }
    MAX-ACCESS read-create
    STATUS     current
    DESCRIPTION
        "The variable for each alMatrix[SD/DS] entry that the


        alMatrixTopNEntries are sorted by, as well as the
        selector of the view of the matrix table that will be
        used.

        The values alMatrixTopNTerminalsPkts and
        alMatrixTopNTerminalsOctets cause collection only from
        protocols that have no child protocols that are counted.  The
        values alMatrixTopNAllPkts and alMatrixTopNAllOctets cause
        collection from all alMatrix entries.

        This object may not be modified if the associated
        alMatrixTopNControlStatus object is equal to active(1)."
    ::= { alMatrixTopNControlEntry 3 }

alMatrixTopNControlTimeRemaining OBJECT-TYPE
    SYNTAX     Integer32 (0..2147483647)
    MAX-ACCESS read-create
    STATUS     current
    DESCRIPTION
        "The number of seconds left in the report currently
        being collected.  When this object is modified by
        the management station, a new collection is started,
        possibly aborting a currently running report.  The
        new value is used as the requested duration of this
        report, and is immediately loaded into the associated
        alMatrixTopNControlDuration object.
        When the report finishes, the probe will automatically
        start another collection with the same initial value
        of alMatrixTopNControlTimeRemaining.  Thus the management
        station may simply read the resulting reports repeatedly,
        checking the startTime and duration each time to ensure that a
        report was not missed or that the report parameters were not
        changed.

        While the value of this object is non-zero, it decrements
        by one per second until it reaches zero.  At the time
        that this object decrements to zero, the report is made
        accessible in the alMatrixTopNTable, overwriting any report
        that may be there.

        When this object is modified by the management station, any
        associated entries in the alMatrixTopNTable shall be deleted.

        (Note that this is a different algorithm than the one used in
        the hostTopNTable)."
    DEFVAL { 1800 }
    ::= { alMatrixTopNControlEntry 4 }


alMatrixTopNControlGeneratedReports OBJECT-TYPE
    SYNTAX     Counter32
    MAX-ACCESS read-only
    STATUS     current
    DESCRIPTION
        "The number of reports that have been generated by this entry."
    ::= { alMatrixTopNControlEntry 5 }

alMatrixTopNControlDuration OBJECT-TYPE
    SYNTAX     Integer32
    MAX-ACCESS read-only
    STATUS     current
    DESCRIPTION
        "The number of seconds that this report has collected
        during the last sampling interval.

        When the associated alMatrixTopNControlTimeRemaining object
        is set, this object shall be set by the probe to the
        same value and shall not be modified until the next
        time the alMatrixTopNControlTimeRemaining is set.

        This value shall be zero if no reports have been
        requested for this alMatrixTopNControlEntry."
    ::= { alMatrixTopNControlEntry 6 }

alMatrixTopNControlRequestedSize OBJECT-TYPE
    SYNTAX     Integer32 (0..2147483647)
    MAX-ACCESS read-create
    STATUS     current
    DESCRIPTION
        "The maximum number of matrix entries requested for this report.

        When this object is created or modified, the probe
        should set alMatrixTopNControlGrantedSize as closely to this
        object as is possible for the particular probe
        implementation and available resources."
    DEFVAL { 150 }
    ::= { alMatrixTopNControlEntry 7 }

alMatrixTopNControlGrantedSize OBJECT-TYPE
    SYNTAX     Integer32 (0..2147483647)
    MAX-ACCESS read-only
    STATUS     current
    DESCRIPTION
        "The maximum number of matrix entries in this report.

        When the associated alMatrixTopNControlRequestedSize object
        is created or modified, the probe should set this


        object as closely to the requested value as is
        possible for the particular implementation and
        available resources. The probe must not lower this
        value except as a result of a set to the associated
        alMatrixTopNControlRequestedSize object.

        If the value of alMatrixTopNControlRateBase is equal to
        alMatrixTopNTerminalsPkts or alMatrixTopNAllPkts, when the
        next topN report is generated, matrix entries with the highest
        value of alMatrixTopNPktRate shall be placed in this table in
        decreasing order of this rate until there is no more room or
        until there are no more matrix entries.

        If the value of alMatrixTopNControlRateBase is equal to
        alMatrixTopNTerminalsOctets or alMatrixTopNAllOctets, when the
        next topN report is generated, matrix entries with the highest
        value of alMatrixTopNOctetRate shall be placed in this table
        in decreasing order of this rate until there is no more room
        or until there are no more matrix entries.

        It is an implementation-specific matter how entries with the
        same value of alMatrixTopNPktRate or alMatrixTopNOctetRate are
        sorted.  It is also an implementation-specific matter as to
        whether or not zero-valued entries are available."
    ::= { alMatrixTopNControlEntry 8 }

alMatrixTopNControlStartTime OBJECT-TYPE
    SYNTAX     TimeStamp
    MAX-ACCESS read-only
    STATUS     current
    DESCRIPTION
        "The value of sysUpTime when this top N report was
        last started.  In other words, this is the time that
        the associated alMatrixTopNControlTimeRemaining object
        was modified to start the requested report or the time
        the report was last automatically (re)started.

        This object may be used by the management station to
        determine if a report was missed or not."
    ::= { alMatrixTopNControlEntry 9 }

alMatrixTopNControlOwner OBJECT-TYPE
    SYNTAX     OwnerString
    MAX-ACCESS read-create
    STATUS     current
    DESCRIPTION
        "The entity that configured this entry and is
        therefore using the resources assigned to it."


    ::= { alMatrixTopNControlEntry 10 }

alMatrixTopNControlStatus OBJECT-TYPE
    SYNTAX     RowStatus
    MAX-ACCESS read-create
    STATUS     current
    DESCRIPTION
        "The status of this alMatrixTopNControlEntry.

        An entry may not exist in the active state unless all
        objects in the entry have an appropriate value.

        If this object is not equal to active(1), all
        associated entries in the alMatrixTopNTable shall be
        deleted by the agent."
    ::= { alMatrixTopNControlEntry 11 }

alMatrixTopNTable OBJECT-TYPE
    SYNTAX     SEQUENCE OF AlMatrixTopNEntry
    MAX-ACCESS not-accessible
    STATUS     current
    DESCRIPTION
        "A set of statistics for those application layer matrix
        entries that have counted the highest number of octets or
        packets."
    ::= { alMatrix 4 }

alMatrixTopNEntry OBJECT-TYPE
    SYNTAX     AlMatrixTopNEntry
    MAX-ACCESS not-accessible
    STATUS     current
    DESCRIPTION
        "A conceptual row in the alMatrixTopNTable.

        The alMatrixTopNControlIndex value in the index identifies
        the alMatrixTopNControlEntry on whose behalf this entry was
        created.

        An example of the indexing of this table is
        alMatrixTopNPktRate.3.10"
    INDEX { alMatrixTopNControlIndex, alMatrixTopNIndex }
    ::= { alMatrixTopNTable 1 }

AlMatrixTopNEntry ::= SEQUENCE {
    alMatrixTopNIndex                      Integer32,
    alMatrixTopNProtocolDirLocalIndex      Integer32,
    alMatrixTopNSourceAddress              OCTET STRING,
    alMatrixTopNDestAddress                OCTET STRING,


    alMatrixTopNAppProtocolDirLocalIndex   Integer32,
    alMatrixTopNPktRate                    Gauge32,
    alMatrixTopNReversePktRate             Gauge32,
    alMatrixTopNOctetRate                  Gauge32,
    alMatrixTopNReverseOctetRate           Gauge32
  }

alMatrixTopNIndex OBJECT-TYPE
    SYNTAX     Integer32 (1..65535)
    MAX-ACCESS not-accessible
    STATUS     current
    DESCRIPTION
        "An index that uniquely identifies an entry in
        the alMatrixTopNTable among those in the same report.
        This index is between 1 and N, where N is the
        number of entries in this report.

        If the value of alMatrixTopNControlRateBase is equal to
        alMatrixTopNTerminalsPkts or alMatrixTopNAllPkts, increasing
        values of alMatrixTopNIndex shall be assigned to entries with
        decreasing values of alMatrixTopNPktRate until index N is
        assigned or there are no more alMatrixTopNEntries.

        If the value of alMatrixTopNControlRateBase is equal to
        alMatrixTopNTerminalsOctets or alMatrixTopNAllOctets,
        increasing values of alMatrixTopNIndex shall be assigned to
        entries with decreasing values of alMatrixTopNOctetRate until
        index N is assigned or there are no more alMatrixTopNEntries."
    ::= { alMatrixTopNEntry 1 }

alMatrixTopNProtocolDirLocalIndex OBJECT-TYPE
    SYNTAX     Integer32 (1..2147483647)
    MAX-ACCESS read-only
    STATUS     current
    DESCRIPTION
        "The protocolDirLocalIndex of the network layer protocol of
        this entry's network address."
    ::= { alMatrixTopNEntry 2 }

alMatrixTopNSourceAddress OBJECT-TYPE
    SYNTAX     OCTET STRING
    MAX-ACCESS read-only
    STATUS     current
    DESCRIPTION
        "The network layer address of the source host in this
        conversation.
        This is represented as an octet string with
        specific semantics and length as identified


        by the associated alMatrixTopNProtocolDirLocalIndex.

        For example, if the alMatrixTopNProtocolDirLocalIndex
        indicates an encapsulation of ip, this object is encoded as a
        length octet of 4, followed by the 4 octets of the ip address,
        in network byte order."
    ::= { alMatrixTopNEntry 3 }

alMatrixTopNDestAddress OBJECT-TYPE
    SYNTAX     OCTET STRING
    MAX-ACCESS read-only
    STATUS     current
    DESCRIPTION
        "The network layer address of the destination host in this
        conversation.

        This is represented as an octet string with
        specific semantics and length as identified
        by the associated alMatrixTopNProtocolDirLocalIndex.

        For example, if the alMatrixTopNProtocolDirLocalIndex
        indicates an encapsulation of ip, this object is encoded as a
        length octet of 4, followed by the 4 octets of the ip address,
        in network byte order."
    ::= { alMatrixTopNEntry 4 }

alMatrixTopNAppProtocolDirLocalIndex OBJECT-TYPE
    SYNTAX     Integer32 (1..2147483647)
    MAX-ACCESS read-only
    STATUS     current
    DESCRIPTION
        "The type of the protocol counted by this matrix entry."
    ::= { alMatrixTopNEntry 5 }

alMatrixTopNPktRate OBJECT-TYPE
    SYNTAX     Gauge32
    MAX-ACCESS read-only
    STATUS     current
    DESCRIPTION
        "The number of packets seen of this protocol from the source
        host to the destination host during this sampling interval,
        counted using the rules for counting the alMatrixSDPkts
        object.

        If the value of alMatrixTopNControlRateBase is
        alMatrixTopNTerminalsPkts or alMatrixTopNAllPkts, this
        variable will be used to sort this report."
    ::= { alMatrixTopNEntry 6 }


alMatrixTopNReversePktRate OBJECT-TYPE
    SYNTAX     Gauge32
    MAX-ACCESS read-only
    STATUS     current
    DESCRIPTION
        "The number of packets seen of this protocol from the
        destination host to the source host during this sampling
        interval, counted using the rules for counting the
        alMatrixDSPkts object  (note that the corresponding
        alMatrixSDPkts object selected is the one whose source address
        is equal to alMatrixTopNDestAddress and whose destination
        address is equal to alMatrixTopNSourceAddress.)

        Note that if the value of alMatrixTopNControlRateBase is equal
        to alMatrixTopNTerminalsPkts or alMatrixTopNAllPkts, the sort
        of topN entries is based entirely on alMatrixTopNPktRate, and
        not on the value of this object."
    ::= { alMatrixTopNEntry 7 }

alMatrixTopNOctetRate OBJECT-TYPE
    SYNTAX     Gauge32
    MAX-ACCESS read-only
    STATUS     current
    DESCRIPTION
        "The number of octets seen of this protocol from the source
        host to the destination host during this sampling interval,
        counted using the rules for counting the alMatrixSDOctets
        object.

        If the value of alMatrixTopNControlRateBase is
        alMatrixTopNTerminalsOctets or alMatrixTopNAllOctets, this
        variable will be used to sort this report."
    ::= { alMatrixTopNEntry 8 }

alMatrixTopNReverseOctetRate OBJECT-TYPE
    SYNTAX     Gauge32
    MAX-ACCESS read-only
    STATUS     current
    DESCRIPTION
        "The number of octets seen of this protocol from the
        destination host to the source host during this sampling
        interval, counted using the rules for counting the
        alMatrixDSOctets object  (note that the corresponding
        alMatrixSDOctets object selected is the one whose source
        address is equal to alMatrixTopNDestAddress and whose
        destination address is equal to alMatrixTopNSourceAddress.)

        Note that if the value of alMatrixTopNControlRateBase is equal


        to alMatrixTopNTerminalsOctets or alMatrixTopNAllOctets, the
        sort of topN entries is based entirely on
        alMatrixTopNOctetRate, and not on the value of this object."
    ::= { alMatrixTopNEntry 9 }

--
-- User History Collection Group (usrHistory)
--
-- The usrHistory group combines mechanisms seen in the alarm and
-- history groups to provide user-specified history collection,
-- utilizing two additional control tables and one additional data
-- table. This function has traditionally been done by NMS
-- applications, via periodic polling.  The usrHistory group allows
-- this task to be offloaded to an RMON probe.
--
-- Data (an ASN.1 INTEGER based object) is collected in the same
-- manner as any history data table (e.g. etherHistoryTable) except
-- that the user specifies the MIB instances to be collected. Objects
-- are collected in bucket-groups, with the intent that all MIB
-- instances in the same bucket-group are collected as atomically as
-- possible by the RMON probe.
--
-- The usrHistoryControlTable is a one-dimensional read-create table.
-- Each row configures a collection of user history buckets, much
-- the same as a historyControlEntry, except that the creation of a
-- row in this table will cause one or more associated instances in
-- the usrHistoryObjectTable to be created. The user specifies the
-- number of bucket elements (rows in the usrHistoryObjectTable)
-- requested, as well as the number of buckets requested.
--
-- The usrHistoryObjectTable is a 2-d read-write table.
-- Each row configures a single MIB instance to be collected.
-- All rows with the same major index constitute a bucket-group.
--
-- The usrHistoryTable is a 3-d read-only table containing
-- the data of associated usrHistoryControlEntries. Each
-- entry represents the value of a single MIB instance
-- during a specific sampling interval (or the rate of
-- change during the interval).
--
-- A sample value is stored in two objects - an absolute value and
-- a status object. This allows numbers from -(2G-1) to +4G to be
-- stored.  The status object also indicates whether a sample is
-- valid. This allows data collection to continue if periodic
-- retrieval of a particular instance fails for any reason.
--
-- Row Creation Order Relationships
--


-- The static nature of the usrHistoryObjectTable creates
-- some row creation/modification issues. The rows in this
-- table need to be set before the associated
-- usrHistoryControlEntry can be activated.
--
-- Note that the usrHistoryObject entries associated with a
-- particular usrHistoryControlEntry are not required to
-- be active before the control entry is activated. However,
-- the usrHistory data entries associated with an inactive
-- usrHistoryObject entry will be inactive (i.e.
-- usrHistoryValStatus == valueNotAvailable).
--

usrHistoryControlTable OBJECT-TYPE
    SYNTAX SEQUENCE OF UsrHistoryControlEntry
    MAX-ACCESS not-accessible
    STATUS current
    DESCRIPTION
        "A list of data-collection configuration entries."
    ::= { usrHistory 1 }

usrHistoryControlEntry OBJECT-TYPE
    SYNTAX UsrHistoryControlEntry
    MAX-ACCESS not-accessible
    STATUS current
    DESCRIPTION
        "A list of parameters that set up a group of user-defined
        MIB objects to be sampled periodically (called a
        bucket-group).

        For example, an instance of usrHistoryControlInterval
        might be named usrHistoryControlInterval.1"
    INDEX { usrHistoryControlIndex }
    ::= { usrHistoryControlTable 1 }

UsrHistoryControlEntry ::= SEQUENCE {
    usrHistoryControlIndex             Integer32,
    usrHistoryControlObjects           Integer32,
    usrHistoryControlBucketsRequested  Integer32,
    usrHistoryControlBucketsGranted    Integer32,
    usrHistoryControlInterval          Integer32,
    usrHistoryControlOwner             OwnerString,
    usrHistoryControlStatus            RowStatus
}

usrHistoryControlIndex OBJECT-TYPE
    SYNTAX Integer32 (1..65535)
    MAX-ACCESS not-accessible


    STATUS current
    DESCRIPTION
        "An index that uniquely identifies an entry in the
        usrHistoryControlTable.  Each such entry defines a
        set of samples at a particular interval for a specified
        set of MIB instances available from the managed system."
    ::= { usrHistoryControlEntry 1 }

usrHistoryControlObjects OBJECT-TYPE
    SYNTAX Integer32 (1..65535)
    MAX-ACCESS read-create
    STATUS current
    DESCRIPTION
        "The number of MIB objects to be collected
        in the portion of usrHistoryTable associated with this
        usrHistoryControlEntry.

        This object may not be modified if the associated instance
        of usrHistoryControlStatus is equal to active(1)."
    ::= { usrHistoryControlEntry 2 }

usrHistoryControlBucketsRequested OBJECT-TYPE
    SYNTAX Integer32 (1..65535)
    MAX-ACCESS read-create
    STATUS current
    DESCRIPTION
        "The requested number of discrete time intervals
        over which data is to be saved in the part of the
        usrHistoryTable associated with this usrHistoryControlEntry.

        When this object is created or modified, the probe
        should set usrHistoryControlBucketsGranted as closely to
        this object as is possible for the particular probe
        implementation and available resources."
    DEFVAL { 50 }
    ::= { usrHistoryControlEntry 3 }

usrHistoryControlBucketsGranted OBJECT-TYPE
    SYNTAX Integer32 (1..65535)
    MAX-ACCESS read-only
    STATUS current
    DESCRIPTION
        "The number of discrete sampling intervals
        over which data shall be saved in the part of
        the usrHistoryTable associated with this
        usrHistoryControlEntry.

        When the associated usrHistoryControlBucketsRequested


        object is created or modified, the probe should set
        this object as closely to the requested value as is
        possible for the particular  probe implementation and
        available resources.  The probe must not lower this
        value except as a result of a modification to the associated
        usrHistoryControlBucketsRequested object.

        The associated usrHistoryControlBucketsRequested object
        should be set before or at the same time as this object
        to allow the probe to accurately estimate the resources
        required for this usrHistoryControlEntry.

        There will be times when the actual number of buckets
        associated with this entry is less than the value of
        this object.  In this case, at the end of each sampling
        interval, a new bucket will be added to the usrHistoryTable.

        When the number of buckets reaches the value of this object
        and a new bucket is to be added to the usrHistoryTable,
        the oldest bucket associated with this usrHistoryControlEntry
        shall be deleted by the agent so that the new bucket can be
        added.

        When the value of this object changes to a value less than
        the current value, entries are deleted from the
        usrHistoryTable associated with this usrHistoryControlEntry.
        Enough of the oldest of these entries shall be deleted by the
        agent so that their number remains less than or equal to the
        new value of this object.

        When the value of this object changes to a value greater
        than the current value, the number of associated usrHistory
        entries may be allowed to grow."
    ::= { usrHistoryControlEntry 4 }

usrHistoryControlInterval OBJECT-TYPE
    SYNTAX Integer32 (1..2147483647)
    MAX-ACCESS read-create
    STATUS current
    DESCRIPTION
        "The interval in seconds over which the data is
        sampled for each bucket in the part of the usrHistory
        table associated with this usrHistoryControlEntry.

        Because the counters in a bucket may overflow at their
        maximum value with no indication, a prudent manager will
        take into account the possibility of overflow in any of


        the associated counters. It is important to consider the
        minimum time in which any counter could overflow on a
        particular media type and set the usrHistoryControlInterval
        object to a value less than this interval.

        This object may not be modified if the associated
        usrHistoryControlStatus object is equal to active(1)."
    DEFVAL { 1800 }
    ::= { usrHistoryControlEntry 5 }

usrHistoryControlOwner OBJECT-TYPE
    SYNTAX OwnerString
    MAX-ACCESS read-create
    STATUS current
    DESCRIPTION
        "The entity that configured this entry and is
        therefore using the resources assigned to it."
    ::= { usrHistoryControlEntry 6 }

usrHistoryControlStatus OBJECT-TYPE
    SYNTAX RowStatus
    MAX-ACCESS read-create
    STATUS current
    DESCRIPTION
        "The status of this variable history control entry.

        An entry may not exist in the active state unless all
        objects in the entry have an appropriate value.

        If this object is not equal to active(1), all associated
        entries in the usrHistoryTable shall be deleted."
    ::= { usrHistoryControlEntry 7 }

-- Object table

usrHistoryObjectTable OBJECT-TYPE
    SYNTAX SEQUENCE OF UsrHistoryObjectEntry
    MAX-ACCESS not-accessible
    STATUS current
    DESCRIPTION
        "A list of data-collection configuration entries."
    ::= { usrHistory 2 }

usrHistoryObjectEntry OBJECT-TYPE
    SYNTAX UsrHistoryObjectEntry
    MAX-ACCESS not-accessible
    STATUS current
    DESCRIPTION


        "A list of MIB instances to be sampled periodically.

        Entries in this table are created when an associated
        usrHistoryControlObjects object is created.

        The usrHistoryControlIndex value in the index is
        that of the associated usrHistoryControlEntry.

        For example, an instance of usrHistoryObjectVariable might be
        usrHistoryObjectVariable.1.3"
    INDEX { usrHistoryControlIndex, usrHistoryObjectIndex }
    ::= { usrHistoryObjectTable 1 }

UsrHistoryObjectEntry ::= SEQUENCE {
    usrHistoryObjectIndex             Integer32,
    usrHistoryObjectVariable          OBJECT IDENTIFIER,
    usrHistoryObjectSampleType        INTEGER
}

usrHistoryObjectIndex OBJECT-TYPE
    SYNTAX Integer32 (1..65535)
    MAX-ACCESS not-accessible
    STATUS current
    DESCRIPTION
        "An index used to uniquely identify an entry in the
        usrHistoryObject table.  Each such entry defines a
        MIB instance to be collected periodically."
    ::= { usrHistoryObjectEntry 1 }

usrHistoryObjectVariable OBJECT-TYPE
    SYNTAX OBJECT IDENTIFIER
    MAX-ACCESS read-create
    STATUS current
    DESCRIPTION
        "The object identifier of the particular variable to be
        sampled.

        Only variables that resolve to an ASN.1 primitive type of
        Integer32 (Integer32, Counter, Gauge, or TimeTicks) may be
        sampled.

        Because SNMP access control is articulated entirely in terms
        of the contents of MIB views, no access control mechanism
        exists that can restrict the value of this object to identify
        only those objects that exist in a particular MIB view.
        Because there is thus no acceptable means of restricting the
        read access that could be obtained through the user history


        mechanism, the probe must only grant write access to this
        object in those views that have read access to all objects on
        the probe.

        During a set operation, if the supplied variable name is not
        available in the selected MIB view, a badValue error must be
        returned.

        This object may not be modified if the associated
        usrHistoryControlStatus object is equal to active(1)."
    ::= { usrHistoryObjectEntry 2 }

usrHistoryObjectSampleType OBJECT-TYPE
    SYNTAX INTEGER {
               absoluteValue(1),
               deltaValue(2)
           }
    MAX-ACCESS read-create
    STATUS current
    DESCRIPTION
        "The method of sampling the selected variable for storage in
        the usrHistoryTable.

        If the value of this object is absoluteValue(1), the value of
        the selected variable will be copied directly into the history
        bucket.

        If the value of this object is deltaValue(2), the value of the
        selected variable at the last sample will be subtracted from
        the current value, and the difference will be stored in the
        history bucket. If the associated usrHistoryObjectVariable
        instance could not be obtained at the previous sample
        interval, then a delta sample is not possible, and the value
        of the associated usrHistoryValStatus object for this interval
        will be valueNotAvailable(1).

        This object may not be modified if the associated
        usrHistoryControlStatus object is equal to active(1)."
    ::= { usrHistoryObjectEntry 3 }

-- data table

usrHistoryTable OBJECT-TYPE
    SYNTAX SEQUENCE OF UsrHistoryEntry
    MAX-ACCESS not-accessible
    STATUS current
    DESCRIPTION
        "A list of user defined history entries."


    ::= { usrHistory 3 }

usrHistoryEntry OBJECT-TYPE
    SYNTAX UsrHistoryEntry
    MAX-ACCESS not-accessible
    STATUS current
    DESCRIPTION
        "A historical sample of user-defined variables.  This sample
        is associated with the usrHistoryControlEntry which set up the
        parameters for a regular collection of these samples.

        The usrHistoryControlIndex value in the index identifies the
        usrHistoryControlEntry on whose behalf this entry was created.

        The usrHistoryObjectIndex value in the index identifies the
        usrHistoryObjectEntry on whose behalf this entry was created.

        For example, an instance of usrHistoryAbsValue, which represents
        the 14th sample of a variable collected as specified by
        usrHistoryControlEntry.1 and usrHistoryObjectEntry.1.5,
        would be named usrHistoryAbsValue.1.14.5"
    INDEX { usrHistoryControlIndex, usrHistorySampleIndex,
            usrHistoryObjectIndex }
    ::= { usrHistoryTable 1 }

UsrHistoryEntry ::= SEQUENCE {
    usrHistorySampleIndex   Integer32,
    usrHistoryIntervalStart TimeStamp,
    usrHistoryIntervalEnd   TimeStamp,
    usrHistoryAbsValue      Gauge32,
    usrHistoryValStatus     INTEGER
}

usrHistorySampleIndex OBJECT-TYPE
    SYNTAX     Integer32 (1..2147483647)
    MAX-ACCESS not-accessible
    STATUS     current
    DESCRIPTION
        "An index that uniquely identifies the particular sample this
        entry represents among all samples associated with the same
        usrHistoryControlEntry. This index starts at 1 and increases
        by one as each new sample is taken."
    ::= { usrHistoryEntry 1 }

usrHistoryIntervalStart OBJECT-TYPE
    SYNTAX TimeStamp
    MAX-ACCESS read-only
    STATUS current


    DESCRIPTION
        "The value of sysUpTime at the start of the interval over
        which this sample was measured.  If the probe keeps track of
        the time of day, it should start the first sample of the
        history at a time such that when the next hour of the day
        begins, a sample is started at that instant.

        Note that following this rule may require the probe to delay
        collecting the first sample of the history, as each sample
        must be of the same interval. Also note that the sample which
        is currently being collected is not accessible in this table
        until the end of its interval."
    ::= { usrHistoryEntry 2 }

usrHistoryIntervalEnd OBJECT-TYPE
    SYNTAX TimeStamp
    MAX-ACCESS read-only
    STATUS current
    DESCRIPTION
        "The value of sysUpTime at the end of the interval over which
        this sample was measured."
    ::= { usrHistoryEntry 3 }

usrHistoryAbsValue OBJECT-TYPE
    SYNTAX Gauge32
    MAX-ACCESS read-only
    STATUS current
    DESCRIPTION
        "The absolute value (i.e. unsigned value) of the
        user-specified statistic during the last sampling period. The
        value during the current sampling period is not made available
        until the period is completed.

        To obtain the true value for this sampling interval, the
        associated instance of usrHistoryValStatus must be checked,
        and usrHistoryAbsValue adjusted as necessary.

        If the MIB instance could not be accessed during the sampling
        interval, then this object will have a value of zero and the
        associated instance of usrHistoryValStatus will be set to
        'valueNotAvailable(1)'."
    ::= { usrHistoryEntry 4 }

usrHistoryValStatus OBJECT-TYPE
    SYNTAX INTEGER {
        valueNotAvailable(1),
        valuePositive(2),


        valueNegative(3)
    }
    MAX-ACCESS read-only
    STATUS current
    DESCRIPTION
        "This object indicates the validity and sign of the data in
        the associated instance of usrHistoryAbsValue.

        If the MIB instance could not be accessed during the sampling
        interval, then 'valueNotAvailable(1)' will be returned.

        If the sample is valid and actual value of the sample is
        greater than or equal to zero then 'valuePositive(2)' is
        returned.

        If the sample is valid and the actual value of the sample is
        less than zero, 'valueNegative(3)' will be returned. The
        associated instance of usrHistoryAbsValue should be multiplied
        by -1 to obtain the true sample value."
    ::= { usrHistoryEntry 5 }

-- The Probe Configuration Group
--
-- This group controls the configuration of various operating
-- parameters of the probe.

ControlString ::= TEXTUAL-CONVENTION
    STATUS current
    DESCRIPTION
        "This data type is used to communicate with a modem or a
        serial data switch.  A ControlString contains embedded
        commands to control how the device will interact with the
        remote device through the serial interface.  Commands are
        represented as two character sequences beginning with
        the `^' character.

        The following commands are recognized by the device (note
        that command characters are case sensitive):

           ^s  Send string that follows which is terminated by the
               next command or the end of string.
           ^c  Delay for the number of seconds that follows.  Toss
               out any data received rather than storing it in a
               buffer for parsing.
           ^t  Set timeout to the value represented by the decimal
               digits that follow.  The default timeout is 20
               seconds. Note that this timeout may be overridden
               by a smaller serialTimeout configured for the


               associated serial interface (see serialConfigTable).
           ^w  Wait for the reply string that follows which is
               terminated by the next command or the end of string.
               Partial and case insensitive matching is applied, ie.
               if the reply string (any case combination) is found
               anywhere in the received string, then the a match is
               found.  If the current timeout elapses without a match,
               then the remaining control string is ignored.
           ^!  The ^ character.
           ^d  Delay the number of seconds specified by the decimal
               digits that follow.
           ^b  Send break for the number of milliseconds specified by
               the decimal digits that follow.  If no digits follow,
               break will be enforced for 250 milliseconds by default.

        The following ASCII control characters may be inserted into
        the `^s' send string or the `^w' reply string:

           ^@    0x00
           ^A    0x01
            ..
           ^M    0x0D
            ..
           ^Z    0x1A
           ^[    0x1B
           ^    0x1C
           ^]    0x1D
           ^^    0x1E
           ^_    0x1F

        Binary data may also be inserted into the data stream.  The
        control sequence for each byte of binary data is ^0x##, where
        ## is the hexadecimal representation of the data byte.  Two
        ASCII characters (0-9, a-f, A-F) must follow the `^0x'
        control prefix.  For example, `^0x0D^0x0A' is interpreted as a
        carriage return followed by a line feed."
    SYNTAX DisplayString

probeCapabilities OBJECT-TYPE
    SYNTAX BITS {
        etherStats(0),
        historyControl(1),
        etherHistory(2),
        alarm(3),
        hosts(4),
        hostTopN(5),
        matrix(6),
        filter(7),


        capture(8),
        event(9),
        tokenRingMLStats(10),
        tokenRingPStats(11),
        tokenRingMLHistory(12),
        tokenRingPHistory(13),
        ringStation(14),
        ringStationOrder(15),
        ringStationConfig(16),
        sourceRouting(17),
        protocolDirectory(18),
        protocolDistribution(19),
        addressMapping(20),
        nlHost(21),
        nlMatrix(22),
        alHost(23),
        alMatrix(24),
        usrHistory(25),
        probeConfig(26)
    }
    MAX-ACCESS read-only
    STATUS current
    DESCRIPTION
        "An indication of the RMON MIB groups supported
        on at least one interface by this probe."
    ::= { probeConfig 1 }

probeSoftwareRev  OBJECT-TYPE
    SYNTAX     DisplayString (SIZE(0..15))
    MAX-ACCESS read-only
    STATUS     current
    DESCRIPTION
        "The software revision of this device.  This string will have
        a zero length if the revision is unknown."
    ::= { probeConfig 2 }

probeHardwareRev  OBJECT-TYPE
    SYNTAX     DisplayString (SIZE(0..31))
    MAX-ACCESS read-only
    STATUS     current
    DESCRIPTION
        "The hardware revision of this device.  This string will have
        a zero length if the revision is unknown."
    ::= { probeConfig 3 }

probeDateTime  OBJECT-TYPE
    SYNTAX     OCTET STRING (SIZE (0 | 8 | 11))
    MAX-ACCESS read-write


    STATUS     current
    DESCRIPTION
        "Probe's current date and time.

         field  octets  contents                  range
         -----  ------  --------                  -----
           1      1-2   year                      0..65536
           2       3    month                     1..12
           3       4    day                       1..31
           4       5    hour                      0..23
           5       6    minutes                   0..59
           6       7    seconds                   0..60
                         (use 60 for leap-second)
           7       8    deci-seconds              0..9
           8       9    direction from UTC        '+' / '-'
           9      10    hours from UTC            0..11
          10      11    minutes from UTC          0..59

         For example, Tuesday May 26, 1992 at 1:30:15 PM
         EDT would be displayed as:

                     1992-5-26,13:30:15.0,-4:0

         Note that if only local time is known, then
         timezone information (fields 8-10) is not
         present, and if no time information is known, the null
         string is returned."
    ::= { probeConfig 4 }

probeResetControl  OBJECT-TYPE
    SYNTAX     INTEGER {
                    running(1),
                    warmBoot(2),
                    coldBoot(3)
              }
    MAX-ACCESS read-write
    STATUS     current
    DESCRIPTION
        "Setting this object to warmBoot(2) causes the device to
        restart the application software with current configuration
        parameters saved in non-volatile memory.  Setting this
        object to coldBoot(3) causes the device to reinitialize
        configuration parameters in non-volatile memory to default
        values and restart the application software.  When the device
        is running normally, this variable has a value of
        running(1)."
    ::= { probeConfig 5 }


-- The following download objects do not restrict an implementation
-- from implementing additional download mechanisms (controlled in an
-- implementation-specific manner).  Further, in the case where the RMON
-- agent shares a processor with other types of systems, the
-- implementation is not required to download those non-RMON functions
-- with this mechanism.

probeDownloadFile  OBJECT-TYPE
    SYNTAX     DisplayString (SIZE(0..127))
    MAX-ACCESS read-write
    STATUS     current
    DESCRIPTION
        "The file name to be downloaded from the TFTP server when a
        download is next requested via this MIB.  This value is set to
        the zero length string when no file name has been specified."
    ::= { probeConfig 6 }

probeDownloadTFTPServer  OBJECT-TYPE
    SYNTAX     IpAddress
    MAX-ACCESS read-write
    STATUS     current
    DESCRIPTION
        "The IP address of the TFTP server that contains the boot
        image to load when a download is next requested via this MIB.
        This value is set to `0.0.0.0' when no IP address has been
        specified."
    ::= { probeConfig 7 }

probeDownloadAction  OBJECT-TYPE
    SYNTAX     INTEGER {
                  notDownloading(1),
                  downloadToPROM(2),
                  downloadToRAM(3)
               }
    MAX-ACCESS read-write
    STATUS     current
    DESCRIPTION
        "When this object is set to downloadToRAM(2) or
        downloadToPROM(3), the device will discontinue its
        normal operation and begin download of the image specified
        by probeDownloadFile from the server specified by
        probeDownloadTFTPServer using the TFTP protocol.  If
        downloadToRAM(2) is specified, the new image is copied
        to RAM only (the old image remains unaltered in the flash
        EPROM).  If downloadToPROM(3) is specified
        the new image is written to the flash EPROM
        memory after its checksum has been verified to be correct.
        When the download process is completed, the device will


        warm boot to restart the newly loaded application.
        When the device is not downloading, this object will have
        a value of notDownloading(1)."
    ::= { probeConfig 8 }

probeDownloadStatus  OBJECT-TYPE
    SYNTAX     INTEGER {
                    downloadSuccess(1),
                    downloadStatusUnknown(2),
                    downloadGeneralError(3),
                    downloadNoResponseFromServer(4),
                    downloadChecksumError(5),
                    downloadIncompatibleImage(6),
                    downloadTftpFileNotFound(7),
                    downloadTftpAccessViolation(8)
               }
    MAX-ACCESS read-only
    STATUS     current
    DESCRIPTION
        "The status of the last download procedure, if any.  This
        object will have a value of downloadStatusUnknown(2) if no
        download process has been performed."
    ::= { probeConfig 9 }

serialConfigTable  OBJECT-TYPE
    SYNTAX     SEQUENCE OF SerialConfigEntry
    MAX-ACCESS not-accessible
    STATUS     current
    DESCRIPTION
        "A table of serial interface configuration entries.  This data
        will be stored in non-volatile memory and preserved across
        probe resets or power loss."
    ::= { probeConfig 10 }

serialConfigEntry  OBJECT-TYPE
    SYNTAX     SerialConfigEntry
    MAX-ACCESS not-accessible
    STATUS     current
    DESCRIPTION
        "A set of configuration parameters for a particular
        serial interface on this device. If the device has no serial
        interfaces, this table is empty.

        The index is composed of the ifIndex assigned to this serial
        line interface."
    INDEX  { ifIndex }
    ::= { serialConfigTable 1 }


SerialConfigEntry ::= SEQUENCE {
    serialMode                   INTEGER,
    serialProtocol               INTEGER,
    serialTimeout                Integer32 (1..65535),
    serialModemInitString        ControlString (SIZE (0..255)),
    serialModemHangUpString      ControlString (SIZE (0..255)),
    serialModemConnectResp       DisplayString (SIZE (0..255)),
    serialModemNoConnectResp     DisplayString (SIZE (0..255)),
    serialDialoutTimeout         Integer32 (1..65535),
    serialStatus                 RowStatus
}

serialMode  OBJECT-TYPE
    SYNTAX     INTEGER {
                   direct(1),
                   modem(2)
               }
    MAX-ACCESS read-create
    STATUS     current
    DESCRIPTION
        "The type of incoming connection to expect on this serial
        interface."
    DEFVAL { direct }
    ::= { serialConfigEntry 1 }

serialProtocol  OBJECT-TYPE
    SYNTAX     INTEGER {
                   other(1),
                   slip(2),
                   ppp(3)
               }
    MAX-ACCESS read-create
    STATUS     current
    DESCRIPTION
        "The type of data link encapsulation to be used on this
        serial interface."
    DEFVAL { slip }
    ::= { serialConfigEntry 2 }

serialTimeout  OBJECT-TYPE
    SYNTAX     Integer32 (1..65535)
    MAX-ACCESS read-create
    STATUS     current
    DESCRIPTION
        "This timeout value is used when the Management Station has
        initiated the conversation over the serial link. This variable
        represents the number of seconds of inactivity allowed before
        terminating the connection on this serial interface. Use the


        serialDialoutTimeout in the case where the probe has initiated
        the connection for the purpose of sending a trap."
    DEFVAL { 300 }
    ::= { serialConfigEntry 3 }

serialModemInitString  OBJECT-TYPE
    SYNTAX     ControlString (SIZE (0..255))
    MAX-ACCESS read-create
    STATUS     current
    DESCRIPTION
        "A control string which controls how a modem attached to this
        serial interface should be initialized.  The initialization
        is performed once during startup and again after each
        connection is terminated if the associated serialMode has the
        value of modem(2).

        A control string that is appropriate for a wide variety of
        modems is: '^s^MATE0Q0V1X4 S0=1 S2=43^M'."
    ::= { serialConfigEntry 4 }

serialModemHangUpString  OBJECT-TYPE
    SYNTAX     ControlString (SIZE (0..255))
    MAX-ACCESS read-create
    STATUS     current
    DESCRIPTION
        "A control string which specifies how to disconnect a modem
         connection on this serial interface.  This object is only
         meaningful if the associated serialMode has the value
         of modem(2).
         A control string that is appropriate for a wide variety of
         modems is: '^d2^s+++^d2^sATH0^M^d2'."
    ::= { serialConfigEntry 5 }

serialModemConnectResp  OBJECT-TYPE
    SYNTAX     DisplayString (SIZE (0..255))
    MAX-ACCESS read-create
    STATUS     current
    DESCRIPTION
        "An ASCII string containing substrings that describe the
        expected modem connection response code and associated bps
        rate.  The substrings are delimited by the first character
        in the string, for example:
           /CONNECT/300/CONNECT 1200/1200/CONNECT 2400/2400/
           CONNECT 4800/4800/CONNECT 9600/9600
        will be interpreted as:
            response code    bps rate
            CONNECT            300
            CONNECT 1200      1200


            CONNECT 2400      2400
            CONNECT 4800      4800
            CONNECT 9600      9600
        The agent will use the information in this string to adjust
        the bps rate of this serial interface once a modem connection
        is established.

        A value that is appropriate for a wide variety of modems is:
        '/CONNECT/300/CONNECT 1200/1200/CONNECT 2400/2400/
         CONNECT 4800/4800/CONNECT 9600/9600/CONNECT 14400/14400/
        CONNECT 19200/19200/CONNECT 38400/38400/'."
    ::= { serialConfigEntry 6 }

serialModemNoConnectResp  OBJECT-TYPE
    SYNTAX     DisplayString (SIZE (0..255))
    MAX-ACCESS read-create
    STATUS     current
    DESCRIPTION
        "An ASCII string containing response codes that may be
        generated by a modem to report the reason why a connection
        attempt has failed.  The response codes are delimited by
        the first character in the string, for example:
           /NO CARRIER/BUSY/NO DIALTONE/NO ANSWER/ERROR/
        If one of these response codes is received via this serial
        interface while attempting to make a modem connection,
        the agent will issue the hang up command as specified by
        serialModemHangUpString.

        A value that is appropriate for a wide variety of modems is:
        '/NO CARRIER/BUSY/NO DIALTONE/NO ANSWER/ERROR/'."
    ::= { serialConfigEntry 7 }

serialDialoutTimeout  OBJECT-TYPE
    SYNTAX     Integer32 (1..65535)
    MAX-ACCESS read-create
    STATUS     current
    DESCRIPTION
        "This timeout value is used when the probe initiates the
        serial connection with the intention of contacting a
        management station. This variable represents the number
        of seconds of inactivity allowed before terminating the
        connection on this serial interface."
    DEFVAL { 20 }
    ::= { serialConfigEntry 8 }

serialStatus  OBJECT-TYPE
    SYNTAX     RowStatus
    MAX-ACCESS read-create


    STATUS     current
    DESCRIPTION
        "The status of this serialConfigEntry.

        An entry may not exist in the active state unless all
        objects in the entry have an appropriate value."
    ::= { serialConfigEntry 9 }

netConfigTable  OBJECT-TYPE
    SYNTAX     SEQUENCE OF NetConfigEntry
    MAX-ACCESS not-accessible
    STATUS     current
    DESCRIPTION
        "A table of netConfigEntries."
    ::= { probeConfig 11 }

netConfigEntry  OBJECT-TYPE
    SYNTAX     NetConfigEntry
    MAX-ACCESS not-accessible
    STATUS     current
    DESCRIPTION
        "A set of configuration parameters for a particular
        network interface on this device. If the device has no network
        interface, this table is empty.

        The index is composed of the ifIndex assigned to the
        corresponding interface."
    INDEX  { ifIndex }
    ::= { netConfigTable 1 }

NetConfigEntry ::= SEQUENCE {
    netConfigIPAddress         IpAddress,
    netConfigSubnetMask        IpAddress,
    netConfigStatus            RowStatus
}

netConfigIPAddress  OBJECT-TYPE
    SYNTAX     IpAddress
    MAX-ACCESS read-create
    STATUS     current
    DESCRIPTION
        "The IP address of this Net interface.  The default value
        for this object is 0.0.0.0.  If either the netConfigIPAddress
        or netConfigSubnetMask are 0.0.0.0, then when the device
        boots, it may use BOOTP to try to figure out what these
        values should be. If BOOTP fails, before the device
        can talk on the network, this value must be configured
        (e.g., through a terminal attached to the device). If BOOTP is


        used, care should be taken to not send BOOTP broadcasts too
        frequently and to eventually send very infrequently if no
        replies are received."
    ::= { netConfigEntry 1 }

netConfigSubnetMask  OBJECT-TYPE
    SYNTAX     IpAddress
    MAX-ACCESS read-create
    STATUS     current
    DESCRIPTION
        "The subnet mask of this Net interface.  The default value
        for this object is 0.0.0.0.  If either the netConfigIPAddress
        or netConfigSubnetMask are 0.0.0.0, then when the device
        boots, it may use BOOTP to try to figure out what these
        values should be. If BOOTP fails, before the device
        can talk on the network, this value must be configured
        (e.g., through a terminal attached to the device). If BOOTP is
        used, care should be taken to not send BOOTP broadcasts too
        frequently and to eventually send very infrequently if no
        replies are received."
    ::= { netConfigEntry 2 }

netConfigStatus  OBJECT-TYPE
    SYNTAX     RowStatus
    MAX-ACCESS read-create
    STATUS     current
    DESCRIPTION
        "The status of this netConfigEntry.

        An entry may not exist in the active state unless all
        objects in the entry have an appropriate value."
    ::= { netConfigEntry 3 }

netDefaultGateway  OBJECT-TYPE
    SYNTAX     IpAddress
    MAX-ACCESS read-create
    STATUS     current
    DESCRIPTION
        "The IP Address of the default gateway.  If this value is
        undefined or unknown, it shall have the value 0.0.0.0."
    ::= { probeConfig 12 }

-- Trap Destination Table
--
-- This table defines the destination addresses for traps generated
-- from the device.  This table maps a community to one or more trap
-- destination entries.
--


-- The same trap will be sent to all destinations specified in the
-- entries that have the same trapDestCommunity as the eventCommunity
-- (as defined by RMON MIB).  Information in this table will be stored
-- in non-volatile memory.  If the device has gone through a hard
-- restart, this information will be reset to its default state.

trapDestTable  OBJECT-TYPE
    SYNTAX     SEQUENCE OF TrapDestEntry
    MAX-ACCESS not-accessible
    STATUS     current
    DESCRIPTION
        "A list of trap destination entries."
    ::= { probeConfig 13 }

trapDestEntry  OBJECT-TYPE
    SYNTAX     TrapDestEntry
    MAX-ACCESS not-accessible
    STATUS     current
    DESCRIPTION
        "This entry includes a destination IP address to which to send
        traps for this community."
    INDEX { trapDestIndex }
    ::= { trapDestTable 1 }

TrapDestEntry ::= SEQUENCE {
    trapDestIndex               Integer32,
    trapDestCommunity           OCTET STRING,
    trapDestProtocol            INTEGER,
    trapDestAddress             OCTET STRING,
    trapDestOwner               OwnerString,
    trapDestStatus              RowStatus
}

trapDestIndex  OBJECT-TYPE
    SYNTAX     Integer32 (1..65535)
    MAX-ACCESS not-accessible
    STATUS     current
    DESCRIPTION
        "A value that uniquely identifies this trapDestEntry."
    ::= { trapDestEntry 1 }

trapDestCommunity  OBJECT-TYPE
    SYNTAX     OCTET STRING (SIZE(0..127))
    MAX-ACCESS read-create
    STATUS     current
    DESCRIPTION
        "A community to which this destination address belongs.
        This entry is associated with any eventEntries in the RMON


        MIB whose value of eventCommunity is equal to the value of
        this object.  Every time an associated event entry sends a
        trap due to an event, that trap will be sent to each
        address in the trapDestTable with a trapDestCommunity equal to
        eventCommunity.

        This object may not be modified if the associated
        trapDestStatus object is equal to active(1)."
    ::= { trapDestEntry 2 }

trapDestProtocol OBJECT-TYPE
    SYNTAX     INTEGER {
                    ip(1),
                    ipx(2)
                }
    MAX-ACCESS read-create
    STATUS     current
    DESCRIPTION
        "The protocol with which to send this trap."
    ::= { trapDestEntry 3 }

trapDestAddress  OBJECT-TYPE
    SYNTAX     OCTET STRING
    MAX-ACCESS read-create
    STATUS     current
    DESCRIPTION
        "The address to send traps on behalf of this entry.

        If the associated trapDestProtocol object is equal to ip(1),
        the encoding of this object is the same as the snmpUDPAddress
        textual convention in [RFC1906]:
          -- for a SnmpUDPAddress of length 6:
          --
          -- octets   contents        encoding
          --  1-4     IP-address      network-byte order
          --  5-6     UDP-port        network-byte order

        If the associated trapDestProtocol object is equal to ipx(2),
        the encoding of this object is the same as the snmpIPXAddress
        textual convention in [RFC1906]:
          -- for a SnmpIPXAddress of length 12:
          --
          -- octets   contents            encoding
          --  1-4     network-number      network-byte order
          --  5-10    physical-address    network-byte order
          -- 11-12    socket-number       network-byte order

        This object may not be modified if the associated


        trapDestStatus object is equal to active(1)."
    ::= { trapDestEntry 4 }

trapDestOwner  OBJECT-TYPE
    SYNTAX     OwnerString
    MAX-ACCESS read-create
    STATUS     current
    DESCRIPTION
        "The entity that configured this entry and is
        therefore using the resources assigned to it."
    ::= { trapDestEntry 5 }

trapDestStatus  OBJECT-TYPE
    SYNTAX     RowStatus
    MAX-ACCESS read-create
    STATUS     current
    DESCRIPTION
        "The status of this trap destination entry.

        An entry may not exist in the active state unless all
        objects in the entry have an appropriate value."
    ::= { trapDestEntry 6 }

-- Serial Connection Table
--
-- The device may communicate with a management station using
-- SLIP.  In order for the device to send traps via SLIP, it must
-- be able to initiate a connection over the serial interface.  The
-- serialConnectionTable stores the parameters for such connection
-- initiation.

serialConnectionTable  OBJECT-TYPE
    SYNTAX     SEQUENCE OF SerialConnectionEntry
    MAX-ACCESS not-accessible
    STATUS     current
    DESCRIPTION
        "A list of serialConnectionEntries."
    ::= { probeConfig 14 }

serialConnectionEntry  OBJECT-TYPE
    SYNTAX     SerialConnectionEntry
    MAX-ACCESS not-accessible
    STATUS     current
    DESCRIPTION
        "Configuration for a SLIP link over a serial line."
    INDEX { serialConnectIndex }
    ::= { serialConnectionTable 1 }


SerialConnectionEntry ::= SEQUENCE {
    serialConnectIndex                   Integer32,
    serialConnectDestIpAddress           IpAddress,
    serialConnectType                    INTEGER,
    serialConnectDialString              ControlString,
    serialConnectSwitchConnectSeq        ControlString,
    serialConnectSwitchDisconnectSeq     ControlString,
    serialConnectSwitchResetSeq          ControlString,
    serialConnectOwner                   OwnerString,
    serialConnectStatus                  RowStatus
}

serialConnectIndex  OBJECT-TYPE
    SYNTAX     Integer32 (1..65535)
    MAX-ACCESS not-accessible
    STATUS     current
    DESCRIPTION
        "A value that uniquely identifies this serialConnection
        entry."
    ::= { serialConnectionEntry 1 }

serialConnectDestIpAddress  OBJECT-TYPE
    SYNTAX     IpAddress
    MAX-ACCESS read-create
    STATUS     current
    DESCRIPTION
        "The IP Address that can be reached at the other end of this
        serial connection.
        This object may not be modified if the associated
        serialConnectStatus object is equal to active(1)."
    ::= { serialConnectionEntry 2 }

serialConnectType  OBJECT-TYPE
    SYNTAX     INTEGER {
                    direct(1),
                    modem(2),
                    switch(3),
                    modemSwitch(4)
               }
    MAX-ACCESS read-create
    STATUS     current
    DESCRIPTION
        "The type of outgoing connection to make.  If this object
        has the value direct(1), then a direct serial connection
        is assumed.  If this object has the value modem(2),
        then serialConnectDialString will be used to make a modem
        connection.  If this object has the value switch(3),


        then serialConnectSwitchConnectSeq will be used to establish
        the connection over a serial data switch, and
        serialConnectSwitchDisconnectSeq will be used to terminate
        the connection.  If this object has the value
        modem-switch(4), then a modem connection will be made first
        followed by the switch connection.

        This object may not be modified if the associated
        serialConnectStatus object is equal to active(1)."

    DEFVAL { direct }
    ::= { serialConnectionEntry 3 }

serialConnectDialString  OBJECT-TYPE
    SYNTAX     ControlString (SIZE(0..255))
    MAX-ACCESS read-create
    STATUS     current
    DESCRIPTION
        "A control string which specifies how to dial the phone
        number in order to establish a modem connection.  The
        string should include dialing prefix and suffix.  For
        example: ``^s^MATD9,888-1234^M'' will instruct the Probe
        to send a carriage return followed by the dialing prefix
        ``ATD'', the phone number ``9,888-1234'', and a carriage
        return as the dialing suffix.
        This object may not be modified if the associated
        serialConnectStatus object is equal to active(1)."
    ::= { serialConnectionEntry 4 }

serialConnectSwitchConnectSeq  OBJECT-TYPE
    SYNTAX     ControlString (SIZE(0..255))
    MAX-ACCESS read-create
    STATUS     current
    DESCRIPTION
        "A control string which specifies how to establish a
        data switch connection.
        This object may not be modified if the associated
        serialConnectStatus object is equal to active(1)."
     ::= { serialConnectionEntry 5 }

serialConnectSwitchDisconnectSeq  OBJECT-TYPE
    SYNTAX     ControlString (SIZE(0..255))
    MAX-ACCESS read-create
    STATUS     current
    DESCRIPTION
        "A control string which specifies how to terminate a
        data switch connection.
        This object may not be modified if the associated


        serialConnectStatus object is equal to active(1)."
    ::= { serialConnectionEntry 6 }

serialConnectSwitchResetSeq  OBJECT-TYPE
    SYNTAX     ControlString (SIZE(0..255))
    MAX-ACCESS read-create
    STATUS     current
    DESCRIPTION
        "A control string which specifies how to reset a data
        switch in the event of a timeout.
        This object may not be modified if the associated
        serialConnectStatus object is equal to active(1)."
    ::= { serialConnectionEntry 7 }

serialConnectOwner  OBJECT-TYPE
    SYNTAX     OwnerString
    MAX-ACCESS read-create
    STATUS     current
    DESCRIPTION
        "The entity that configured this entry and is
        therefore using the resources assigned to it."
    ::= { serialConnectionEntry 8 }

serialConnectStatus  OBJECT-TYPE
    SYNTAX     RowStatus
    MAX-ACCESS read-create
    STATUS     current
    DESCRIPTION
        "The status of this serialConnectionEntry.

        If the manager attempts to set this object to active(1) when
        the serialConnectType is set to modem(2) or modem-switch(4)
        and the serialConnectDialString is a zero-length string or
        cannot be correctly parsed as a ConnectString, the set
        request will be rejected with badValue(3).

        If the manager attempts to set this object to active(1) when
        the serialConnectType is set to switch(3) or modem-switch(4)
        and the serialConnectSwitchConnectSeq,
        the serialConnectSwitchDisconnectSeq, or
        the serialConnectSwitchResetSeq are zero-length strings
        or cannot be correctly parsed as ConnectStrings, the set
        request will be rejected with badValue(3).

        An entry may not exist in the active state unless all
        objects in the entry have an appropriate value."
    ::= { serialConnectionEntry 9 }


--
-- Extensions to the RMON 1 MIB for RMON 2 devices
--
-- These extensions include the standard TimeStamp Textual
-- Convention for all control tables, as well as an augmentation of
-- the filter entry that provides variable-length offsets into
-- packets.

-- Each of the following, except for filterDroppedFrames, is a
-- read-only object which, if implemented, automatically appears when
-- the RMON1 row it is associated with is created.

etherStats2Table  OBJECT-TYPE
    SYNTAX     SEQUENCE OF EtherStats2Entry
    MAX-ACCESS not-accessible
    STATUS     current
    DESCRIPTION
        "Contains the RMON-2 augmentations to RMON-1."
    ::= { statistics 4 }

etherStats2Entry  OBJECT-TYPE
    SYNTAX     EtherStats2Entry
    MAX-ACCESS not-accessible
    STATUS     current
    DESCRIPTION
        "Contains the RMON-2 augmentations to RMON-1."
    AUGMENTS { etherStatsEntry }
    ::= { etherStats2Table 1 }

EtherStats2Entry ::= SEQUENCE {
    etherStatsDroppedFrames     Counter32,
    etherStatsCreateTime        TimeStamp
}

etherStatsDroppedFrames OBJECT-TYPE
    SYNTAX     Counter32
    MAX-ACCESS read-only
    STATUS     current
    DESCRIPTION
       "The total number of frames which were received by the probe
        and therefore not accounted for in the *StatsDropEvents, but
        for which the probe chose not to count for this entry for
        whatever reason.  Most often, this event occurs when the probe
        is out of some resources and decides to shed load from this
        collection.

        This count does not include packets that were not counted


        because they had MAC-layer errors.

        Note that, unlike the dropEvents counter, this number is the
        exact number of frames dropped."
    ::= { etherStats2Entry 1 }

etherStatsCreateTime OBJECT-TYPE
    SYNTAX     TimeStamp
    MAX-ACCESS read-only
    STATUS     current
    DESCRIPTION
        "The value of sysUpTime when this control entry was last
        activated. This can be used by the management station to
        ensure that the table has not been deleted and recreated
        between polls."
    ::= { etherStats2Entry 2 }

historyControl2Table  OBJECT-TYPE
    SYNTAX     SEQUENCE OF HistoryControl2Entry
    MAX-ACCESS not-accessible
    STATUS     current
    DESCRIPTION
        "Contains the RMON-2 augmentations to RMON-1."
    ::= { history 5 }

historyControl2Entry  OBJECT-TYPE
    SYNTAX     HistoryControl2Entry
    MAX-ACCESS not-accessible
    STATUS     current
    DESCRIPTION
        "Contains the RMON-2 augmentations to RMON-1."
    AUGMENTS { historyControlEntry }
    ::= { historyControl2Table 1 }

HistoryControl2Entry ::= SEQUENCE {
    historyControlDroppedFrames Counter32
}

historyControlDroppedFrames OBJECT-TYPE
    SYNTAX     Counter32
    MAX-ACCESS read-only
    STATUS     current
    DESCRIPTION
       "The total number of frames which were received by the probe
        and therefore not accounted for in the *StatsDropEvents, but
        for which the probe chose not to count for this entry for
        whatever reason.  Most often, this event occurs when the probe
        is out of some resources and decides to shed load from this


        collection.

        This count does not include packets that were not counted
        because they had MAC-layer errors.

        Note that, unlike the dropEvents counter, this number is the
        exact number of frames dropped."
    ::= { historyControl2Entry 1 }

hostControl2Table  OBJECT-TYPE
    SYNTAX     SEQUENCE OF HostControl2Entry
    MAX-ACCESS not-accessible
    STATUS     current
    DESCRIPTION
        "Contains the RMON-2 augmentations to RMON-1."
    ::= { hosts 4 }

hostControl2Entry  OBJECT-TYPE
    SYNTAX     HostControl2Entry
    MAX-ACCESS not-accessible
    STATUS     current
    DESCRIPTION
        "Contains the RMON-2 augmentations to RMON-1."
    AUGMENTS { hostControlEntry }
    ::= { hostControl2Table 1 }

HostControl2Entry ::= SEQUENCE {
    hostControlDroppedFrames    Counter32,
    hostControlCreateTime       TimeStamp
}

hostControlDroppedFrames OBJECT-TYPE
    SYNTAX     Counter32
    MAX-ACCESS read-only
    STATUS     current
    DESCRIPTION
       "The total number of frames which were received by the probe
        and therefore not accounted for in the *StatsDropEvents, but
        for which the probe chose not to count for this entry for
        whatever reason.  Most often, this event occurs when the probe
        is out of some resources and decides to shed load from this
        collection.

        This count does not include packets that were not counted
        because they had MAC-layer errors.

        Note that, unlike the dropEvents counter, this number is the
        exact number of frames dropped."


    ::= { hostControl2Entry 1 }

hostControlCreateTime OBJECT-TYPE
    SYNTAX     TimeStamp
    MAX-ACCESS read-only
    STATUS     current
    DESCRIPTION
        "The value of sysUpTime when this control entry was last
        activated. This can be used by the management station to
        ensure that the table has not been deleted and recreated
        between polls."
    ::= { hostControl2Entry 2 }

matrixControl2Table  OBJECT-TYPE
    SYNTAX     SEQUENCE OF MatrixControl2Entry
    MAX-ACCESS not-accessible
    STATUS     current
    DESCRIPTION
        "Contains the RMON-2 augmentations to RMON-1."
    ::= { matrix 4 }

matrixControl2Entry  OBJECT-TYPE
    SYNTAX     MatrixControl2Entry
    MAX-ACCESS not-accessible
    STATUS     current
    DESCRIPTION
        "Contains the RMON-2 augmentations to RMON-1."
    AUGMENTS { matrixControlEntry }
    ::= { matrixControl2Table 1 }

MatrixControl2Entry ::= SEQUENCE {
    matrixControlDroppedFrames  Counter32,
    matrixControlCreateTime     TimeStamp
}

matrixControlDroppedFrames OBJECT-TYPE
    SYNTAX     Counter32
    MAX-ACCESS read-only
    STATUS     current
    DESCRIPTION
       "The total number of frames which were received by the probe
        and therefore not accounted for in the *StatsDropEvents, but
        for which the probe chose not to count for this entry for
        whatever reason.  Most often, this event occurs when the probe
        is out of some resources and decides to shed load from this
        collection.

        This count does not include packets that were not counted


        because they had MAC-layer errors.

        Note that, unlike the dropEvents counter, this number is the
        exact number of frames dropped."
    ::= { matrixControl2Entry 1 }

matrixControlCreateTime OBJECT-TYPE
    SYNTAX     TimeStamp
    MAX-ACCESS read-only
    STATUS     current
    DESCRIPTION
        "The value of sysUpTime when this control entry was last
        activated. This can be used by the management station to
        ensure that the table has not been deleted and recreated
        between polls."
    ::= { matrixControl2Entry 2 }

channel2Table  OBJECT-TYPE
    SYNTAX     SEQUENCE OF Channel2Entry
    MAX-ACCESS not-accessible
    STATUS     current
    DESCRIPTION
        "Contains the RMON-2 augmentations to RMON-1."
    ::= { filter 3 }

channel2Entry  OBJECT-TYPE
    SYNTAX     Channel2Entry
    MAX-ACCESS not-accessible
    STATUS     current
    DESCRIPTION
        "Contains the RMON-2 augmentations to RMON-1."
    AUGMENTS { channelEntry }
    ::= { channel2Table 1 }

Channel2Entry ::= SEQUENCE {
    channelDroppedFrames    Counter32,
    channelCreateTime       TimeStamp
}

channelDroppedFrames OBJECT-TYPE
    SYNTAX     Counter32
    MAX-ACCESS read-only
    STATUS     current
    DESCRIPTION
       "The total number of frames which were received by the probe
        and therefore not accounted for in the *StatsDropEvents, but
        for which the probe chose not to count for this entry for
        whatever reason.  Most often, this event occurs when the probe


        is out of some resources and decides to shed load from this
        collection.

        This count does not include packets that were not counted
        because they had MAC-layer errors.

        Note that, unlike the dropEvents counter, this number is the
        exact number of frames dropped."
    ::= { channel2Entry 1 }

channelCreateTime OBJECT-TYPE
    SYNTAX     TimeStamp
    MAX-ACCESS read-only
    STATUS     current
    DESCRIPTION
        "The value of sysUpTime when this control entry was last
        activated. This can be used by the management station to
        ensure that the table has not been deleted and recreated
        between polls."
    ::= { channel2Entry 2 }

tokenRingMLStats2Table  OBJECT-TYPE
    SYNTAX     SEQUENCE OF TokenRingMLStats2Entry
    MAX-ACCESS not-accessible
    STATUS     current
    DESCRIPTION
        "Contains the RMON-2 augmentations to RMON-1."
    ::= { statistics 5 }

tokenRingMLStats2Entry  OBJECT-TYPE
    SYNTAX     TokenRingMLStats2Entry
    MAX-ACCESS not-accessible
    STATUS     current
    DESCRIPTION
        "Contains the RMON-2 augmentations to RMON-1."
    AUGMENTS { tokenRingMLStatsEntry }
    ::= { tokenRingMLStats2Table 1 }

TokenRingMLStats2Entry ::= SEQUENCE {
    tokenRingMLStatsDroppedFrames       Counter32,
    tokenRingMLStatsCreateTime          TimeStamp
}

tokenRingMLStatsDroppedFrames OBJECT-TYPE
    SYNTAX     Counter32
    MAX-ACCESS read-only
    STATUS     current
    DESCRIPTION


       "The total number of frames which were received by the probe
        and therefore not accounted for in the *StatsDropEvents, but
        for which the probe chose not to count for this entry for
        whatever reason.  Most often, this event occurs when the probe
        is out of some resources and decides to shed load from this
        collection.

        This count does not include packets that were not counted
        because they had MAC-layer errors.

        Note that, unlike the dropEvents counter, this number is the
        exact number of frames dropped."
    ::= { tokenRingMLStats2Entry 1 }

tokenRingMLStatsCreateTime OBJECT-TYPE
    SYNTAX     TimeStamp
    MAX-ACCESS read-only
    STATUS     current
    DESCRIPTION
        "The value of sysUpTime when this control entry was last activated.
        This can be used by the management station to ensure that the
        table has not been deleted and recreated between polls."
    ::= { tokenRingMLStats2Entry 2 }

tokenRingPStats2Table  OBJECT-TYPE
    SYNTAX     SEQUENCE OF TokenRingPStats2Entry
    MAX-ACCESS not-accessible
    STATUS     current
    DESCRIPTION
        "Contains the RMON-2 augmentations to RMON-1."
    ::= { statistics 6 }

tokenRingPStats2Entry  OBJECT-TYPE
    SYNTAX     TokenRingPStats2Entry
    MAX-ACCESS not-accessible
    STATUS     current
    DESCRIPTION
        "Contains the RMON-2 augmentations to RMON-1."
    AUGMENTS {  tokenRingPStatsEntry }
    ::= { tokenRingPStats2Table 1 }

TokenRingPStats2Entry ::= SEQUENCE {
    tokenRingPStatsDroppedFrames    Counter32,
    tokenRingPStatsCreateTime       TimeStamp
}

tokenRingPStatsDroppedFrames OBJECT-TYPE
    SYNTAX     Counter32


    MAX-ACCESS read-only
    STATUS     current
    DESCRIPTION
       "The total number of frames which were received by the probe
        and therefore not accounted for in the *StatsDropEvents, but
        for which the probe chose not to count for this entry for
        whatever reason.  Most often, this event occurs when the probe
        is out of some resources and decides to shed load from this
        collection.

        This count does not include packets that were not counted
        because they had MAC-layer errors.

        Note that, unlike the dropEvents counter, this number is the
        exact number of frames dropped."
    ::= { tokenRingPStats2Entry 1 }

tokenRingPStatsCreateTime OBJECT-TYPE
    SYNTAX     TimeStamp
    MAX-ACCESS read-only
    STATUS     current
    DESCRIPTION
        "The value of sysUpTime when this control entry was last activated.
        This can be used by the management station to ensure that the
        table has not been deleted and recreated between polls."
    ::= { tokenRingPStats2Entry 2 }

ringStationControl2Table  OBJECT-TYPE
    SYNTAX     SEQUENCE OF RingStationControl2Entry
    MAX-ACCESS not-accessible
    STATUS     current
    DESCRIPTION
        "Contains the RMON-2 augmentations to RMON-1."
    ::= { tokenRing 7 }

ringStationControl2Entry  OBJECT-TYPE
    SYNTAX     RingStationControl2Entry
    MAX-ACCESS not-accessible
    STATUS     current
    DESCRIPTION
        "Contains the RMON-2 augmentations to RMON-1."
    AUGMENTS { ringStationControlEntry }
    ::= { ringStationControl2Table 1 }

RingStationControl2Entry ::= SEQUENCE {
    ringStationControlDroppedFrames Counter32,
    ringStationControlCreateTime    TimeStamp
}


ringStationControlDroppedFrames OBJECT-TYPE
    SYNTAX     Counter32
    MAX-ACCESS read-only
    STATUS     current
    DESCRIPTION
       "The total number of frames which were received by the probe
        and therefore not accounted for in the *StatsDropEvents, but
        for which the probe chose not to count for this entry for
        whatever reason.  Most often, this event occurs when the probe
        is out of some resources and decides to shed load from this
        collection.

        This count does not include packets that were not counted
        because they had MAC-layer errors.

        Note that, unlike the dropEvents counter, this number is the
        exact number of frames dropped."
    ::= { ringStationControl2Entry 1 }

ringStationControlCreateTime OBJECT-TYPE
    SYNTAX     TimeStamp
    MAX-ACCESS read-only
    STATUS     current
    DESCRIPTION
        "The value of sysUpTime when this control entry was last activated.
        This can be used by the management station to ensure that the
        table has not been deleted and recreated between polls."
    ::= { ringStationControl2Entry 2 }

sourceRoutingStats2Table  OBJECT-TYPE
    SYNTAX     SEQUENCE OF SourceRoutingStats2Entry
    MAX-ACCESS not-accessible
    STATUS     current
    DESCRIPTION
        "Contains the RMON-2 augmentations to RMON-1."
    ::= { tokenRing 8 }

sourceRoutingStats2Entry  OBJECT-TYPE
    SYNTAX     SourceRoutingStats2Entry
    MAX-ACCESS not-accessible
    STATUS     current
    DESCRIPTION
        "Contains the RMON-2 augmentations to RMON-1."
    AUGMENTS { sourceRoutingStatsEntry }
    ::= { sourceRoutingStats2Table 1 }

SourceRoutingStats2Entry ::= SEQUENCE {
    sourceRoutingStatsDroppedFrames Counter32,


    sourceRoutingStatsCreateTime    TimeStamp
}

sourceRoutingStatsDroppedFrames OBJECT-TYPE
    SYNTAX     Counter32
    MAX-ACCESS read-only
    STATUS     current
    DESCRIPTION
       "The total number of frames which were received by the probe
        and therefore not accounted for in the *StatsDropEvents, but
        for which the probe chose not to count for this entry for
        whatever reason.  Most often, this event occurs when the probe
        is out of some resources and decides to shed load from this
        collection.

        This count does not include packets that were not counted
        because they had MAC-layer errors.

        Note that, unlike the dropEvents counter, this number is the
        exact number of frames dropped."
    ::= { sourceRoutingStats2Entry 1 }

sourceRoutingStatsCreateTime OBJECT-TYPE
    SYNTAX     TimeStamp
    MAX-ACCESS read-only
    STATUS     current
    DESCRIPTION
        "The value of sysUpTime when this control entry was last activated.
        This can be used by the management station to ensure that the
        table has not been deleted and recreated between polls."
    ::= { sourceRoutingStats2Entry 2 }

filter2Table OBJECT-TYPE
    SYNTAX     SEQUENCE OF Filter2Entry
    MAX-ACCESS not-accessible
    STATUS     current
    DESCRIPTION
        "Provides a variable-length packet filter feature to the
        RMON-1 filter table."
    ::= { filter 4 }

filter2Entry OBJECT-TYPE
    SYNTAX     Filter2Entry
    MAX-ACCESS not-accessible
    STATUS     current
    DESCRIPTION
        "Provides a variable-length packet filter feature to the
        RMON-1 filter table."


    AUGMENTS { filterEntry }
    ::= { filter2Table 1 }

Filter2Entry ::= SEQUENCE {
    filterProtocolDirDataLocalIndex     Integer32,
    filterProtocolDirLocalIndex         Integer32
}

filterProtocolDirDataLocalIndex OBJECT-TYPE
    SYNTAX     Integer32 (0..2147483647)
    MAX-ACCESS read-create
    STATUS     current
    DESCRIPTION
        "When this object is set to a non-zero value, the filter that
        it is associated with performs the following operations on
        every packet:

        1) - If the packet doesn't match the protocol directory entry
             identified by this object, discard the packet and exit
             (i.e., discard the packet if it is not of the identified
             protocol).
        2) - If the associated filterProtocolDirLocalIndex is non-zero
             and the packet doesn't match the protocol directory
             entry identified by that object, discard the packet and
             exit
        3) - If the packet matches, perform the regular filter
             algorithm as if the beginning of this named protocol is
             the beginning of the packet, potentially applying the
             filterOffset value to move further into the packet."
    DEFVAL { 0 }
    ::= { filter2Entry 1 }

filterProtocolDirLocalIndex OBJECT-TYPE
    SYNTAX     Integer32 (0..2147483647)
    MAX-ACCESS read-create
    STATUS     current
    DESCRIPTION
        "When this object is set to a non-zero value, the filter that
        it is associated with will discard the packet if the packet
        doesn't match this protocol directory entry."
    DEFVAL { 0 }
    ::= { filter2Entry 2 }

-- Conformance Macros

rmon2MIBCompliances OBJECT IDENTIFIER ::= { rmonConformance 1 }
rmon2MIBGroups      OBJECT IDENTIFIER ::= { rmonConformance 2 }


rmon2MIBCompliance MODULE-COMPLIANCE
    STATUS  current
    DESCRIPTION
        "Describes the requirements for conformance to
        the RMON2 MIB"
    MODULE  -- this module
        MANDATORY-GROUPS { protocolDirectoryGroup,
                           protocolDistributionGroup,
                           addressMapGroup,
                           nlHostGroup,
                           nlMatrixGroup,
                           usrHistoryGroup,
                           probeInformationGroup }

        GROUP   rmon1EnhancementGroup
        DESCRIPTION
            "The rmon1EnhancementGroup is mandatory for systems which
            implement RMON [RFC1757]"
    ::= { rmon2MIBCompliances 1 }

rmon2MIBApplicationLayerCompliance MODULE-COMPLIANCE
    STATUS  current
    DESCRIPTION
        "Describes the requirements for conformance to
        the RMON2 MIB with Application Layer Enhancements."
    MODULE  -- this module
        MANDATORY-GROUPS { protocolDirectoryGroup,
                           protocolDistributionGroup,
                           addressMapGroup,
                           nlHostGroup,
                           nlMatrixGroup,
                           alHostGroup,
                           alMatrixGroup,
                           usrHistoryGroup,
                           probeInformationGroup }

        GROUP   rmon1EnhancementGroup
        DESCRIPTION
            "The rmon1EnhancementGroup is mandatory for systems which
            implement RMON [RFC1757]"
    ::= { rmon2MIBCompliances 2 }

protocolDirectoryGroup OBJECT-GROUP
    OBJECTS { protocolDirLastChange,
              protocolDirLocalIndex, protocolDirDescr,
              protocolDirType, protocolDirAddressMapConfig,
              protocolDirHostConfig, protocolDirMatrixConfig,


              protocolDirOwner, protocolDirStatus }
    STATUS  current
    DESCRIPTION
        "Lists the inventory of protocols the probe has the capability
        of monitoring and allows the addition, deletion, and
        configuration of entries in this list."
    ::= { rmon2MIBGroups 1 }

protocolDistributionGroup OBJECT-GROUP
    OBJECTS { protocolDistControlDataSource,
              protocolDistControlDroppedFrames,
              protocolDistControlCreateTime,
              protocolDistControlOwner, protocolDistControlStatus,
              protocolDistStatsPkts, protocolDistStatsOctets }
    STATUS  current
    DESCRIPTION
        "Collects the relative amounts of octets and packets for the
        different protocols detected on a network segment."
    ::= { rmon2MIBGroups 2 }

addressMapGroup OBJECT-GROUP
    OBJECTS { addressMapInserts, addressMapDeletes,
              addressMapMaxDesiredEntries,
              addressMapControlDataSource,
              addressMapControlDroppedFrames,
              addressMapControlOwner, addressMapControlStatus,
              addressMapPhysicalAddress,
              addressMapLastChange }
    STATUS  current
    DESCRIPTION
        "Lists MAC address to network address bindings discovered by
        the probe and what interface they were last seen on."
    ::= { rmon2MIBGroups 3 }

nlHostGroup OBJECT-GROUP
    OBJECTS { hlHostControlDataSource,
              hlHostControlNlDroppedFrames, hlHostControlNlInserts,
              hlHostControlNlDeletes,
              hlHostControlNlMaxDesiredEntries,
              hlHostControlAlDroppedFrames, hlHostControlAlInserts,
              hlHostControlAlDeletes,
              hlHostControlAlMaxDesiredEntries, hlHostControlOwner,
              hlHostControlStatus, nlHostInPkts, nlHostOutPkts,
              nlHostInOctets, nlHostOutOctets,
              nlHostOutMacNonUnicastPkts, nlHostCreateTime }
    STATUS  current
    DESCRIPTION
        "Counts the amount of traffic sent from and to each network


        address discovered by the probe. Note that while the
        hlHostControlTable also has objects that control an optional
        alHostTable, implementation of the alHostTable is not required
        to fully implement this group."
    ::= { rmon2MIBGroups 4 }

nlMatrixGroup OBJECT-GROUP
    OBJECTS { hlMatrixControlDataSource,
              hlMatrixControlNlDroppedFrames,
              hlMatrixControlNlInserts, hlMatrixControlNlDeletes,
              hlMatrixControlNlMaxDesiredEntries,
              hlMatrixControlAlDroppedFrames,
              hlMatrixControlAlInserts, hlMatrixControlAlDeletes,
              hlMatrixControlAlMaxDesiredEntries,
              hlMatrixControlOwner, hlMatrixControlStatus,
              nlMatrixSDPkts, nlMatrixSDOctets, nlMatrixSDCreateTime,
              nlMatrixDSPkts, nlMatrixDSOctets, nlMatrixDSCreateTime,
              nlMatrixTopNControlMatrixIndex,
              nlMatrixTopNControlRateBase,
              nlMatrixTopNControlTimeRemaining,
              nlMatrixTopNControlGeneratedReports,
              nlMatrixTopNControlDuration,
              nlMatrixTopNControlRequestedSize,
              nlMatrixTopNControlGrantedSize,
              nlMatrixTopNControlStartTime,
              nlMatrixTopNControlOwner, nlMatrixTopNControlStatus,
              nlMatrixTopNProtocolDirLocalIndex,
              nlMatrixTopNSourceAddress, nlMatrixTopNDestAddress,
              nlMatrixTopNPktRate, nlMatrixTopNReversePktRate,
              nlMatrixTopNOctetRate, nlMatrixTopNReverseOctetRate }
    STATUS  current
    DESCRIPTION
        "Counts the amount of traffic sent between each pair of
        network addresses discovered by the probe. Note that while the
        hlMatrixControlTable also has objects that control optional
        alMatrixTables, implementation of the alMatrixTables is not
        required to fully implement this group."
    ::= { rmon2MIBGroups 5 }

alHostGroup OBJECT-GROUP
    OBJECTS { alHostInPkts, alHostOutPkts,
              alHostInOctets, alHostOutOctets, alHostCreateTime }
    STATUS  current
    DESCRIPTION
        "Counts the amount of traffic, by protocol, sent from and to
        each network address discovered by the probe. Implementation
        of this group requires implementation of the Network Layer
        Host Group."


    ::= { rmon2MIBGroups 6 }

alMatrixGroup OBJECT-GROUP
    OBJECTS { alMatrixSDPkts, alMatrixSDOctets, alMatrixSDCreateTime,
              alMatrixDSPkts, alMatrixDSOctets, alMatrixDSCreateTime,
              alMatrixTopNControlMatrixIndex,
              alMatrixTopNControlRateBase,
              alMatrixTopNControlTimeRemaining,
              alMatrixTopNControlGeneratedReports,
              alMatrixTopNControlDuration,
              alMatrixTopNControlRequestedSize,
              alMatrixTopNControlGrantedSize,
              alMatrixTopNControlStartTime,
              alMatrixTopNControlOwner, alMatrixTopNControlStatus,
              alMatrixTopNProtocolDirLocalIndex,
              alMatrixTopNSourceAddress, alMatrixTopNDestAddress,
              alMatrixTopNAppProtocolDirLocalIndex,
              alMatrixTopNPktRate, alMatrixTopNReversePktRate,
              alMatrixTopNOctetRate, alMatrixTopNReverseOctetRate }
    STATUS  current
    DESCRIPTION
        "Counts the amount of traffic, by protocol, sent between each
        pair of network addresses discovered by the
        probe. Implementation of this group requires implementation of
        the Network Layer Matrix Group."
    ::= { rmon2MIBGroups 7 }

usrHistoryGroup OBJECT-GROUP
    OBJECTS { usrHistoryControlObjects,
              usrHistoryControlBucketsRequested,
              usrHistoryControlBucketsGranted,
              usrHistoryControlInterval,
              usrHistoryControlOwner, usrHistoryControlStatus,
              usrHistoryObjectVariable, usrHistoryObjectSampleType,
              usrHistoryIntervalStart, usrHistoryIntervalEnd,
              usrHistoryAbsValue, usrHistoryValStatus }
    STATUS  current
    DESCRIPTION
        "The usrHistoryGroup provides user-defined collection of
        historical information from MIB objects on the probe."
    ::= { rmon2MIBGroups 8 }

probeInformationGroup OBJECT-GROUP
    OBJECTS { probeCapabilities,
              probeSoftwareRev, probeHardwareRev, probeDateTime }
    STATUS  current
    DESCRIPTION
        "This group describes various operating parameters of the


        probe as well as controlling the local time of the probe."
    ::= { rmon2MIBGroups 9 }

probeConfigurationGroup OBJECT-GROUP
    OBJECTS { probeResetControl, probeDownloadFile,
              probeDownloadTFTPServer, probeDownloadAction,
              probeDownloadStatus,
              serialMode, serialProtocol, serialTimeout,
              serialModemInitString, serialModemHangUpString,
              serialModemConnectResp, serialModemNoConnectResp,
              serialDialoutTimeout, serialStatus,
              netConfigIPAddress, netConfigSubnetMask,
              netConfigStatus, netDefaultGateway,
              trapDestCommunity, trapDestProtocol, trapDestAddress,
              trapDestOwner, trapDestStatus,
              serialConnectDestIpAddress, serialConnectType,
              serialConnectDialString, serialConnectSwitchConnectSeq,
              serialConnectSwitchDisconnectSeq,
              serialConnectSwitchResetSeq,
              serialConnectOwner, serialConnectStatus }
    STATUS  current
    DESCRIPTION
        "This group controls the configuration of various operating
        parameters of the probe."
    ::= { rmon2MIBGroups 10 }

rmon1EnhancementGroup OBJECT-GROUP
    OBJECTS { historyControlDroppedFrames, hostControlDroppedFrames,
              hostControlCreateTime, matrixControlDroppedFrames,
              matrixControlCreateTime, channelDroppedFrames,
              channelCreateTime, filterProtocolDirDataLocalIndex,
              filterProtocolDirLocalIndex }
    STATUS  current
    DESCRIPTION
        "This group adds some enhancements to RMON-1 that help
        management stations."
    ::= { rmon2MIBGroups 11 }

rmon1EthernetEnhancementGroup OBJECT-GROUP
    OBJECTS { etherStatsDroppedFrames, etherStatsCreateTime }
    STATUS  current
    DESCRIPTION
        "This group adds some enhancements to RMON-1 that help
        management stations."
    ::= { rmon2MIBGroups 12 }

rmon1TokenRingEnhancementGroup OBJECT-GROUP
    OBJECTS { tokenRingMLStatsDroppedFrames,


              tokenRingMLStatsCreateTime,
              tokenRingPStatsDroppedFrames, tokenRingPStatsCreateTime,
              ringStationControlDroppedFrames,
              ringStationControlCreateTime,
              sourceRoutingStatsDroppedFrames,
              sourceRoutingStatsCreateTime }
    STATUS  current
    DESCRIPTION
        "This group adds some enhancements to RMON-1 that help
        management stations."
    ::= { rmon2MIBGroups 13 }
END


-- $Id: P-BRIDGE-MIB.txt,v 1.3 2000/07/14 08:14:27 hyung Exp $
-- From: RFC 2674 

P-BRIDGE-MIB DEFINITIONS ::= BEGIN

-- -------------------------------------------------------------
-- MIB for IEEE 802.1p devices
-- -------------------------------------------------------------

IMPORTS
    MODULE-IDENTITY, OBJECT-TYPE, Counter32, Counter64
        FROM SNMPv2-SMI
    TruthValue, TimeInterval, MacAddress, TEXTUAL-CONVENTION
        FROM SNMPv2-TC
    MODULE-COMPLIANCE, OBJECT-GROUP
        FROM SNMPv2-CONF
    dot1dTp, dot1dTpPort, dot1dBridge,
    dot1dBasePortEntry, dot1dBasePort
        FROM BRIDGE-MIB;


pBridgeMIB MODULE-IDENTITY
    LAST-UPDATED "9908250000Z"
    ORGANIZATION "IETF Bridge MIB Working Group"
    CONTACT-INFO
        "       Les Bell
        Postal: 3Com Europe Ltd.
                3Com Centre, Boundary Way
                Hemel Hempstead, Herts. HP2 7YU
                UK
         Phone: +44 1442 438025
         Email: Les_Bell@3Com.com

                Andrew Smith
        Postal: Extreme Networks
                3585 Monroe St.
                Santa Clara CA 95051
                USA
         Phone: +1 408 579 2821
         Email: andrew@extremenetworks.com

                Paul Langille
        Postal: Newbridge Networks
                5 Corporate Drive
                Andover, MA 01810
                USA
         Phone: +1 978 691 4665
         Email: langille@newbridge.com

                Anil Rijhsinghani
        Postal: Cabletron Systems
                50 Minuteman Road
                Andover, MA 01810
                USA
         Phone: +1 978 684 1295
         Email: anil@cabletron.com

                Keith McCloghrie
        Postal: cisco Systems, Inc.
                170 West Tasman Drive
                San Jose, CA 95134-1706
                USA
         Phone: +1 408 526 5260
         Email: kzm@cisco.com"

    DESCRIPTION
        "The Bridge MIB Extension module for managing Priority
        and Multicast Filtering, defined by IEEE 802.1D-1998."


-- revision history

    REVISION     "9908250000Z"
    DESCRIPTION
         "Initial version, published as RFC 2674."

    ::= { dot1dBridge 6 }

pBridgeMIBObjects OBJECT IDENTIFIER ::= { pBridgeMIB 1 }

-- -------------------------------------------------------------
-- Textual Conventions
-- -------------------------------------------------------------

EnabledStatus ::= TEXTUAL-CONVENTION
    STATUS      current
    DESCRIPTION
        "A simple status value for the object."
    SYNTAX      INTEGER { enabled(1), disabled(2) }

-- -------------------------------------------------------------

-- -------------------------------------------------------------
-- groups in the P-BRIDGE MIB
-- -------------------------------------------------------------

dot1dExtBase    OBJECT IDENTIFIER ::= { pBridgeMIBObjects 1 }
dot1dPriority   OBJECT IDENTIFIER ::= { pBridgeMIBObjects 2 }
dot1dGarp       OBJECT IDENTIFIER ::= { pBridgeMIBObjects 3 }
dot1dGmrp       OBJECT IDENTIFIER ::= { pBridgeMIBObjects 4 }

-- -------------------------------------------------------------

-- -------------------------------------------------------------
-- the dot1dExtBase group
-- -------------------------------------------------------------

dot1dDeviceCapabilities OBJECT-TYPE
    SYNTAX      BITS {
        dot1dExtendedFilteringServices(0),
                              -- can perform filtering of
                              -- individual multicast addresses
                              -- controlled by GMRP.
        dot1dTrafficClasses(1),
                              -- can map user priority to
                              -- multiple traffic classes.


        dot1qStaticEntryIndividualPort(2),
                              -- dot1qStaticUnicastReceivePort &
                              -- dot1qStaticMulticastReceivePort
                              -- can represent non-zero entries.
        dot1qIVLCapable(3),   -- Independent VLAN Learning.
        dot1qSVLCapable(4),   -- Shared VLAN Learning.
        dot1qHybridCapable(5),
                              -- both IVL & SVL simultaneously.
        dot1qConfigurablePvidTagging(6),
                              -- whether the implementation
                              -- supports the ability to
                              -- override the default PVID
                              -- setting and its egress status
                              -- (VLAN-Tagged or Untagged) on
                              -- each port.
        dot1dLocalVlanCapable(7)
                              -- can support multiple local
                              -- bridges, outside of the scope
                              -- of 802.1Q defined VLANs.
    }
    MAX-ACCESS  read-only
    STATUS      current
    DESCRIPTION
        "Indicates the optional parts of IEEE 802.1D and 802.1Q
        that are implemented by this device and are manageable
        through this MIB.  Capabilities that are allowed on a
        per-port basis are indicated in dot1dPortCapabilities."
    REFERENCE
        "ISO/IEC 15802-3 Section 5.2,
        IEEE 802.1Q/D11 Section 5.2, 12.10.1.1.3/b/2"
    ::= { dot1dExtBase 1 }

dot1dTrafficClassesEnabled OBJECT-TYPE
    SYNTAX      TruthValue
    MAX-ACCESS  read-write
    STATUS      current
    DESCRIPTION
        "The value true(1) indicates that Traffic Classes are
        enabled on this bridge.  When false(2), the bridge
        operates with a single priority level for all traffic."
    DEFVAL      { true }
    ::= { dot1dExtBase 2 }

dot1dGmrpStatus OBJECT-TYPE
    SYNTAX      EnabledStatus
    MAX-ACCESS  read-write
    STATUS      current
    DESCRIPTION


        "The administrative status requested by management for
        GMRP.  The value enabled(1) indicates that GMRP should
        be enabled on this device, in all VLANs, on all ports
        for which it has not been specifically disabled.  When
        disabled(2), GMRP is disabled, in all VLANs, on all
        ports and all GMRP packets will be forwarded
        transparently.  This object affects both Applicant and
        Registrar state machines.  A transition from disabled(2)
        to enabled(1) will cause a reset of all GMRP state
        machines on all ports."
    DEFVAL      { enabled }
    ::= { dot1dExtBase 3 }

-- -------------------------------------------------------------
-- Port Capabilities Table
-- -------------------------------------------------------------

dot1dPortCapabilitiesTable OBJECT-TYPE
    SYNTAX      SEQUENCE OF Dot1dPortCapabilitiesEntry
    MAX-ACCESS  not-accessible
    STATUS      current
    DESCRIPTION
        "A table that contains capabilities information about
        every port that is associated with this bridge."
    ::= { dot1dExtBase 4 }

dot1dPortCapabilitiesEntry OBJECT-TYPE
    SYNTAX      Dot1dPortCapabilitiesEntry
    MAX-ACCESS  not-accessible
    STATUS      current
    DESCRIPTION
        "A set of capabilities information about this port
        indexed by dot1dBasePort."
    AUGMENTS { dot1dBasePortEntry }
    ::= { dot1dPortCapabilitiesTable 1 }

Dot1dPortCapabilitiesEntry ::=
    SEQUENCE {
        dot1dPortCapabilities
            BITS
    }

dot1dPortCapabilities OBJECT-TYPE
    SYNTAX      BITS {
        dot1qDot1qTagging(0), -- supports 802.1Q VLAN tagging of
                              -- frames and GVRP.
        dot1qConfigurableAcceptableFrameTypes(1),
                              -- allows modified values of


                              -- dot1qPortAcceptableFrameTypes.
        dot1qIngressFiltering(2)
                              -- supports the discarding of any
                              -- frame received on a Port whose
                              -- VLAN classification does not
                              -- include that Port in its Member
                              -- set.
    }
    MAX-ACCESS  read-only
    STATUS      current
    DESCRIPTION
        "Indicates the parts of IEEE 802.1D and 802.1Q that are
        optional on a per-port basis that are implemented by
        this device and are manageable through this MIB."
    REFERENCE
        "ISO/IEC 15802-3 Section 5.2,
        IEEE 802.1Q/D11 Section 5.2"
    ::= { dot1dPortCapabilitiesEntry 1 }

-- -------------------------------------------------------------
-- the dot1dPriority group
-- -------------------------------------------------------------

-- -------------------------------------------------------------
-- Port Priority Table
-- -------------------------------------------------------------

dot1dPortPriorityTable OBJECT-TYPE
    SYNTAX      SEQUENCE OF Dot1dPortPriorityEntry
    MAX-ACCESS  not-accessible
    STATUS      current
    DESCRIPTION
        "A table that contains information about every port that
        is associated with this transparent bridge."
    ::= { dot1dPriority 1 }

dot1dPortPriorityEntry OBJECT-TYPE
    SYNTAX      Dot1dPortPriorityEntry
    MAX-ACCESS  not-accessible
    STATUS      current
    DESCRIPTION
        "A list of Default User Priorities for each port of a
        transparent bridge.  This is indexed by dot1dBasePort."
    AUGMENTS { dot1dBasePortEntry }
    ::= { dot1dPortPriorityTable 1 }

Dot1dPortPriorityEntry ::=
    SEQUENCE {


        dot1dPortDefaultUserPriority
            INTEGER,
        dot1dPortNumTrafficClasses
            INTEGER
    }

dot1dPortDefaultUserPriority OBJECT-TYPE
    SYNTAX      INTEGER (0..7)
    MAX-ACCESS  read-write
    STATUS      current
    DESCRIPTION
        "The default ingress User Priority for this port.  This
        only has effect on media, such as Ethernet, that do not
        support native User Priority."
    ::= { dot1dPortPriorityEntry 1 }

dot1dPortNumTrafficClasses OBJECT-TYPE
    SYNTAX      INTEGER (1..8)
    MAX-ACCESS  read-write
    STATUS      current
    DESCRIPTION
        "The number of egress traffic classes supported on this
        port.  This object may optionally be read-only."
    ::= { dot1dPortPriorityEntry 2 }

-- -------------------------------------------------------------
-- User Priority Regeneration Table
-- -------------------------------------------------------------

dot1dUserPriorityRegenTable OBJECT-TYPE
    SYNTAX      SEQUENCE OF Dot1dUserPriorityRegenEntry
    MAX-ACCESS  not-accessible
    STATUS      current
    DESCRIPTION
        "A list of Regenerated User Priorities for each received
        User Priority on each port of a bridge.  The Regenerated
        User Priority value may be used to index the Traffic
        Class Table for each input port.  This only has effect
        on media that support native User Priority.  The default
        values for Regenerated User Priorities are the same as
        the User Priorities."
    REFERENCE
        "ISO/IEC 15802-3 Section 6.4"
    ::= { dot1dPriority 2 }


dot1dUserPriorityRegenEntry OBJECT-TYPE
    SYNTAX      Dot1dUserPriorityRegenEntry
    MAX-ACCESS  not-accessible
    STATUS      current
    DESCRIPTION
        "A mapping of incoming User Priority to a Regenerated
        User Priority."
    INDEX   { dot1dBasePort, dot1dUserPriority }
    ::= { dot1dUserPriorityRegenTable 1 }

Dot1dUserPriorityRegenEntry ::=
    SEQUENCE {
        dot1dUserPriority
            INTEGER,
        dot1dRegenUserPriority
            INTEGER
    }

dot1dUserPriority OBJECT-TYPE
    SYNTAX      INTEGER (0..7)
    MAX-ACCESS  not-accessible
    STATUS      current
    DESCRIPTION
        "The User Priority for a frame received on this port."
    ::= { dot1dUserPriorityRegenEntry 1 }

dot1dRegenUserPriority OBJECT-TYPE
    SYNTAX      INTEGER (0..7)
    MAX-ACCESS  read-write
    STATUS      current
    DESCRIPTION
        "The Regenerated User Priority the incoming User
        Priority is mapped to for this port."
    ::= { dot1dUserPriorityRegenEntry 2 }

-- -------------------------------------------------------------
-- Traffic Class Table
-- -------------------------------------------------------------

dot1dTrafficClassTable OBJECT-TYPE
    SYNTAX      SEQUENCE OF Dot1dTrafficClassEntry
    MAX-ACCESS  not-accessible
    STATUS      current
    DESCRIPTION
        "A table mapping evaluated User Priority to Traffic
        Class, for forwarding by the bridge.  Traffic class is a
        number in the range (0..(dot1dPortNumTrafficClasses-1))."
    REFERENCE


        "ISO/IEC 15802-3 Table 7-2"
    ::= { dot1dPriority 3 }

dot1dTrafficClassEntry OBJECT-TYPE
    SYNTAX      Dot1dTrafficClassEntry
    MAX-ACCESS  not-accessible
    STATUS      current
    DESCRIPTION
        "User Priority to Traffic Class mapping."
    INDEX   { dot1dBasePort, dot1dTrafficClassPriority }
    ::= { dot1dTrafficClassTable 1 }

Dot1dTrafficClassEntry ::=
    SEQUENCE {
        dot1dTrafficClassPriority
            INTEGER,
        dot1dTrafficClass
            INTEGER
    }

dot1dTrafficClassPriority OBJECT-TYPE
    SYNTAX      INTEGER (0..7)
    MAX-ACCESS  not-accessible
    STATUS      current
    DESCRIPTION
        "The Priority value determined for the received frame.
        This value is equivalent to the priority indicated in
        the tagged frame received, or one of the evaluated
        priorities, determined according to the media-type.

        For untagged frames received from Ethernet media, this
        value is equal to the dot1dPortDefaultUserPriority value
        for the ingress port.

        For untagged frames received from non-Ethernet media,
        this value is equal to the dot1dRegenUserPriority value
        for the ingress port and media-specific user priority."
    ::= { dot1dTrafficClassEntry 1 }

dot1dTrafficClass OBJECT-TYPE
    SYNTAX      INTEGER (0..7)
    MAX-ACCESS  read-write
    STATUS      current
    DESCRIPTION
        "The Traffic Class the received frame is mapped to."
    ::= { dot1dTrafficClassEntry 2 }

-- -------------------------------------------------------------


-- Outbound Access Priority Table
-- -------------------------------------------------------------

dot1dPortOutboundAccessPriorityTable OBJECT-TYPE
    SYNTAX      SEQUENCE OF Dot1dPortOutboundAccessPriorityEntry
    MAX-ACCESS  not-accessible
    STATUS      current
    DESCRIPTION
        "A table mapping Regenerated User Priority to Outbound
        Access Priority.  This is a fixed mapping for all port
        types, with two options for 802.5 Token Ring."
    REFERENCE
        "ISO/IEC 15802-3 Table 7-3"
    ::= { dot1dPriority 4 }

dot1dPortOutboundAccessPriorityEntry OBJECT-TYPE
    SYNTAX      Dot1dPortOutboundAccessPriorityEntry
    MAX-ACCESS  not-accessible
    STATUS      current
    DESCRIPTION
        "Regenerated User Priority to Outbound Access Priority
        mapping."
    INDEX   { dot1dBasePort, dot1dRegenUserPriority }
    ::= { dot1dPortOutboundAccessPriorityTable 1 }

Dot1dPortOutboundAccessPriorityEntry ::=
    SEQUENCE {
        dot1dPortOutboundAccessPriority
            INTEGER
    }

dot1dPortOutboundAccessPriority OBJECT-TYPE
    SYNTAX      INTEGER (0..7)
    MAX-ACCESS  read-only
    STATUS      current
    DESCRIPTION
        "The Outbound Access Priority the received frame is
        mapped to."
    ::= { dot1dPortOutboundAccessPriorityEntry 1 }

-- -------------------------------------------------------------
-- the dot1dGarp group
-- -------------------------------------------------------------

-- -------------------------------------------------------------
-- The GARP Port Table
-- -------------------------------------------------------------


dot1dPortGarpTable OBJECT-TYPE
    SYNTAX      SEQUENCE OF Dot1dPortGarpEntry
    MAX-ACCESS  not-accessible
    STATUS      current
    DESCRIPTION
        "A table of GARP control information about every bridge
        port.  This is indexed by dot1dBasePort."
    ::= { dot1dGarp 1 }

dot1dPortGarpEntry OBJECT-TYPE
    SYNTAX      Dot1dPortGarpEntry
    MAX-ACCESS  not-accessible
    STATUS      current
    DESCRIPTION
        "GARP control information for a bridge port."
    AUGMENTS { dot1dBasePortEntry }
    ::= { dot1dPortGarpTable 1 }

Dot1dPortGarpEntry ::=
    SEQUENCE {
        dot1dPortGarpJoinTime
            TimeInterval,
        dot1dPortGarpLeaveTime
            TimeInterval,
        dot1dPortGarpLeaveAllTime
            TimeInterval
    }

dot1dPortGarpJoinTime OBJECT-TYPE
    SYNTAX      TimeInterval
    MAX-ACCESS  read-write
    STATUS      current
    DESCRIPTION
        "The GARP Join time, in centiseconds."
    DEFVAL      { 20 }
    ::= { dot1dPortGarpEntry 1 }

dot1dPortGarpLeaveTime OBJECT-TYPE
    SYNTAX      TimeInterval
    MAX-ACCESS  read-write
    STATUS      current
    DESCRIPTION
        "The GARP Leave time, in centiseconds."
    DEFVAL      { 60 }
    ::= { dot1dPortGarpEntry 2 }


dot1dPortGarpLeaveAllTime OBJECT-TYPE
    SYNTAX      TimeInterval
    MAX-ACCESS  read-write
    STATUS      current
    DESCRIPTION
        "The GARP LeaveAll time, in centiseconds."
    DEFVAL      { 1000 }
    ::= { dot1dPortGarpEntry 3 }

-- -------------------------------------------------------------
-- The GMRP Port Configuration and Status Table
-- -------------------------------------------------------------

dot1dPortGmrpTable OBJECT-TYPE
    SYNTAX      SEQUENCE OF Dot1dPortGmrpEntry
    MAX-ACCESS  not-accessible
    STATUS      current
    DESCRIPTION
        "A table of GMRP control and status information about
        every bridge port.  Augments the dot1dBasePortTable."
    ::= { dot1dGmrp 1 }

dot1dPortGmrpEntry OBJECT-TYPE
    SYNTAX      Dot1dPortGmrpEntry
    MAX-ACCESS  not-accessible
    STATUS      current
    DESCRIPTION
        "GMRP control and status information for a bridge port."
    AUGMENTS { dot1dBasePortEntry }
    ::= { dot1dPortGmrpTable 1 }

Dot1dPortGmrpEntry ::=
    SEQUENCE {
        dot1dPortGmrpStatus
            EnabledStatus,
        dot1dPortGmrpFailedRegistrations
            Counter32,
        dot1dPortGmrpLastPduOrigin
            MacAddress
    }

dot1dPortGmrpStatus OBJECT-TYPE
    SYNTAX      EnabledStatus
    MAX-ACCESS  read-write
    STATUS      current


    DESCRIPTION
        "The administrative state of GMRP operation on this port. The
        value enabled(1) indicates that GMRP is enabled on this port
        in all VLANs as long as dot1dGmrpStatus is also enabled(1).
        A value of disabled(2) indicates that GMRP is disabled on
        this port in all VLANs: any GMRP packets received will
        be silently discarded and no GMRP registrations will be
        propagated from other ports. Setting this to a value of
        enabled(1) will be stored by the agent but will only take
        effect on the GMRP protocol operation if dot1dGmrpStatus
        also indicates the value enabled(1).  This object affects
        all GMRP Applicant and Registrar state machines on this
        port.  A transition from disabled(2) to enabled(1) will
        cause a reset of all GMRP state machines on this port."
    DEFVAL      { enabled }
    ::= { dot1dPortGmrpEntry 1 }

dot1dPortGmrpFailedRegistrations OBJECT-TYPE
    SYNTAX      Counter32
    MAX-ACCESS  read-only
    STATUS      current
    DESCRIPTION
        "The total number of failed GMRP registrations, for any
        reason, in all VLANs, on this port."
    ::= { dot1dPortGmrpEntry 2 }

dot1dPortGmrpLastPduOrigin OBJECT-TYPE
    SYNTAX      MacAddress
    MAX-ACCESS  read-only
    STATUS      current
    DESCRIPTION
        "The Source MAC Address of the last GMRP message
        received on this port."
    ::= { dot1dPortGmrpEntry 3 }

-- -------------------------------------------------------------
--  High Capacity Port Table for Transparent Bridges
-- -------------------------------------------------------------

dot1dTpHCPortTable OBJECT-TYPE
    SYNTAX      SEQUENCE OF Dot1dTpHCPortEntry
    MAX-ACCESS  not-accessible
    STATUS      current
    DESCRIPTION
        "A table that contains information about every high
        capacity port that is associated with this transparent
        bridge."
    ::= { dot1dTp 5 }


dot1dTpHCPortEntry OBJECT-TYPE
    SYNTAX      Dot1dTpHCPortEntry
    MAX-ACCESS  not-accessible
    STATUS      current
    DESCRIPTION
        "Statistics information for each high capacity port of a
        transparent bridge."
    INDEX   { dot1dTpPort }
    ::= { dot1dTpHCPortTable 1 }

Dot1dTpHCPortEntry ::=
    SEQUENCE {
        dot1dTpHCPortInFrames
            Counter64,
        dot1dTpHCPortOutFrames
            Counter64,
        dot1dTpHCPortInDiscards
            Counter64
    }

dot1dTpHCPortInFrames OBJECT-TYPE
    SYNTAX      Counter64
    MAX-ACCESS  read-only
    STATUS      current
    DESCRIPTION
        "The number of frames that have been received by this
        port from its segment.  Note that a frame received on
        the interface corresponding to this port is only counted
        by this object if and only if it is for a protocol being
        processed by the local bridging function, including
        bridge management frames."
    REFERENCE
        "ISO/IEC 15802-3 Section 14.6.1.1.3"
    ::= { dot1dTpHCPortEntry 1 }

dot1dTpHCPortOutFrames OBJECT-TYPE
    SYNTAX      Counter64
    MAX-ACCESS  read-only
    STATUS      current
    DESCRIPTION
        "The number of frames that have been transmitted by this
        port to its segment.  Note that a frame transmitted on
        the interface corresponding to this port is only counted
        by this object if and only if it is for a protocol being
        processed by the local bridging function, including
        bridge management frames."


    REFERENCE
        "ISO/IEC 15802-3 Section 14.6.1.1.3"
    ::= { dot1dTpHCPortEntry 2 }

dot1dTpHCPortInDiscards OBJECT-TYPE
    SYNTAX      Counter64
    MAX-ACCESS  read-only
    STATUS      current
    DESCRIPTION
        "Count of valid frames that have been received by this
        port from its segment which were discarded (i.e.,
        filtered) by the Forwarding Process."
    REFERENCE
        "ISO/IEC 15802-3 Section 14.6.1.1.3"
    ::= { dot1dTpHCPortEntry 3 }

-- ----------------------------------------------------
--  Upper part of High Capacity Port Table for Transparent Bridges
-- ----------------------------------------------------

dot1dTpPortOverflowTable OBJECT-TYPE
    SYNTAX      SEQUENCE OF Dot1dTpPortOverflowEntry
    MAX-ACCESS  not-accessible
    STATUS      current
    DESCRIPTION
        "A table that contains the most-significant bits of
        statistics counters for ports that are associated with this
        transparent bridge that are on high capacity interfaces, as
        defined in the conformance clauses for this table. This table
        is provided as a way to read 64-bit counters for agents which
        support only SNMPv1.

        Note that the reporting of most-significant and
        least-significant counter bits separately runs the risk of
        missing an overflow of the lower bits in the interval between
        sampling. The manager must be aware of this possibility, even
        within the same varbindlist, when interpreting the results of
        a request or asynchronous notification."
    ::= { dot1dTp 6 }

dot1dTpPortOverflowEntry OBJECT-TYPE
    SYNTAX      Dot1dTpPortOverflowEntry
    MAX-ACCESS  not-accessible


    STATUS      current
    DESCRIPTION
        "The most significant bits of statistics counters for a high
        capacity interface of a transparent bridge. Each object is
        associated with a corresponding object in dot1dTpPortTable
        which indicates the least significant bits of the counter."
    INDEX   { dot1dTpPort }
    ::= { dot1dTpPortOverflowTable 1 }

Dot1dTpPortOverflowEntry ::=
    SEQUENCE {
        dot1dTpPortInOverflowFrames
            Counter32,
        dot1dTpPortOutOverflowFrames
            Counter32,
        dot1dTpPortInOverflowDiscards
            Counter32
    }

dot1dTpPortInOverflowFrames OBJECT-TYPE
    SYNTAX      Counter32
    MAX-ACCESS  read-only
    STATUS      current
    DESCRIPTION
        "The number of times the associated dot1dTpPortInFrames
        counter has overflowed."
    REFERENCE
        "ISO/IEC 15802-3 Section 14.6.1.1.3"
    ::= { dot1dTpPortOverflowEntry 1 }

dot1dTpPortOutOverflowFrames OBJECT-TYPE
    SYNTAX      Counter32
    MAX-ACCESS  read-only
    STATUS      current
    DESCRIPTION
        "The number of times the associated dot1dTpPortOutFrames
        counter has overflowed."
    REFERENCE
        "ISO/IEC 15802-3 Section 14.6.1.1.3"
    ::= { dot1dTpPortOverflowEntry 2 }

dot1dTpPortInOverflowDiscards OBJECT-TYPE
    SYNTAX      Counter32
    MAX-ACCESS  read-only
    STATUS      current


    DESCRIPTION
        "The number of times the associated
        dot1dTpPortInDiscards counter has overflowed."
    REFERENCE
        "ISO/IEC 15802-3 Section 14.6.1.1.3"
    ::= { dot1dTpPortOverflowEntry 3 }

-- -------------------------------------------------------------
-- IEEE 802.1p MIB - Conformance Information
-- -------------------------------------------------------------

pBridgeConformance OBJECT IDENTIFIER ::= { pBridgeMIB 2 }

pBridgeGroups OBJECT IDENTIFIER ::= { pBridgeConformance 1 }

pBridgeCompliances OBJECT IDENTIFIER
    ::= { pBridgeConformance 2 }

-- -------------------------------------------------------------
-- units of conformance
-- -------------------------------------------------------------

pBridgeExtCapGroup OBJECT-GROUP
    OBJECTS {
        dot1dDeviceCapabilities,
        dot1dPortCapabilities
    }
    STATUS      current
    DESCRIPTION
        "A collection of objects indicating the optional
        capabilites of the device."
    ::= { pBridgeGroups 1 }

pBridgeDeviceGmrpGroup OBJECT-GROUP
    OBJECTS {
        dot1dGmrpStatus
    }
    STATUS      current
    DESCRIPTION
        "A collection of objects providing device-level control
        for the Multicast Filtering extended bridge services."
    ::= { pBridgeGroups 2 }


pBridgeDevicePriorityGroup OBJECT-GROUP
    OBJECTS {
        dot1dTrafficClassesEnabled
    }
    STATUS      current
    DESCRIPTION
        "A collection of objects providing device-level control
        for the Priority services."
    ::= { pBridgeGroups 3 }

pBridgeDefaultPriorityGroup OBJECT-GROUP
    OBJECTS {
        dot1dPortDefaultUserPriority
    }
    STATUS      current
    DESCRIPTION
        "A collection of objects defining the User Priority
        applicable to each port for media which do not support
        native User Priority."
    ::= { pBridgeGroups 4 }

pBridgeRegenPriorityGroup OBJECT-GROUP
    OBJECTS {
        dot1dRegenUserPriority
    }
    STATUS      current
    DESCRIPTION
        "A collection of objects defining the User Priorities
        applicable to each port for media which support native
        User Priority."
    ::= { pBridgeGroups 5 }

pBridgePriorityGroup OBJECT-GROUP
    OBJECTS {
        dot1dPortNumTrafficClasses,
        dot1dTrafficClass
    }
    STATUS      current
    DESCRIPTION
        "A collection of objects defining the traffic classes
        within a bridge for each evaluated User Priority."
    ::= { pBridgeGroups 6 }


pBridgeAccessPriorityGroup OBJECT-GROUP
    OBJECTS {
        dot1dPortOutboundAccessPriority
    }
    STATUS      current
    DESCRIPTION
        "A collection of objects defining the media dependent
        outbound access level for each priority."
    ::= { pBridgeGroups 7 }

pBridgePortGarpGroup OBJECT-GROUP
    OBJECTS {
        dot1dPortGarpJoinTime,
        dot1dPortGarpLeaveTime,
        dot1dPortGarpLeaveAllTime
    }
    STATUS      current
    DESCRIPTION
        "A collection of objects providing port level control
        and status information for GARP operation."
    ::= { pBridgeGroups 8 }

pBridgePortGmrpGroup OBJECT-GROUP
    OBJECTS {
        dot1dPortGmrpStatus,
        dot1dPortGmrpFailedRegistrations,
        dot1dPortGmrpLastPduOrigin
    }
    STATUS      current
    DESCRIPTION
        "A collection of objects providing port level control
        and status information for GMRP operation."
    ::= { pBridgeGroups 9 }

pBridgeHCPortGroup OBJECT-GROUP
    OBJECTS {
        dot1dTpHCPortInFrames,
        dot1dTpHCPortOutFrames,
        dot1dTpHCPortInDiscards
    }
    STATUS      current
    DESCRIPTION
        "A collection of objects providing 64-bit statistics
         counters for high capacity bridge ports."
    ::= { pBridgeGroups 10 }


pBridgePortOverflowGroup OBJECT-GROUP
    OBJECTS {
        dot1dTpPortInOverflowFrames,
        dot1dTpPortOutOverflowFrames,
        dot1dTpPortInOverflowDiscards
    }
    STATUS      current
    DESCRIPTION
        "A collection of objects providing overflow statistics
        counters for high capacity bridge ports."
    ::= { pBridgeGroups 11 }

-- -------------------------------------------------------------
-- compliance statements
-- -------------------------------------------------------------

pBridgeCompliance MODULE-COMPLIANCE
    STATUS  current
    DESCRIPTION
        "The compliance statement for device support of Priority
        and Multicast Filtering extended bridging services."

    MODULE
        MANDATORY-GROUPS { pBridgeExtCapGroup }

        GROUP       pBridgeDeviceGmrpGroup
        DESCRIPTION
            "This group is mandatory for devices supporting the GMRP
            application, defined by IEEE 802.1D Extended Filtering
            Services."

        GROUP       pBridgeDevicePriorityGroup
        DESCRIPTION
            "This group is mandatory only for devices supporting
            the priority forwarding operations defined by IEEE
            802.1D."

        GROUP       pBridgeDefaultPriorityGroup
        DESCRIPTION
            "This group is mandatory only for devices supporting
            the priority forwarding operations defined by the
            extended bridge services with media types, such as
            Ethernet, that do not support native User Priority."


        GROUP       pBridgeRegenPriorityGroup
        DESCRIPTION
            "This group is mandatory only for devices supporting
            the priority forwarding operations defined by IEEE 802.1D
            and which have interface media types that support
            native User Priority e.g. IEEE 802.5."

        GROUP       pBridgePriorityGroup
        DESCRIPTION
            "This group is mandatory only for devices supporting
            the priority forwarding operations defined by IEEE 802.1D."

        GROUP       pBridgeAccessPriorityGroup
        DESCRIPTION
            "This group is optional and is relevant only for devices
            supporting the priority forwarding operations defined by
            IEEE 802.1D and which have interface media types that support
            native Access Priority e.g. IEEE 802.5."

        GROUP       pBridgePortGarpGroup
        DESCRIPTION
            "This group is mandatory for devices supporting any
            of the GARP applications: e.g. GMRP, defined by the
            extended filtering services of 802.1D; or GVRP,
            defined by 802.1Q (refer to the Q-BRIDGE-MIB for
            conformance statements for GVRP)."

        GROUP       pBridgePortGmrpGroup
        DESCRIPTION
            "This group is mandatory for devices supporting the
            GMRP application, as defined by IEEE 802.1D Extended
            Filtering Services."

        GROUP       pBridgeHCPortGroup
        DESCRIPTION
            "Support for this group in a device is mandatory for those
            bridge ports which map to network interfaces that have the
            value of the corresponding instance of ifSpeed
            greater than 650,000,000 bits/second."

        GROUP       pBridgePortOverflowGroup
        DESCRIPTION
            "Support for this group in a device is mandatory for those
            bridge ports which map to network interfaces that have the
            value of the corresponding instance of ifSpeed
            greater than 650,000,000 bits/second."


        OBJECT      dot1dPortNumTrafficClasses
        MIN-ACCESS  read-only
        DESCRIPTION
            "Write access is not required."

        OBJECT      dot1dTrafficClass
        MIN-ACCESS  read-only
        DESCRIPTION
            "Write access is not required."

        OBJECT      dot1dRegenUserPriority
        MIN-ACCESS  read-only
        DESCRIPTION
            "Write access is not required."

       ::= { pBridgeCompliances 1 }

END


Q-BRIDGE-MIB DEFINITIONS ::= BEGIN

-- -------------------------------------------------------------
-- MIB for IEEE 802.1Q Devices
-- -------------------------------------------------------------

IMPORTS
    MODULE-IDENTITY, OBJECT-TYPE,
    Counter32, Counter64, Unsigned32, TimeTicks
        FROM SNMPv2-SMI
    RowStatus, TruthValue, TEXTUAL-CONVENTION, MacAddress
        FROM SNMPv2-TC
    SnmpAdminString
        FROM SNMP-FRAMEWORK-MIB
    MODULE-COMPLIANCE, OBJECT-GROUP
        FROM SNMPv2-CONF
    dot1dBridge, dot1dBasePortEntry, dot1dBasePort
        FROM BRIDGE-MIB
    EnabledStatus
        FROM P-BRIDGE-MIB
    TimeFilter
        FROM RMON2-MIB;

qBridgeMIB MODULE-IDENTITY
    LAST-UPDATED "9908250000Z"
    ORGANIZATION "IETF Bridge MIB Working Group"

    CONTACT-INFO
        "       Les Bell
        Postal: 3Com Europe Ltd.
                3Com Centre, Boundary Way
                Hemel Hempstead, Herts. HP2 7YU
                UK
         Phone: +44 1442 438025
         Email: Les_Bell@3Com.com

                Andrew Smith
        Postal: Extreme Networks
                3585 Monroe St.
                Santa Clara CA 95051
                USA
         Phone: +1 408 579 2821
         Email: andrew@extremenetworks.com

                Paul Langille
        Postal: Newbridge Networks
                5 Corporate Drive
                Andover, MA 01810
                USA
         Phone: +1 978 691 4665
         Email: langille@newbridge.com

                Anil Rijhsinghani
        Postal: Cabletron Systems
                50 Minuteman Road
                Andover, MA 01810
                USA
         Phone: +1 978 684 1295
         Email: anil@cabletron.com

                Keith McCloghrie
        Postal: cisco Systems, Inc.
                170 West Tasman Drive
                San Jose, CA 95134-1706
                USA
         Phone: +1 408 526 5260
         Email: kzm@cisco.com"
    DESCRIPTION
        "The VLAN Bridge MIB module for managing Virtual Bridged
        Local Area Networks, as defined by IEEE 802.1Q-1998."

-- revision history

    REVISION     "9908250000Z"
    DESCRIPTION
         "Initial version, published as RFC 2674."

    ::= { dot1dBridge 7 }

qBridgeMIBObjects OBJECT IDENTIFIER ::= { qBridgeMIB 1 }

-- -------------------------------------------------------------
-- Textual Conventions
-- -------------------------------------------------------------

PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING

VlanIndex ::= TEXTUAL-CONVENTION
    STATUS      current
    DESCRIPTION
        "A value used to index per-VLAN tables: values of 0 and
        4095 are not permitted; if the value is between 1 and
        4094 inclusive, it represents an IEEE 802.1Q VLAN-ID with
        global scope within a given bridged domain (see VlanId
        textual convention).  If the value is greater than 4095
        then it represents a VLAN with scope local to the
        particular agent, i.e. one without a global VLAN-ID
        assigned to it. Such VLANs are outside the scope of
        IEEE 802.1Q but it is convenient to be able to manage them
        in the same way using this MIB."
    SYNTAX      Unsigned32

VlanId ::= TEXTUAL-CONVENTION
    STATUS      current
    DESCRIPTION
        "A 12-bit VLAN ID used in the VLAN Tag header."
    SYNTAX      INTEGER (1..4094)

-- -------------------------------------------------------------
-- groups in the Q-BRIDGE MIB
-- -------------------------------------------------------------

dot1qBase       OBJECT IDENTIFIER ::= { qBridgeMIBObjects 1 }
dot1qTp         OBJECT IDENTIFIER ::= { qBridgeMIBObjects 2 }
dot1qStatic     OBJECT IDENTIFIER ::= { qBridgeMIBObjects 3 }
dot1qVlan       OBJECT IDENTIFIER ::= { qBridgeMIBObjects 4 }

-- -------------------------------------------------------------

-- -------------------------------------------------------------
-- dot1qBase group
-- -------------------------------------------------------------

dot1qVlanVersionNumber OBJECT-TYPE
    SYNTAX      INTEGER {
                    version1(1)
                }
    MAX-ACCESS  read-only
    STATUS      current
    DESCRIPTION
        "The version number of IEEE 802.1Q that this device
        supports."
    REFERENCE
        "IEEE 802.1Q/D11 Section 12.10.1.1"
    ::= { dot1qBase 1 }

dot1qMaxVlanId OBJECT-TYPE
    SYNTAX      VlanId
    MAX-ACCESS  read-only
    STATUS      current
    DESCRIPTION
        "The maximum IEEE 802.1Q VLAN ID that this device
        supports."
    REFERENCE
        "IEEE 802.1Q/D11 Section 9.3.2.3"
    ::= { dot1qBase 2 }

dot1qMaxSupportedVlans OBJECT-TYPE
    SYNTAX      Unsigned32
    MAX-ACCESS  read-only
    STATUS      current
    DESCRIPTION
        "The maximum number of IEEE 802.1Q VLANs that this
        device supports."
    REFERENCE
        "IEEE 802.1Q/D11 Section 12.10.1.1"
    ::= { dot1qBase 3 }

dot1qNumVlans OBJECT-TYPE
    SYNTAX      Unsigned32
    MAX-ACCESS  read-only
    STATUS      current
    DESCRIPTION
        "The current number of IEEE 802.1Q VLANs that are
        configured in this device."
    REFERENCE
        "IEEE 802.1Q/D11 Section 12.7.1.1"
    ::= { dot1qBase 4 }

dot1qGvrpStatus OBJECT-TYPE
    SYNTAX      EnabledStatus
    MAX-ACCESS  read-write
    STATUS      current
    DESCRIPTION
        "The administrative status requested by management for
        GVRP.  The value enabled(1) indicates that GVRP should
        be enabled on this device, on all ports for which it has
        not been specifically disabled.  When disabled(2), GVRP
        is disabled on all ports and all GVRP packets will be
        forwarded transparently.  This object affects all GVRP
        Applicant and Registrar state machines.  A transition
        from disabled(2) to enabled(1) will cause a reset of all
        GVRP state machines on all ports."
    DEFVAL      { enabled }
    ::= { dot1qBase 5 }

-- -------------------------------------------------------------
-- the dot1qTp group
-- -------------------------------------------------------------

-- -------------------------------------------------------------
-- the current Filtering Database Table
-- -------------------------------------------------------------

dot1qFdbTable OBJECT-TYPE
    SYNTAX      SEQUENCE OF Dot1qFdbEntry
    MAX-ACCESS  not-accessible
    STATUS      current
    DESCRIPTION
        "A table that contains configuration and control
        information for each Filtering Database currently
        operating on this device.  Entries in this table appear
        automatically when VLANs are assigned FDB IDs in the
        dot1qVlanCurrentTable."
    ::= { dot1qTp 1 }

dot1qFdbEntry OBJECT-TYPE
    SYNTAX      Dot1qFdbEntry
    MAX-ACCESS  not-accessible
    STATUS      current
    DESCRIPTION
        "Information about a specific Filtering Database."
    INDEX   { dot1qFdbId }
    ::= { dot1qFdbTable 1 }

Dot1qFdbEntry ::=
    SEQUENCE {
        dot1qFdbId
            Unsigned32,
        dot1qFdbDynamicCount
            Counter32
    }

dot1qFdbId OBJECT-TYPE
    SYNTAX       Unsigned32
    MAX-ACCESS   not-accessible
    STATUS       current
    DESCRIPTION
        "The identity of this Filtering Database."
    ::= { dot1qFdbEntry 1 }

dot1qFdbDynamicCount OBJECT-TYPE
    SYNTAX       Counter32
    MAX-ACCESS   read-only
    STATUS       current
    DESCRIPTION
        "The current number of dynamic entries in this
        Filtering Database."
    REFERENCE
        "IEEE 802.1Q/D11 Section 12.7.1.1.3"
    ::= { dot1qFdbEntry 2 }

-- -------------------------------------------------------------
-- Multiple Forwarding Databases for 802.1Q Transparent devices
-- This table is an alternative to the dot1dTpFdbTable,
-- previously defined for 802.1D devices which only support a
-- single Forwarding Database.
-- -------------------------------------------------------------

dot1qTpFdbTable OBJECT-TYPE
    SYNTAX      SEQUENCE OF Dot1qTpFdbEntry
    MAX-ACCESS  not-accessible
    STATUS      current
    DESCRIPTION
        "A table that contains information about unicast entries
        for which the device has forwarding and/or filtering
        information.  This information is used by the
        transparent bridging function in determining how to
        propagate a received frame."
    REFERENCE
        "IEEE 802.1Q/D11 Section 12.7.7"
    ::= { dot1qTp 2 }

dot1qTpFdbEntry OBJECT-TYPE
    SYNTAX      Dot1qTpFdbEntry
    MAX-ACCESS  not-accessible
    STATUS      current
    DESCRIPTION
        "Information about a specific unicast MAC address for
        which the device has some forwarding and/or filtering
        information."
    INDEX   { dot1qFdbId, dot1qTpFdbAddress }
    ::= { dot1qTpFdbTable 1 }

Dot1qTpFdbEntry ::=
    SEQUENCE {
        dot1qTpFdbAddress
            MacAddress,
        dot1qTpFdbPort
            INTEGER,
        dot1qTpFdbStatus
            INTEGER
    }

dot1qTpFdbAddress OBJECT-TYPE
    SYNTAX      MacAddress
    MAX-ACCESS  not-accessible
    STATUS      current

    DESCRIPTION
        "A unicast MAC address for which the device has
        forwarding and/or filtering information."
    ::= { dot1qTpFdbEntry 1 }

dot1qTpFdbPort OBJECT-TYPE
    SYNTAX      INTEGER (0..65535)
    MAX-ACCESS  read-only
    STATUS      current
    DESCRIPTION
        "Either the value '0', or the port number of the port on
        which a frame having a source address equal to the value
        of the corresponding instance of dot1qTpFdbAddress has
        been seen.  A value of '0' indicates that the port
        number has not been learned but that the device does
        have some forwarding/filtering information about this
        address (e.g. in the dot1qStaticUnicastTable).
        Implementors are encouraged to assign the port value to
        this object whenever it is learned even for addresses
        for which the corresponding value of dot1qTpFdbStatus is
        not learned(3)."
    ::= { dot1qTpFdbEntry 2 }

dot1qTpFdbStatus OBJECT-TYPE
    SYNTAX      INTEGER {
                    other(1),
                    invalid(2),
                    learned(3),
                    self(4),
                    mgmt(5)
                }
    MAX-ACCESS  read-only
    STATUS      current
    DESCRIPTION
        "The status of this entry.  The meanings of the values
        are:
            other(1) - none of the following.  This may include
                the case where some other MIB object (not the
                corresponding instance of dot1qTpFdbPort, nor an
                entry in the dot1qStaticUnicastTable) is being
                used to determine if and how frames addressed to
                the value of the corresponding instance of
                dot1qTpFdbAddress are being forwarded.
            invalid(2) - this entry is no longer valid (e.g., it
                was learned but has since aged out), but has not
                yet been flushed from the table.
            learned(3) - the value of the corresponding instance
                of dot1qTpFdbPort was learned and is being used.

            self(4) - the value of the corresponding instance of
                dot1qTpFdbAddress represents one of the device's
                addresses.  The corresponding instance of
                dot1qTpFdbPort indicates which of the device's
                ports has this address.
            mgmt(5) - the value of the corresponding instance of
                dot1qTpFdbAddress is also the value of an
                existing instance of dot1qStaticAddress."
    ::= { dot1qTpFdbEntry 3 }

-- -------------------------------------------------------------
-- Dynamic Group Registration Table
-- -------------------------------------------------------------

dot1qTpGroupTable OBJECT-TYPE
    SYNTAX      SEQUENCE OF Dot1qTpGroupEntry
    MAX-ACCESS  not-accessible
    STATUS      current
    DESCRIPTION
        "A table containing filtering information for VLANs
        configured into the bridge by (local or network)
        management, or learnt dynamically, specifying the set of
        ports to which frames received on a VLAN for this FDB
        and containing a specific Group destination address are
        allowed to be forwarded."
    ::= { dot1qTp 3 }

dot1qTpGroupEntry OBJECT-TYPE
    SYNTAX      Dot1qTpGroupEntry
    MAX-ACCESS  not-accessible
    STATUS      current
    DESCRIPTION
        "Filtering information configured into the bridge by
        management, or learnt dynamically, specifying the set of
        ports to which frames received on a VLAN and containing
        a specific Group destination address, are allowed to be
        forwarded.  The subset of these ports learnt dynamically
        is also provided."
    INDEX   { dot1qVlanIndex, dot1qTpGroupAddress }
    ::= { dot1qTpGroupTable 1 }

Dot1qTpGroupEntry ::=
    SEQUENCE {
        dot1qTpGroupAddress
            MacAddress,
        dot1qTpGroupEgressPorts
            PortList,
        dot1qTpGroupLearnt

            PortList
    }

dot1qTpGroupAddress OBJECT-TYPE
    SYNTAX      MacAddress
    MAX-ACCESS  not-accessible
    STATUS      current
    DESCRIPTION
        "The destination Group MAC address in a frame to which
        this entry's filtering information applies."
    ::= { dot1qTpGroupEntry 1 }

dot1qTpGroupEgressPorts OBJECT-TYPE
    SYNTAX      PortList
    MAX-ACCESS  read-only
    STATUS      current
    DESCRIPTION
        "The complete set of ports, in this VLAN, to which
        frames destined for this Group MAC address are currently
        being explicitly forwarded.  This does not include ports
        for which this address is only implicitly forwarded, in
        the dot1qForwardAllPorts list."
    ::= { dot1qTpGroupEntry 2 }

dot1qTpGroupLearnt OBJECT-TYPE
    SYNTAX      PortList
    MAX-ACCESS  read-only
    STATUS      current
    DESCRIPTION
        "The subset of ports in dot1qTpGroupEgressPorts which
        were learnt by GMRP or some other dynamic mechanism, in
        this Filtering database."
    ::= { dot1qTpGroupEntry 3 }

-- -------------------------------------------------------------
-- Service Requirements Group
-- -------------------------------------------------------------

dot1qForwardAllTable OBJECT-TYPE
    SYNTAX      SEQUENCE OF Dot1qForwardAllEntry
    MAX-ACCESS  not-accessible
    STATUS      current
    DESCRIPTION
        "A table containing forwarding information for each
        VLAN, specifying the set of ports to which forwarding of
        all multicasts applies, configured statically by
        management or dynamically by GMRP.  An entry appears in
        this table for all VLANs that are currently

        instantiated."
    REFERENCE
        "IEEE 802.1Q/D11 Section 12.7.2, 12.7.7"
    ::= { dot1qTp 4 }

dot1qForwardAllEntry OBJECT-TYPE
    SYNTAX      Dot1qForwardAllEntry
    MAX-ACCESS  not-accessible
    STATUS      current
    DESCRIPTION
        "Forwarding information for a VLAN, specifying the set
        of ports to which all multicasts should be forwarded,
        configured statically by management or dynamically by
        GMRP."
    INDEX   { dot1qVlanIndex }
    ::= { dot1qForwardAllTable 1 }

Dot1qForwardAllEntry ::=
    SEQUENCE {
        dot1qForwardAllPorts
            PortList,
        dot1qForwardAllStaticPorts
            PortList,
        dot1qForwardAllForbiddenPorts
            PortList
    }

dot1qForwardAllPorts OBJECT-TYPE
    SYNTAX      PortList
    MAX-ACCESS  read-only
    STATUS      current
    DESCRIPTION
        "The complete set of ports in this VLAN to which all
        multicast group-addressed frames are to be forwarded.
        This includes ports for which this need has been
        determined dynamically by GMRP, or configured statically
        by management."
    ::= { dot1qForwardAllEntry 1 }

dot1qForwardAllStaticPorts OBJECT-TYPE
    SYNTAX      PortList
    MAX-ACCESS  read-write
    STATUS      current

    DESCRIPTION
        "The set of ports configured by management in this VLAN
        to which all multicast group-addressed frames are to be
        forwarded.  Ports entered in this list will also appear
        in the complete set shown by dot1qForwardAllPorts.  This
        value will be restored after the device is reset.  This
        only applies to ports that are members of the VLAN,
        defined by dot1qVlanCurrentEgressPorts.  A port may not
        be added in this set if it is already a member of the
        set of ports in dot1qForwardAllForbiddenPorts.  The
        default value is a string of ones of appropriate length,
        to indicate standard non-EFS behaviour, i.e.  forward
        all multicasts to all ports."
    ::= { dot1qForwardAllEntry 2 }

dot1qForwardAllForbiddenPorts OBJECT-TYPE
    SYNTAX      PortList
    MAX-ACCESS  read-write
    STATUS      current
    DESCRIPTION
        "The set of ports configured by management in this VLAN
        for which the Service Requirement attribute Forward All
        Multicast Groups may not be dynamically registered by
        GMRP.  This value will be restored after the device is
        reset.  A port may not be added in this set if it is
        already a member of the set of ports in
        dot1qForwardAllStaticPorts.  The default value is a
        string of zeros of appropriate length."
    ::= { dot1qForwardAllEntry 3 }

dot1qForwardUnregisteredTable OBJECT-TYPE
    SYNTAX      SEQUENCE OF Dot1qForwardUnregisteredEntry
    MAX-ACCESS  not-accessible
    STATUS      current
    DESCRIPTION
        "A table containing forwarding information for each
        VLAN, specifying the set of ports to which forwarding of
        multicast group-addressed frames for which there is no
        more specific forwarding information applies.  This is
        configured statically by management and determined
        dynamically by GMRP.  An entry appears in this table for
        all VLANs that are currently instantiated."
    REFERENCE
        "IEEE 802.1Q/D11 Section 12.7.2, 12.7.7"
    ::= { dot1qTp 5 }

dot1qForwardUnregisteredEntry OBJECT-TYPE
    SYNTAX      Dot1qForwardUnregisteredEntry

    MAX-ACCESS  not-accessible
    STATUS      current
    DESCRIPTION
        "Forwarding information for a VLAN, specifying the set
        of ports to which all multicasts for which there is no
        more specific forwarding information shall be forwarded.
        This is configured statically by management or
        dynamically by GMRP."
    INDEX   { dot1qVlanIndex }
    ::= { dot1qForwardUnregisteredTable 1 }

Dot1qForwardUnregisteredEntry ::=
    SEQUENCE {
        dot1qForwardUnregisteredPorts
            PortList,
        dot1qForwardUnregisteredStaticPorts
            PortList,
        dot1qForwardUnregisteredForbiddenPorts
            PortList
    }

dot1qForwardUnregisteredPorts OBJECT-TYPE
    SYNTAX      PortList
    MAX-ACCESS  read-only
    STATUS      current
    DESCRIPTION
        "The complete set of ports in this VLAN to which
        multicast group-addressed frames for which there is no
        more specific forwarding information will be forwarded.
        This includes ports for which this need has been
        determined dynamically by GMRP, or configured statically
        by management."
    ::= { dot1qForwardUnregisteredEntry 1 }

dot1qForwardUnregisteredStaticPorts OBJECT-TYPE
    SYNTAX      PortList
    MAX-ACCESS  read-write
    STATUS      current
    DESCRIPTION
        "The set of ports configured by management, in this
        VLAN, to which multicast group-addressed frames for
        which there is no more specific forwarding information
        are to be forwarded.  Ports entered in this list will
        also appear in the complete set shown by
        dot1qForwardUnregisteredPorts.  This value will be
        restored after the device is reset.  A port may not be
        added in this set if it is already a member of the set
        of ports in dot1qForwardUnregisteredForbiddenPorts.  The

        default value is a string of zeros of appropriate
        length, although this has no effect with the default
        value of dot1qForwardAllStaticPorts."
    ::= { dot1qForwardUnregisteredEntry 2 }

dot1qForwardUnregisteredForbiddenPorts OBJECT-TYPE
    SYNTAX      PortList
    MAX-ACCESS  read-write
    STATUS      current
    DESCRIPTION
        "The set of ports configured by management in this VLAN
        for which the Service Requirement attribute Forward
        Unregistered Multicast Groups may not be dynamically
        registered by GMRP.  This value will be restored after
        the device is reset.  A port may not be added in this
        set if it is already a member of the set of ports in
        dot1qForwardUnregisteredStaticPorts.  The default value
        is a string of zeros of appropriate length."
    ::= { dot1qForwardUnregisteredEntry 3 }

-- -------------------------------------------------------------
-- The Static (Destination-Address Filtering) Database
-- -------------------------------------------------------------

dot1qStaticUnicastTable OBJECT-TYPE
    SYNTAX      SEQUENCE OF Dot1qStaticUnicastEntry
    MAX-ACCESS  not-accessible
    STATUS      current
    DESCRIPTION
        "A table containing filtering information for Unicast
        MAC addresses for each Filtering Database, configured
        into the device by (local or network) management
        specifying the set of ports to which frames received
        from specific ports and containing specific unicast
        destination addresses are allowed to be forwarded.  A
        value of zero in this table as the port number from
        which frames with a specific destination address are
        received, is used to specify all ports for which there
        is no specific entry in this table for that particular
        destination address.  Entries are valid for unicast
        addresses only."
    REFERENCE
        "IEEE 802.1Q/D11 Section 12.7.7,
        ISO/IEC 15802-3 Section 7.9.1"
    ::= { dot1qStatic 1 }

dot1qStaticUnicastEntry OBJECT-TYPE
    SYNTAX      Dot1qStaticUnicastEntry
    MAX-ACCESS  not-accessible
    STATUS      current
    DESCRIPTION
        "Filtering information configured into the device by
        (local or network) management specifying the set of
        ports to which frames received from a specific port and
        containing a specific unicast destination address are
        allowed to be forwarded."
    INDEX   {
        dot1qFdbId,
        dot1qStaticUnicastAddress,
        dot1qStaticUnicastReceivePort
    }
    ::= { dot1qStaticUnicastTable 1 }

Dot1qStaticUnicastEntry ::=
    SEQUENCE {
        dot1qStaticUnicastAddress
            MacAddress,
        dot1qStaticUnicastReceivePort
            INTEGER,
        dot1qStaticUnicastAllowedToGoTo
            PortList,
        dot1qStaticUnicastStatus
            INTEGER
    }

dot1qStaticUnicastAddress OBJECT-TYPE
    SYNTAX      MacAddress
    MAX-ACCESS  not-accessible
    STATUS      current
    DESCRIPTION
        "The destination MAC address in a frame to which this
        entry's filtering information applies.  This object must
        take the value of a unicast address."
    ::= { dot1qStaticUnicastEntry 1 }

dot1qStaticUnicastReceivePort OBJECT-TYPE
    SYNTAX      INTEGER (0..65535)
    MAX-ACCESS  not-accessible
    STATUS      current
    DESCRIPTION
        "Either the value '0', or the port number of the port
        from which a frame must be received in order for this
        entry's filtering information to apply.  A value of zero
        indicates that this entry applies on all ports of the

        device for which there is no other applicable entry."
    ::= { dot1qStaticUnicastEntry 2 }

dot1qStaticUnicastAllowedToGoTo OBJECT-TYPE
    SYNTAX      PortList
    MAX-ACCESS  read-write
    STATUS      current
    DESCRIPTION
        "The set of ports for which a frame with a specific
        unicast address will be flooded in the event that it
        has not been learned.  It also specifies the set of
        ports a specific unicast address may be dynamically
        learnt on.  The dot1qTpFdbTable will have an equivalent
        entry with a dot1qTpFdbPort value of '0' until this
        address has been learnt, when it will be updated with
        the port the address has been seen on.  This only
        applies to ports that are members of the VLAN, defined
        by dot1qVlanCurrentEgressPorts.  The default value of
        this object is a string of ones of appropriate length."
    REFERENCE
        "IEEE 802.1Q/D11 Table 8-5, ISO/IEC 15802-3 Table 7-5"
    ::= { dot1qStaticUnicastEntry 3 }

dot1qStaticUnicastStatus OBJECT-TYPE
    SYNTAX      INTEGER {
                    other(1),
                    invalid(2),
                    permanent(3),
                    deleteOnReset(4),
                    deleteOnTimeout(5)
                }
    MAX-ACCESS  read-write
    STATUS      current
    DESCRIPTION
        "This object indicates the status of this entry.
            other(1) - this entry is currently in use but
                the conditions under which it will remain
                so differ from the following values.
            invalid(2) - writing this value to the object
                removes the corresponding entry.
            permanent(3) - this entry is currently in use
                and will remain so after the next reset of
                the bridge.
            deleteOnReset(4) - this entry is currently in
                use and will remain so until the next
                reset of the bridge.

            deleteOnTimeout(5) - this entry is currently in
                use and will remain so until it is aged out."
    DEFVAL      { permanent }
    ::= { dot1qStaticUnicastEntry 4 }

dot1qStaticMulticastTable OBJECT-TYPE
    SYNTAX      SEQUENCE OF Dot1qStaticMulticastEntry
    MAX-ACCESS  not-accessible
    STATUS      current
    DESCRIPTION
        "A table containing filtering information for Multicast
        and Broadcast MAC addresses for each VLAN, configured
        into the device by (local or network) management
        specifying the set of ports to which frames received
        from specific ports and containing specific Multicast
        and Broadcast destination addresses are allowed to be
        forwarded.  A value of zero in this table as the port
        number from which frames with a specific destination
        address are received, is used to specify all ports for
        which there is no specific entry in this table for that
        particular destination address.  Entries are valid for
        Multicast and Broadcast addresses only."
    REFERENCE
        "IEEE 802.1Q/D11 Section 12.7.7,
        ISO/IEC 15802-3 Section 7.9.1"
    ::= { dot1qStatic 2 }

dot1qStaticMulticastEntry OBJECT-TYPE
    SYNTAX      Dot1qStaticMulticastEntry
    MAX-ACCESS  not-accessible
    STATUS      current
    DESCRIPTION
        "Filtering information configured into the device by
        (local or network) management specifying the set of
        ports to which frames received from this specific port
        for this VLAN and containing this Multicast or Broadcast
        destination address are allowed to be forwarded."
    INDEX   {
        dot1qVlanIndex,
        dot1qStaticMulticastAddress,
        dot1qStaticMulticastReceivePort
    }
    ::= { dot1qStaticMulticastTable 1 }

Dot1qStaticMulticastEntry ::=
    SEQUENCE {
        dot1qStaticMulticastAddress
            MacAddress,
        dot1qStaticMulticastReceivePort
            INTEGER,
        dot1qStaticMulticastStaticEgressPorts
            PortList,
        dot1qStaticMulticastForbiddenEgressPorts
            PortList,
        dot1qStaticMulticastStatus
            INTEGER
    }

dot1qStaticMulticastAddress OBJECT-TYPE
    SYNTAX      MacAddress
    MAX-ACCESS  not-accessible
    STATUS      current
    DESCRIPTION
        "The destination MAC address in a frame to which this
        entry's filtering information applies.  This object must
        take the value of a Multicast or Broadcast address."
    ::= { dot1qStaticMulticastEntry 1 }

dot1qStaticMulticastReceivePort OBJECT-TYPE
    SYNTAX      INTEGER (0..65535)
    MAX-ACCESS  not-accessible
    STATUS      current
    DESCRIPTION
        "Either the value '0', or the port number of the port
        from which a frame must be received in order for this
        entry's filtering information to apply.  A value of zero
        indicates that this entry applies on all ports of the
        device for which there is no other applicable entry."
    ::= { dot1qStaticMulticastEntry 2 }

dot1qStaticMulticastStaticEgressPorts OBJECT-TYPE
    SYNTAX      PortList
    MAX-ACCESS  read-write
    STATUS      current

    DESCRIPTION
        "The set of ports to which frames received from a
        specific port and destined for a specific Multicast or
        Broadcast MAC address must be forwarded, regardless of
        any dynamic information e.g. from GMRP.  A port may not
        be added in this set if it is already a member of the
        set of ports in dot1qStaticMulticastForbiddenEgressPorts.
        The default value of this object is a string of ones of
        appropriate length."
    ::= { dot1qStaticMulticastEntry 3 }

dot1qStaticMulticastForbiddenEgressPorts OBJECT-TYPE
    SYNTAX      PortList
    MAX-ACCESS  read-write
    STATUS      current
    DESCRIPTION
        "The set of ports to which frames received from a
        specific port and destined for a specific Multicast or
        Broadcast MAC address must not be forwarded, regardless
        of any dynamic information e.g. from GMRP.  A port may
        not be added in this set if it is already a member of the
        set of ports in dot1qStaticMulticastStaticEgressPorts.
        The default value of this object is a string of zeros of
        appropriate length."
    ::= { dot1qStaticMulticastEntry 4 }

dot1qStaticMulticastStatus OBJECT-TYPE
    SYNTAX      INTEGER {
                    other(1),
                    invalid(2),
                    permanent(3),
                    deleteOnReset(4),
                    deleteOnTimeout(5)
                }
    MAX-ACCESS  read-write
    STATUS      current
    DESCRIPTION
        "This object indicates the status of this entry.
            other(1) - this entry is currently in use but
                the conditions under which it will remain
                so differ from the following values.
            invalid(2) - writing this value to the object
                removes the corresponding entry.
            permanent(3) - this entry is currently in use
                and will remain so after the next reset of
                the bridge.

            deleteOnReset(4) - this entry is currently in
                use and will remain so until the next
                reset of the bridge.
            deleteOnTimeout(5) - this entry is currently in
                use and will remain so until it is aged out."
    DEFVAL      { permanent }
    ::= { dot1qStaticMulticastEntry 5 }

-- -------------------------------------------------------------
-- The Current VLAN Database
-- -------------------------------------------------------------

dot1qVlanNumDeletes OBJECT-TYPE
    SYNTAX     Counter32
    MAX-ACCESS read-only
    STATUS     current
    DESCRIPTION
        "The number of times a VLAN entry has been deleted from
        the dot1qVlanCurrentTable (for any reason).  If an entry
        is deleted, then inserted, and then deleted, this
        counter will be incremented by 2."
    ::= { dot1qVlan 1 }

dot1qVlanCurrentTable OBJECT-TYPE
    SYNTAX      SEQUENCE OF Dot1qVlanCurrentEntry
    MAX-ACCESS  not-accessible
    STATUS      current
    DESCRIPTION
        "A table containing current configuration information
        for each VLAN currently configured into the device by
        (local or network) management, or dynamically created
        as a result of GVRP requests received."
    ::= { dot1qVlan 2 }

dot1qVlanCurrentEntry OBJECT-TYPE
    SYNTAX      Dot1qVlanCurrentEntry
    MAX-ACCESS  not-accessible
    STATUS      current
    DESCRIPTION
        "Information for a VLAN configured into the device by
        (local or network) management, or dynamically created
        as a result of GVRP requests received."
    INDEX   { dot1qVlanTimeMark, dot1qVlanIndex }
    ::= { dot1qVlanCurrentTable 1 }

Dot1qVlanCurrentEntry ::=
    SEQUENCE {
        dot1qVlanTimeMark
            TimeFilter,
        dot1qVlanIndex
            VlanIndex,
        dot1qVlanFdbId
            Unsigned32,
        dot1qVlanCurrentEgressPorts
            PortList,
        dot1qVlanCurrentUntaggedPorts
            PortList,
        dot1qVlanStatus
            INTEGER,
        dot1qVlanCreationTime
            TimeTicks
    }

dot1qVlanTimeMark OBJECT-TYPE
    SYNTAX      TimeFilter
    MAX-ACCESS  not-accessible
    STATUS      current
    DESCRIPTION
        "A TimeFilter for this entry.  See the TimeFilter
        textual convention to see how this works."
    ::= { dot1qVlanCurrentEntry 1 }

dot1qVlanIndex OBJECT-TYPE
    SYNTAX      VlanIndex
    MAX-ACCESS  not-accessible
    STATUS      current
    DESCRIPTION
        "The VLAN-ID or other identifier refering to this VLAN."
    ::= { dot1qVlanCurrentEntry 2 }

dot1qVlanFdbId OBJECT-TYPE
    SYNTAX      Unsigned32
    MAX-ACCESS  read-only
    STATUS      current
    DESCRIPTION
        "The Filtering Database used by this VLAN.  This is one
        of the dot1qFdbId values in the dot1qFdbTable.  This
        value is allocated automatically by the device whenever
        the VLAN is created: either dynamically by GVRP, or by

        management, in dot1qVlanStaticTable.  Allocation of this
        value follows the learning constraints defined for this
        VLAN in dot1qLearningConstraintsTable."
    ::= { dot1qVlanCurrentEntry 3 }

dot1qVlanCurrentEgressPorts OBJECT-TYPE
    SYNTAX      PortList
    MAX-ACCESS  read-only
    STATUS      current
    DESCRIPTION
        "The set of ports which are transmitting traffic for
        this VLAN as either tagged or untagged frames."
    REFERENCE
        "IEEE 802.1Q/D11 Section 12.10.2.1"
    ::= { dot1qVlanCurrentEntry 4 }

dot1qVlanCurrentUntaggedPorts OBJECT-TYPE
    SYNTAX      PortList
    MAX-ACCESS  read-only
    STATUS      current
    DESCRIPTION
        "The set of ports which are transmitting traffic for
        this VLAN as untagged frames."
    REFERENCE
        "IEEE 802.1Q/D11 Section 12.10.2.1"
    ::= { dot1qVlanCurrentEntry 5 }

dot1qVlanStatus OBJECT-TYPE
    SYNTAX      INTEGER {
                    other(1),
                    permanent(2),
                    dynamicGvrp(3)
                }
    MAX-ACCESS  read-only
    STATUS      current
    DESCRIPTION
        "This object indicates the status of this entry.
            other(1) - this entry is currently in use but the
                conditions under which it will remain so differ
                from the following values.
            permanent(2) - this entry, corresponding to an entry
                in dot1qVlanStaticTable, is currently in use and
                will remain so after the next reset of the
                device.  The port lists for this entry include
                ports from the equivalent dot1qVlanStaticTable
                entry and ports learnt dynamically.
            dynamicGvrp(3) - this entry is currently in use

                and will remain so until removed by GVRP.  There
                is no static entry for this VLAN and it will be
                removed when the last port leaves the VLAN."
    ::= { dot1qVlanCurrentEntry 6 }

dot1qVlanCreationTime OBJECT-TYPE
    SYNTAX      TimeTicks
    MAX-ACCESS  read-only
    STATUS      current
    DESCRIPTION
        "The value of sysUpTime when this VLAN was created."
    ::= { dot1qVlanCurrentEntry 7 }

-- -------------------------------------------------------------
-- The Static VLAN Database
-- -------------------------------------------------------------

dot1qVlanStaticTable OBJECT-TYPE
    SYNTAX      SEQUENCE OF Dot1qVlanStaticEntry
    MAX-ACCESS  not-accessible
    STATUS      current
    DESCRIPTION
        "A table containing static configuration information for
        each VLAN configured into the device by (local or
        network) management.  All entries are permanent and will
        be restored after the device is reset."
    ::= { dot1qVlan 3 }

dot1qVlanStaticEntry OBJECT-TYPE
    SYNTAX      Dot1qVlanStaticEntry
    MAX-ACCESS  not-accessible
    STATUS      current
    DESCRIPTION
        "Static information for a VLAN configured into the
        device by (local or network) management."
    INDEX   { dot1qVlanIndex }
    ::= { dot1qVlanStaticTable 1 }

Dot1qVlanStaticEntry ::=
    SEQUENCE {
        dot1qVlanStaticName
            SnmpAdminString,
        dot1qVlanStaticEgressPorts
            PortList,
        dot1qVlanForbiddenEgressPorts
            PortList,

        dot1qVlanStaticUntaggedPorts
            PortList,
        dot1qVlanStaticRowStatus
            RowStatus
    }

dot1qVlanStaticName OBJECT-TYPE
    SYNTAX      SnmpAdminString (SIZE (0..32))
    MAX-ACCESS  read-create
    STATUS      current
    DESCRIPTION
        "An administratively assigned string, which may be used
        to identify the VLAN."
    REFERENCE
        "IEEE 802.1Q/D11 Section 12.10.2.1"
    ::= { dot1qVlanStaticEntry 1 }

dot1qVlanStaticEgressPorts OBJECT-TYPE
    SYNTAX      PortList
    MAX-ACCESS  read-create
    STATUS      current
    DESCRIPTION
        "The set of ports which are permanently assigned to the
        egress list for this VLAN by management.  Changes to a
        bit in this object affect the per-port per-VLAN
        Registrar control for Registration Fixed for the
        relevant GVRP state machine on each port.  A port may
        not be added in this set if it is already a member of
        the set of ports in dot1qVlanForbiddenEgressPorts.  The
        default value of this object is a string of zeros of
        appropriate length, indicating not fixed."
    REFERENCE
        "IEEE 802.1Q/D11 Section 12.7.7.3, 11.2.3.2.3"
    ::= { dot1qVlanStaticEntry 2 }

dot1qVlanForbiddenEgressPorts OBJECT-TYPE
    SYNTAX      PortList
    MAX-ACCESS  read-create
    STATUS      current
    DESCRIPTION
        "The set of ports which are prohibited by management
        from being included in the egress list for this VLAN.
        Changes to this object that cause a port to be included
        or excluded affect the per-port per-VLAN Registrar

        control for Registration Forbidden for the relevant GVRP
        state machine on each port.  A port may not be added in
        this set if it is already a member of the set of ports
        in dot1qVlanStaticEgressPorts.  The default value of
        this object is a string of zeros of appropriate length,
        excluding all ports from the forbidden set."
    REFERENCE
        "IEEE 802.1Q/D11 Section 12.7.7.3, 11.2.3.2.3"
    ::= { dot1qVlanStaticEntry 3 }

dot1qVlanStaticUntaggedPorts OBJECT-TYPE
    SYNTAX      PortList
    MAX-ACCESS  read-create
    STATUS      current
    DESCRIPTION
        "The set of ports which should transmit egress packets
        for this VLAN as untagged.  The default value of this
        object for the default VLAN (dot1qVlanIndex = 1) is a string
        of appropriate length including all ports.  There is no
        specified default for other VLANs.  If a device agent cannot
        support the set of ports being set then it will reject the
        set operation with an error. An example might be if a
        manager attempts to set more than one VLAN to be untagged
        on egress where the device does not support this IEEE 802.1Q
        option."
    REFERENCE
        "IEEE 802.1Q/D11 Section 12.10.2.1"
    ::= { dot1qVlanStaticEntry 4 }

dot1qVlanStaticRowStatus OBJECT-TYPE
    SYNTAX      RowStatus
    MAX-ACCESS  read-create
    STATUS      current
    DESCRIPTION
        "This object indicates the status of this entry."
    ::= { dot1qVlanStaticEntry 5 }

dot1qNextFreeLocalVlanIndex OBJECT-TYPE
    SYNTAX      INTEGER (0|4096..2147483647)
    MAX-ACCESS  read-only
    STATUS      current
    DESCRIPTION
        "The next available value for dot1qVlanIndex of a local
        VLAN entry in dot1qVlanStaticTable.  This will report
        values >=4096 if a new Local VLAN may be created or else
        the value 0 if this is not possible.

        A row creation operation in this table for an entry with a local
        VlanIndex value may fail if the current value of this object
        is not used as the index. Even if the value read is used,
        there is no guarantee that it will still be the valid index
        when the create operation is attempted - another manager may
        have already got in during the intervening time interval.
        In this case, dot1qNextFreeLocalVlanIndex should be re-read
        and the creation re-tried with the new value.

        This value will automatically change when the current value is
        used to create a new row."
    ::= { dot1qVlan 4 }

-- -------------------------------------------------------------
-- The VLAN Port Configuration Table
-- -------------------------------------------------------------

dot1qPortVlanTable OBJECT-TYPE
    SYNTAX      SEQUENCE OF Dot1qPortVlanEntry
    MAX-ACCESS  not-accessible
    STATUS      current
    DESCRIPTION
        "A table containing per port control and status
        information for VLAN configuration in the device."
    ::= { dot1qVlan 5 }

dot1qPortVlanEntry OBJECT-TYPE
    SYNTAX      Dot1qPortVlanEntry
    MAX-ACCESS  not-accessible
    STATUS      current
    DESCRIPTION
        "Information controlling VLAN configuration for a port
        on the device.  This is indexed by dot1dBasePort."
    AUGMENTS { dot1dBasePortEntry }
    ::= { dot1qPortVlanTable 1 }

Dot1qPortVlanEntry ::=
    SEQUENCE {
        dot1qPvid
            VlanIndex,
        dot1qPortAcceptableFrameTypes
            INTEGER,
        dot1qPortIngressFiltering
            TruthValue,
        dot1qPortGvrpStatus
            EnabledStatus,

        dot1qPortGvrpFailedRegistrations
            Counter32,
        dot1qPortGvrpLastPduOrigin
            MacAddress
    }

dot1qPvid OBJECT-TYPE
    SYNTAX      VlanIndex
    MAX-ACCESS  read-write
    STATUS      current
    DESCRIPTION
        "The PVID, the VLAN ID assigned to untagged frames or
        Priority-Tagged frames received on this port."
    REFERENCE
        "IEEE 802.1Q/D11 Section 12.10.1.1"
    DEFVAL      { 1 }
    ::= { dot1qPortVlanEntry 1 }

dot1qPortAcceptableFrameTypes OBJECT-TYPE
    SYNTAX      INTEGER {
                    admitAll(1),
                    admitOnlyVlanTagged(2)
                }
    MAX-ACCESS  read-write
    STATUS      current
    DESCRIPTION
        "When this is admitOnlyVlanTagged(2) the device will
        discard untagged frames or Priority-Tagged frames
        received on this port.  When admitAll(1), untagged
        frames or Priority-Tagged frames received on this port
        will be accepted and assigned to the PVID for this port.

        This control does not affect VLAN independent BPDU
        frames, such as GVRP and STP.  It does affect VLAN
        dependent BPDU frames, such as GMRP."
    REFERENCE
        "IEEE 802.1Q/D11 Section 12.10.1.3"
    DEFVAL      { admitAll }
    ::= { dot1qPortVlanEntry 2 }

dot1qPortIngressFiltering OBJECT-TYPE
    SYNTAX      TruthValue
    MAX-ACCESS  read-write
    STATUS      current

    DESCRIPTION
        "When this is true(1) the device will discard incoming
        frames for VLANs which do not include this Port in its
        Member set.  When false(2), the port will accept all
        incoming frames.

        This control does not affect VLAN independent BPDU
        frames, such as GVRP and STP.  It does affect VLAN
        dependent BPDU frames, such as GMRP."
    REFERENCE
        "IEEE 802.1Q/D11 Section 12.10.1.4"
    DEFVAL      { false }
    ::= { dot1qPortVlanEntry 3 }

dot1qPortGvrpStatus OBJECT-TYPE
    SYNTAX      EnabledStatus
    MAX-ACCESS  read-write
    STATUS      current
    DESCRIPTION
        "The state of GVRP operation on this port.  The value
        enabled(1) indicates that GVRP is enabled on this port,
        as long as dot1qGvrpStatus is also enabled for this
        device.  When disabled(2) but dot1qGvrpStatus is still
        enabled for the device, GVRP is disabled on this port:
        any GVRP packets received will be silently discarded and
        no GVRP registrations will be propagated from other
        ports.  This object affects all GVRP Applicant and
        Registrar state machines on this port.  A transition
        from disabled(2) to enabled(1) will cause a reset of all
        GVRP state machines on this port."
    DEFVAL      { enabled }
    ::= { dot1qPortVlanEntry 4 }

dot1qPortGvrpFailedRegistrations OBJECT-TYPE
    SYNTAX      Counter32
    MAX-ACCESS  read-only
    STATUS      current
    DESCRIPTION
        "The total number of failed GVRP registrations, for any
        reason, on this port."
    ::= { dot1qPortVlanEntry 5 }

dot1qPortGvrpLastPduOrigin OBJECT-TYPE
    SYNTAX      MacAddress
    MAX-ACCESS  read-only
    STATUS      current

    DESCRIPTION
        "The Source MAC Address of the last GVRP message
        received on this port."
    ::= { dot1qPortVlanEntry 6 }

-- -------------------------------------------------------------
-- Per port VLAN Statistics Table
-- -------------------------------------------------------------

dot1qPortVlanStatisticsTable OBJECT-TYPE
    SYNTAX      SEQUENCE OF Dot1qPortVlanStatisticsEntry
    MAX-ACCESS  not-accessible
    STATUS      current
    DESCRIPTION
        "A table containing per-port, per-VLAN statistics for
        traffic received. Separate objects are provided for both the
        most-significant and least-significant bits of statistics
        counters for ports that are associated with this transparent
        bridge. The most-significant bit objects are only required on
        high capacity interfaces, as defined in the conformance clauses
        for these objects. This mechanism is provided as a way to read
        64-bit counters for agents which support only SNMPv1.

        Note that the reporting of most-significant and least-
        significant counter bits separately runs the risk of missing
        an overflow of the lower bits in the interval between sampling.
        The manager must be aware of this possibility, even within the
        same varbindlist, when interpreting the results of a request or
        asynchronous notification."
    ::= { dot1qVlan 6 }

dot1qPortVlanStatisticsEntry OBJECT-TYPE
    SYNTAX      Dot1qPortVlanStatisticsEntry
    MAX-ACCESS  not-accessible
    STATUS      current
    DESCRIPTION
        "Traffic statistics for a VLAN on an interface."
    INDEX   { dot1dBasePort, dot1qVlanIndex }
    ::= { dot1qPortVlanStatisticsTable 1 }

Dot1qPortVlanStatisticsEntry ::=
    SEQUENCE {

        dot1qTpVlanPortInFrames
            Counter32,
        dot1qTpVlanPortOutFrames
            Counter32,
        dot1qTpVlanPortInDiscards
            Counter32,
        dot1qTpVlanPortInOverflowFrames
            Counter32,
        dot1qTpVlanPortOutOverflowFrames
            Counter32,
        dot1qTpVlanPortInOverflowDiscards
            Counter32
    }

dot1qTpVlanPortInFrames OBJECT-TYPE
    SYNTAX      Counter32
    MAX-ACCESS  read-only
    STATUS      current
    DESCRIPTION
        "The number of valid frames received by this port from
        its segment which were classified as belonging to this
        VLAN.  Note that a frame received on this port is
        counted by this object if and only if it is for a
        protocol being processed by the local forwarding process
        for this VLAN.  This object includes received bridge
        management frames classified as belonging to this VLAN
        (e.g. GMRP, but not GVRP or STP)."
    REFERENCE
        "IEEE 802.1Q/D11 Section 12.6.1.1.3(a)"
    ::= { dot1qPortVlanStatisticsEntry 1 }

dot1qTpVlanPortOutFrames OBJECT-TYPE
    SYNTAX      Counter32
    MAX-ACCESS  read-only
    STATUS      current
    DESCRIPTION
        "The number of valid frames transmitted by this port to
        its segment from the local forwarding process for this
        VLAN.  This includes bridge management frames originated
        by this device which are classified as belonging to this
        VLAN (e.g. GMRP, but not GVRP or STP)."
    REFERENCE
        "IEEE 802.1Q/D11 Section 12.6.1.1.3(d)"
    ::= { dot1qPortVlanStatisticsEntry 2 }

dot1qTpVlanPortInDiscards OBJECT-TYPE
    SYNTAX      Counter32
    MAX-ACCESS  read-only
    STATUS      current
    DESCRIPTION
        "The number of valid frames received by this port from
        its segment which were classified as belonging to this
        VLAN which were discarded due to VLAN related reasons.
        Specifically, the IEEE 802.1Q counters for Discard
        Inbound and Discard on Ingress Filtering."
    REFERENCE
        "IEEE 802.1Q/D11 Section 12.6.1.1.3"
    ::= { dot1qPortVlanStatisticsEntry 3 }

dot1qTpVlanPortInOverflowFrames OBJECT-TYPE
    SYNTAX      Counter32
    MAX-ACCESS  read-only
    STATUS      current
    DESCRIPTION
        "The number of times the associated
        dot1qTpVlanPortInFrames counter has overflowed."
    REFERENCE
        "ISO/IEC 15802-3 Section 14.6.1.1.3"
    ::= { dot1qPortVlanStatisticsEntry 4 }

dot1qTpVlanPortOutOverflowFrames OBJECT-TYPE
    SYNTAX      Counter32
    MAX-ACCESS  read-only
    STATUS      current
    DESCRIPTION
        "The number of times the associated
        dot1qTpVlanPortOutFrames counter has overflowed."
    REFERENCE
        "ISO/IEC 15802-3 Section 14.6.1.1.3"
    ::= { dot1qPortVlanStatisticsEntry 5 }

dot1qTpVlanPortInOverflowDiscards OBJECT-TYPE
    SYNTAX      Counter32
    MAX-ACCESS  read-only
    STATUS      current
    DESCRIPTION
        "The number of times the associated
        dot1qTpVlanPortInDiscards counter has overflowed."
    REFERENCE
        "ISO/IEC 15802-3 Section 14.6.1.1.3"
    ::= { dot1qPortVlanStatisticsEntry 6 }

dot1qPortVlanHCStatisticsTable OBJECT-TYPE
    SYNTAX      SEQUENCE OF Dot1qPortVlanHCStatisticsEntry
    MAX-ACCESS  not-accessible
    STATUS      current
    DESCRIPTION
        "A table containing per port, per VLAN statistics for
        traffic on high capacity interfaces."
    ::= { dot1qVlan 7 }

dot1qPortVlanHCStatisticsEntry OBJECT-TYPE
    SYNTAX      Dot1qPortVlanHCStatisticsEntry
    MAX-ACCESS  not-accessible
    STATUS      current
    DESCRIPTION
        "Traffic statistics for a VLAN on a high capacity
        interface."
    INDEX   { dot1dBasePort, dot1qVlanIndex }
    ::= { dot1qPortVlanHCStatisticsTable 1 }

Dot1qPortVlanHCStatisticsEntry ::=
    SEQUENCE {
        dot1qTpVlanPortHCInFrames
            Counter64,
        dot1qTpVlanPortHCOutFrames
            Counter64,
        dot1qTpVlanPortHCInDiscards
            Counter64
    }

dot1qTpVlanPortHCInFrames OBJECT-TYPE
    SYNTAX      Counter64
    MAX-ACCESS  read-only
    STATUS      current
    DESCRIPTION
        "The number of valid frames received by this port from
        its segment which were classified as belonging to this
        VLAN.  Note that a frame received on this port is
        counted by this object if and only if it is for a
        protocol being processed by the local forwarding process
        for this VLAN.  This object includes received bridge
        management frames classified as belonging to this VLAN
        (e.g. GMRP, but not GVRP or STP)."
    REFERENCE
        "IEEE 802.1Q/D11 Section 12.6.1.1.3(a)"
    ::= { dot1qPortVlanHCStatisticsEntry 1 }

dot1qTpVlanPortHCOutFrames OBJECT-TYPE
    SYNTAX      Counter64
    MAX-ACCESS  read-only
    STATUS      current
    DESCRIPTION
        "The number of valid frames transmitted by this port to
        its segment from the local forwarding process for this
        VLAN.  This includes bridge management frames originated
        by this device which are classified as belonging to this
        VLAN (e.g. GMRP, but not GVRP or STP)."
    REFERENCE
        "IEEE 802.1Q/D11 Section 12.6.1.1.3(d)"
    ::= { dot1qPortVlanHCStatisticsEntry 2 }

dot1qTpVlanPortHCInDiscards OBJECT-TYPE
    SYNTAX      Counter64
    MAX-ACCESS  read-only
    STATUS      current
    DESCRIPTION
        "The number of valid frames received by this port from
        its segment which were classified as belonging to this
        VLAN which were discarded due to VLAN related reasons.
        Specifically, the IEEE 802.1Q counters for Discard
        Inbound and Discard on Ingress Filtering."
    REFERENCE
        "IEEE 802.1Q/D11 Section 12.6.1.1.3"
    ::= { dot1qPortVlanHCStatisticsEntry 3 }

-- -------------------------------------------------------------
-- The VLAN Learning Constraints Table
-- -------------------------------------------------------------

dot1qLearningConstraintsTable OBJECT-TYPE
    SYNTAX      SEQUENCE OF Dot1qLearningConstraintsEntry
    MAX-ACCESS  not-accessible
    STATUS      current
    DESCRIPTION
        "A table containing learning constraints for sets of
        Shared and Independendent VLANs."
    REFERENCE
        "IEEE 802.1Q/D11 Section 12.10.3.1"
    ::= { dot1qVlan 8 }

dot1qLearningConstraintsEntry OBJECT-TYPE
    SYNTAX      Dot1qLearningConstraintsEntry
    MAX-ACCESS  not-accessible
    STATUS      current

    DESCRIPTION
        "A learning constraint defined for a VLAN."
    INDEX   { dot1qConstraintVlan, dot1qConstraintSet }
    ::= { dot1qLearningConstraintsTable 1 }

Dot1qLearningConstraintsEntry ::=
    SEQUENCE {
        dot1qConstraintVlan
            VlanIndex,
        dot1qConstraintSet
            INTEGER,
        dot1qConstraintType
            INTEGER,
        dot1qConstraintStatus
            RowStatus
    }

dot1qConstraintVlan OBJECT-TYPE
    SYNTAX      VlanIndex
    MAX-ACCESS  not-accessible
    STATUS      current
    DESCRIPTION
        "The index of the row in dot1qVlanCurrentTable for the
        VLAN constrained by this entry."
    ::= { dot1qLearningConstraintsEntry 1 }

dot1qConstraintSet OBJECT-TYPE
    SYNTAX      INTEGER (0..65535)
    MAX-ACCESS  not-accessible
    STATUS      current
    DESCRIPTION
        "The identity of the constraint set to which
        dot1qConstraintVlan belongs.  These values may be chosen
        by the management station."
    ::= { dot1qLearningConstraintsEntry 2 }

dot1qConstraintType OBJECT-TYPE
    SYNTAX      INTEGER {
                    independent(1),
                    shared(2)
                }
    MAX-ACCESS  read-create
    STATUS      current
    DESCRIPTION
        "The type of constraint this entry defines.
            independent(1) - the VLAN, dot1qConstraintVlan,
                uses an independent filtering database from all

                other VLANs in the same set, defined by
                dot1qConstraintSet.
            shared(2) - the VLAN, dot1qConstraintVlan, shares
                the same filtering database as all other VLANs
                in the same set, defined by dot1qConstraintSet."
    ::= { dot1qLearningConstraintsEntry 3 }

dot1qConstraintStatus OBJECT-TYPE
    SYNTAX      RowStatus
    MAX-ACCESS  read-create
    STATUS      current
    DESCRIPTION
        "The status of this entry."
    ::= { dot1qLearningConstraintsEntry 4 }

dot1qConstraintSetDefault OBJECT-TYPE
    SYNTAX      INTEGER (0..65535)
    MAX-ACCESS  read-write
    STATUS      current
    DESCRIPTION
        "The identity of the constraint set to which a VLAN
        belongs, if there is not an explicit entry for that VLAN
        in dot1qLearningConstraintsTable."
    ::= { dot1qVlan 9 }

dot1qConstraintTypeDefault OBJECT-TYPE
    SYNTAX      INTEGER {
                    independent(1),
                    shared(2)
                }
    MAX-ACCESS  read-write
    STATUS      current
    DESCRIPTION
        "The type of constraint set to which a VLAN belongs, if
        there is not an explicit entry for that VLAN in
        dot1qLearningConstraintsTable.  The types are as defined
        for dot1qConstraintType."
    ::= { dot1qVlan 10 }

-- -------------------------------------------------------------
-- IEEE 802.1Q MIB - Conformance Information
-- -------------------------------------------------------------

qBridgeConformance OBJECT IDENTIFIER ::= { qBridgeMIB 2 }

qBridgeGroups OBJECT IDENTIFIER ::= { qBridgeConformance 1 }

qBridgeCompliances OBJECT IDENTIFIER
    ::= { qBridgeConformance 2 }

-- -------------------------------------------------------------
-- units of conformance
-- -------------------------------------------------------------

qBridgeBaseGroup OBJECT-GROUP
    OBJECTS {
        dot1qVlanVersionNumber,
        dot1qMaxVlanId,
        dot1qMaxSupportedVlans,
        dot1qNumVlans,
        dot1qGvrpStatus
    }
    STATUS      current
    DESCRIPTION
        "A collection of objects providing device level control
        and status information for the Virtual LAN bridge
        services."
    ::= { qBridgeGroups 1 }

qBridgeFdbUnicastGroup OBJECT-GROUP
    OBJECTS {
        dot1qFdbDynamicCount,
        dot1qTpFdbPort,
        dot1qTpFdbStatus
    }
    STATUS      current
    DESCRIPTION
        "A collection of objects providing information about all
        unicast addresses, learnt dynamically or statically
        configured by management, in each Filtering Database."
    ::= { qBridgeGroups 2 }

qBridgeFdbMulticastGroup OBJECT-GROUP
    OBJECTS {
        dot1qTpGroupEgressPorts,
        dot1qTpGroupLearnt
    }

    STATUS      current
    DESCRIPTION
        "A collection of objects providing information about all
        multicast addresses, learnt dynamically or statically
        configured by management, in each Filtering Database."
    ::= { qBridgeGroups 3 }

qBridgeServiceRequirementsGroup OBJECT-GROUP
    OBJECTS {
        dot1qForwardAllPorts,
        dot1qForwardAllStaticPorts,
        dot1qForwardAllForbiddenPorts,
        dot1qForwardUnregisteredPorts,
        dot1qForwardUnregisteredStaticPorts,
        dot1qForwardUnregisteredForbiddenPorts
    }
    STATUS      current
    DESCRIPTION
        "A collection of objects providing information about
        service requirements, learnt dynamically or statically
        configured by management, in each Filtering Database."
    ::= { qBridgeGroups 4 }

qBridgeFdbStaticGroup OBJECT-GROUP
    OBJECTS {
        dot1qStaticUnicastAllowedToGoTo,
        dot1qStaticUnicastStatus,
        dot1qStaticMulticastStaticEgressPorts,
        dot1qStaticMulticastForbiddenEgressPorts,
        dot1qStaticMulticastStatus
    }
    STATUS      current
    DESCRIPTION
        "A collection of objects providing information about
        unicast and multicast addresses statically configured by
        management, in each Filtering Database or VLAN."
    ::= { qBridgeGroups 5 }

qBridgeVlanGroup OBJECT-GROUP
    OBJECTS {
        dot1qVlanNumDeletes,
        dot1qVlanFdbId,
        dot1qVlanCurrentEgressPorts,
        dot1qVlanCurrentUntaggedPorts,
        dot1qVlanStatus,
        dot1qVlanCreationTime
    }

    STATUS      current
    DESCRIPTION
        "A collection of objects providing information about
        all VLANs currently configured on this device."
    ::= { qBridgeGroups 6 }

qBridgeVlanStaticGroup OBJECT-GROUP
    OBJECTS {
        dot1qVlanStaticName,
        dot1qVlanStaticEgressPorts,
        dot1qVlanForbiddenEgressPorts,
        dot1qVlanStaticUntaggedPorts,
        dot1qVlanStaticRowStatus,
        dot1qNextFreeLocalVlanIndex
    }
    STATUS      current
    DESCRIPTION
        "A collection of objects providing information about
        VLANs statically configured by management."
    ::= { qBridgeGroups 7 }

qBridgePortGroup OBJECT-GROUP
    OBJECTS {
        dot1qPvid,
        dot1qPortAcceptableFrameTypes,
        dot1qPortIngressFiltering,
        dot1qPortGvrpStatus,
        dot1qPortGvrpFailedRegistrations,
        dot1qPortGvrpLastPduOrigin
    }
    STATUS      current
    DESCRIPTION
        "A collection of objects providing port level VLAN
        control and status information for all ports."
    ::= { qBridgeGroups 8 }

qBridgeVlanStatisticsGroup OBJECT-GROUP
    OBJECTS {
        dot1qTpVlanPortInFrames,
        dot1qTpVlanPortOutFrames,
        dot1qTpVlanPortInDiscards
    }
    STATUS      current
    DESCRIPTION
        "A collection of objects providing per-port packet
        statistics for all VLANs currently configured on this
        device."
    ::= { qBridgeGroups 9 }

qBridgeVlanStatisticsOverflowGroup OBJECT-GROUP
    OBJECTS {
        dot1qTpVlanPortInOverflowFrames,
        dot1qTpVlanPortOutOverflowFrames,
        dot1qTpVlanPortInOverflowDiscards
    }
    STATUS      current
    DESCRIPTION
        "A collection of objects providing overflow counters for
        per-port packet statistics for all VLANs currently configured
        on this device for high capacity interfaces, defined as those
        that have the value of the corresponding instance of
        ifSpeed greater than 650,000,000 bits/second."
    ::= { qBridgeGroups 10 }

qBridgeVlanHCStatisticsGroup OBJECT-GROUP
    OBJECTS {
        dot1qTpVlanPortHCInFrames,
        dot1qTpVlanPortHCOutFrames,
        dot1qTpVlanPortHCInDiscards
    }
    STATUS      current
    DESCRIPTION
        "A collection of objects providing per-port packet
        statistics for all VLANs currently configured on this
        device for high capacity interfaces, defined as those
        that have the value of the corresponding instance of
        ifSpeed greater than 650,000,000 bits/second."
    ::= { qBridgeGroups 11 }

qBridgeLearningConstraintsGroup OBJECT-GROUP
    OBJECTS {
        dot1qConstraintType,
        dot1qConstraintStatus
    }
    STATUS      current
    DESCRIPTION
        "A collection of objects defining the Filtering Database
        constraints all VLANs have with each other."
    ::= { qBridgeGroups 12 }

qBridgeLearningConstraintDefaultGroup OBJECT-GROUP
    OBJECTS {
        dot1qConstraintSetDefault,
        dot1qConstraintTypeDefault
    }

    STATUS      current
    DESCRIPTION
        "A collection of objects defining the default Filtering
        Database constraints for VLANs which have no specific
        constraints defined."
    ::= { qBridgeGroups 13 }

-- -------------------------------------------------------------
-- compliance statements
-- -------------------------------------------------------------

qBridgeCompliance MODULE-COMPLIANCE
    STATUS  current
    DESCRIPTION
        "The compliance statement for device support of Virtual
        LAN Bridge services."

    MODULE
        MANDATORY-GROUPS {
            qBridgeBaseGroup,
            qBridgeVlanGroup,
            qBridgeVlanStaticGroup,
            qBridgePortGroup
        }

        GROUP       qBridgeFdbUnicastGroup
        DESCRIPTION
            "This group is mandatory for bridges that implement
            802.1Q transparent bridging."

        GROUP       qBridgeFdbMulticastGroup
        DESCRIPTION
            "This group is mandatory for bridges that implement
            802.1Q transparent bridging."

        GROUP       qBridgeServiceRequirementsGroup
        DESCRIPTION
            "This group is mandatory for bridges that implement
            extended filtering services.  All objects must be
            read-write if extended-filtering services are
            enabled."

        GROUP       qBridgeFdbStaticGroup
        DESCRIPTION
            "This group is optional."

        GROUP       qBridgeVlanStatisticsGroup
        DESCRIPTION
            "This group is optional as there may be significant
            implementation cost associated with its support."

        GROUP       qBridgeVlanStatisticsOverflowGroup
        DESCRIPTION
            "This group is optional as there may be significant
            implementation cost associated with its support. It is most
            relevant for high capacity interfaces where the SNMP agent
            supports only SNMPv1."

        GROUP       qBridgeVlanHCStatisticsGroup
        DESCRIPTION
            "This group is optional as there may be significant
            implementation cost associated with its support. It is most
            relevant for high capacity interfaces."

        GROUP       qBridgeLearningConstraintsGroup
        DESCRIPTION
            "This group is mandatory for devices implementing
             both Independent VLAN Learning (IVL) and Shared
             VLAN Learning (SVL) modes of operation of the
             filtering database, as defined by IEEE 802.1Q."

        GROUP       qBridgeLearningConstraintDefaultGroup
        DESCRIPTION
            "This group is mandatory for devices implementing
             both Independent VLAN Learning (IVL) and Shared
             VLAN Learning (SVL) modes of operation of the
             filtering database, as defined by IEEE 802.1Q."

        OBJECT      dot1qPortAcceptableFrameTypes
        MIN-ACCESS  read-only
        DESCRIPTION
            "Write access is not required as this is an optional
            capability in IEEE 802.1Q."

        OBJECT      dot1qPortIngressFiltering
        MIN-ACCESS  read-only
        DESCRIPTION
            "Write access is not required as this is an optional
            capability in IEEE 802.1Q."

        OBJECT      dot1qConstraintSetDefault
        MIN-ACCESS  read-only
        DESCRIPTION
            "Write access is not required as this is an optional
            capability in IEEE 802.1Q."

        OBJECT      dot1qConstraintTypeDefault
        MIN-ACCESS  read-only
        DESCRIPTION
            "Write access is not required as this is an optional
            capability in IEEE 802.1Q."

       ::= { qBridgeCompliances 1 }

END

INET-ADDRESS-MIB DEFINITIONS ::= BEGIN

   IMPORTS
     MODULE-IDENTITY, mib-2 FROM SNMPv2-SMI
     TEXTUAL-CONVENTION     FROM SNMPv2-TC;

   inetAddressMIB MODULE-IDENTITY
     LAST-UPDATED "200006080000Z"
     ORGANIZATION
         "IETF Operations and Management Area"
     CONTACT-INFO
         "Mike Daniele
          Compaq Computer Corporation
          110 Spit Brook Rd
          Nashua, NH  03062, USA

          Phone: +1 603 884-1423
          EMail: daniele@zk3.dec.com

          Brian Haberman
          Nortel Networks
          4039 Emperor Blvd., Suite 200
          Durham, NC  27703, USA

          Phone: +1 919 992-4439
          EMail: haberman@nortelnetworks.com

          Shawn A. Routhier
          Wind River Systems, Inc.
          1 Tara Blvd, Suite 403
          Nashua, NH  03062, USA

          Phone: +1 603 897-2000
          EMail: sar@epilogue.com


          Juergen Schoenwaelder
          TU Braunschweig
          Bueltenweg 74/75
          38106 Braunschweig, Germany

          Phone: +49 531 391-3289
          EMail: schoenw@ibr.cs.tu-bs.de

          Send comments to mibs@ops.ietf.org."

   DESCRIPTION
     "This MIB module defines textual conventions for
      representing Internet addresses. An Internet
      address can be an IPv4 address, an IPv6 address
      or a DNS domain name."

   REVISION     "200006080000Z"
   DESCRIPTION
       "Initial version, published as RFC 2851."
   ::= { mib-2 76 }

   InetAddressType ::= TEXTUAL-CONVENTION
     STATUS      current
     DESCRIPTION
         "A value that represents a type of Internet address.

          unknown(0)  An unknown address type. This value MUST
                      be used if the value of the corresponding
                      InetAddress object is a zero-length string.
                      It may also be used to indicate an IP address
                      which is not in one of the formats defined
                      below.

          ipv4(1)     An IPv4 address as defined by the
                      InetAddressIPv4 textual convention.

          ipv6(2)     An IPv6 address as defined by the
                      InetAddressIPv6 textual convention.

          dns(16)     A DNS domain name as defined by the
                      InetAddressDNS textual convention.

          Each definition of a concrete InetAddressType value must be
          accompanied by a definition of a textual convention for use
          with that InetAddressType.

          The InetAddressType textual convention SHOULD NOT be subtyped
          in object type definitions to support future extensions. It


          MAY be subtyped in compliance statements in order to require
          only a subset of these address types for a compliant
          implementation."
     SYNTAX      INTEGER {
                     unknown(0),
                     ipv4(1),    -- these named numbers are aligned
                     ipv6(2),    -- with AddressFamilyNumbers from
                     dns(16)     -- IANA-ADDRESS-FAMILY-NUMBERS-MIB
                 }

   InetAddress ::= TEXTUAL-CONVENTION
     STATUS       current
     DESCRIPTION
         "Denotes a generic Internet address.

          An InetAddress value is always interpreted within the
          context of an InetAddressType value. The InetAddressType
          object which defines the context must be registered
          immediately before the object which uses the InetAddress
          textual convention. In other words, the object identifiers
          for the InetAddressType object and the InetAddress object
          MUST have the same length and the last sub-identifier of
          the InetAddressType object MUST be 1 less than the last
          sub-identifier of the InetAddress object.

          When this textual convention is used as the syntax of an
          index object, there may be issues with the limit of 128
          sub-identifiers specified in SMIv2, STD 58. In this case,
          the OBJECT-TYPE declaration MUST include a 'SIZE' clause
          to limit the number of potential instance sub-identifiers."
     SYNTAX      OCTET STRING (SIZE (0..255))

   InetAddressIPv4 ::= TEXTUAL-CONVENTION
     DISPLAY-HINT "1d.1d.1d.1d"
     STATUS       current
     DESCRIPTION
         "Represents an IPv4 network address:

            octets   contents         encoding
             1-4     IP address       network-byte order

          The corresponding InetAddressType value is ipv4(1)."
     SYNTAX       OCTET STRING (SIZE (4))

   InetAddressIPv6 ::= TEXTUAL-CONVENTION
     DISPLAY-HINT "2x:2x:2x:2x:2x:2x:2x:2x%4d"
     STATUS       current
     DESCRIPTION


         "Represents an IPv6 network address:

            octets   contents         encoding
             1-16    IPv6 address     network-byte order
            17-20    scope identifier network-byte order

          The corresponding InetAddressType value is ipv6(2).

          The scope identifier (bytes 17-20) MUST NOT be present
          for global IPv6 addresses. For non-global IPv6 addresses
          (e.g. link-local or site-local addresses), the scope
          identifier MUST always be present. It contains a link
          identifier for link-local and a site identifier for
          site-local IPv6 addresses.

          The scope identifier MUST disambiguate identical address
          values. For link-local addresses, the scope identifier will
          typically be the interface index (ifIndex as defined in the
          IF-MIB, RFC 2233) of the interface on which the address is
          configured.

          The scope identifier may contain the special value 0
          which refers to the default scope. The default scope
          may be used in cases where the valid scope identifier
          is not known (e.g., a management application needs to
          write a site-local InetAddressIPv6 address without
          knowing the site identifier value). The default scope
          SHOULD NOT be used as an easy way out in cases where
          the scope identifier for a non-global IPv6 is known."
     SYNTAX       OCTET STRING (SIZE (16|20))

   InetAddressDNS ::= TEXTUAL-CONVENTION
     DISPLAY-HINT "255a"
     STATUS       current
     DESCRIPTION
         "Represents a DNS domain name. The name SHOULD be
          fully qualified whenever possible.

          The corresponding InetAddressType is dns(16).

          The DESCRIPTION clause of InetAddress objects that
          may have InetAddressDNS values must fully describe
          how (and when) such names are to be resolved to IP
          addresses."
     SYNTAX       OCTET STRING (SIZE (1..255))

END

IGMP-STD-MIB DEFINITIONS ::= BEGIN

IMPORTS
    MODULE-IDENTITY, OBJECT-TYPE, mib-2, Counter32, Gauge32,
    Unsigned32, IpAddress, TimeTicks FROM SNMPv2-SMI
    RowStatus, TruthValue            FROM SNMPv2-TC
    MODULE-COMPLIANCE, OBJECT-GROUP  FROM SNMPv2-CONF
    InterfaceIndexOrZero,
    InterfaceIndex                   FROM IF-MIB;

igmpStdMIB MODULE-IDENTITY
    LAST-UPDATED "200009280000Z" -- September 28, 2000
    ORGANIZATION "IETF IDMR Working Group."
    CONTACT-INFO
            " Dave Thaler
              Microsoft Corporation
              One Microsoft Way
              Redmond, WA  98052-6399
              US

              Phone: +1 425 703 8835
              EMail: dthaler@microsoft.com"
    DESCRIPTION
            "The MIB module for IGMP Management."
    REVISION     "200009280000Z" -- September 28, 2000


    DESCRIPTION
            "Initial version, published as RFC 2933."
    ::= { mib-2 85 }

igmpMIBObjects     OBJECT IDENTIFIER ::= { igmpStdMIB 1 }

--
--  The IGMP Interface Table
--

igmpInterfaceTable OBJECT-TYPE
    SYNTAX     SEQUENCE OF IgmpInterfaceEntry
    MAX-ACCESS not-accessible
    STATUS     current
    DESCRIPTION
            "The (conceptual) table listing the interfaces on which IGMP
            is enabled."
    ::= { igmpMIBObjects 1 }

igmpInterfaceEntry OBJECT-TYPE
    SYNTAX     IgmpInterfaceEntry
    MAX-ACCESS not-accessible
    STATUS     current
    DESCRIPTION
            "An entry (conceptual row) representing an interface on
            which IGMP is enabled."
    INDEX      { igmpInterfaceIfIndex }
    ::= { igmpInterfaceTable 1 }

IgmpInterfaceEntry ::= SEQUENCE {
    igmpInterfaceIfIndex               InterfaceIndex,
    igmpInterfaceQueryInterval         Unsigned32,
    igmpInterfaceStatus                RowStatus,
    igmpInterfaceVersion               Unsigned32,
    igmpInterfaceQuerier               IpAddress,
    igmpInterfaceQueryMaxResponseTime  Unsigned32,
    igmpInterfaceQuerierUpTime         TimeTicks,
    igmpInterfaceQuerierExpiryTime     TimeTicks,
    igmpInterfaceVersion1QuerierTimer  TimeTicks,
    igmpInterfaceWrongVersionQueries   Counter32,
    igmpInterfaceJoins                 Counter32,
    igmpInterfaceProxyIfIndex          InterfaceIndexOrZero,
    igmpInterfaceGroups                Gauge32,
    igmpInterfaceRobustness            Unsigned32,
    igmpInterfaceLastMembQueryIntvl    Unsigned32
}


igmpInterfaceIfIndex OBJECT-TYPE
    SYNTAX     InterfaceIndex
    MAX-ACCESS not-accessible
    STATUS     current
    DESCRIPTION
            "The ifIndex value of the interface for which IGMP is
            enabled."
    ::= { igmpInterfaceEntry 1 }

igmpInterfaceQueryInterval OBJECT-TYPE
    SYNTAX     Unsigned32
    UNITS      "seconds"
    MAX-ACCESS read-create
    STATUS     current
    DESCRIPTION
            "The frequency at which IGMP Host-Query packets are
            transmitted on this interface."
    DEFVAL     { 125 }
    ::= { igmpInterfaceEntry 2 }

igmpInterfaceStatus OBJECT-TYPE
    SYNTAX     RowStatus
    MAX-ACCESS read-create
    STATUS     current
    DESCRIPTION
            "The activation of a row enables IGMP on the interface.  The
            destruction of a row disables IGMP on the interface."
    ::= { igmpInterfaceEntry 3 }

igmpInterfaceVersion OBJECT-TYPE
    SYNTAX     Unsigned32
    MAX-ACCESS read-create
    STATUS     current
    DESCRIPTION
            "The version of IGMP which is running on this interface.
            This object can be used to configure a router capable of
            running either value.  For IGMP to function correctly, all
            routers on a LAN must be configured to run the same version
            of IGMP on that LAN."
    DEFVAL     { 2 }
    ::= { igmpInterfaceEntry 4 }

igmpInterfaceQuerier OBJECT-TYPE
    SYNTAX     IpAddress
    MAX-ACCESS read-only
    STATUS     current
    DESCRIPTION
            "The address of the IGMP Querier on the IP subnet to which


            this interface is attached."
    ::= { igmpInterfaceEntry 5 }

igmpInterfaceQueryMaxResponseTime OBJECT-TYPE
    SYNTAX     Unsigned32 (0..255)
    UNITS      "tenths of seconds"
    MAX-ACCESS read-create
    STATUS     current
    DESCRIPTION
            "The maximum query response time advertised in IGMPv2
            queries on this interface."
    DEFVAL     { 100 }
    ::= { igmpInterfaceEntry 6 }

igmpInterfaceQuerierUpTime OBJECT-TYPE
    SYNTAX     TimeTicks
    MAX-ACCESS read-only
    STATUS     current
    DESCRIPTION
            "The time since igmpInterfaceQuerier was last changed."
    ::= { igmpInterfaceEntry 7 }

igmpInterfaceQuerierExpiryTime OBJECT-TYPE
    SYNTAX     TimeTicks
    MAX-ACCESS read-only
    STATUS     current
    DESCRIPTION
            "The amount of time remaining before the Other Querier
            Present Timer expires.  If the local system is the querier,
            the value of this object is zero."
    ::= { igmpInterfaceEntry 8 }

igmpInterfaceVersion1QuerierTimer OBJECT-TYPE
    SYNTAX     TimeTicks
    MAX-ACCESS read-only
    STATUS     current
    DESCRIPTION
            "The time remaining until the host assumes that there are no
            IGMPv1 routers present on the interface.  While this is non-
            zero, the host will reply to all queries with version 1
            membership reports."
    ::= { igmpInterfaceEntry 9 }

igmpInterfaceWrongVersionQueries OBJECT-TYPE
    SYNTAX     Counter32
    MAX-ACCESS read-only
    STATUS     current
    DESCRIPTION


            "The number of queries received whose IGMP version does not
            match igmpInterfaceVersion, over the lifetime of the row
            entry.  IGMP requires that all routers on a LAN be
            configured to run the same version of IGMP.  Thus, if any
            queries are received with the wrong version, this indicates
            a configuration error."
    ::= { igmpInterfaceEntry 10 }

igmpInterfaceJoins OBJECT-TYPE
    SYNTAX     Counter32
    MAX-ACCESS read-only
    STATUS     current
    DESCRIPTION
            "The number of times a group membership has been added on
            this interface; that is, the number of times an entry for
            this interface has been added to the Cache Table.  This
            object gives an indication of the amount of IGMP activity
            over the lifetime of the row entry."
    ::= { igmpInterfaceEntry 11 }

igmpInterfaceProxyIfIndex OBJECT-TYPE
    SYNTAX     InterfaceIndexOrZero
    MAX-ACCESS read-create
    STATUS     current
    DESCRIPTION
            "Some devices implement a form of IGMP proxying whereby
            memberships learned on the interface represented by this
            row, cause IGMP Host Membership Reports to be sent on the
            interface whose ifIndex value is given by this object.  Such
            a device would implement the igmpV2RouterMIBGroup only on
            its router interfaces (those interfaces with non-zero
            igmpInterfaceProxyIfIndex).  Typically, the value of this
            object is 0, indicating that no proxying is being done."
    DEFVAL     { 0 }
    ::= { igmpInterfaceEntry 12 }

igmpInterfaceGroups OBJECT-TYPE
    SYNTAX     Gauge32
    MAX-ACCESS read-only
    STATUS     current
    DESCRIPTION
            "The current number of entries for this interface in the
            Cache Table."
    ::= { igmpInterfaceEntry 13 }

igmpInterfaceRobustness OBJECT-TYPE
    SYNTAX     Unsigned32 (1..255)
    MAX-ACCESS read-create


    STATUS     current
    DESCRIPTION
            "The Robustness Variable allows tuning for the expected
            packet loss on a subnet.  If a subnet is expected to be
            lossy, the Robustness Variable may be increased.  IGMP is
            robust to (Robustness Variable-1) packet losses."
    DEFVAL     { 2 }
    ::= { igmpInterfaceEntry 14 }

igmpInterfaceLastMembQueryIntvl OBJECT-TYPE
    SYNTAX     Unsigned32 (0..255)
    UNITS      "tenths of seconds"
    MAX-ACCESS read-create
    STATUS     current
    DESCRIPTION
            "The Last Member Query Interval is the Max Response Time
            inserted into Group-Specific Queries sent in response to
            Leave Group messages, and is also the amount of time between
            Group-Specific Query messages.  This value may be tuned to
            modify the leave latency of the network.  A reduced value
            results in reduced time to detect the loss of the last
            member of a group.  The value of this object is irrelevant
            if igmpInterfaceVersion is 1."
    DEFVAL     { 10 }
    ::= { igmpInterfaceEntry 15 }

--
--  The IGMP Cache Table
--

igmpCacheTable OBJECT-TYPE
    SYNTAX     SEQUENCE OF IgmpCacheEntry
    MAX-ACCESS not-accessible
    STATUS     current
    DESCRIPTION
            "The (conceptual) table listing the IP multicast groups for
            which there are members on a particular interface."
    ::= { igmpMIBObjects 2 }

igmpCacheEntry OBJECT-TYPE
    SYNTAX     IgmpCacheEntry
    MAX-ACCESS not-accessible
    STATUS     current
    DESCRIPTION
            "An entry (conceptual row) in the igmpCacheTable."
    INDEX      { igmpCacheAddress, igmpCacheIfIndex }
    ::= { igmpCacheTable 1 }


IgmpCacheEntry ::= SEQUENCE {
    igmpCacheAddress            IpAddress,
    igmpCacheIfIndex            InterfaceIndex,
    igmpCacheSelf               TruthValue,
    igmpCacheLastReporter       IpAddress,
    igmpCacheUpTime             TimeTicks,
    igmpCacheExpiryTime         TimeTicks,
    igmpCacheStatus             RowStatus,
    igmpCacheVersion1HostTimer  TimeTicks
}

igmpCacheAddress OBJECT-TYPE
    SYNTAX     IpAddress
    MAX-ACCESS not-accessible
    STATUS     current
    DESCRIPTION
            "The IP multicast group address for which this entry
            contains information."
    ::= { igmpCacheEntry 1 }

igmpCacheIfIndex OBJECT-TYPE
    SYNTAX     InterfaceIndex
    MAX-ACCESS not-accessible
    STATUS     current
    DESCRIPTION
            "The interface for which this entry contains information for
            an IP multicast group address."
    ::= { igmpCacheEntry 2 }

igmpCacheSelf OBJECT-TYPE
    SYNTAX     TruthValue
    MAX-ACCESS read-create
    STATUS     current
    DESCRIPTION
            "An indication of whether the local system is a member of
            this group address on this interface."
    DEFVAL     { true }
    ::= { igmpCacheEntry 3 }

igmpCacheLastReporter OBJECT-TYPE
    SYNTAX     IpAddress
    MAX-ACCESS read-only
    STATUS     current
    DESCRIPTION
            "The IP address of the source of the last membership report
            received for this IP Multicast group address on this
            interface.  If no membership report has been received, this
            object has the value 0.0.0.0."


    ::= { igmpCacheEntry 4 }

igmpCacheUpTime OBJECT-TYPE
    SYNTAX     TimeTicks
    MAX-ACCESS read-only
    STATUS     current
    DESCRIPTION
            "The time elapsed since this entry was created."
    ::= { igmpCacheEntry 5 }

igmpCacheExpiryTime OBJECT-TYPE
    SYNTAX     TimeTicks
    MAX-ACCESS read-only
    STATUS     current
    DESCRIPTION
            "The minimum amount of time remaining before this entry will
            be aged out.  A value of 0 indicates that the entry is only
            present because igmpCacheSelf is true and that if the router
            left the group, this entry would be aged out immediately.
            Note that some implementations may process membership
            reports from the local system in the same way as reports
            from other hosts, so a value of 0 is not required."
    ::= { igmpCacheEntry 6 }

igmpCacheStatus OBJECT-TYPE
    SYNTAX     RowStatus
    MAX-ACCESS read-create
    STATUS     current
    DESCRIPTION
            "The status of this entry."
    ::= { igmpCacheEntry 7 }

igmpCacheVersion1HostTimer OBJECT-TYPE
    SYNTAX     TimeTicks
    MAX-ACCESS read-only
    STATUS     current
    DESCRIPTION
            "The time remaining until the local router will assume that
            there are no longer any IGMP version 1 members on the IP
            subnet attached to this interface.  Upon hearing any IGMPv1
            Membership Report, this value is reset to the group
            membership timer.  While this time remaining is non-zero,
            the local router ignores any IGMPv2 Leave messages for this
            group that it receives on this interface."
    ::= { igmpCacheEntry 8 }

-- conformance information


igmpMIBConformance
               OBJECT IDENTIFIER ::= { igmpStdMIB 2 }
igmpMIBCompliances
               OBJECT IDENTIFIER ::= { igmpMIBConformance 1 }
igmpMIBGroups  OBJECT IDENTIFIER ::= { igmpMIBConformance 2 }

-- compliance statements

igmpV1HostMIBCompliance MODULE-COMPLIANCE
    STATUS  current
    DESCRIPTION
            "The compliance statement for hosts running IGMPv1 and
            implementing the IGMP MIB."
    MODULE  -- this module
    MANDATORY-GROUPS { igmpBaseMIBGroup }

    OBJECT     igmpInterfaceStatus
    MIN-ACCESS read-only
    DESCRIPTION
             "Write access is not required."

    OBJECT     igmpCacheStatus
    MIN-ACCESS read-only
    DESCRIPTION
             "Write access is not required."

    ::= { igmpMIBCompliances 1 }

igmpV1RouterMIBCompliance MODULE-COMPLIANCE
    STATUS  current
    DESCRIPTION
            "The compliance statement for routers running IGMPv1 and
            implementing the IGMP MIB."
    MODULE  -- this module
      MANDATORY-GROUPS { igmpBaseMIBGroup,
                       igmpRouterMIBGroup
                     }

    OBJECT     igmpInterfaceStatus
    MIN-ACCESS read-only
    DESCRIPTION
             "Write access is not required."
    OBJECT     igmpCacheStatus
    MIN-ACCESS read-only
    DESCRIPTION
             "Write access is not required."


    ::= { igmpMIBCompliances 2 }

igmpV2HostMIBCompliance MODULE-COMPLIANCE
    STATUS  current
    DESCRIPTION
            "The compliance statement for hosts running IGMPv2 and
            implementing the IGMP MIB."
    MODULE  -- this module
    MANDATORY-GROUPS { igmpBaseMIBGroup,
                       igmpV2HostMIBGroup
                     }

    OBJECT     igmpInterfaceStatus
    MIN-ACCESS read-only
    DESCRIPTION
             "Write access is not required."

    OBJECT     igmpCacheStatus
    MIN-ACCESS read-only
    DESCRIPTION
             "Write access is not required."

    ::= { igmpMIBCompliances 3 }

igmpV2RouterMIBCompliance MODULE-COMPLIANCE
    STATUS  current
    DESCRIPTION
            "The compliance statement for routers running IGMPv2 and
            implementing the IGMP MIB."
    MODULE  -- this module
    MANDATORY-GROUPS { igmpBaseMIBGroup,
                       igmpRouterMIBGroup,
                       igmpV2RouterMIBGroup
                     }

    OBJECT     igmpInterfaceStatus
    MIN-ACCESS read-only
    DESCRIPTION
             "Write access is not required."
    OBJECT     igmpCacheStatus
    MIN-ACCESS read-only
    DESCRIPTION
             "Write access is not required."

    ::= { igmpMIBCompliances 4 }

-- units of conformance


igmpBaseMIBGroup OBJECT-GROUP
    OBJECTS { igmpCacheSelf,
              igmpCacheStatus, igmpInterfaceStatus
            }
    STATUS  current
    DESCRIPTION
            "The basic collection of objects providing management of
            IGMP version 1 or 2."
    ::= { igmpMIBGroups 1 }

igmpRouterMIBGroup OBJECT-GROUP
    OBJECTS { igmpCacheUpTime, igmpCacheExpiryTime,
              igmpInterfaceJoins, igmpInterfaceGroups,
              igmpCacheLastReporter, igmpInterfaceQuerierUpTime,
              igmpInterfaceQuerierExpiryTime,
              igmpInterfaceQueryInterval
            }
    STATUS  current
    DESCRIPTION
            "A collection of additional objects for management of IGMP
            version 1 or 2 in routers."
    ::= { igmpMIBGroups 2 }

igmpV2HostMIBGroup OBJECT-GROUP
    OBJECTS { igmpInterfaceVersion1QuerierTimer }
    STATUS  current
    DESCRIPTION
            "A collection of additional objects for management of IGMP
            version 2 in hosts."
    ::= { igmpMIBGroups 3 }

igmpHostOptMIBGroup OBJECT-GROUP
    OBJECTS { igmpCacheLastReporter, igmpInterfaceQuerier }
    STATUS  current
    DESCRIPTION
            "A collection of optional objects for IGMP hosts.
            Supporting this group can be especially useful in an
            environment with a router which does not support the IGMP
            MIB."
    ::= { igmpMIBGroups 4 }

igmpV2RouterMIBGroup OBJECT-GROUP
    OBJECTS { igmpInterfaceVersion, igmpInterfaceQuerier,
              igmpInterfaceQueryMaxResponseTime,
              igmpInterfaceRobustness,
              igmpInterfaceWrongVersionQueries,


              igmpInterfaceLastMembQueryIntvl,
              igmpCacheVersion1HostTimer
            }
    STATUS  current
    DESCRIPTION
            "A collection of additional objects for management of IGMP
            version 2 in routers."
    ::= { igmpMIBGroups 5 }

igmpV2ProxyMIBGroup OBJECT-GROUP
    OBJECTS { igmpInterfaceProxyIfIndex }
    STATUS  current
    DESCRIPTION
            "A collection of additional objects for management of IGMP
            proxy devices."
    ::= { igmpMIBGroups 6 }

END

HDSL2-SHDSL-LINE-MIB DEFINITIONS ::= BEGIN

IMPORTS
MODULE-IDENTITY,
OBJECT-TYPE,
Counter32,
Unsigned32,
Gauge32,
NOTIFICATION-TYPE,
Integer32,
transmission                  FROM SNMPv2-SMI
RowStatus,
TEXTUAL-CONVENTION            FROM SNMPv2-TC
ifIndex                       FROM IF-MIB
PerfCurrentCount,
PerfIntervalCount             FROM PerfHist-TC-MIB
SnmpAdminString               FROM SNMP-FRAMEWORK-MIB
MODULE-COMPLIANCE,
OBJECT-GROUP,
NOTIFICATION-GROUP            FROM SNMPv2-CONF;

hdsl2ShdslMIB MODULE-IDENTITY
    LAST-UPDATED "200205090000Z" -- May 9, 2002
    ORGANIZATION "ADSLMIB Working Group"
    CONTACT-INFO "WG-email:  adslmib@ietf.org
               Info:      https://www1.ietf.org/mailman/listinfo/adslmib
               Chair:     Mike Sneed


               Postal:    P.O. Box 37324
                          Raleigh NC 27627-7324
               Email:     sneedmike@hotmail.com

               Co-editor: Bob Ray
                          PESA Switching Systems, Inc.
               Postal:    330-A Wynn Drive
                          Huntsville, AL 35805 USA
               Email:     rray@pesa.com
               Phone:     +1 256 726 9200 ext. 142

               Co-editor: Rajesh Abbi
                          Alcatel USA
               Postal:    2912 Wake Forest Road
                          Raleigh, NC 27609-7860 USA

               Email:     Rajesh.Abbi@alcatel.com
               Phone:     +1 919 850 6194
              "

DESCRIPTION
     "This MIB module defines a collection of objects for managing
      HDSL2/SHDSL lines.  An agent may reside at either end of the
      line, however the MIB is designed to require no management
      communication between the modems beyond that inherent in the
      low-level EOC line protocol as defined in ANSI T1E1.4/2000-006
      (for HDSL2 lines), or in ITU G.991.2 (for SHDSL lines)."
 REVISION "200205090000Z" -- May 9, 2002
 DESCRIPTION "Initial version, published as RFC 3276."

 ::= { transmission 48 }

hdsl2ShdslMibObjects OBJECT IDENTIFIER ::= { hdsl2ShdslMIB 1 }

-- Textual Conventions used in this MIB
--

Hdsl2ShdslPerfCurrDayCount ::= TEXTUAL-CONVENTION
   STATUS    current
   DESCRIPTION
     "A gauge associated with interface performance measurements in
      a current 1-day (24 hour) measurement interval.

      The value of this gauge starts at zero at the beginning of an
      interval and is increased when associated events occur, until
      the end of the 1-day interval.  At that time the value of the
      gauge is stored in the previous 1-day history interval, as
      defined in a companion object of type


      Hdsl2Shdsl1DayIntevalCount, and the current interval gauge
      is restarted at zero.

      In the case where the agent has no valid data available for
      this interval the corresponding object instance is not
      available and upon a retrieval request a corresponding error
      message shall be returned to indicate that this instance does
      not exist.  Please note that zero is a valid value."
   SYNTAX  Gauge32

Hdsl2Shdsl1DayIntervalCount ::= TEXTUAL-CONVENTION
   STATUS    current
   DESCRIPTION
     "A counter associated with interface performance measurements
      during the most previous 1-day (24 hour) measurement interval.
      The value of this gauge is equal to the value of the current
      day gauge, as defined in a companion object of type
      Hdsl2ShdslPerfCurrDayCount, at the end of its most recent
      interval.

      In the case where the agent has no valid data available for
      this interval the corresponding object instance is not
      available and upon a retrieval request a corresponding error
      message shall be returned to indicate that this instance does
      not exist."
   SYNTAX  Gauge32

Hdsl2ShdslPerfTimeElapsed ::= TEXTUAL-CONVENTION
   STATUS    current
   DESCRIPTION
     "The number of seconds that have elapsed since the beginning of
      the current measurement period.  If, for some reason, such as
      an adjustment in the system's time-of-day clock or the addition
      of a leap second, the current interval exceeds the maximum
      value, the agent will return the maximum value.

      For 15 minute intervals, the range is limited to (0..899).
      For 24 hour intervals, the range is limited to (0..86399)."
   SYNTAX    Unsigned32(0..86399)

Hdsl2ShdslPerfIntervalThreshold ::= TEXTUAL-CONVENTION
   STATUS    current
   DESCRIPTION
     "This convention defines a range of values that may be set in
      a fault threshold alarm control.  As the number of seconds in
      a 15-minute interval numbers at most 900, objects of this type
      may have a range of 0...900, where the value of 0 disables the
      alarm."


   SYNTAX    Unsigned32(0..900)

Hdsl2ShdslUnitId ::= TEXTUAL-CONVENTION
   STATUS    current
   DESCRIPTION
     "This is the unique identification for all units in a
      HDSL2/SHDSL Span.  It is based on the EOC unit addressing
      scheme with reference to the xtuC."
   SYNTAX    INTEGER
           {
           xtuC(1),
           xtuR(2),
           xru1(3),
           xru2(4),
           xru3(5),
           xru4(6),
           xru5(7),
           xru6(8),
           xru7(9),
           xru8(10)
           }

Hdsl2ShdslUnitSide ::= TEXTUAL-CONVENTION
   STATUS    current
   DESCRIPTION
     "This is the referenced side of a HDSL2/SHDSL unit - Network
      or Customer side.  The side facing the Network is the Network
      side, while the side facing the Customer is the Customer side."
   SYNTAX    INTEGER
           {
           networkSide(1),
           customerSide(2)
           }

Hdsl2ShdslWirePair ::= TEXTUAL-CONVENTION
   STATUS    current
   DESCRIPTION
     "This is the referenced pair of wires in a HDSL2/SHDSL Segment.
      HDSL2 only supports a single pair (wirePair1), while SHDSL
      supports an optional second pair (wirePair2)."
   SYNTAX    INTEGER
           {
           wirePair1(1),
           wirePair2(2)
           }

Hdsl2ShdslTransmissionModeType ::= TEXTUAL-CONVENTION
   STATUS    current


   DESCRIPTION
     "Contains the regional setting of the HDSL2/SHDSL span,
     represented as a bit-map of possible settings. The various
     bit positions are:

     Bit   Meaning      Description
     1     region 1     Indicates ITU-T G.991.2 Annex A.
     2     region 2     Indicates ITU-T G.991.2 Annex B."
   SYNTAX      BITS
           {
           region1(0),
           region2(1)
           }

Hdsl2ShdslClockReferenceType ::= TEXTUAL-CONVENTION
   STATUS    current
   DESCRIPTION
     "The various STU-C symbol clock references for the
     HDSL2/SHDSL span, represented as an enumeration."
   SYNTAX    INTEGER
          {
          localClk(1),          -- Mode-1 per G991.2
          networkClk(2),        -- Mode-2 per G991.2
          dataOrNetworkClk(3),  -- Mode-3a per G991.2
          dataClk(4)            -- Mode-3b per G991.2
          }

-- Span Configuration Group
--

hdsl2ShdslSpanConfTable OBJECT-TYPE
   SYNTAX     SEQUENCE OF Hdsl2ShdslSpanConfEntry
   MAX-ACCESS not-accessible
   STATUS     current
   DESCRIPTION
     "This table supports overall configuration of HDSL2/SHDSL
      Spans.  Entries in this table MUST be maintained in a
      persistent manner."
   ::= { hdsl2ShdslMibObjects 1 }

hdsl2ShdslSpanConfEntry OBJECT-TYPE
   SYNTAX      Hdsl2ShdslSpanConfEntry
   MAX-ACCESS  not-accessible
   STATUS      current
   DESCRIPTION
     "An entry in the hdsl2ShdslSpanConfTable.  Each entry
      represents the complete Span in a single HDSL2/SHDSL line.
      It is indexed by the ifIndex of the associated HDSL2/SHDSL


      line."
   INDEX { ifIndex }
   ::= { hdsl2ShdslSpanConfTable 1 }

Hdsl2ShdslSpanConfEntry ::=
   SEQUENCE
   {
   hdsl2ShdslSpanConfNumRepeaters          Unsigned32,
   hdsl2ShdslSpanConfProfile               SnmpAdminString,
   hdsl2ShdslSpanConfAlarmProfile          SnmpAdminString
   }

   hdsl2ShdslSpanConfNumRepeaters OBJECT-TYPE
   SYNTAX      Unsigned32(0..8)
   UNITS       "repeaters"
   MAX-ACCESS  read-write
   STATUS      current
   DESCRIPTION
     "This object provisions the number of repeaters/regenerators
     in this HDSL2/SHDSL Span."
   ::= { hdsl2ShdslSpanConfEntry 1 }

hdsl2ShdslSpanConfProfile OBJECT-TYPE
   SYNTAX      SnmpAdminString (SIZE(1..32))
   MAX-ACCESS  read-write
   STATUS      current
   DESCRIPTION
     "This object is a pointer to a span configuration profile in
     the hdsl2ShdslSpanConfProfileTable, which applies to this span.
     The value of this object is the index of the referenced profile
     in the hdsl2ShdslSpanConfProfileTable.  Note that span
     configuration profiles are only applicable to SHDSL lines.

     HDSL2 lines MUST reference the default profile, 'DEFVAL'.
     By default, this object will have the value 'DEFVAL' (the index
     of the default profile).

     Any attempt to set this object to a value that is not the value
     of the index for an active entry in the profile table,
     hdsl2ShdslSpanConfProfileTable, MUST be rejected."
   ::= { hdsl2ShdslSpanConfEntry 2 }

hdsl2ShdslSpanConfAlarmProfile OBJECT-TYPE
   SYNTAX      SnmpAdminString (SIZE(1..32))
   MAX-ACCESS  read-write
   STATUS      current
   DESCRIPTION
     "This object is a pointer to an Alarm configuration profile in


     the hdsl2ShdslEndpointAlarmConfProfileTable.  The value of this
     object is the index of the referenced profile in the
     hdsl2ShdslEndpointAlarmConfProfileTable.  The alarm threshold
     configuration in the referenced profile will be used by default
     for all segment endpoints in this span.  Individual endpoints
     may override this profile by explicitly specifying some other
     profile in the hdsl2ShdslEndpointConfTable.  By default, this
     object will have the value 'DEFVAL' (the index of the default
     profile).

     Any attempt to set this object to a value that is not the value
     of the index for an active entry in the profile table,
     hdsl2ShdslEndpointAlarmConfProfileTable, MUST be rejected."
   ::= { hdsl2ShdslSpanConfEntry 3 }

-- Span Status Group
--

hdsl2ShdslSpanStatusTable OBJECT-TYPE
   SYNTAX     SEQUENCE OF Hdsl2ShdslSpanStatusEntry
   MAX-ACCESS not-accessible
   STATUS     current
   DESCRIPTION
     "This table provides overall status information of
      HDSL2/SHDSL spans.  This table contains live data from
      equipment.  As such, it is NOT persistent."
   ::= { hdsl2ShdslMibObjects 2 }

hdsl2ShdslSpanStatusEntry OBJECT-TYPE
   SYNTAX      Hdsl2ShdslSpanStatusEntry
   MAX-ACCESS  not-accessible
   STATUS      current
   DESCRIPTION
     "An entry in the hdsl2ShdslSpanStatusTable.  Each entry
      represents the complete span in a single HDSL2/SHDSL line.
      It is indexed by the ifIndex of the associated HDSL2/SHDSL
      line."
   INDEX { ifIndex }
   ::= { hdsl2ShdslSpanStatusTable 1 }

Hdsl2ShdslSpanStatusEntry ::=
   SEQUENCE
   {
   hdsl2ShdslStatusNumAvailRepeaters        Unsigned32,
   hdsl2ShdslStatusMaxAttainableLineRate    Unsigned32,
   hdsl2ShdslStatusActualLineRate           Unsigned32,
   hdsl2ShdslStatusTransmissionModeCurrent
             Hdsl2ShdslTransmissionModeType


   }

hdsl2ShdslStatusNumAvailRepeaters OBJECT-TYPE
   SYNTAX      Unsigned32(0..8)
   MAX-ACCESS  read-only
   STATUS      current
   DESCRIPTION
     "Contains the actual number of repeaters/regenerators
      discovered in this HDSL2/SHDSL span."
   ::= { hdsl2ShdslSpanStatusEntry 1 }

hdsl2ShdslStatusMaxAttainableLineRate OBJECT-TYPE
   SYNTAX      Unsigned32(0..4112000)
   UNITS       "bps"
   MAX-ACCESS  read-only
   STATUS      current
   DESCRIPTION
     "Contains the maximum attainable line rate in this HDSL2/SHDSL
      span.  This object provides the maximum rate the line is
      capable of achieving.  This is based upon measurements made
      during line probing."
   ::= { hdsl2ShdslSpanStatusEntry 2 }

hdsl2ShdslStatusActualLineRate OBJECT-TYPE
   SYNTAX      Unsigned32(0..4112000)
   UNITS       "bps"
   MAX-ACCESS  read-only
   STATUS      current
   DESCRIPTION
     "Contains the actual line rate in this HDSL2/SHDSL span.  This
     should equal ifSpeed."
   ::= { hdsl2ShdslSpanStatusEntry 3 }

hdsl2ShdslStatusTransmissionModeCurrent OBJECT-TYPE
   SYNTAX      Hdsl2ShdslTransmissionModeType
   MAX-ACCESS  read-only
   STATUS      current
   DESCRIPTION
     "Contains the current Power Spectral Density (PSD) regional
      setting of the HDSL2/SHDSL span."
   ::= { hdsl2ShdslSpanStatusEntry 4 }

-- Unit Inventory Group
--

hdsl2ShdslInventoryTable OBJECT-TYPE
   SYNTAX     SEQUENCE OF Hdsl2ShdslInventoryEntry
   MAX-ACCESS not-accessible


   STATUS     current
   DESCRIPTION
     "This table supports retrieval of unit inventory information
      available via the EOC from units in a HDSL2/SHDSL line.

      Entries in this table are dynamically created during the
      line discovery process.  The life cycle for these entries
      is as follows:

         - xtu discovers a device, either a far-end xtu or an xru
         - an inventory table entry is created for the device
         - the line goes down for whatever reason
         - inventory table entries for unreachable devices are
           destroyed.

      As these entries are created/destroyed dynamically, they
      are NOT persistent."
   ::= { hdsl2ShdslMibObjects 3 }

hdsl2ShdslInventoryEntry OBJECT-TYPE
   SYNTAX      Hdsl2ShdslInventoryEntry
   MAX-ACCESS  not-accessible
   STATUS      current
   DESCRIPTION
     "An entry in the hdsl2ShdslInventoryTable.  Each entry
      represents inventory information for a single unit in a
      HDSL2/SHDSL line.  It is indexed by the ifIndex of the
      HDSL2/SHDSL line and the Hdsl2ShdslUnitId of the
      associated unit."
   INDEX { ifIndex, hdsl2ShdslInvIndex }
   ::= { hdsl2ShdslInventoryTable 1 }

Hdsl2ShdslInventoryEntry ::=
   SEQUENCE
   {
   hdsl2ShdslInvIndex                      Hdsl2ShdslUnitId,
   hdsl2ShdslInvVendorID                   OCTET STRING,
   hdsl2ShdslInvVendorModelNumber          OCTET STRING,
   hdsl2ShdslInvVendorSerialNumber         OCTET STRING,
   hdsl2ShdslInvVendorEOCSoftwareVersion   Integer32,
   hdsl2ShdslInvStandardVersion            Integer32,
   hdsl2ShdslInvVendorListNumber           OCTET STRING,
   hdsl2ShdslInvVendorIssueNumber          OCTET STRING,
   hdsl2ShdslInvVendorSoftwareVersion      OCTET STRING,
   hdsl2ShdslInvEquipmentCode              OCTET STRING,
   hdsl2ShdslInvVendorOther                OCTET STRING,
   hdsl2ShdslInvTransmissionModeCapability
                         Hdsl2ShdslTransmissionModeType


   }

hdsl2ShdslInvIndex OBJECT-TYPE
   SYNTAX      Hdsl2ShdslUnitId
   MAX-ACCESS  not-accessible
   STATUS      current
   DESCRIPTION
      "Each entry in this table corresponds to a physical element
      in a HDSL2/SHDSL Span.  It is based on the EOC unit addressing
      scheme with reference to the xtuC."
   ::= { hdsl2ShdslInventoryEntry 1 }

hdsl2ShdslInvVendorID OBJECT-TYPE
   SYNTAX      OCTET STRING(SIZE(8))
   MAX-ACCESS  read-only
   STATUS      current
   DESCRIPTION
     "Vendor ID as reported in an Inventory Response message."
   ::= { hdsl2ShdslInventoryEntry 2 }

hdsl2ShdslInvVendorModelNumber OBJECT-TYPE
   SYNTAX      OCTET STRING(SIZE(12))
   MAX-ACCESS  read-only
   STATUS      current
   DESCRIPTION
     "Vendor model number as reported in an Inventory Response
      message."
   ::= { hdsl2ShdslInventoryEntry 3 }

hdsl2ShdslInvVendorSerialNumber OBJECT-TYPE
   SYNTAX      OCTET STRING(SIZE(12))
   MAX-ACCESS  read-only
   STATUS      current
   DESCRIPTION
     "Vendor serial number as reported in an Inventory Response
      message."
   ::= { hdsl2ShdslInventoryEntry 4 }

hdsl2ShdslInvVendorEOCSoftwareVersion OBJECT-TYPE
   SYNTAX      Integer32
   MAX-ACCESS  read-only
   STATUS      current
   DESCRIPTION
     "Vendor EOC version as reported in a Discovery Response
      message."
   ::= { hdsl2ShdslInventoryEntry 5 }

hdsl2ShdslInvStandardVersion OBJECT-TYPE


   SYNTAX      Integer32
   MAX-ACCESS  read-only
   STATUS      current
   DESCRIPTION
     "Version of the HDSL2/SHDSL standard implemented, as reported
      in an Inventory Response message."
   ::= { hdsl2ShdslInventoryEntry 6 }

hdsl2ShdslInvVendorListNumber OBJECT-TYPE
   SYNTAX      OCTET STRING(SIZE(3))
   MAX-ACCESS  read-only
   STATUS      current
   DESCRIPTION
     "Vendor list number as reported in an Inventory Response
      message."
   ::= { hdsl2ShdslInventoryEntry 7 }

hdsl2ShdslInvVendorIssueNumber OBJECT-TYPE
   SYNTAX      OCTET STRING(SIZE(2))
   MAX-ACCESS  read-only
   STATUS      current
   DESCRIPTION
     "Vendor issue number as reported in an Inventory Response
      message."
   ::= { hdsl2ShdslInventoryEntry 8 }

hdsl2ShdslInvVendorSoftwareVersion OBJECT-TYPE
   SYNTAX      OCTET STRING(SIZE(6))
   MAX-ACCESS  read-only
   STATUS      current
   DESCRIPTION
     "Vendor software version as reported in an Inventory Response
      message."
   ::= { hdsl2ShdslInventoryEntry 9 }

hdsl2ShdslInvEquipmentCode OBJECT-TYPE
   SYNTAX      OCTET STRING(SIZE(10))
   MAX-ACCESS  read-only
   STATUS      current
   DESCRIPTION
     "Equipment code conforming to ANSI T1.213, Coded Identification
      of Equipment Entities."
   ::= { hdsl2ShdslInventoryEntry 10 }

hdsl2ShdslInvVendorOther OBJECT-TYPE
   SYNTAX      OCTET STRING(SIZE(12))
   MAX-ACCESS  read-only
   STATUS      current


   DESCRIPTION
     "Other vendor information as reported in an Inventory Response
      message."
   ::= { hdsl2ShdslInventoryEntry 11 }

hdsl2ShdslInvTransmissionModeCapability OBJECT-TYPE
   SYNTAX      Hdsl2ShdslTransmissionModeType
   MAX-ACCESS  read-only
   STATUS      current
   DESCRIPTION
     "Contains the transmission mode capability of the SHDSL unit."
   ::= { hdsl2ShdslInventoryEntry 12 }

-- Segment Endpoint Configuration Group
--

hdsl2ShdslEndpointConfTable OBJECT-TYPE
   SYNTAX      SEQUENCE OF Hdsl2ShdslEndpointConfEntry
   MAX-ACCESS  not-accessible
   STATUS      current
   DESCRIPTION
     "This table supports configuration parameters for segment
      endpoints in a HDSL2/SHDSL line.  As this table is indexed
      by ifIndex, it MUST be maintained in a persistent manner."
   ::= { hdsl2ShdslMibObjects 4 }

hdsl2ShdslEndpointConfEntry OBJECT-TYPE
   SYNTAX      Hdsl2ShdslEndpointConfEntry
   MAX-ACCESS  not-accessible
   STATUS      current
   DESCRIPTION
     "An entry in the hdsl2ShdslEndpointConfTable.  Each entry
      represents a single segment endpoint in a HDSL2/SHDSL line.
      It is indexed by the ifIndex of the HDSL2/SHDSL line, the
      UnitId of the associated unit, the side of the unit, and the
      wire-pair of the associated modem."
   INDEX { ifIndex, hdsl2ShdslInvIndex, hdsl2ShdslEndpointSide,
           hdsl2ShdslEndpointWirePair}
   ::= { hdsl2ShdslEndpointConfTable 1 }

Hdsl2ShdslEndpointConfEntry ::=
   SEQUENCE
   {
   hdsl2ShdslEndpointSide                   Hdsl2ShdslUnitSide,
   hdsl2ShdslEndpointWirePair               Hdsl2ShdslWirePair,
   hdsl2ShdslEndpointAlarmConfProfile       SnmpAdminString
   }


hdsl2ShdslEndpointSide OBJECT-TYPE
   SYNTAX      Hdsl2ShdslUnitSide
   MAX-ACCESS  not-accessible
   STATUS      current
   DESCRIPTION
     "The side of the unit associated with this segment endpoint -
      Network/Customer side - as per the Hdsl2ShdslUnitSide textual
      convention."
   ::= { hdsl2ShdslEndpointConfEntry 1 }

hdsl2ShdslEndpointWirePair OBJECT-TYPE
   SYNTAX      Hdsl2ShdslWirePair
   MAX-ACCESS  not-accessible
   STATUS      current
   DESCRIPTION
     "The wire-pair of the modem associated with this segment
      endpoint as per the Hdsl2ShdslWirePair textual convention."
   ::= { hdsl2ShdslEndpointConfEntry 2 }

hdsl2ShdslEndpointAlarmConfProfile OBJECT-TYPE
   SYNTAX      SnmpAdminString (SIZE(0..32))
   MAX-ACCESS  read-write
   STATUS      current
   DESCRIPTION
     "This object configures the alarm threshold values to be used
      for this segment endpoint.  The values are obtained from the
      alarm configuration profile referenced by this object.  The
      value of this object is the index of the referenced profile in
      the hdsl2ShdslEndpointAlarmConfProfileTable, or NULL (a zero-
      length SnmpAdminString).  If the value is a zero-length
      SnmpAdminString, the endpoint uses the default Alarm
      Configuration Profile for the associated span as per the
      hdsl2ShdslSpanConfAlarmProfile object in the
      hdsl2ShdslSpanConfTable.  The default value of this object is
      a zero-length SnmpAdminString.

      Any attempt to set this object to a value that is not the value
      of the index for an active entry in the profile table,
      hdsl2ShdslEndpointAlarmConfProfileTable, MUST be rejected."
   ::= { hdsl2ShdslEndpointConfEntry 3 }

-- Segment Endpoint Current Status/Performance Group
--

hdsl2ShdslEndpointCurrTable OBJECT-TYPE
   SYNTAX      SEQUENCE OF Hdsl2ShdslEndpointCurrEntry
   MAX-ACCESS  not-accessible
   STATUS      current


   DESCRIPTION
     "This table contains current status and performance information
      for segment endpoints in HDSL2/SHDSL Lines.  As with other
      tables in this MIB indexed by ifIndex, entries in this table
      MUST be maintained in a persistent manner."
   ::= { hdsl2ShdslMibObjects 5 }

hdsl2ShdslEndpointCurrEntry OBJECT-TYPE
   SYNTAX      Hdsl2ShdslEndpointCurrEntry
   MAX-ACCESS  not-accessible
   STATUS      current
   DESCRIPTION
     "An entry in the hdsl2ShdslEndpointCurrTable.  Each entry
     contains status and performance information relating to a
     single segment endpoint.  It is indexed by the ifIndex of the
     HDSL2/SHDSL line, the UnitId of the associated unit, the side
     of the unit, and the wire-pair of the associated modem."
   INDEX { ifIndex, hdsl2ShdslInvIndex, hdsl2ShdslEndpointSide,
           hdsl2ShdslEndpointWirePair }
   ::= { hdsl2ShdslEndpointCurrTable 1 }

Hdsl2ShdslEndpointCurrEntry ::=
   SEQUENCE
   {
   hdsl2ShdslEndpointCurrAtn                Integer32,
   hdsl2ShdslEndpointCurrSnrMgn             Integer32,
   hdsl2ShdslEndpointCurrStatus             BITS,
   hdsl2ShdslEndpointES                     Counter32,
   hdsl2ShdslEndpointSES                    Counter32,
   hdsl2ShdslEndpointCRCanomalies           Counter32,
   hdsl2ShdslEndpointLOSWS                  Counter32,
   hdsl2ShdslEndpointUAS                    Counter32,
   hdsl2ShdslEndpointCurr15MinTimeElapsed
                             Hdsl2ShdslPerfTimeElapsed,
   hdsl2ShdslEndpointCurr15MinES            PerfCurrentCount,
   hdsl2ShdslEndpointCurr15MinSES           PerfCurrentCount,
   hdsl2ShdslEndpointCurr15MinCRCanomalies  PerfCurrentCount,
   hdsl2ShdslEndpointCurr15MinLOSWS         PerfCurrentCount,
   hdsl2ShdslEndpointCurr15MinUAS           PerfCurrentCount,
   hdsl2ShdslEndpointCurr1DayTimeElapsed
                             Hdsl2ShdslPerfTimeElapsed,
   hdsl2ShdslEndpointCurr1DayES
                             Hdsl2ShdslPerfCurrDayCount,
   hdsl2ShdslEndpointCurr1DaySES
                             Hdsl2ShdslPerfCurrDayCount,
   hdsl2ShdslEndpointCurr1DayCRCanomalies
                             Hdsl2ShdslPerfCurrDayCount,
   hdsl2ShdslEndpointCurr1DayLOSWS


                             Hdsl2ShdslPerfCurrDayCount,
   hdsl2ShdslEndpointCurr1DayUAS
                             Hdsl2ShdslPerfCurrDayCount
   }

hdsl2ShdslEndpointCurrAtn OBJECT-TYPE
   SYNTAX      Integer32(-127..128)
   UNITS       "dB"
   MAX-ACCESS  read-only
   STATUS      current
   DESCRIPTION
     "The current loop attenuation for this endpoint as reported in
      a Network or Customer Side Performance Status message."
   REFERENCE   "HDSL2 Section 7.5.3.7; SHDSL Section 9.5.5.7"
   ::= { hdsl2ShdslEndpointCurrEntry 1 }

hdsl2ShdslEndpointCurrSnrMgn OBJECT-TYPE
   SYNTAX      Integer32(-127..128)
   UNITS       "dB"
   MAX-ACCESS  read-only
   STATUS      current
   DESCRIPTION
     "The current SNR margin for this endpoint as reported in a
      Status Response/SNR message."
   REFERENCE   "HDSL2 Section 7.5.3.7; SHDSL Section 9.5.5.7"
   ::= { hdsl2ShdslEndpointCurrEntry 2 }

hdsl2ShdslEndpointCurrStatus OBJECT-TYPE
   SYNTAX      BITS
               {
               noDefect(0),
               powerBackoff(1),
               deviceFault(2),
               dcContinuityFault(3),
               snrMarginAlarm(4),
               loopAttenuationAlarm(5),
               loswFailureAlarm(6),
               configInitFailure(7),
               protocolInitFailure(8),
               noNeighborPresent(9),
               loopbackActive(10)
               }
   MAX-ACCESS  read-only
   STATUS      current
   DESCRIPTION
     "Contains the current state of the endpoint.  This is a
     bitmap of possible conditions. The various bit positions
     are:


     noDefect               There no defects on the line.

     powerBackoff           Indicates enhanced Power Backoff.

     deviceFault            Indicates a vendor-dependent
                            diagnostic or self-test fault
                            has been detected.

     dcContinuityFault      Indicates vendor-dependent
                            conditions that interfere with
                            span powering such as short and
                            open circuits.

     snrMarginAlarm         Indicates that the SNR margin
                            has dropped below the alarm threshold.

     loopAttenuationAlarm   Indicates that the loop attenuation
                            exceeds the alarm threshold.

     loswFailureAlarm       Indicates a forward LOSW alarm.

     configInitFailure      Endpoint failure during initialization
                            due to paired endpoint not able to
                            support requested configuration.

     protocolInitFailure    Endpoint failure during initialization
                            due to incompatible protocol used by
                            the paired endpoint.

     noNeighborPresent      Endpoint failure during initialization
                            due to no activation sequence detected
                            from paired endpoint.

     loopbackActive         A loopback is currently active at this
                            Segment Endpoint.

     This is intended to supplement ifOperStatus.  Note that there
     is a 1-1 relationship between the status bits defined in this
     object and the notification thresholds defined elsewhere in
     this MIB."
   REFERENCE   "HDSL2 Section 7.5.3.7; SHDSL Section 9.5.5.7"
   ::= { hdsl2ShdslEndpointCurrEntry 3 }

hdsl2ShdslEndpointES OBJECT-TYPE
   SYNTAX      Counter32
   UNITS       "seconds"
   MAX-ACCESS  read-only
   STATUS      current


   DESCRIPTION
     "Count of Errored Seconds (ES) on this endpoint since the xU
      was last restarted."
   REFERENCE   "HDSL2 Section 7.5.3.7; SHDSL Section 9.5.5.7"
   ::= { hdsl2ShdslEndpointCurrEntry 4 }

hdsl2ShdslEndpointSES OBJECT-TYPE
   SYNTAX       Counter32
   UNITS        "seconds"
   MAX-ACCESS   read-only
   STATUS       current
   DESCRIPTION
     "Count of Severely Errored Seconds (SES) on this endpoint
      since the xU was last restarted."
   REFERENCE   "HDSL2 Section 7.5.3.7; SHDSL Section 9.5.5.7"
   ::= { hdsl2ShdslEndpointCurrEntry 5 }

hdsl2ShdslEndpointCRCanomalies OBJECT-TYPE
   SYNTAX       Counter32
   UNITS        "detected CRC Anomalies"
   MAX-ACCESS   read-only
   STATUS       current
   DESCRIPTION
     "Count of CRC anomalies on this endpoint since the xU was
      last restarted."
   REFERENCE   "HDSL2 Section 7.5.3.7; SHDSL Section 9.5.5.7"
   ::= { hdsl2ShdslEndpointCurrEntry 6 }

hdsl2ShdslEndpointLOSWS OBJECT-TYPE
   SYNTAX       Counter32
   UNITS        "seconds"
   MAX-ACCESS   read-only
   STATUS       current
   DESCRIPTION
     "Count of Loss of Sync Word (LOSW) Seconds on this endpoint
      since the xU was last restarted."
   REFERENCE   "HDSL2 Section 7.5.3.7; SHDSL Section 9.5.5.7"
   ::= { hdsl2ShdslEndpointCurrEntry 7 }

hdsl2ShdslEndpointUAS OBJECT-TYPE
   SYNTAX       Counter32
   UNITS        "seconds"
   MAX-ACCESS   read-only
   STATUS       current
   DESCRIPTION
     "Count of Unavailable Seconds (UAS) on this endpoint since
      the xU was last restarted."
   REFERENCE   "HDSL2 Section 7.5.3.7; SHDSL Section 9.5.5.7"


   ::= { hdsl2ShdslEndpointCurrEntry 8 }

hdsl2ShdslEndpointCurr15MinTimeElapsed OBJECT-TYPE
   SYNTAX       Hdsl2ShdslPerfTimeElapsed
   UNITS        "seconds"
   MAX-ACCESS   read-only
   STATUS       current
   DESCRIPTION
     "Total elapsed seconds in the current 15-minute interval."
   ::= { hdsl2ShdslEndpointCurrEntry 9 }

hdsl2ShdslEndpointCurr15MinES OBJECT-TYPE
   SYNTAX       PerfCurrentCount
   UNITS        "seconds"
   MAX-ACCESS   read-only
   STATUS       current
   DESCRIPTION
     "Count of Errored Seconds (ES) in the current 15-minute
      interval."
   REFERENCE   "HDSL2 Section 7.5.3.7; SHDSL Section 9.5.5.7"
   ::= { hdsl2ShdslEndpointCurrEntry 10 }

hdsl2ShdslEndpointCurr15MinSES OBJECT-TYPE
   SYNTAX       PerfCurrentCount
   UNITS        "seconds"
   MAX-ACCESS   read-only
   STATUS       current
   DESCRIPTION
     "Count of Severely Errored Seconds (SES) in the current
      15-minute interval."
   REFERENCE   "HDSL2 Section 7.5.3.7; SHDSL Section 9.5.5.7"
   ::= { hdsl2ShdslEndpointCurrEntry 11 }

hdsl2ShdslEndpointCurr15MinCRCanomalies OBJECT-TYPE
   SYNTAX       PerfCurrentCount
   UNITS        "detected CRC Anomalies"
   MAX-ACCESS   read-only
   STATUS       current
   DESCRIPTION
     "Count of CRC anomalies in the current 15-minute interval."
   REFERENCE   "HDSL2 Section 7.5.3.7; SHDSL Section 9.5.5.7"
   ::= { hdsl2ShdslEndpointCurrEntry 12 }

hdsl2ShdslEndpointCurr15MinLOSWS OBJECT-TYPE
   SYNTAX       PerfCurrentCount
   UNITS        "seconds"
   MAX-ACCESS   read-only
   STATUS       current


   DESCRIPTION
     "Count of Loss of Sync Word (LOSW) Seconds in the current
      15-minute interval."
   REFERENCE   "HDSL2 Section 7.5.3.7; SHDSL Section 9.5.5.7"
   ::= { hdsl2ShdslEndpointCurrEntry 13 }

hdsl2ShdslEndpointCurr15MinUAS OBJECT-TYPE
   SYNTAX       PerfCurrentCount
   UNITS        "seconds"
   MAX-ACCESS   read-only
   STATUS       current
   DESCRIPTION
     "Count of Unavailable Seconds (UAS) in the current 15-minute
      interval."
   REFERENCE   "HDSL2 Section 7.5.3.7; SHDSL Section 9.5.5.7"
   ::= { hdsl2ShdslEndpointCurrEntry 14 }

hdsl2ShdslEndpointCurr1DayTimeElapsed OBJECT-TYPE
   SYNTAX       Hdsl2ShdslPerfTimeElapsed
   UNITS        "seconds"
   MAX-ACCESS   read-only
   STATUS       current
   DESCRIPTION
     "Number of seconds that have elapsed since the beginning of
      the current 1-day interval."
   ::= { hdsl2ShdslEndpointCurrEntry 15 }

hdsl2ShdslEndpointCurr1DayES OBJECT-TYPE
   SYNTAX       Hdsl2ShdslPerfCurrDayCount
   UNITS        "seconds"
   MAX-ACCESS   read-only
   STATUS       current
   DESCRIPTION
     "Count of Errored Seconds (ES) during the current day as
      measured by hdsl2ShdslEndpointCurr1DayTimeElapsed."
   REFERENCE   "HDSL2 Section 7.5.3.7; SHDSL Section 9.5.5.7"
   ::= { hdsl2ShdslEndpointCurrEntry 16 }

hdsl2ShdslEndpointCurr1DaySES OBJECT-TYPE
   SYNTAX       Hdsl2ShdslPerfCurrDayCount
   UNITS        "seconds"
   MAX-ACCESS   read-only
   STATUS       current
   DESCRIPTION
     "Count of Severely Errored Seconds (SES) during the current
      day as measured by hdsl2ShdslEndpointCurr1DayTimeElapsed."
   REFERENCE   "HDSL2 Section 7.5.3.7; SHDSL Section 9.5.5.7"
   ::= { hdsl2ShdslEndpointCurrEntry 17 }


hdsl2ShdslEndpointCurr1DayCRCanomalies OBJECT-TYPE
   SYNTAX       Hdsl2ShdslPerfCurrDayCount
   UNITS        "detected CRC Anomalies"
   MAX-ACCESS   read-only
   STATUS       current
   DESCRIPTION
     "Count of CRC anomalies during the current day as measured
      by hdsl2ShdslEndpointCurr1DayTimeElapsed."
   REFERENCE   "HDSL2 Section 7.5.3.7; SHDSL Section 9.5.5.7"
   ::= { hdsl2ShdslEndpointCurrEntry 18 }

hdsl2ShdslEndpointCurr1DayLOSWS OBJECT-TYPE
   SYNTAX       Hdsl2ShdslPerfCurrDayCount
   UNITS        "seconds"
   MAX-ACCESS   read-only
   STATUS       current
   DESCRIPTION
     "Count of Loss of Sync Word (LOSW) Seconds during the current
      day as measured by hdsl2ShdslEndpointCurr1DayTimeElapsed."
   REFERENCE   "HDSL2 Section 7.5.3.7; SHDSL Section 9.5.5.7"
   ::= { hdsl2ShdslEndpointCurrEntry 19 }

hdsl2ShdslEndpointCurr1DayUAS OBJECT-TYPE
   SYNTAX       Hdsl2ShdslPerfCurrDayCount
   UNITS        "seconds"
   MAX-ACCESS   read-only
   STATUS       current
   DESCRIPTION
     "Count of Unavailable Seconds (UAS) during the current day as
      measured by hdsl2ShdslEndpointCurr1DayTimeElapsed."
   REFERENCE   "HDSL2 Section 7.5.3.7; SHDSL Section 9.5.5.7"
   ::= { hdsl2ShdslEndpointCurrEntry 20 }

-- Segment Endpoint 15-Minute Interval Status/Performance Group
--

hdsl2Shdsl15MinIntervalTable OBJECT-TYPE
   SYNTAX      SEQUENCE OF Hdsl2Shdsl15MinIntervalEntry
   MAX-ACCESS  not-accessible
   STATUS      current
   DESCRIPTION
     "This table provides one row for each HDSL2/SHDSL endpoint
      performance data collection interval.  This table contains
      live data from equipment.  As such, it is NOT persistent."
   ::= { hdsl2ShdslMibObjects 6 }

hdsl2Shdsl15MinIntervalEntry OBJECT-TYPE
   SYNTAX      Hdsl2Shdsl15MinIntervalEntry


   MAX-ACCESS  not-accessible
   STATUS      current
   DESCRIPTION
     "An entry in the hdsl2Shdsl15MinIntervalTable."
   INDEX { ifIndex, hdsl2ShdslInvIndex, hdsl2ShdslEndpointSide,
           hdsl2ShdslEndpointWirePair, hdsl2Shdsl15MinIntervalNumber}
   ::= { hdsl2Shdsl15MinIntervalTable 1 }

Hdsl2Shdsl15MinIntervalEntry ::=
   SEQUENCE
   {
   hdsl2Shdsl15MinIntervalNumber         Unsigned32,
   hdsl2Shdsl15MinIntervalES             PerfIntervalCount,
   hdsl2Shdsl15MinIntervalSES            PerfIntervalCount,
   hdsl2Shdsl15MinIntervalCRCanomalies   PerfIntervalCount,
   hdsl2Shdsl15MinIntervalLOSWS          PerfIntervalCount,
   hdsl2Shdsl15MinIntervalUAS            PerfIntervalCount
   }

hdsl2Shdsl15MinIntervalNumber OBJECT-TYPE
   SYNTAX      Unsigned32(1..96)
   MAX-ACCESS  not-accessible
   STATUS      current
   DESCRIPTION
     "Performance Data Interval number. 1 is the the most recent
      previous interval; interval 96 is 24 hours ago. Intervals
      2..96 are optional."
   ::= { hdsl2Shdsl15MinIntervalEntry 1 }

hdsl2Shdsl15MinIntervalES OBJECT-TYPE
   SYNTAX      PerfIntervalCount
   UNITS       "seconds"
   MAX-ACCESS  read-only
   STATUS      current
   DESCRIPTION
     "Count of Errored Seconds (ES) during the interval."
   REFERENCE   "HDSL2 Section 7.5.3.7; SHDSL Section 9.5.5.7"
   ::= { hdsl2Shdsl15MinIntervalEntry 2 }

hdsl2Shdsl15MinIntervalSES OBJECT-TYPE
   SYNTAX      PerfIntervalCount
   UNITS       "seconds"
   MAX-ACCESS  read-only
   STATUS      current
   DESCRIPTION
     "Count of Severely Errored Seconds (SES) during the interval."
   REFERENCE   "HDSL2 Section 7.5.3.7; SHDSL Section 9.5.5.7"
   ::= { hdsl2Shdsl15MinIntervalEntry 3 }


hdsl2Shdsl15MinIntervalCRCanomalies OBJECT-TYPE
   SYNTAX      PerfIntervalCount
   UNITS       "detected CRC Anomalies"
   MAX-ACCESS  read-only
   STATUS      current
   DESCRIPTION
     "Count of CRC anomalies during the interval."
   REFERENCE   "HDSL2 Section 7.5.3.7; SHDSL Section 9.5.5.7"
   ::= { hdsl2Shdsl15MinIntervalEntry 4 }

hdsl2Shdsl15MinIntervalLOSWS OBJECT-TYPE
   SYNTAX      PerfIntervalCount
   UNITS       "seconds"
   MAX-ACCESS  read-only
   STATUS      current
   DESCRIPTION
     "Count of Loss of Sync Word (LOSW) Seconds during the
      interval."
   REFERENCE   "HDSL2 Section 7.5.3.7; SHDSL Section 9.5.5.7"
   ::= { hdsl2Shdsl15MinIntervalEntry 5 }

hdsl2Shdsl15MinIntervalUAS OBJECT-TYPE
   SYNTAX      PerfIntervalCount
   UNITS       "seconds"
   MAX-ACCESS  read-only
   STATUS      current
   DESCRIPTION
     "Count of Unavailable Seconds (UAS) during the interval."
   REFERENCE   "HDSL2 Section 7.5.3.7; SHDSL Section 9.5.5.7"
   ::= { hdsl2Shdsl15MinIntervalEntry 6 }

-- Segment Endpoint 1-Day Interval Status/Performance Group
--

hdsl2Shdsl1DayIntervalTable OBJECT-TYPE
   SYNTAX      SEQUENCE OF Hdsl2Shdsl1DayIntervalEntry
   MAX-ACCESS  not-accessible
   STATUS      current
   DESCRIPTION
     "This table provides one row for each HDSL2/SHDSL endpoint
      performance data collection interval.  This table contains
      live data from equipment.  As such, it is NOT persistent."
   ::= { hdsl2ShdslMibObjects 7 }

hdsl2Shdsl1DayIntervalEntry OBJECT-TYPE
   SYNTAX      Hdsl2Shdsl1DayIntervalEntry
   MAX-ACCESS  not-accessible
   STATUS      current


   DESCRIPTION
     "An entry in the hdsl2Shdsl1DayIntervalTable."
   INDEX { ifIndex, hdsl2ShdslInvIndex, hdsl2ShdslEndpointSide,
           hdsl2ShdslEndpointWirePair, hdsl2Shdsl1DayIntervalNumber }
   ::= { hdsl2Shdsl1DayIntervalTable 1 }

Hdsl2Shdsl1DayIntervalEntry ::=
   SEQUENCE
   {
   hdsl2Shdsl1DayIntervalNumber         Unsigned32,
   hdsl2Shdsl1DayIntervalMoniSecs       Hdsl2ShdslPerfTimeElapsed,
   hdsl2Shdsl1DayIntervalES             Hdsl2Shdsl1DayIntervalCount,
   hdsl2Shdsl1DayIntervalSES            Hdsl2Shdsl1DayIntervalCount,
   hdsl2Shdsl1DayIntervalCRCanomalies   Hdsl2Shdsl1DayIntervalCount,
   hdsl2Shdsl1DayIntervalLOSWS          Hdsl2Shdsl1DayIntervalCount,
   hdsl2Shdsl1DayIntervalUAS            Hdsl2Shdsl1DayIntervalCount
   }

hdsl2Shdsl1DayIntervalNumber OBJECT-TYPE
   SYNTAX      Unsigned32(1..30)
   MAX-ACCESS  not-accessible
   STATUS      current
   DESCRIPTION
     "History Data Interval number. Interval 1 is the the most
      recent previous day; interval 30 is 30 days ago. Intervals
      2..30 are optional."
   ::= { hdsl2Shdsl1DayIntervalEntry 1 }

hdsl2Shdsl1DayIntervalMoniSecs OBJECT-TYPE
   SYNTAX       Hdsl2ShdslPerfTimeElapsed
   UNITS        "seconds"
   MAX-ACCESS   read-only
   STATUS       current
   DESCRIPTION
     "The amount of time in the 1-day interval over which the
      performance monitoring information is actually counted.
      This value will be the same as the interval duration except
      in a situation where performance monitoring data could not
      be collected for any reason."
   ::= { hdsl2Shdsl1DayIntervalEntry 2 }

hdsl2Shdsl1DayIntervalES OBJECT-TYPE
   SYNTAX       Hdsl2Shdsl1DayIntervalCount
   UNITS        "seconds"
   MAX-ACCESS   read-only
   STATUS       current
   DESCRIPTION
     "Count of Errored Seconds (ES) during the 1-day interval as


      measured by hdsl2Shdsl1DayIntervalMoniSecs."
   REFERENCE   "HDSL2 Section 7.5.3.7; SHDSL Section 9.5.5.7"
   ::= { hdsl2Shdsl1DayIntervalEntry 3 }

hdsl2Shdsl1DayIntervalSES OBJECT-TYPE
   SYNTAX       Hdsl2Shdsl1DayIntervalCount
   UNITS        "seconds"
   MAX-ACCESS   read-only
   STATUS       current
   DESCRIPTION
     "Count of Severely Errored Seconds (SES) during the 1-day
      interval as measured by hdsl2Shdsl1DayIntervalMoniSecs."
   REFERENCE   "HDSL2 Section 7.5.3.7; SHDSL Section 9.5.5.7"
   ::= { hdsl2Shdsl1DayIntervalEntry 4 }

hdsl2Shdsl1DayIntervalCRCanomalies OBJECT-TYPE
   SYNTAX       Hdsl2Shdsl1DayIntervalCount
   UNITS        "detected CRC Anomalies"
   MAX-ACCESS   read-only
   STATUS       current
   DESCRIPTION
     "Count of CRC anomalies during the 1-day interval as
      measured by hdsl2Shdsl1DayIntervalMoniSecs."
   REFERENCE   "HDSL2 Section 7.5.3.7; SHDSL Section 9.5.5.7"
   ::= { hdsl2Shdsl1DayIntervalEntry 5 }

hdsl2Shdsl1DayIntervalLOSWS OBJECT-TYPE
   SYNTAX       Hdsl2Shdsl1DayIntervalCount
   UNITS        "seconds"
   MAX-ACCESS   read-only
   STATUS       current
   DESCRIPTION
     "Count of Loss of Sync Word (LOSW) Seconds during the 1-day
      interval as measured by hdsl2Shdsl1DayIntervalMoniSecs."
   REFERENCE   "HDSL2 Section 7.5.3.7; SHDSL Section 9.5.5.7"
   ::= { hdsl2Shdsl1DayIntervalEntry 6 }

hdsl2Shdsl1DayIntervalUAS OBJECT-TYPE
   SYNTAX       Hdsl2Shdsl1DayIntervalCount
   UNITS        "seconds"
   MAX-ACCESS   read-only
   STATUS       current
   DESCRIPTION
     "Count of Unavailable Seconds (UAS) during the 1-day interval
      as measured by hdsl2Shdsl1DayIntervalMoniSecs."
   REFERENCE   "HDSL2 Section 7.5.3.7; SHDSL Section 9.5.5.7"
   ::= { hdsl2Shdsl1DayIntervalEntry 7 }


-- Maintenance Group
--

hdsl2ShdslEndpointMaintTable OBJECT-TYPE
   SYNTAX      SEQUENCE OF Hdsl2ShdslEndpointMaintEntry
   MAX-ACCESS  not-accessible
   STATUS      current
   DESCRIPTION
     "This table supports maintenance operations (eg. loopbacks)
      to be performed on HDSL2/SHDSL segment endpoints.  This table
      contains live data from equipment.  As such, it is NOT
      persistent."
   ::= { hdsl2ShdslMibObjects 8 }

hdsl2ShdslEndpointMaintEntry OBJECT-TYPE
   SYNTAX      Hdsl2ShdslEndpointMaintEntry
   MAX-ACCESS  not-accessible
   STATUS      current
   DESCRIPTION
     "An entry in the hdsl2ShdslEndpointMaintTable.  Each entry
      corresponds to a single segment endpoint, and is indexed by the
      ifIndex of the HDSL2/SHDSL line, the UnitId of the associated
      unit and the side of the unit."
   INDEX { ifIndex, hdsl2ShdslInvIndex, hdsl2ShdslEndpointSide }
   ::= { hdsl2ShdslEndpointMaintTable 1 }

Hdsl2ShdslEndpointMaintEntry ::=
   SEQUENCE
   {
   hdsl2ShdslMaintLoopbackConfig      INTEGER,
   hdsl2ShdslMaintTipRingReversal     INTEGER,
   hdsl2ShdslMaintPowerBackOff        INTEGER,
   hdsl2ShdslMaintSoftRestart         INTEGER
   }

hdsl2ShdslMaintLoopbackConfig OBJECT-TYPE
   SYNTAX      INTEGER
               {
               noLoopback(1),
               normalLoopback(2),
               specialLoopback(3)
               }
   MAX-ACCESS  read-write
   STATUS      current
   DESCRIPTION
     "This object controls configuration of loopbacks for the
      associated segment endpoint.  The status of the loopback
      is obtained via the hdsl2ShdslEndpointCurrStatus object."


   ::= { hdsl2ShdslEndpointMaintEntry 1 }

hdsl2ShdslMaintTipRingReversal OBJECT-TYPE
   SYNTAX      INTEGER
               {
               normal(1),
               reversed(2)
               }
   MAX-ACCESS  read-only
   STATUS      current
   DESCRIPTION
     "This object indicates the state of the tip/ring pair at the
      associated segment endpoint."
   ::= { hdsl2ShdslEndpointMaintEntry 2 }

hdsl2ShdslMaintPowerBackOff OBJECT-TYPE
   SYNTAX      INTEGER
               {
               default(1),
               enhanced(2)
               }
   MAX-ACCESS  read-write
   STATUS      current
   DESCRIPTION
     "This object configures the receiver at the associated
      segment endpoint to operate in default or enhanced power
      backoff mode."
   ::= { hdsl2ShdslEndpointMaintEntry 3 }

hdsl2ShdslMaintSoftRestart OBJECT-TYPE
   SYNTAX      INTEGER
               {
               ready(1),
               restart(2)
               }
   MAX-ACCESS  read-write
   STATUS      current
   DESCRIPTION
     "This object enables the manager to trigger a soft restart
      of the modem at the associated segment endpoint.  The manager
      may only set this object to the 'restart(2)' value, which
      initiates a restart.  The agent will perform a restart after
      approximately 5 seconds.  Following the 5 second period, the
      agent will restore the object to the 'ready(1)' state."
   ::= { hdsl2ShdslEndpointMaintEntry 4 }

hdsl2ShdslUnitMaintTable OBJECT-TYPE
   SYNTAX      SEQUENCE OF Hdsl2ShdslUnitMaintEntry


   MAX-ACCESS  not-accessible
   STATUS      current
   DESCRIPTION
     "This table supports maintenance operations for units in a
      HDSL2/SHDSL line.  Entries in this table MUST be maintained
      in a persistent manner."
   ::= { hdsl2ShdslMibObjects 9 }

hdsl2ShdslUnitMaintEntry OBJECT-TYPE
   SYNTAX      Hdsl2ShdslUnitMaintEntry
   MAX-ACCESS  not-accessible
   STATUS      current
   DESCRIPTION
     "An entry in the hdsl2ShdslUnitMaintTable.  Each entry
      corresponds to a single unit, and is indexed by the ifIndex
      of the HDSL2/SHDSL line and the UnitId of the associated
      unit."
   INDEX { ifIndex, hdsl2ShdslInvIndex  }
   ::= { hdsl2ShdslUnitMaintTable 1 }

Hdsl2ShdslUnitMaintEntry ::=
   SEQUENCE
   {
   hdsl2ShdslMaintLoopbackTimeout     Integer32,
   hdsl2ShdslMaintUnitPowerSource     INTEGER
   }

hdsl2ShdslMaintLoopbackTimeout OBJECT-TYPE
   SYNTAX      Integer32(0..4095)
   UNITS       "minutes"
   MAX-ACCESS  read-write
   STATUS      current
   DESCRIPTION
     "This object configures the timeout value for loopbacks
      initiated at segments endpoints contained in the associated
      unit.  A value of 0 disables the timeout."
   ::= { hdsl2ShdslUnitMaintEntry 1 }

hdsl2ShdslMaintUnitPowerSource OBJECT-TYPE
   SYNTAX      INTEGER
               {
               local(1),
               span(2)
               }
   MAX-ACCESS  read-only
   STATUS      current
   DESCRIPTION
     "This object indicates the DC power source being used by the


      associated unit."
   ::= { hdsl2ShdslUnitMaintEntry 2 }

-- Span Configuration Profile Group
--

hdsl2ShdslSpanConfProfileTable OBJECT-TYPE
   SYNTAX      SEQUENCE OF Hdsl2ShdslSpanConfProfileEntry
   MAX-ACCESS  not-accessible
   STATUS      current
   DESCRIPTION
     "This table supports definitions of span configuration
      profiles for SHDSL lines.  HDSL2 does not support these
      configuration options.  This table MUST be maintained
      in a persistent manner."
   ::= { hdsl2ShdslMibObjects 10 }

hdsl2ShdslSpanConfProfileEntry OBJECT-TYPE
   SYNTAX      Hdsl2ShdslSpanConfProfileEntry
   MAX-ACCESS  not-accessible
   STATUS      current
   DESCRIPTION
     "Each entry corresponds to a single span configuration
      profile.  Each profile contains a set of span configuration
      parameters.  The configuration parameters in a profile are
      applied to those lines referencing that profile (see the
      hdsl2ShdslSpanConfProfile object).  Profiles may be
      created/deleted using the row creation/deletion mechanism
      via hdsl2ShdslSpanConfProfileRowStatus.  If an active
      entry is referenced in hdsl2ShdslSpanConfProfile, the
      entry MUST remain active until all references are removed."
   INDEX { IMPLIED hdsl2ShdslSpanConfProfileName }
   ::= { hdsl2ShdslSpanConfProfileTable 1 }

Hdsl2ShdslSpanConfProfileEntry ::=
   SEQUENCE
   {
   hdsl2ShdslSpanConfProfileName               SnmpAdminString,
   hdsl2ShdslSpanConfWireInterface             INTEGER,
   hdsl2ShdslSpanConfMinLineRate               Unsigned32,
   hdsl2ShdslSpanConfMaxLineRate               Unsigned32,
   hdsl2ShdslSpanConfPSD                       INTEGER,
   hdsl2ShdslSpanConfTransmissionMode
                                   Hdsl2ShdslTransmissionModeType,
   hdsl2ShdslSpanConfRemoteEnabled             INTEGER,
   hdsl2ShdslSpanConfPowerFeeding              INTEGER,
   hdsl2ShdslSpanConfCurrCondTargetMarginDown  Integer32,
   hdsl2ShdslSpanConfWorstCaseTargetMarginDown Integer32,


   hdsl2ShdslSpanConfCurrCondTargetMarginUp    Integer32,
   hdsl2ShdslSpanConfWorstCaseTargetMarginUp   Integer32,
   hdsl2ShdslSpanConfUsedTargetMargins         BITS,
   hdsl2ShdslSpanConfReferenceClock
                                   Hdsl2ShdslClockReferenceType,
   hdsl2ShdslSpanConfLineProbeEnable           INTEGER,
   hdsl2ShdslSpanConfProfileRowStatus          RowStatus
   }

hdsl2ShdslSpanConfProfileName OBJECT-TYPE
   SYNTAX      SnmpAdminString (SIZE(1..32))
   MAX-ACCESS  not-accessible
   STATUS      current
   DESCRIPTION
     "This object is the unique index associated with this profile.
      Entries in this table are referenced via the object
      hdsl2ShdslSpanConfProfile in Hdsl2ShdslSpanConfEntry."
   ::= { hdsl2ShdslSpanConfProfileEntry 1 }

hdsl2ShdslSpanConfWireInterface OBJECT-TYPE
   SYNTAX      INTEGER
               {
               twoWire(1),
               fourWire(2)
               }
   MAX-ACCESS  read-create
   STATUS      current
   DESCRIPTION
     "This object configures the two-wire or optional four-wire
      operation for SHDSL Lines."
   DEFVAL      { twoWire }
   ::= { hdsl2ShdslSpanConfProfileEntry 2 }

hdsl2ShdslSpanConfMinLineRate OBJECT-TYPE
   SYNTAX      Unsigned32(0..4112000)
   UNITS       "bps"
   MAX-ACCESS  read-create
   STATUS      current
   DESCRIPTION
     "This object configures the minimum transmission rate for
      the associated SHDSL Line in bits-per-second (bps).  If
      the minimum line rate equals the maximum line rate
      (hdsl2ShdslSpanMaxLineRate), the line rate is considered
      'fixed'.  If the minimum line rate is less than the maximum
      line rate, the line rate is considered 'rate-adaptive'."
   DEFVAL      { 1552000 }
   ::= { hdsl2ShdslSpanConfProfileEntry 3 }


hdsl2ShdslSpanConfMaxLineRate OBJECT-TYPE
   SYNTAX      Unsigned32(0..4112000)
   UNITS       "bps"
   MAX-ACCESS  read-create
   STATUS      current
   DESCRIPTION
     "This object configures the maximum transmission rate for
      the associated SHDSL Line in bits-per-second (bps).  If
      the minimum line rate equals the maximum line rate
      (hdsl2ShdslSpanMaxLineRate), the line rate is considered
      'fixed'.  If the minimum line rate is less than the maximum
      line rate, the line rate is considered 'rate-adaptive'."
   DEFVAL      { 1552000 }
   ::= { hdsl2ShdslSpanConfProfileEntry 4 }

hdsl2ShdslSpanConfPSD OBJECT-TYPE
   SYNTAX      INTEGER
               {
               symmetric(1),
               asymmetric(2)
               }
   MAX-ACCESS  read-create
   STATUS      current
   DESCRIPTION
     "This object configures use of symmetric/asymmetric PSD (Power
      Spectral Density) Mask for the associated SHDSL Line.  Support
      for symmetric PSD is mandatory for all supported data rates.
      Support for asymmetric PSD is optional."
   DEFVAL      { symmetric }
   ::= { hdsl2ShdslSpanConfProfileEntry 5 }

hdsl2ShdslSpanConfTransmissionMode OBJECT-TYPE
   SYNTAX      Hdsl2ShdslTransmissionModeType
   MAX-ACCESS  read-create
   STATUS      current
   DESCRIPTION
     "This object specifies the regional setting for the SHDSL
      line."
   DEFVAL      { { region1 } }
   ::= { hdsl2ShdslSpanConfProfileEntry 6 }

hdsl2ShdslSpanConfRemoteEnabled OBJECT-TYPE
   SYNTAX      INTEGER
               {
               enabled(1),
               disabled(2)
               }
   MAX-ACCESS  read-create


   STATUS      current
   DESCRIPTION
     "This object enables/disables support for remote management
      of the units in a SHDSL line from the STU-R via the EOC."
   DEFVAL      { enabled }
   ::= { hdsl2ShdslSpanConfProfileEntry 7 }

hdsl2ShdslSpanConfPowerFeeding OBJECT-TYPE
   SYNTAX      INTEGER
               {
               noPower(1),
               powerFeed(2),
               wettingCurrent(3)
               }
   MAX-ACCESS  read-create
   STATUS      current
   DESCRIPTION
     "This object enables/disables support for optional power
      feeding in a SHDSL line."
   DEFVAL      { noPower }
   ::= { hdsl2ShdslSpanConfProfileEntry 8 }

hdsl2ShdslSpanConfCurrCondTargetMarginDown OBJECT-TYPE
   SYNTAX      Integer32(-10..21)
   UNITS       "dB"
   MAX-ACCESS  read-create
   STATUS      current
   DESCRIPTION
     "This object specifies the downstream current condition target
      SNR margin for a SHDSL line.  The SNR margin is the difference
      between the desired SNR and the actual SNR.  Target SNR margin
      is the desired SNR margin for a unit."
   DEFVAL      { 0 }
   ::= { hdsl2ShdslSpanConfProfileEntry 9 }

hdsl2ShdslSpanConfWorstCaseTargetMarginDown OBJECT-TYPE
   SYNTAX      Integer32(-10..21)
   UNITS       "dB"
   MAX-ACCESS  read-create
   STATUS      current
   DESCRIPTION
     "This object specifies the downstream worst case target SNR
      margin for a SHDSL line.  The SNR margin is the difference
      between the desired SNR and the actual SNR.  Target SNR
      margin is the desired SNR margin for a unit."
   DEFVAL      { 0 }
   ::= { hdsl2ShdslSpanConfProfileEntry 10 }


hdsl2ShdslSpanConfCurrCondTargetMarginUp OBJECT-TYPE
   SYNTAX      Integer32(-10..21)
   UNITS       "dB"
   MAX-ACCESS  read-create
   STATUS      current
   DESCRIPTION
     "This object specifies the upstream current condition target
      SNR margin for a SHDSL line.  The SNR margin is the difference
      between the desired SNR and the actual SNR.  Target SNR margin
      is the desired SNR margin for a unit."
   DEFVAL      { 0 }
   ::= { hdsl2ShdslSpanConfProfileEntry 11 }

hdsl2ShdslSpanConfWorstCaseTargetMarginUp OBJECT-TYPE
   SYNTAX      Integer32(-10..21)
   UNITS       "dB"
   MAX-ACCESS  read-create
   STATUS      current
   DESCRIPTION
     "This object specifies the upstream worst case target SNR
      margin for a SHDSL line.  The SNR margin is the difference
      between the desired SNR and the actual SNR.  Target SNR margin
      is the desired SNR margin for a unit."
   DEFVAL      { 0 }
   ::= { hdsl2ShdslSpanConfProfileEntry 12 }

hdsl2ShdslSpanConfUsedTargetMargins OBJECT-TYPE
   SYNTAX      BITS
               {
               currCondDown(0),
               worstCaseDown(1),
               currCondUp(2),
               worstCaseUp(3)
               }
   MAX-ACCESS  read-create
   STATUS      current
   DESCRIPTION
     "Contains indicates whether a target SNR margin is enabled or
      disabled.  This is a bit-map of possible settings.  The
      various bit positions are:

      currCondDown     current condition downstream target SNR
                       margin enabled

      worstCaseDown    worst case downstream target SNR margin
                       enabled

      currCondUp       current condition upstream target SNR


                       margin enabled

      worstCaseUp      worst case upstream target SNR margin
                       enabled."
   DEFVAL      { { currCondDown } }
   ::= { hdsl2ShdslSpanConfProfileEntry 13 }

hdsl2ShdslSpanConfReferenceClock OBJECT-TYPE
   SYNTAX      Hdsl2ShdslClockReferenceType
   MAX-ACCESS  read-create
   STATUS      current
   DESCRIPTION
     "This object configures the clock reference for the STU-C
     in a SHDSL Line."
   DEFVAL      { localClk }
   ::= { hdsl2ShdslSpanConfProfileEntry 14 }

hdsl2ShdslSpanConfLineProbeEnable OBJECT-TYPE
   SYNTAX      INTEGER
               {
               disable(1),
               enable(2)
               }
   MAX-ACCESS  read-create
   STATUS      current
   DESCRIPTION
     "This object enables/disables support for Line Probe of
     the units in a SHDSL line.  When Line Probe is enabled, the
     system performs Line Probing to find the best possible
     rate.  If Line probe is disabled, the rate adaptation phase
     is skipped to shorten set up time."
   DEFVAL      { disable }
   ::= { hdsl2ShdslSpanConfProfileEntry 15 }

hdsl2ShdslSpanConfProfileRowStatus OBJECT-TYPE
   SYNTAX      RowStatus
   MAX-ACCESS  read-create
   STATUS      current
   DESCRIPTION
     "This object controls creation/deletion of the associated
      entry in this table per the semantics of RowStatus.  If an
      active entry is referenced in hdsl2ShdslSpanConfProfile, the
      entry MUST remain active until all references are removed."
   ::= { hdsl2ShdslSpanConfProfileEntry 16 }

-- Segment Endpoint Alarm Configuration Profile group
--


hdsl2ShdslEndpointAlarmConfProfileTable OBJECT-TYPE
   SYNTAX      SEQUENCE OF Hdsl2ShdslEndpointAlarmConfProfileEntry
   MAX-ACCESS  not-accessible
   STATUS      current
   DESCRIPTION
     "This table supports definitions of alarm configuration
      profiles for HDSL2/SHDSL segment endpoints.  This table
      MUST be maintained in a persistent manner."
   ::= { hdsl2ShdslMibObjects 11 }

hdsl2ShdslEndpointAlarmConfProfileEntry OBJECT-TYPE
   SYNTAX      Hdsl2ShdslEndpointAlarmConfProfileEntry
   MAX-ACCESS  not-accessible
   STATUS      current
   DESCRIPTION
     "Each entry corresponds to a single alarm configuration profile.
      Each profile contains a set of parameters for setting alarm
      thresholds for various performance attributes monitored at
      HDSL2/SHDSL segment endpoints.  Profiles may be created/deleted
      using the row creation/deletion mechanism via
      hdsl2ShdslEndpointAlarmConfProfileRowStatus.  If an active
      entry is referenced in either hdsl2ShdslSpanConfAlarmProfile
      or hdsl2ShdslEndpointAlarmConfProfile, the entry MUST remain
      active until all references are removed."
   INDEX { IMPLIED hdsl2ShdslEndpointAlarmConfProfileName }
   ::= { hdsl2ShdslEndpointAlarmConfProfileTable 1 }

Hdsl2ShdslEndpointAlarmConfProfileEntry ::=
   SEQUENCE
   {
   hdsl2ShdslEndpointAlarmConfProfileName       SnmpAdminString,
   hdsl2ShdslEndpointThreshLoopAttenuation      Integer32,
   hdsl2ShdslEndpointThreshSNRMargin            Integer32,
   hdsl2ShdslEndpointThreshES
               Hdsl2ShdslPerfIntervalThreshold,
   hdsl2ShdslEndpointThreshSES
               Hdsl2ShdslPerfIntervalThreshold,
   hdsl2ShdslEndpointThreshCRCanomalies         Integer32,
   hdsl2ShdslEndpointThreshLOSWS
               Hdsl2ShdslPerfIntervalThreshold,
   hdsl2ShdslEndpointThreshUAS
               Hdsl2ShdslPerfIntervalThreshold,
   hdsl2ShdslEndpointAlarmConfProfileRowStatus  RowStatus
   }

hdsl2ShdslEndpointAlarmConfProfileName OBJECT-TYPE
   SYNTAX      SnmpAdminString (SIZE(1..32))
   MAX-ACCESS  not-accessible


   STATUS      current
   DESCRIPTION
     "This object is the unique index associated with this profile."
   ::= { hdsl2ShdslEndpointAlarmConfProfileEntry 1 }

hdsl2ShdslEndpointThreshLoopAttenuation OBJECT-TYPE
   SYNTAX      Integer32(-127..128)
   UNITS       "dB"
   MAX-ACCESS  read-create
   STATUS      current
   DESCRIPTION
     "This object configures the loop attenuation alarm threshold.
      When the current value of hdsl2ShdslEndpointCurrAtn reaches
      or exceeds this threshold, a hdsl2ShdslLoopAttenCrossing
      MAY be generated."
   DEFVAL      { 0 }
   ::= { hdsl2ShdslEndpointAlarmConfProfileEntry 2 }

hdsl2ShdslEndpointThreshSNRMargin OBJECT-TYPE
   SYNTAX      Integer32(-127..128)
   UNITS       "dB"
   MAX-ACCESS  read-create
   STATUS      current
   DESCRIPTION
     "This object configures the SNR margin alarm threshold.
      When the current value of hdsl2ShdslEndpointCurrSnrMgn
      reaches or drops below this threshold, a
      hdsl2ShdslSNRMarginCrossing MAY be generated."
   DEFVAL      { 0 }
   ::= { hdsl2ShdslEndpointAlarmConfProfileEntry 3 }

hdsl2ShdslEndpointThreshES OBJECT-TYPE
   SYNTAX      Hdsl2ShdslPerfIntervalThreshold
   UNITS       "seconds"
   MAX-ACCESS  read-create
   STATUS      current
   DESCRIPTION
     "This object configures the threshold for the number of
      errored seconds (ES) within any given 15-minute performance
      data collection interval.  If the value of errored seconds
      in a particular 15-minute collection interval reaches/
      exceeds this value, a hdsl2ShdslPerfESThresh MAY be
      generated.  At most one notification will be sent per
      interval per endpoint."
   DEFVAL      { 0 }
   ::= { hdsl2ShdslEndpointAlarmConfProfileEntry 4 }

hdsl2ShdslEndpointThreshSES OBJECT-TYPE


   SYNTAX      Hdsl2ShdslPerfIntervalThreshold
   UNITS       "seconds"
   MAX-ACCESS  read-create
   STATUS      current
   DESCRIPTION
     "This object configures the threshold for the number of
      severely errored seconds (SES) within any given 15-minute
      performance data collection interval.  If the value of
      severely errored seconds in a particular 15-minute collection
      interval reaches/exceeds this value, a hdsl2ShdslPerfSESThresh
      MAY be generated.  At most one notification will be sent per
      interval per endpoint."
   DEFVAL      { 0 }
   ::= { hdsl2ShdslEndpointAlarmConfProfileEntry 5 }

hdsl2ShdslEndpointThreshCRCanomalies OBJECT-TYPE
   SYNTAX      Integer32
   UNITS       "detected CRC Anomalies"
   MAX-ACCESS  read-create
   STATUS      current
   DESCRIPTION
     "This object configures the threshold for the number of
      CRC anomalies within any given 15-minute performance data
      collection interval.  If the value of CRC anomalies in a
      particular 15-minute collection interval reaches/exceeds
      this value, a hdsl2ShdslPerfCRCanomaliesThresh MAY be
      generated.  At most one notification will be sent per
      interval per endpoint."
   DEFVAL      { 0 }
   ::= { hdsl2ShdslEndpointAlarmConfProfileEntry 6 }

hdsl2ShdslEndpointThreshLOSWS OBJECT-TYPE
   SYNTAX      Hdsl2ShdslPerfIntervalThreshold
   UNITS       "seconds"
   MAX-ACCESS  read-create
   STATUS      current
   DESCRIPTION
     "This object configures the threshold for the number of
      Loss of Sync Word (LOSW) Seconds within any given 15-minute
      performance data collection interval.  If the value of LOSW
      in a particular 15-minute collection interval reaches/exceeds
      this value, a hdsl2ShdslPerfLOSWSThresh MAY be generated.
      At most one notification will be sent per interval per
      endpoint."
   DEFVAL      { 0 }
   ::= { hdsl2ShdslEndpointAlarmConfProfileEntry 7 }

hdsl2ShdslEndpointThreshUAS OBJECT-TYPE


   SYNTAX      Hdsl2ShdslPerfIntervalThreshold
   UNITS       "seconds"
   MAX-ACCESS  read-create
   STATUS      current
   DESCRIPTION
     "This object configures the threshold for the number of
      unavailable seconds (UAS) within any given 15-minute
      performance data collection interval.  If the value of UAS
      in a particular 15-minute collection interval reaches/exceeds
      this value, a hdsl2ShdslPerfUASThresh MAY be generated.
      At most one notification will be sent per interval per
      endpoint."
   DEFVAL      { 0 }
   ::= { hdsl2ShdslEndpointAlarmConfProfileEntry 8 }

hdsl2ShdslEndpointAlarmConfProfileRowStatus OBJECT-TYPE
   SYNTAX      RowStatus
   MAX-ACCESS  read-create
   STATUS      current
   DESCRIPTION
     "This object controls creation/deletion of the associated
      entry in this table as per the semantics of RowStatus.
      If an active entry is referenced in either
      hdsl2ShdslSpanConfAlarmProfile or
      hdsl2ShdslEndpointAlarmConfProfile, the entry MUST remain
      active until all references are removed."
   ::= { hdsl2ShdslEndpointAlarmConfProfileEntry 9 }

-- Notifications Group
--

hdsl2ShdslNotifications OBJECT IDENTIFIER ::= { hdsl2ShdslMIB 0 }

hdsl2ShdslLoopAttenCrossing NOTIFICATION-TYPE
   OBJECTS
   {
   hdsl2ShdslEndpointCurrAtn,
   hdsl2ShdslEndpointThreshLoopAttenuation
   }
   STATUS     current
   DESCRIPTION
     "This notification indicates that the loop attenuation
      threshold (as per the hdsl2ShdslEndpointThreshLoopAttenuation
      value) has been reached/exceeded for the HDSL2/SHDSL segment
      endpoint."
   ::= { hdsl2ShdslNotifications 1 }

hdsl2ShdslSNRMarginCrossing NOTIFICATION-TYPE


   OBJECTS
   {

   hdsl2ShdslEndpointCurrSnrMgn,
   hdsl2ShdslEndpointThreshSNRMargin
   }
   STATUS     current
   DESCRIPTION
     "This notification indicates that the SNR margin threshold (as
      per the hdsl2ShdslEndpointThreshSNRMargin value) has been
      reached/exceeded for the HDSL2/SHDSL segment endpoint."
   ::= { hdsl2ShdslNotifications 2 }

hdsl2ShdslPerfESThresh NOTIFICATION-TYPE
   OBJECTS
   {
   hdsl2ShdslEndpointCurr15MinES,
   hdsl2ShdslEndpointThreshES
   }
   STATUS     current
   DESCRIPTION
     "This notification indicates that the errored seconds threshold
      (as per the hdsl2ShdslEndpointThreshES value) has been reached/
      exceeded for the HDSL2/SHDSL segment endpoint."
   ::= { hdsl2ShdslNotifications 3 }

hdsl2ShdslPerfSESThresh NOTIFICATION-TYPE
   OBJECTS
   {
   hdsl2ShdslEndpointCurr15MinSES,
   hdsl2ShdslEndpointThreshSES
   }
   STATUS     current
   DESCRIPTION
     "This notification indicates that the severely errored seconds
      threshold (as per the hdsl2ShdslEndpointThreshSES value) has
      been reached/exceeded for the HDSL2/SHDSL Segment Endpoint."
   ::= { hdsl2ShdslNotifications 4 }

hdsl2ShdslPerfCRCanomaliesThresh NOTIFICATION-TYPE
   OBJECTS
   {
   hdsl2ShdslEndpointCurr15MinCRCanomalies,
   hdsl2ShdslEndpointThreshCRCanomalies
   }
   STATUS    current
   DESCRIPTION
     "This notification indicates that the CRC anomalies threshold


      (as per the hdsl2ShdslEndpointThreshCRCanomalies value) has
      been reached/exceeded for the HDSL2/SHDSL Segment Endpoint."
   ::= { hdsl2ShdslNotifications 5 }

hdsl2ShdslPerfLOSWSThresh NOTIFICATION-TYPE
   OBJECTS
   {

   hdsl2ShdslEndpointCurr15MinLOSWS,
   hdsl2ShdslEndpointThreshLOSWS
   }
   STATUS     current
   DESCRIPTION
     "This notification indicates that the LOSW seconds threshold
      (as per the hdsl2ShdslEndpointThreshLOSWS value) has been
      reached/exceeded for the HDSL2/SHDSL segment endpoint."
   ::= { hdsl2ShdslNotifications 6 }

hdsl2ShdslPerfUASThresh NOTIFICATION-TYPE
   OBJECTS
   {
   hdsl2ShdslEndpointCurr15MinUAS,
   hdsl2ShdslEndpointThreshUAS
   }
   STATUS     current
   DESCRIPTION
     "This notification indicates that the unavailable seconds
      threshold (as per the hdsl2ShdslEndpointThreshUAS value) has
      been reached/exceeded for the HDSL2/SHDSL segment endpoint."
   ::= { hdsl2ShdslNotifications 7 }

hdsl2ShdslSpanInvalidNumRepeaters NOTIFICATION-TYPE
   OBJECTS
   {
   hdsl2ShdslSpanConfNumRepeaters
   }
   STATUS     current
   DESCRIPTION
     "This notification indicates that a mismatch has been detected
      between the number of repeater/regenerator units configured
      for a HDSL2/SHDSL line via the hdsl2ShdslSpanConfNumRepeaters
      object and the actual number of repeater/regenerator units
      discovered via the EOC."
   ::= { hdsl2ShdslNotifications 8 }

hdsl2ShdslLoopbackFailure NOTIFICATION-TYPE
   OBJECTS
   {


   hdsl2ShdslMaintLoopbackConfig
   }
   STATUS     current
   DESCRIPTION
     "This notification indicates that an endpoint maintenance
      loopback command failed for an HDSL2/SHDSL segment."
   ::= { hdsl2ShdslNotifications 9 }

hdsl2ShdslpowerBackoff NOTIFICATION-TYPE
   OBJECTS
   {
   hdsl2ShdslEndpointCurrStatus
   }
   STATUS    current
   DESCRIPTION
     "This notification indicates that the bit setting for
      powerBackoff in the hdsl2ShdslEndpointCurrStatus object for
      this endpoint has changed."
   ::= { hdsl2ShdslNotifications 10 }

hdsl2ShdsldeviceFault NOTIFICATION-TYPE
   OBJECTS
   {
   hdsl2ShdslEndpointCurrStatus
   }
   STATUS    current
   DESCRIPTION
     "This notification indicates that the bit setting for
      deviceFault in the hdsl2ShdslEndpointCurrStatus object for
      this endpoint has changed."
   ::= { hdsl2ShdslNotifications 11 }

hdsl2ShdsldcContinuityFault NOTIFICATION-TYPE
   OBJECTS
   {
   hdsl2ShdslEndpointCurrStatus
   }
   STATUS    current
   DESCRIPTION
     "This notification indicates that the bit setting for
      dcContinuityFault in the hdsl2ShdslEndpointCurrStatus object
      for this endpoint has changed."
   ::= { hdsl2ShdslNotifications 12 }

hdsl2ShdslconfigInitFailure NOTIFICATION-TYPE
   OBJECTS
   {
   hdsl2ShdslEndpointCurrStatus


   }
   STATUS    current
   DESCRIPTION
     "This notification indicates that the bit setting for
      configInitFailure in the hdsl2ShdslEndpointCurrStatus object
      for this endpoint has changed."
   ::= { hdsl2ShdslNotifications 13 }

hdsl2ShdslprotocolInitFailure NOTIFICATION-TYPE
   OBJECTS
   {
   hdsl2ShdslEndpointCurrStatus
   }
   STATUS    current
   DESCRIPTION
     "This notification indicates that the bit setting for
      protocolInitFailure in the hdsl2ShdslEndpointCurrStatus
      object for this endpoint has changed."
   ::= { hdsl2ShdslNotifications 14 }

hdsl2ShdslnoNeighborPresent NOTIFICATION-TYPE
   OBJECTS
   {
   hdsl2ShdslEndpointCurrStatus
   }
   STATUS    current
   DESCRIPTION
     "This notification indicates that the bit setting for
      noNeighborPresent in the hdsl2ShdslEndpointCurrStatus object
      for this endpoint has changed."
   ::= { hdsl2ShdslNotifications 15 }

hdsl2ShdslLocalPowerLoss NOTIFICATION-TYPE
   OBJECTS
   {
   hdsl2ShdslInvVendorID
   }
   STATUS    current
   DESCRIPTION
     "This notification indicates impending unit failure due to
      loss of local power (last gasp)."
   ::= { hdsl2ShdslNotifications 16 }

-- conformance information
--

hdsl2ShdslConformance OBJECT IDENTIFIER ::= { hdsl2ShdslMIB 3 }
hdsl2ShdslGroups      OBJECT IDENTIFIER ::=


             { hdsl2ShdslConformance 1 }
hdsl2ShdslCompliances OBJECT IDENTIFIER ::=
             { hdsl2ShdslConformance 2 }

-- agent compliance statements

hdsl2ShdslLineMibCompliance MODULE-COMPLIANCE
   STATUS  current
   DESCRIPTION
     "The section outlines compliance requirements for this MIB."
   MODULE
   MANDATORY-GROUPS
   {
   hdsl2ShdslSpanConfGroup,
   hdsl2ShdslSpanStatusGroup,
   hdsl2ShdslInventoryGroup,
   hdsl2ShdslEndpointConfGroup,
   hdsl2ShdslEndpointCurrGroup,
   hdsl2Shdsl15MinIntervalGroup,
   hdsl2Shdsl1DayIntervalGroup,
   hdsl2ShdslMaintenanceGroup,
   hdsl2ShdslEndpointAlarmConfGroup,
   hdsl2ShdslNotificationGroup
   }

GROUP  hdsl2ShdslInventoryShdslGroup
   DESCRIPTION
     "Support for this group is only required for implementations
     supporting SHDSL lines."

GROUP  hdsl2ShdslSpanShdslStatusGroup
   DESCRIPTION
     "Support for this group is only required for implementations
     supporting SHDSL lines."

GROUP  hdsl2ShdslSpanConfProfileGroup
   DESCRIPTION
     "Support for this group is only required for implementations
     supporting SHDSL lines."

   ::= { hdsl2ShdslCompliances 1 }

-- units of conformance
--

hdsl2ShdslSpanConfGroup OBJECT-GROUP
   OBJECTS
   {


   hdsl2ShdslSpanConfNumRepeaters,
   hdsl2ShdslSpanConfProfile,
   hdsl2ShdslSpanConfAlarmProfile
   }
   STATUS      current
   DESCRIPTION
     "This group supports objects for configuring span related
      parameters for HDSL2/SHDSL lines."
   ::= { hdsl2ShdslGroups 1 }

hdsl2ShdslSpanStatusGroup OBJECT-GROUP
   OBJECTS
   {
   hdsl2ShdslStatusNumAvailRepeaters
   }
   STATUS      current
   DESCRIPTION
     "This group supports objects for retrieving span related
      status for HDSL2/SHDSL lines."
   ::= { hdsl2ShdslGroups 2 }

hdsl2ShdslInventoryShdslGroup OBJECT-GROUP
   OBJECTS
   {
   hdsl2ShdslInvTransmissionModeCapability
   }
   STATUS      current
   DESCRIPTION
     "This group supports objects for retrieving SHDSL-specific
      inventory information."
   ::= { hdsl2ShdslGroups 3 }

hdsl2ShdslSpanShdslStatusGroup OBJECT-GROUP
   OBJECTS
   {
   hdsl2ShdslStatusMaxAttainableLineRate,
   hdsl2ShdslStatusActualLineRate,
   hdsl2ShdslStatusTransmissionModeCurrent
   }
   STATUS      current
   DESCRIPTION
     "This group supports objects for retrieving SHDSL-specific
      span related status."
   ::= { hdsl2ShdslGroups 4 }

hdsl2ShdslInventoryGroup OBJECT-GROUP
   OBJECTS
   {


   hdsl2ShdslInvVendorID,
   hdsl2ShdslInvVendorModelNumber,
   hdsl2ShdslInvVendorSerialNumber,
   hdsl2ShdslInvVendorEOCSoftwareVersion,
   hdsl2ShdslInvStandardVersion,
   hdsl2ShdslInvVendorListNumber,
   hdsl2ShdslInvVendorIssueNumber,
   hdsl2ShdslInvVendorSoftwareVersion,
   hdsl2ShdslInvEquipmentCode,
   hdsl2ShdslInvVendorOther
   }
   STATUS      current
   DESCRIPTION
     "This group supports objects that provide unit inventory
      information about the units in HDSL2/SHDSL lines."
   ::= { hdsl2ShdslGroups 5 }

hdsl2ShdslEndpointConfGroup OBJECT-GROUP
   OBJECTS
   {
   hdsl2ShdslEndpointCurrAtn
   }
   STATUS      current
   DESCRIPTION
     "This group supports objects for configuring parameters for
      segment endpoints in HDSL2/SHDSL lines."
   ::= { hdsl2ShdslGroups 6 }

hdsl2ShdslEndpointCurrGroup OBJECT-GROUP
   OBJECTS
   {
   hdsl2ShdslEndpointCurrAtn,
   hdsl2ShdslEndpointCurrSnrMgn,
   hdsl2ShdslEndpointCurrStatus,
   hdsl2ShdslEndpointES,
   hdsl2ShdslEndpointSES,
   hdsl2ShdslEndpointCRCanomalies,
   hdsl2ShdslEndpointLOSWS,
   hdsl2ShdslEndpointUAS,
   hdsl2ShdslEndpointCurr15MinTimeElapsed,
   hdsl2ShdslEndpointCurr15MinES,
   hdsl2ShdslEndpointCurr15MinSES,
   hdsl2ShdslEndpointCurr15MinCRCanomalies,
   hdsl2ShdslEndpointCurr15MinLOSWS,
   hdsl2ShdslEndpointCurr15MinUAS,
   hdsl2ShdslEndpointCurr1DayTimeElapsed,
   hdsl2ShdslEndpointCurr1DayES,
   hdsl2ShdslEndpointCurr1DaySES,


   hdsl2ShdslEndpointCurr1DayCRCanomalies,
   hdsl2ShdslEndpointCurr1DayLOSWS,
   hdsl2ShdslEndpointCurr1DayUAS
   }
   STATUS      current
   DESCRIPTION
     "This group supports objects which provide current status and
      performance measurements relating to segment endpoints in
      HDSL2/SHDSL lines."
   ::= { hdsl2ShdslGroups 7 }

hdsl2Shdsl15MinIntervalGroup OBJECT-GROUP
   OBJECTS
   {
   hdsl2Shdsl15MinIntervalES,
   hdsl2Shdsl15MinIntervalSES,
   hdsl2Shdsl15MinIntervalCRCanomalies,
   hdsl2Shdsl15MinIntervalLOSWS,
   hdsl2Shdsl15MinIntervalUAS
   }
   STATUS      current
   DESCRIPTION
     "This group supports objects which maintain historic
      performance measurements relating to segment endpoints in
      HDSL2/SHDSL lines in 15-minute intervals."
   ::= { hdsl2ShdslGroups 8 }

hdsl2Shdsl1DayIntervalGroup OBJECT-GROUP
   OBJECTS
   {
   hdsl2Shdsl1DayIntervalMoniSecs,
   hdsl2Shdsl1DayIntervalES,
   hdsl2Shdsl1DayIntervalSES,
   hdsl2Shdsl1DayIntervalCRCanomalies,
   hdsl2Shdsl1DayIntervalLOSWS,
   hdsl2Shdsl1DayIntervalUAS
   }
   STATUS      current
   DESCRIPTION
     "This group supports objects which maintain historic
      performance measurements relating to segment endpoints in
      HDSL2/SHDSL lines in 1-day intervals."
   ::= { hdsl2ShdslGroups 9 }

hdsl2ShdslMaintenanceGroup OBJECT-GROUP
   OBJECTS
   {
   hdsl2ShdslMaintLoopbackConfig,


   hdsl2ShdslMaintTipRingReversal,
   hdsl2ShdslMaintPowerBackOff,
   hdsl2ShdslMaintSoftRestart,
   hdsl2ShdslMaintLoopbackTimeout,
   hdsl2ShdslMaintUnitPowerSource
   }
   STATUS      current
   DESCRIPTION
     "This group supports objects that provide support for
      maintenance actions for HDSL2/SHDSL lines."
   ::= { hdsl2ShdslGroups 10 }

hdsl2ShdslEndpointAlarmConfGroup OBJECT-GROUP
   OBJECTS
   {
   hdsl2ShdslEndpointAlarmConfProfile,
   hdsl2ShdslEndpointThreshLoopAttenuation,
   hdsl2ShdslEndpointThreshSNRMargin,
   hdsl2ShdslEndpointThreshES,
   hdsl2ShdslEndpointThreshSES,
   hdsl2ShdslEndpointThreshCRCanomalies,
   hdsl2ShdslEndpointThreshLOSWS,
   hdsl2ShdslEndpointThreshUAS,
   hdsl2ShdslEndpointAlarmConfProfileRowStatus
   }
   STATUS      current
   DESCRIPTION
     "This group supports objects that allow configuration of alarm
      thresholds for various performance parameters for HDSL2/SHDSL
      lines."
   ::= { hdsl2ShdslGroups 11 }

hdsl2ShdslNotificationGroup NOTIFICATION-GROUP
   NOTIFICATIONS
   {
   hdsl2ShdslLoopAttenCrossing,
   hdsl2ShdslSNRMarginCrossing,
   hdsl2ShdslPerfESThresh,
   hdsl2ShdslPerfSESThresh,
   hdsl2ShdslPerfCRCanomaliesThresh,
   hdsl2ShdslPerfLOSWSThresh,
   hdsl2ShdslPerfUASThresh,
   hdsl2ShdslSpanInvalidNumRepeaters,
   hdsl2ShdslLoopbackFailure,
   hdsl2ShdslpowerBackoff,
   hdsl2ShdsldeviceFault,
   hdsl2ShdsldcContinuityFault,
   hdsl2ShdslconfigInitFailure,


   hdsl2ShdslprotocolInitFailure,
   hdsl2ShdslnoNeighborPresent,
   hdsl2ShdslLocalPowerLoss
   }
   STATUS      current
   DESCRIPTION
     "This group supports notifications of significant conditions
     associated with HDSL2/SHDSL lines."
   ::= { hdsl2ShdslGroups 12 }

hdsl2ShdslSpanConfProfileGroup OBJECT-GROUP
   OBJECTS
   {
   hdsl2ShdslSpanConfWireInterface,
   hdsl2ShdslSpanConfMinLineRate,
   hdsl2ShdslSpanConfMaxLineRate,
   hdsl2ShdslSpanConfPSD,
   hdsl2ShdslSpanConfTransmissionMode,
   hdsl2ShdslSpanConfRemoteEnabled,
   hdsl2ShdslSpanConfPowerFeeding,
   hdsl2ShdslSpanConfCurrCondTargetMarginDown,
   hdsl2ShdslSpanConfWorstCaseTargetMarginDown,
   hdsl2ShdslSpanConfCurrCondTargetMarginUp,
   hdsl2ShdslSpanConfWorstCaseTargetMarginUp,
   hdsl2ShdslSpanConfUsedTargetMargins,
   hdsl2ShdslSpanConfReferenceClock,
   hdsl2ShdslSpanConfLineProbeEnable,
   hdsl2ShdslSpanConfProfileRowStatus
   }
   STATUS      current
   DESCRIPTION
     "This group supports objects that constitute configuration
      profiles for configuring span related parameters in SHDSL
      lines."
   ::= { hdsl2ShdslGroups 13 }
END

DS1-MIB DEFINITIONS ::= BEGIN

     IMPORTS
          MODULE-IDENTITY, OBJECT-TYPE,
          NOTIFICATION-TYPE, transmission         FROM SNMPv2-SMI
          DisplayString, TimeStamp, TruthValue    FROM SNMPv2-TC
          MODULE-COMPLIANCE, OBJECT-GROUP,
          NOTIFICATION-GROUP                      FROM SNMPv2-CONF
          InterfaceIndex, ifIndex                 FROM IF-MIB
          PerfCurrentCount, PerfIntervalCount,
          PerfTotalCount                          FROM PerfHist-TC-MIB;

     ds1 MODULE-IDENTITY
         LAST-UPDATED "9808011830Z"
         ORGANIZATION "IETF Trunk MIB Working Group"
         CONTACT-INFO
           "        David Fowler

            Postal: Newbridge Networks Corporation
                    600 March Road
                    Kanata, Ontario, Canada K2K 2E6

                    Tel: +1 613 591 3600


                    Fax: +1 613 599 3667

            E-mail: davef@newbridge.com"
         DESCRIPTION
              "The MIB module to describe DS1, E1, DS2, and
               E2 interfaces objects."

         ::= { transmission 18 }

     -- note that this subsumes cept (19) and g703at2mb (67)
     -- there is no separate CEPT or G703AT2MB MIB

     -- The DS1 Near End Group

     -- The DS1 Near End Group consists of five tables:
     --    DS1 Configuration
     --    DS1 Current
     --    DS1 Interval
     --    DS1 Total
     --    DS1 Channel Table

     -- The DS1 Configuration Table

     dsx1ConfigTable OBJECT-TYPE
          SYNTAX  SEQUENCE OF Dsx1ConfigEntry
          MAX-ACCESS  not-accessible
          STATUS  current
          DESCRIPTION
                 "The DS1 Configuration table."
          ::= { ds1 6 }

     dsx1ConfigEntry OBJECT-TYPE
          SYNTAX  Dsx1ConfigEntry
          MAX-ACCESS  not-accessible
          STATUS  current
          DESCRIPTION
                 "An entry in the DS1 Configuration table."
          INDEX   { dsx1LineIndex }
          ::= { dsx1ConfigTable 1 }

     Dsx1ConfigEntry ::=
          SEQUENCE {
              dsx1LineIndex                        InterfaceIndex,
              dsx1IfIndex                          InterfaceIndex,
              dsx1TimeElapsed                      INTEGER,
              dsx1ValidIntervals                   INTEGER,
              dsx1LineType                         INTEGER,
              dsx1LineCoding                       INTEGER,


              dsx1SendCode                         INTEGER,
              dsx1CircuitIdentifier                DisplayString,
              dsx1LoopbackConfig                   INTEGER,
              dsx1LineStatus                       INTEGER,
              dsx1SignalMode                       INTEGER,
              dsx1TransmitClockSource              INTEGER,
              dsx1Fdl                              INTEGER,
              dsx1InvalidIntervals                 INTEGER,
              dsx1LineLength                       INTEGER,
              dsx1LineStatusLastChange             TimeStamp,
              dsx1LineStatusChangeTrapEnable       INTEGER,
              dsx1LoopbackStatus                   INTEGER,
              dsx1Ds1ChannelNumber                 INTEGER,
              dsx1Channelization                   INTEGER
     }

     dsx1LineIndex OBJECT-TYPE
          SYNTAX  InterfaceIndex
          MAX-ACCESS  read-only
          STATUS  current
          DESCRIPTION
                 "This object should be made equal to ifIndex.  The
                 next paragraph describes its previous usage.
                 Making the object equal to ifIndex allows proper
                 use of ifStackTable and ds0/ds0bundle mibs.

                 Previously, this object is the identifier of a DS1
                 Interface on a managed device.  If there is an
                 ifEntry that is directly associated with this and
                 only this DS1 interface, it should have the same
                 value as ifIndex.  Otherwise, number the
                 dsx1LineIndices with an unique identifier
                 following the rules of choosing a number that is
                 greater than ifNumber and numbering the inside
                 interfaces (e.g., equipment side) with even
                 numbers and outside interfaces (e.g, network side)
                 with odd numbers."
          ::= { dsx1ConfigEntry 1 }

     dsx1IfIndex OBJECT-TYPE
          SYNTAX  InterfaceIndex
          MAX-ACCESS  read-only
          STATUS  deprecated
          DESCRIPTION
                 "This value for this object is equal to the value
                 of ifIndex from the Interfaces table of MIB II
                 (RFC 1213)."
          ::= { dsx1ConfigEntry 2 }


     dsx1TimeElapsed OBJECT-TYPE
          SYNTAX  INTEGER (0..899)
          MAX-ACCESS  read-only
          STATUS  current
          DESCRIPTION
                   "The number of seconds that have elapsed since
                        the beginning of the near end current error-
                   measurement period.  If, for some reason, such
                        as an adjustment in the system's time-of-day
                        clock, the current interval exceeds the maximum
                        value, the agent will return the maximum value."

          ::= { dsx1ConfigEntry 3 }

     dsx1ValidIntervals OBJECT-TYPE
          SYNTAX  INTEGER (0..96)
          MAX-ACCESS  read-only
          STATUS  current
          DESCRIPTION
                 "The number of previous near end intervals for
                 which data was collected.  The value will be
                 96 unless the interface was brought online within
                 the last 24 hours, in which case the value will be
                 the number of complete 15 minute near end
                 intervals since the interface has been online.  In
                 the case where the agent is a proxy, it is
                 possible that some intervals are unavailable.  In
                 this case, this interval is the maximum interval
                 number for which data is available."
          ::= { dsx1ConfigEntry 4 }

     dsx1LineType OBJECT-TYPE
          SYNTAX  INTEGER {
                     other(1),
                     dsx1ESF(2),
                     dsx1D4(3),
                     dsx1E1(4),
                     dsx1E1CRC(5),
                     dsx1E1MF(6),
                     dsx1E1CRCMF(7),
                     dsx1Unframed(8),
                     dsx1E1Unframed(9),
                     dsx1DS2M12(10),
                     dsx2E2(11)
                 }
          MAX-ACCESS  read-write
          STATUS  current
          DESCRIPTION


                 "This variable indicates  the  variety  of  DS1
                 Line  implementing  this  circuit.  The type of
                 circuit affects the number of bits  per  second
                 that  the circuit can reasonably carry, as well
                 as the interpretation of the  usage  and  error
                 statistics.  The values, in sequence, describe:

                 TITLE:         SPECIFICATION:
                 dsx1ESF         Extended SuperFrame DS1 (T1.107)
                 dsx1D4          AT&T D4 format DS1 (T1.107)
                 dsx1E1          ITU-T Recommendation G.704
                                  (Table 4a)
                 dsx1E1-CRC      ITU-T Recommendation G.704
                                  (Table 4b)
                 dsxE1-MF        G.704 (Table 4a) with TS16
                                  multiframing enabled
                 dsx1E1-CRC-MF   G.704 (Table 4b) with TS16
                                  multiframing enabled
                 dsx1Unframed    DS1 with No Framing
                 dsx1E1Unframed  E1 with No Framing (G.703)
                 dsx1DS2M12      DS2 frame format (T1.107)
                 dsx1E2          E2 frame format (G.704)

                 For clarification, the capacity for each E1 type
                 is as listed below:
                 dsx1E1Unframed - E1, no framing = 32 x 64k = 2048k
                 dsx1E1 or dsx1E1CRC - E1, with framing,
                    no signalling = 31 x 64k = 1984k
                 dsx1E1MF or dsx1E1CRCMF - E1, with framing,
                    signalling = 30 x 64k = 1920k

                 For further information See ITU-T Recomm G.704"
          ::= { dsx1ConfigEntry 5 }

     dsx1LineCoding OBJECT-TYPE
          SYNTAX  INTEGER {
                     dsx1JBZS (1),
                     dsx1B8ZS (2),
                     dsx1HDB3 (3),
                     dsx1ZBTSI (4),
                     dsx1AMI (5),
                     other(6),
                     dsx1B6ZS(7)
                 }
          MAX-ACCESS  read-write
          STATUS  current
          DESCRIPTION
                 "This variable describes the variety of Zero Code


                 Suppression used on this interface, which in turn
                 affects a number of its characteristics.

                 dsx1JBZS refers the Jammed Bit Zero Suppression,
                 in which the AT&T specification of at least one
                 pulse every 8 bit periods is literally implemented
                 by forcing a pulse in bit 8 of each channel.
                 Thus, only seven bits per channel, or 1.344 Mbps,
                 is available for data.

                 dsx1B8ZS refers to the use of a specified pattern
                 of normal bits and bipolar violations which are
                 used to replace a sequence of eight zero bits.

                 ANSI Clear Channels may use dsx1ZBTSI, or Zero
                 Byte Time Slot Interchange.

                 E1 links, with or without CRC, use dsx1HDB3 or
                 dsx1AMI.

                 dsx1AMI refers to a mode wherein no zero code
                 suppression is present and the line encoding does
                 not solve the problem directly.  In this
                 application, the higher layer must provide data
                 which meets or exceeds the pulse density
                 requirements, such as inverting HDLC data.

                 dsx1B6ZS refers to the user of a specifed pattern
                 of normal bits and bipolar violations which are
                 used to replace a sequence of six zero bits.  Used
                 for DS2."

          ::= { dsx1ConfigEntry 6 }

     dsx1SendCode OBJECT-TYPE
          SYNTAX  INTEGER {
                    dsx1SendNoCode(1),
                    dsx1SendLineCode(2),
                    dsx1SendPayloadCode(3),
                    dsx1SendResetCode(4),
                    dsx1SendQRS(5),
                    dsx1Send511Pattern(6),
                    dsx1Send3in24Pattern(7),
                    dsx1SendOtherTestPattern(8)
                    }
          MAX-ACCESS  read-write
          STATUS  current
          DESCRIPTION


                 "This variable indicates what type of code is
                 being sent across the DS1 interface by the device.
                 Setting this variable causes the interface to send
                 the code requested.  The values mean:
           dsx1SendNoCode
                sending looped or normal data

           dsx1SendLineCode
                sending a request for a line loopback

           dsx1SendPayloadCode
                sending a request for a payload loopback

           dsx1SendResetCode
                sending a loopback termination request

           dsx1SendQRS
                sending a Quasi-Random Signal  (QRS)  test
                pattern

           dsx1Send511Pattern
                sending a 511 bit fixed test pattern

           dsx1Send3in24Pattern
                sending a fixed test pattern of 3 bits set
                in 24

           dsx1SendOtherTestPattern
                sending a test pattern  other  than  those
                described by this object"
::= { dsx1ConfigEntry 7 }

     dsx1CircuitIdentifier OBJECT-TYPE
          SYNTAX  DisplayString (SIZE (0..255))
          MAX-ACCESS  read-write
          STATUS  current
          DESCRIPTION
                 "This variable contains the transmission vendor's
                 circuit identifier, for the purpose of
                 facilitating troubleshooting."
          ::= { dsx1ConfigEntry 8 }

     dsx1LoopbackConfig OBJECT-TYPE
          SYNTAX  INTEGER {
                      dsx1NoLoop(1),
                      dsx1PayloadLoop(2),
                      dsx1LineLoop(3),
                      dsx1OtherLoop(4),


                      dsx1InwardLoop(5),
                      dsx1DualLoop(6)
                    }
          MAX-ACCESS  read-write
          STATUS  current
          DESCRIPTION
                 "This variable represents the desired loopback
                 configuration of the DS1 interface.  Agents
                 supporting read/write access should return
                 inconsistentValue in response to a requested
                 loopback state that the interface does not
                 support.  The values mean:

                 dsx1NoLoop
                  Not in the loopback state.  A device that is not
                 capable of performing a loopback on the interface
                 shall always return this as its value.

                 dsx1PayloadLoop
                  The received signal at this interface is looped
                 through the device.  Typically the received signal
                 is looped back for retransmission after it has
                 passed through the device's framing function.

                 dsx1LineLoop
                  The received signal at this interface does not go
                 through the device (minimum penetration) but is
                 looped back out.

                 dsx1OtherLoop
                  Loopbacks that are not defined here.

                 dsx1InwardLoop
                  The transmitted signal at this interface is
                 looped back and received by the same interface.
                 What is transmitted onto the line is product
                 dependent.

                 dsx1DualLoop
                  Both dsx1LineLoop and dsx1InwardLoop will be
                 active simultaneously."
          ::= { dsx1ConfigEntry 9 }

     dsx1LineStatus OBJECT-TYPE
          SYNTAX  INTEGER (1..131071)
          MAX-ACCESS  read-only
          STATUS  current
          DESCRIPTION


                 "This variable indicates the Line Status of the
                 interface.  It contains loopback, failure,
                 received 'alarm' and transmitted 'alarms
                 information.

                 The dsx1LineStatus is a bit map represented as a
                 sum, therefore, it can represent multiple failures
                 (alarms) and a LoopbackState simultaneously.

                 dsx1NoAlarm must be set if and only if no other
                 flag is set.

                 If the dsx1loopbackState bit is set, the loopback
                 in effect can be determined from the
                 dsx1loopbackConfig object.
       The various bit positions are:
      1     dsx1NoAlarm           No alarm present
      2     dsx1RcvFarEndLOF      Far end LOF (a.k.a., Yellow Alarm)
      4     dsx1XmtFarEndLOF      Near end sending LOF Indication
      8     dsx1RcvAIS            Far end sending AIS
     16     dsx1XmtAIS            Near end sending AIS
     32     dsx1LossOfFrame       Near end LOF (a.k.a., Red Alarm)
     64     dsx1LossOfSignal      Near end Loss Of Signal
    128     dsx1LoopbackState     Near end is looped
    256     dsx1T16AIS            E1 TS16 AIS
    512     dsx1RcvFarEndLOMF     Far End Sending TS16 LOMF
   1024     dsx1XmtFarEndLOMF     Near End Sending TS16 LOMF
   2048     dsx1RcvTestCode       Near End detects a test code
   4096     dsx1OtherFailure      any line status not defined here
   8192     dsx1UnavailSigState   Near End in Unavailable Signal
                                  State
  16384     dsx1NetEquipOOS       Carrier Equipment Out of Service
  32768     dsx1RcvPayloadAIS     DS2 Payload AIS
  65536     dsx1Ds2PerfThreshold  DS2 Performance Threshold
                                  Exceeded"
     ::= { dsx1ConfigEntry 10 }

     dsx1SignalMode OBJECT-TYPE
          SYNTAX  INTEGER {
                     none (1),
                     robbedBit (2),
                     bitOriented (3),
                     messageOriented (4),
                     other (5)
                 }
          MAX-ACCESS  read-write
          STATUS  current
          DESCRIPTION


            "'none' indicates that no bits are reserved for
            signaling on this channel.

            'robbedBit' indicates that DS1 Robbed Bit  Sig-
            naling is in use.

            'bitOriented' indicates that E1 Channel  Asso-
            ciated Signaling is in use.

            'messageOriented' indicates that Common  Chan-
            nel Signaling is in use either on channel 16 of
            an E1 link or channel 24 of a DS1."
          ::= { dsx1ConfigEntry 11 }

     dsx1TransmitClockSource OBJECT-TYPE
          SYNTAX  INTEGER {
                     loopTiming(1),
                     localTiming(2),
                     throughTiming(3)
                 }
          MAX-ACCESS  read-write
          STATUS  current
          DESCRIPTION
            "The source of Transmit Clock.
             'loopTiming' indicates that the recovered re-
            ceive clock is used as the transmit clock.

             'localTiming' indicates that a local clock
            source is used or when an external clock is
            attached to the box containing the interface.

             'throughTiming' indicates that recovered re-
            ceive clock from another interface is used as
            the transmit clock."
          ::= { dsx1ConfigEntry 12 }

     dsx1Fdl OBJECT-TYPE
          SYNTAX  INTEGER (1..15)
          MAX-ACCESS  read-write
          STATUS  current
          DESCRIPTION
            "This bitmap describes the use of  the  facili-
            ties data link, and is the sum of the capabili-
            ties.  Set any bits that are appropriate:

            other(1),
            dsx1AnsiT1403(2),
            dsx1Att54016(4),


            dsx1FdlNone(8)

             'other' indicates that a protocol  other  than
            one following is used.

             'dsx1AnsiT1403' refers to the  FDL  exchange
            recommended by ANSI.

             'dsx1Att54016' refers to ESF FDL exchanges.

             'dsx1FdlNone' indicates that the device  does
            not use the FDL."
          ::= { dsx1ConfigEntry 13 }

     dsx1InvalidIntervals OBJECT-TYPE
          SYNTAX  INTEGER (0..96)
          MAX-ACCESS  read-only
          STATUS  current
          DESCRIPTION
                 "The number of intervals in the range from 0 to
                 dsx1ValidIntervals for which no data is
                 available.  This object will typically be zero
                 except in cases where the data for some intervals
                 are not available (e.g., in proxy situations)."
          ::= { dsx1ConfigEntry 14 }

     dsx1LineLength OBJECT-TYPE
          SYNTAX  INTEGER (0..64000)
          UNITS  "meters"
          MAX-ACCESS  read-write
          STATUS  current
          DESCRIPTION
                 "The length of the ds1 line in meters. This
                 objects provides information for line build out
                 circuitry.  This object is only useful if the
                 interface has configurable line build out
                 circuitry."

          ::= { dsx1ConfigEntry 15 }

     dsx1LineStatusLastChange OBJECT-TYPE
          SYNTAX  TimeStamp
          MAX-ACCESS  read-only
          STATUS  current
          DESCRIPTION
                 "The value of MIB II's sysUpTime object at the
                 time this DS1 entered its current line status
                 state.  If the current state was entered prior to


                 the last re-initialization of the proxy-agent,
                 then this object contains a zero value."
          ::= { dsx1ConfigEntry 16 }

     dsx1LineStatusChangeTrapEnable  OBJECT-TYPE
          SYNTAX      INTEGER {
                         enabled(1),
                         disabled(2)
                      }
          MAX-ACCESS  read-write
          STATUS      current
          DESCRIPTION
                 "Indicates whether dsx1LineStatusChange traps
                 should be generated for this interface."
          DEFVAL { disabled }
          ::= { dsx1ConfigEntry 17 }

     dsx1LoopbackStatus  OBJECT-TYPE
          SYNTAX      INTEGER (1..127)
          MAX-ACCESS  read-only
          STATUS      current
          DESCRIPTION
                 "This variable represents the current state of the
                 loopback on the DS1 interface.  It contains
                 information about loopbacks established by a
                 manager and remotely from the far end.

                 The dsx1LoopbackStatus is a bit map represented as
                 a sum, therefore is can represent multiple
                 loopbacks simultaneously.

                 The various bit positions are:
                  1  dsx1NoLoopback
                  2  dsx1NearEndPayloadLoopback
                  4  dsx1NearEndLineLoopback
                  8  dsx1NearEndOtherLoopback
                 16  dsx1NearEndInwardLoopback
                 32  dsx1FarEndPayloadLoopback
                 64  dsx1FarEndLineLoopback"

     ::= { dsx1ConfigEntry 18 }

     dsx1Ds1ChannelNumber  OBJECT-TYPE
          SYNTAX      INTEGER (0..28)
          MAX-ACCESS  read-only
          STATUS      current
          DESCRIPTION
                 "This variable represents the channel number of


                 the DS1/E1 on its parent Ds2/E2 or DS3/E3.  A
                 value of 0 indicated this DS1/E1 does not have a
                 parent DS3/E3."

     ::= { dsx1ConfigEntry 19 }

     dsx1Channelization  OBJECT-TYPE
          SYNTAX      INTEGER {
                         disabled(1),
                         enabledDs0(2),
                         enabledDs1(3)
                      }
          MAX-ACCESS  read-write
          STATUS      current
          DESCRIPTION
                 "Indicates whether this ds1/e1 is channelized or
                 unchannelized.  The value of enabledDs0 indicates
                 that this is a DS1 channelized into DS0s.  The
                 value of enabledDs1 indicated that this is a DS2
                 channelized into DS1s.  Setting this value will
                 cause the creation or deletion of entries in the
                 ifTable for the DS0s that are within the DS1."
     ::= { dsx1ConfigEntry 20 }

     -- The DS1 Current Table
     dsx1CurrentTable OBJECT-TYPE
          SYNTAX  SEQUENCE OF Dsx1CurrentEntry
          MAX-ACCESS  not-accessible
          STATUS  current
          DESCRIPTION
                 "The DS1 current table contains various statistics
                 being collected for the current 15 minute
                 interval."
          ::= { ds1 7 }

     dsx1CurrentEntry OBJECT-TYPE
          SYNTAX  Dsx1CurrentEntry
          MAX-ACCESS  not-accessible
          STATUS  current
          DESCRIPTION
                 "An entry in the DS1 Current table."
                      INDEX   { dsx1CurrentIndex }
                      ::= { dsx1CurrentTable 1 }

     Dsx1CurrentEntry ::=
          SEQUENCE {
              dsx1CurrentIndex            InterfaceIndex,
              dsx1CurrentESs              PerfCurrentCount,


              dsx1CurrentSESs             PerfCurrentCount,
              dsx1CurrentSEFSs            PerfCurrentCount,
              dsx1CurrentUASs             PerfCurrentCount,
              dsx1CurrentCSSs             PerfCurrentCount,
              dsx1CurrentPCVs             PerfCurrentCount,
              dsx1CurrentLESs             PerfCurrentCount,
              dsx1CurrentBESs             PerfCurrentCount,
              dsx1CurrentDMs              PerfCurrentCount,
              dsx1CurrentLCVs             PerfCurrentCount
     }

     dsx1CurrentIndex OBJECT-TYPE
          SYNTAX  InterfaceIndex
          MAX-ACCESS  read-only
          STATUS  current
          DESCRIPTION
                 "The index value which uniquely identifies  the
                 DS1 interface to which this entry is applicable.
                 The interface identified by a particular value of
                 this index is the same interface as identified by
                 the same value as a dsx1LineIndex object
                 instance."
          ::= { dsx1CurrentEntry 1 }

     dsx1CurrentESs OBJECT-TYPE
          SYNTAX  PerfCurrentCount
          MAX-ACCESS  read-only
          STATUS  current
          DESCRIPTION
                 "The number of Errored Seconds."
          ::= { dsx1CurrentEntry 2 }

     dsx1CurrentSESs OBJECT-TYPE
          SYNTAX  PerfCurrentCount
          MAX-ACCESS  read-only
          STATUS  current
          DESCRIPTION
                 "The number of Severely Errored Seconds."
          ::= { dsx1CurrentEntry 3 }

     dsx1CurrentSEFSs OBJECT-TYPE
          SYNTAX  PerfCurrentCount
          MAX-ACCESS  read-only
          STATUS  current
          DESCRIPTION
                 "The number of Severely Errored Framing Seconds."
          ::= { dsx1CurrentEntry 4 }


     dsx1CurrentUASs OBJECT-TYPE
          SYNTAX  PerfCurrentCount
          MAX-ACCESS  read-only
          STATUS  current
          DESCRIPTION
                 "The number of Unavailable Seconds."
          ::= { dsx1CurrentEntry 5 }

     dsx1CurrentCSSs OBJECT-TYPE
          SYNTAX  PerfCurrentCount
          MAX-ACCESS  read-only
          STATUS  current
          DESCRIPTION
                 "The number of Controlled Slip Seconds."
          ::= { dsx1CurrentEntry 6 }

     dsx1CurrentPCVs OBJECT-TYPE
          SYNTAX  PerfCurrentCount
          MAX-ACCESS  read-only
          STATUS  current
          DESCRIPTION
                 "The number of Path Coding Violations."
          ::= { dsx1CurrentEntry 7 }

     dsx1CurrentLESs OBJECT-TYPE
          SYNTAX  PerfCurrentCount
          MAX-ACCESS  read-only
          STATUS  current
          DESCRIPTION
                 "The number of Line Errored Seconds."
          ::= { dsx1CurrentEntry 8 }

     dsx1CurrentBESs OBJECT-TYPE
          SYNTAX PerfCurrentCount
          MAX-ACCESS read-only
          STATUS current
          DESCRIPTION
                 "The number of Bursty Errored Seconds."
          ::= { dsx1CurrentEntry 9 }

     dsx1CurrentDMs OBJECT-TYPE
          SYNTAX PerfCurrentCount
          MAX-ACCESS read-only
          STATUS current
          DESCRIPTION
                 "The number of Degraded Minutes."
          ::= { dsx1CurrentEntry 10 }


     dsx1CurrentLCVs OBJECT-TYPE
          SYNTAX PerfCurrentCount
          MAX-ACCESS read-only
          STATUS current
          DESCRIPTION
                 "The number of Line Code Violations (LCVs)."
          ::= { dsx1CurrentEntry 11 }

     -- The DS1 Interval Table
     dsx1IntervalTable OBJECT-TYPE
          SYNTAX  SEQUENCE OF Dsx1IntervalEntry
          MAX-ACCESS  not-accessible
          STATUS  current
          DESCRIPTION
                 "The DS1 Interval Table contains various
                 statistics collected by each DS1 Interface over
                 the previous 24 hours of operation.  The past 24
                 hours are broken into 96 completed 15 minute
                 intervals.  Each row in this table represents one
                 such interval (identified by dsx1IntervalNumber)
                 for one specific instance (identified by
                 dsx1IntervalIndex)."
          ::= { ds1 8 }

     dsx1IntervalEntry OBJECT-TYPE
          SYNTAX  Dsx1IntervalEntry
          MAX-ACCESS  not-accessible
          STATUS  current
          DESCRIPTION
                 "An entry in the DS1 Interval table."
          INDEX   { dsx1IntervalIndex, dsx1IntervalNumber }
          ::= { dsx1IntervalTable 1 }

     Dsx1IntervalEntry ::=
          SEQUENCE {
              dsx1IntervalIndex             InterfaceIndex,
              dsx1IntervalNumber            INTEGER,
              dsx1IntervalESs               PerfIntervalCount,
              dsx1IntervalSESs              PerfIntervalCount,
              dsx1IntervalSEFSs             PerfIntervalCount,
              dsx1IntervalUASs              PerfIntervalCount,
              dsx1IntervalCSSs              PerfIntervalCount,
              dsx1IntervalPCVs              PerfIntervalCount,
              dsx1IntervalLESs              PerfIntervalCount,
              dsx1IntervalBESs              PerfIntervalCount,
              dsx1IntervalDMs               PerfIntervalCount,
              dsx1IntervalLCVs              PerfIntervalCount,


              dsx1IntervalValidData         TruthValue
     }

     dsx1IntervalIndex OBJECT-TYPE
          SYNTAX  InterfaceIndex
          MAX-ACCESS  read-only
          STATUS  current
          DESCRIPTION
                 "The index value which uniquely identifies the DS1
                 interface to which this entry is applicable.  The
                 interface identified by a particular value of this
                 index is the same interface as identified by the
                 same value as a dsx1LineIndex object instance."
          ::= { dsx1IntervalEntry 1 }

     dsx1IntervalNumber OBJECT-TYPE
          SYNTAX  INTEGER (1..96)
          MAX-ACCESS  read-only
          STATUS  current
          DESCRIPTION
                 "A number between 1 and 96, where 1 is the most
                 recently completed 15 minute interval and 96 is
                 the 15 minutes interval completed 23 hours and 45
                 minutes prior to interval 1."
          ::= { dsx1IntervalEntry 2 }

     dsx1IntervalESs OBJECT-TYPE
          SYNTAX  PerfIntervalCount
          MAX-ACCESS  read-only
          STATUS  current
          DESCRIPTION
                 "The number of Errored Seconds."
          ::= { dsx1IntervalEntry 3 }

     dsx1IntervalSESs OBJECT-TYPE
          SYNTAX  PerfIntervalCount
          MAX-ACCESS  read-only
          STATUS  current
          DESCRIPTION
                 "The number of Severely Errored Seconds."
          ::= { dsx1IntervalEntry 4 }

     dsx1IntervalSEFSs OBJECT-TYPE
          SYNTAX  PerfIntervalCount
          MAX-ACCESS  read-only
          STATUS  current
          DESCRIPTION
                 "The number of Severely Errored Framing Seconds."


          ::= { dsx1IntervalEntry 5 }

     dsx1IntervalUASs OBJECT-TYPE
          SYNTAX  PerfIntervalCount
          MAX-ACCESS  read-only
          STATUS  current
          DESCRIPTION
                 "The number of Unavailable Seconds.  This object
                 may decrease if the occurance of unavailable
                 seconds occurs across an inteval boundary."
          ::= { dsx1IntervalEntry 6 }

     dsx1IntervalCSSs OBJECT-TYPE
          SYNTAX  PerfIntervalCount
          MAX-ACCESS  read-only
          STATUS  current
          DESCRIPTION
                 "The number of Controlled Slip Seconds."
          ::= { dsx1IntervalEntry 7 }

     dsx1IntervalPCVs OBJECT-TYPE
          SYNTAX  PerfIntervalCount
          MAX-ACCESS  read-only
          STATUS  current
          DESCRIPTION
                 "The number of Path Coding Violations."
          ::= { dsx1IntervalEntry 8 }

     dsx1IntervalLESs OBJECT-TYPE
          SYNTAX  PerfIntervalCount
          MAX-ACCESS  read-only
          STATUS  current
          DESCRIPTION
                 "The number of Line Errored Seconds."
          ::= { dsx1IntervalEntry 9 }

     dsx1IntervalBESs OBJECT-TYPE
          SYNTAX PerfIntervalCount
          MAX-ACCESS read-only
          STATUS current
          DESCRIPTION
                 "The number of Bursty Errored Seconds."
          ::= { dsx1IntervalEntry 10 }

     dsx1IntervalDMs OBJECT-TYPE
          SYNTAX PerfIntervalCount
          MAX-ACCESS read-only
          STATUS current


          DESCRIPTION
                 "The number of Degraded Minutes."
          ::= { dsx1IntervalEntry 11 }

     dsx1IntervalLCVs OBJECT-TYPE
          SYNTAX PerfIntervalCount
          MAX-ACCESS read-only
          STATUS current
          DESCRIPTION
                 "The number of Line Code Violations."
          ::= { dsx1IntervalEntry 12 }

     dsx1IntervalValidData OBJECT-TYPE
          SYNTAX TruthValue
          MAX-ACCESS read-only
          STATUS current
          DESCRIPTION
                 "This variable indicates if the data for this
                 interval is valid."
          ::= { dsx1IntervalEntry 13 }

     -- The DS1 Total Table
     dsx1TotalTable OBJECT-TYPE
          SYNTAX  SEQUENCE OF Dsx1TotalEntry
          MAX-ACCESS  not-accessible
          STATUS  current
          DESCRIPTION
                 "The DS1 Total Table contains the cumulative sum
                 of the various statistics for the 24 hour period
                 preceding the current interval."
          ::= { ds1 9 }

     dsx1TotalEntry OBJECT-TYPE
          SYNTAX  Dsx1TotalEntry
          MAX-ACCESS  not-accessible
          STATUS  current
          DESCRIPTION
                 "An entry in the DS1 Total table."
          INDEX   { dsx1TotalIndex }
          ::= { dsx1TotalTable 1 }

     Dsx1TotalEntry ::=
          SEQUENCE {
              dsx1TotalIndex                InterfaceIndex,
              dsx1TotalESs                  PerfTotalCount,
              dsx1TotalSESs                 PerfTotalCount,
              dsx1TotalSEFSs                PerfTotalCount,
              dsx1TotalUASs                 PerfTotalCount,


              dsx1TotalCSSs                 PerfTotalCount,
              dsx1TotalPCVs                 PerfTotalCount,
              dsx1TotalLESs                 PerfTotalCount,
              dsx1TotalBESs                 PerfTotalCount,
              dsx1TotalDMs                  PerfTotalCount,
              dsx1TotalLCVs                 PerfTotalCount
     }

     dsx1TotalIndex OBJECT-TYPE
          SYNTAX  InterfaceIndex
          MAX-ACCESS  read-only
          STATUS  current
          DESCRIPTION
                 "The index value which uniquely identifies the DS1
                 interface to which this entry is applicable.  The
                 interface identified by a particular value of this
                 index is the same interface as identified by the
                 same value as a dsx1LineIndex object instance."

          ::= { dsx1TotalEntry 1 }

     dsx1TotalESs OBJECT-TYPE
          SYNTAX  PerfTotalCount
          MAX-ACCESS  read-only
          STATUS  current
          DESCRIPTION
                 "The sum of Errored Seconds encountered by a DS1
                 interface in the previous 24 hour interval.
                 Invalid 15 minute intervals count as 0."
          ::= { dsx1TotalEntry 2 }

     dsx1TotalSESs OBJECT-TYPE
          SYNTAX  PerfTotalCount
          MAX-ACCESS  read-only
          STATUS  current
          DESCRIPTION
                 "The number of Severely Errored Seconds
                 encountered by a DS1 interface in the previous 24
                 hour interval.  Invalid 15 minute intervals count
                 as 0."
          ::= { dsx1TotalEntry 3 }

     dsx1TotalSEFSs OBJECT-TYPE
          SYNTAX  PerfTotalCount
          MAX-ACCESS  read-only
          STATUS  current
          DESCRIPTION
                 "The number of Severely Errored Framing Seconds


                 encountered by a DS1 interface in the previous 24
                 hour interval.  Invalid 15 minute intervals count
                 as 0."
          ::= { dsx1TotalEntry 4 }

     dsx1TotalUASs OBJECT-TYPE
          SYNTAX  PerfTotalCount
          MAX-ACCESS  read-only
          STATUS  current
          DESCRIPTION
                 "The number of Unavailable Seconds encountered by
                 a DS1 interface in the previous 24 hour interval.
                 Invalid 15 minute intervals count as 0."
          ::= { dsx1TotalEntry 5 }

     dsx1TotalCSSs OBJECT-TYPE
          SYNTAX  PerfTotalCount
          MAX-ACCESS  read-only
          STATUS  current
          DESCRIPTION
                 "The number of Controlled Slip Seconds encountered
                 by a DS1 interface in the previous 24 hour
                 interval.  Invalid 15 minute intervals count as
                 0."
          ::= { dsx1TotalEntry 6 }

     dsx1TotalPCVs OBJECT-TYPE
          SYNTAX  PerfTotalCount
          MAX-ACCESS  read-only
          STATUS  current
          DESCRIPTION
                 "The number of Path Coding Violations encountered
                 by a DS1 interface in the previous 24 hour
                 interval.  Invalid 15 minute intervals count as
                 0."
          ::= { dsx1TotalEntry 7 }

     dsx1TotalLESs OBJECT-TYPE
          SYNTAX  PerfTotalCount
          MAX-ACCESS  read-only
          STATUS  current
          DESCRIPTION
                 "The number of Line Errored Seconds encountered by
                 a DS1 interface in the previous 24 hour interval.
                 Invalid 15 minute intervals count as 0."
          ::= { dsx1TotalEntry 8 }

     dsx1TotalBESs OBJECT-TYPE


          SYNTAX PerfTotalCount
          MAX-ACCESS read-only
          STATUS current
          DESCRIPTION
                 "The number of Bursty Errored Seconds (BESs)
                 encountered by a DS1 interface in the previous 24
                 hour interval. Invalid 15 minute intervals count
                 as 0."
          ::= { dsx1TotalEntry 9 }

     dsx1TotalDMs OBJECT-TYPE
          SYNTAX PerfTotalCount
          MAX-ACCESS read-only
          STATUS current
          DESCRIPTION
                 "The number of Degraded Minutes (DMs) encountered
                 by a DS1 interface in the previous 24 hour
                 interval.  Invalid 15 minute intervals count as
                 0."
          ::= { dsx1TotalEntry 10 }

     dsx1TotalLCVs OBJECT-TYPE
          SYNTAX PerfTotalCount
          MAX-ACCESS read-only
          STATUS current
          DESCRIPTION
                 "The number of Line Code Violations (LCVs)
                 encountered by a DS1 interface in the current 15
                 minute interval.  Invalid 15 minute intervals
                 count as 0."
          ::= { dsx1TotalEntry 11 }

     -- The DS1 Channel Table
     dsx1ChanMappingTable OBJECT-TYPE
          SYNTAX  SEQUENCE OF Dsx1ChanMappingEntry
          MAX-ACCESS  not-accessible
          STATUS  current
          DESCRIPTION
                 "The DS1 Channel Mapping table.  This table maps a
                 DS1 channel number on a particular DS3 into an
                 ifIndex.  In the presence of DS2s, this table can
                 be used to map a DS2 channel number on a DS3 into
                 an ifIndex, or used to map a DS1 channel number on
                 a DS2 onto an ifIndex."
          ::= { ds1 16 }

     dsx1ChanMappingEntry OBJECT-TYPE
          SYNTAX  Dsx1ChanMappingEntry


          MAX-ACCESS  not-accessible
          STATUS  current
          DESCRIPTION
                 "An entry in the DS1 Channel Mapping table.  There
                 is an entry in this table corresponding to each
                 ds1 ifEntry within any interface that is
                 channelized to the individual ds1 ifEntry level.

                 This table is intended to facilitate mapping from
                 channelized interface / channel number to DS1
                 ifEntry.  (e.g. mapping (DS3 ifIndex, DS1 Channel
                 Number) -> ifIndex)

                 While this table provides information that can
                 also be found in the ifStackTable and
                 dsx1ConfigTable, it provides this same information
                 with a single table lookup, rather than by walking
                 the ifStackTable to find the various constituent
                 ds1 ifTable entries, and testing various
                 dsx1ConfigTable entries to check for the entry
                 with the applicable DS1 channel number."
          INDEX   { ifIndex, dsx1Ds1ChannelNumber }
          ::= { dsx1ChanMappingTable 1 }

     Dsx1ChanMappingEntry ::=
          SEQUENCE {
              dsx1ChanMappedIfIndex  InterfaceIndex
     }

     dsx1ChanMappedIfIndex OBJECT-TYPE
          SYNTAX  InterfaceIndex
          MAX-ACCESS  read-only
          STATUS  current
          DESCRIPTION
                 "This object indicates the ifIndex value assigned
                 by the agent for the individual ds1 ifEntry that
                 corresponds to the given DS1 channel number
                 (specified by the INDEX element
                 dsx1Ds1ChannelNumber) of the given channelized
                 interface (specified by INDEX element ifIndex)."
          ::= { dsx1ChanMappingEntry 1 }

     -- The DS1 Far End Current Table

     dsx1FarEndCurrentTable OBJECT-TYPE
          SYNTAX  SEQUENCE OF Dsx1FarEndCurrentEntry
          MAX-ACCESS  not-accessible


          STATUS  current
          DESCRIPTION
                 "The DS1 Far End Current table contains various
                 statistics being collected for the current 15
                 minute interval.  The statistics are collected
                 from the far end messages on the Facilities Data
                 Link.  The definitions are the same as described
                 for the near-end information."
          ::= { ds1 10 }

     dsx1FarEndCurrentEntry OBJECT-TYPE
          SYNTAX  Dsx1FarEndCurrentEntry
          MAX-ACCESS  not-accessible
          STATUS  current
          DESCRIPTION
                 "An entry in the DS1 Far End Current table."
          INDEX   { dsx1FarEndCurrentIndex }
          ::= { dsx1FarEndCurrentTable 1 }

     Dsx1FarEndCurrentEntry ::=
          SEQUENCE {
              dsx1FarEndCurrentIndex      InterfaceIndex,
              dsx1FarEndTimeElapsed       INTEGER,
              dsx1FarEndValidIntervals    INTEGER,
              dsx1FarEndCurrentESs        PerfCurrentCount,
              dsx1FarEndCurrentSESs       PerfCurrentCount,
              dsx1FarEndCurrentSEFSs      PerfCurrentCount,
              dsx1FarEndCurrentUASs       PerfCurrentCount,
              dsx1FarEndCurrentCSSs       PerfCurrentCount,
              dsx1FarEndCurrentLESs       PerfCurrentCount,
              dsx1FarEndCurrentPCVs       PerfCurrentCount,
              dsx1FarEndCurrentBESs       PerfCurrentCount,
              dsx1FarEndCurrentDMs        PerfCurrentCount,
              dsx1FarEndInvalidIntervals  INTEGER
     }

     dsx1FarEndCurrentIndex OBJECT-TYPE
          SYNTAX  InterfaceIndex
          MAX-ACCESS  read-only
          STATUS  current
          DESCRIPTION
                 "The index value which uniquely identifies the DS1
                 interface to which this entry is applicable.  The
                 interface identified by a particular value of this
                 index is identical to the interface identified by
                 the same value of dsx1LineIndex."
          ::= { dsx1FarEndCurrentEntry 1 }


     dsx1FarEndTimeElapsed OBJECT-TYPE
          SYNTAX  INTEGER (0..899)
          MAX-ACCESS  read-only
          STATUS  current
          DESCRIPTION
                      "The number of seconds that have elapsed since the
                 beginning of the far end current error-measurement
                 period.  If, for some reason, such as an
                 adjustment in the system's time-of-day clock, the
                 current interval exceeds the maximum value, the
                 agent will return the maximum value."
          ::= { dsx1FarEndCurrentEntry 2 }

     dsx1FarEndValidIntervals OBJECT-TYPE
          SYNTAX  INTEGER (0..96)
          MAX-ACCESS  read-only
          STATUS  current
          DESCRIPTION
                      "The number of previous far end intervals for
                 which data was collected.  The value will be
                 96 unless the interface was brought online within
                 the last 24 hours, in which case the value will be
                 the number of complete 15 minute far end intervals
                 since the interface has been online."
          ::= { dsx1FarEndCurrentEntry 3 }

     dsx1FarEndCurrentESs OBJECT-TYPE
          SYNTAX  PerfCurrentCount
          MAX-ACCESS  read-only
          STATUS  current
          DESCRIPTION
                 "The number of Far End Errored Seconds."
          ::= { dsx1FarEndCurrentEntry 4 }

     dsx1FarEndCurrentSESs OBJECT-TYPE
          SYNTAX  PerfCurrentCount
          MAX-ACCESS  read-only
          STATUS  current
          DESCRIPTION
                 "The number of Far End Severely Errored Seconds."

          ::= { dsx1FarEndCurrentEntry 5 }

     dsx1FarEndCurrentSEFSs OBJECT-TYPE
          SYNTAX  PerfCurrentCount
          MAX-ACCESS  read-only
          STATUS  current
          DESCRIPTION


                 "The number of Far End Severely Errored Framing
                 Seconds."
          ::= { dsx1FarEndCurrentEntry 6 }

     dsx1FarEndCurrentUASs OBJECT-TYPE
          SYNTAX  PerfCurrentCount
          MAX-ACCESS  read-only
          STATUS  current
          DESCRIPTION
                 "The number of Unavailable Seconds."
          ::= { dsx1FarEndCurrentEntry 7 }

     dsx1FarEndCurrentCSSs OBJECT-TYPE
          SYNTAX  PerfCurrentCount
          MAX-ACCESS  read-only
          STATUS  current
          DESCRIPTION
                 "The number of Far End Controlled Slip Seconds."
          ::= { dsx1FarEndCurrentEntry 8 }

     dsx1FarEndCurrentLESs OBJECT-TYPE
          SYNTAX  PerfCurrentCount
          MAX-ACCESS  read-only
          STATUS  current
          DESCRIPTION
                 "The number of Far End Line Errored Seconds."
          ::= { dsx1FarEndCurrentEntry 9 }

     dsx1FarEndCurrentPCVs OBJECT-TYPE
          SYNTAX  PerfCurrentCount
          MAX-ACCESS  read-only
          STATUS  current
          DESCRIPTION
                 "The number of Far End Path Coding Violations."
          ::= { dsx1FarEndCurrentEntry 10 }

     dsx1FarEndCurrentBESs OBJECT-TYPE
          SYNTAX PerfCurrentCount
          MAX-ACCESS read-only
          STATUS current
          DESCRIPTION
                 "The number of Far End Bursty Errored Seconds."
          ::= { dsx1FarEndCurrentEntry 11 }

     dsx1FarEndCurrentDMs OBJECT-TYPE
          SYNTAX PerfCurrentCount
          MAX-ACCESS read-only
          STATUS current


          DESCRIPTION
                 "The number of Far End Degraded Minutes."
          ::= { dsx1FarEndCurrentEntry 12 }

     dsx1FarEndInvalidIntervals OBJECT-TYPE
          SYNTAX  INTEGER (0..96)
          MAX-ACCESS  read-only
          STATUS  current
          DESCRIPTION
                 "The number of intervals in the range from 0 to
                 dsx1FarEndValidIntervals for which no data is
                 available.  This object will typically be zero
                 except in cases where the data for some intervals
                 are not available (e.g., in proxy situations)."
          ::= { dsx1FarEndCurrentEntry 13 }

     -- The DS1 Far End Interval Table
     dsx1FarEndIntervalTable OBJECT-TYPE
          SYNTAX  SEQUENCE OF Dsx1FarEndIntervalEntry
          MAX-ACCESS  not-accessible
          STATUS  current
          DESCRIPTION
                 "The DS1 Far End Interval Table contains various
                 statistics collected by each DS1 interface over
                 the previous 24 hours of operation.  The past 24
                 hours are broken into 96 completed 15 minute
                 intervals. Each row in this table represents one
                 such interval (identified by
                 dsx1FarEndIntervalNumber) for one specific
                 instance (identified by dsx1FarEndIntervalIndex)."
          ::= { ds1 11 }

     dsx1FarEndIntervalEntry OBJECT-TYPE
          SYNTAX  Dsx1FarEndIntervalEntry
          MAX-ACCESS  not-accessible
          STATUS  current
          DESCRIPTION
                 "An entry in the DS1 Far End Interval table."

          INDEX   { dsx1FarEndIntervalIndex,
                    dsx1FarEndIntervalNumber }
          ::= { dsx1FarEndIntervalTable 1 }

     Dsx1FarEndIntervalEntry ::=
          SEQUENCE {
              dsx1FarEndIntervalIndex       InterfaceIndex,
              dsx1FarEndIntervalNumber      INTEGER,
              dsx1FarEndIntervalESs         PerfIntervalCount,


              dsx1FarEndIntervalSESs        PerfIntervalCount,
              dsx1FarEndIntervalSEFSs       PerfIntervalCount,
              dsx1FarEndIntervalUASs        PerfIntervalCount,
              dsx1FarEndIntervalCSSs        PerfIntervalCount,
              dsx1FarEndIntervalLESs        PerfIntervalCount,
              dsx1FarEndIntervalPCVs        PerfIntervalCount,
              dsx1FarEndIntervalBESs        PerfIntervalCount,
              dsx1FarEndIntervalDMs         PerfIntervalCount,
              dsx1FarEndIntervalValidData   TruthValue
     }

     dsx1FarEndIntervalIndex OBJECT-TYPE
          SYNTAX  InterfaceIndex
          MAX-ACCESS  read-only
          STATUS  current
          DESCRIPTION
                 "The index value which uniquely identifies the DS1
                 interface to which this entry is applicable.  The
                 interface identified by a particular value of this
                 index is identical to the interface identified by
                 the same value of dsx1LineIndex."
          ::= { dsx1FarEndIntervalEntry 1 }

     dsx1FarEndIntervalNumber OBJECT-TYPE
          SYNTAX  INTEGER (1..96)
          MAX-ACCESS  read-only
          STATUS  current
          DESCRIPTION
                 "A number between 1 and 96, where 1 is the most
                 recently completed 15 minute interval and 96 is
                 the 15 minutes interval completed 23 hours and 45
                 minutes prior to interval 1."
          ::= { dsx1FarEndIntervalEntry 2 }

     dsx1FarEndIntervalESs OBJECT-TYPE
          SYNTAX  PerfIntervalCount
          MAX-ACCESS  read-only
          STATUS  current
          DESCRIPTION
                 "The number of Far End Errored Seconds."
          ::= { dsx1FarEndIntervalEntry 3 }

     dsx1FarEndIntervalSESs OBJECT-TYPE
          SYNTAX  PerfIntervalCount
          MAX-ACCESS  read-only
          STATUS  current
          DESCRIPTION
                 "The number of Far End Severely Errored Seconds."


          ::= { dsx1FarEndIntervalEntry 4 }

     dsx1FarEndIntervalSEFSs OBJECT-TYPE
          SYNTAX  PerfIntervalCount
          MAX-ACCESS  read-only
          STATUS  current
          DESCRIPTION
                 "The number of Far End Severely Errored Framing
                 Seconds."
          ::= { dsx1FarEndIntervalEntry 5 }

     dsx1FarEndIntervalUASs OBJECT-TYPE
          SYNTAX  PerfIntervalCount
          MAX-ACCESS  read-only
          STATUS  current
          DESCRIPTION
                 "The number of Unavailable Seconds."
          ::= { dsx1FarEndIntervalEntry 6 }

     dsx1FarEndIntervalCSSs OBJECT-TYPE
          SYNTAX  PerfIntervalCount
          MAX-ACCESS  read-only
          STATUS  current
          DESCRIPTION
                 "The number of Far End Controlled Slip Seconds."
          ::= { dsx1FarEndIntervalEntry 7 }

     dsx1FarEndIntervalLESs OBJECT-TYPE
          SYNTAX  PerfIntervalCount
          MAX-ACCESS  read-only
          STATUS  current
          DESCRIPTION
                 "The number of Far End Line Errored Seconds."

          ::= { dsx1FarEndIntervalEntry 8 }

     dsx1FarEndIntervalPCVs OBJECT-TYPE
          SYNTAX  PerfIntervalCount
          MAX-ACCESS  read-only
          STATUS  current
          DESCRIPTION
                 "The number of Far End Path Coding Violations."
          ::= { dsx1FarEndIntervalEntry 9 }

     dsx1FarEndIntervalBESs OBJECT-TYPE
          SYNTAX PerfIntervalCount
          MAX-ACCESS read-only
          STATUS current


          DESCRIPTION
                 "The number of Far End Bursty Errored Seconds."
          ::= { dsx1FarEndIntervalEntry 10 }

     dsx1FarEndIntervalDMs OBJECT-TYPE
          SYNTAX PerfIntervalCount
          MAX-ACCESS read-only
          STATUS current
          DESCRIPTION
                 "The number of Far End Degraded Minutes."
          ::= { dsx1FarEndIntervalEntry 11 }

     dsx1FarEndIntervalValidData OBJECT-TYPE
          SYNTAX TruthValue
          MAX-ACCESS read-only
          STATUS current
          DESCRIPTION
                      "This variable indicates if the data for this
                 interval is valid."
          ::= { dsx1FarEndIntervalEntry 12 }

     -- The DS1 Far End Total Table

     dsx1FarEndTotalTable OBJECT-TYPE
          SYNTAX  SEQUENCE OF Dsx1FarEndTotalEntry
          MAX-ACCESS  not-accessible
          STATUS  current
          DESCRIPTION
                 "The DS1 Far End Total Table contains the
                 cumulative sum of the various statistics for the
                 24 hour period preceding the current interval."
          ::= { ds1 12 }

     dsx1FarEndTotalEntry OBJECT-TYPE
          SYNTAX  Dsx1FarEndTotalEntry
          MAX-ACCESS  not-accessible
          STATUS  current
          DESCRIPTION
                 "An entry in the DS1 Far End Total table."
          INDEX   { dsx1FarEndTotalIndex }
          ::= { dsx1FarEndTotalTable 1 }

     Dsx1FarEndTotalEntry ::=
          SEQUENCE {
              dsx1FarEndTotalIndex          InterfaceIndex,
              dsx1FarEndTotalESs            PerfTotalCount,
              dsx1FarEndTotalSESs           PerfTotalCount,
              dsx1FarEndTotalSEFSs          PerfTotalCount,


              dsx1FarEndTotalUASs           PerfTotalCount,
              dsx1FarEndTotalCSSs           PerfTotalCount,
              dsx1FarEndTotalLESs           PerfTotalCount,
              dsx1FarEndTotalPCVs           PerfTotalCount,
              dsx1FarEndTotalBESs           PerfTotalCount,
              dsx1FarEndTotalDMs            PerfTotalCount
     }

     dsx1FarEndTotalIndex OBJECT-TYPE
          SYNTAX  InterfaceIndex
          MAX-ACCESS  read-only
          STATUS  current
          DESCRIPTION
                 "The index value which uniquely identifies the DS1
                 interface to which this entry is applicable.  The
                 interface identified by a particular value of this
                 index is identical to the interface identified by
                 the same value of dsx1LineIndex."

          ::= { dsx1FarEndTotalEntry 1 }

     dsx1FarEndTotalESs OBJECT-TYPE
          SYNTAX  PerfTotalCount
          MAX-ACCESS  read-only
          STATUS  current
          DESCRIPTION
                 "The number of Far End Errored Seconds encountered
                 by a DS1 interface in the previous 24 hour
                 interval.  Invalid 15 minute intervals count as
                 0."
          ::= { dsx1FarEndTotalEntry 2 }

     dsx1FarEndTotalSESs OBJECT-TYPE
          SYNTAX  PerfTotalCount
          MAX-ACCESS  read-only
          STATUS  current
          DESCRIPTION
                 "The number of Far End Severely Errored Seconds
                 encountered by a DS1 interface in the previous 24
                 hour interval.  Invalid 15 minute intervals count
                 as 0."
          ::= { dsx1FarEndTotalEntry 3 }

     dsx1FarEndTotalSEFSs OBJECT-TYPE
          SYNTAX  PerfTotalCount
          MAX-ACCESS  read-only
          STATUS  current
          DESCRIPTION


                 "The number of Far End Severely Errored Framing
                 Seconds encountered by a DS1 interface in the
                 previous 24 hour interval. Invalid 15 minute
                 intervals count as 0."
          ::= { dsx1FarEndTotalEntry 4 }

     dsx1FarEndTotalUASs OBJECT-TYPE
          SYNTAX  PerfTotalCount
          MAX-ACCESS  read-only
          STATUS  current
          DESCRIPTION
                 "The number of Unavailable Seconds encountered by
                 a DS1 interface in the previous 24 hour interval.
                 Invalid 15 minute intervals count as 0."
          ::= { dsx1FarEndTotalEntry 5 }

     dsx1FarEndTotalCSSs OBJECT-TYPE
          SYNTAX  PerfTotalCount
          MAX-ACCESS  read-only
          STATUS  current
          DESCRIPTION
                 "The number of Far End Controlled Slip Seconds
                 encountered by a DS1 interface in the previous 24
                 hour interval.  Invalid 15 minute intervals count
                 as 0."
          ::= { dsx1FarEndTotalEntry 6 }

     dsx1FarEndTotalLESs OBJECT-TYPE
          SYNTAX  PerfTotalCount
          MAX-ACCESS  read-only
          STATUS  current
          DESCRIPTION
                 "The number of Far End Line Errored Seconds
                 encountered by a DS1 interface in the previous 24
                 hour interval.  Invalid 15 minute intervals count
                 as 0."
          ::= { dsx1FarEndTotalEntry 7 }

     dsx1FarEndTotalPCVs OBJECT-TYPE
          SYNTAX  PerfTotalCount
          MAX-ACCESS  read-only
          STATUS  current
          DESCRIPTION
                 "The number of Far End Path Coding Violations
                 reported via the far end block error count
                 encountered by a DS1 interface in the previous 24
                 hour interval.  Invalid 15 minute intervals count
                 as 0."


          ::= { dsx1FarEndTotalEntry 8 }

     dsx1FarEndTotalBESs OBJECT-TYPE
          SYNTAX PerfTotalCount
          MAX-ACCESS read-only
          STATUS current
          DESCRIPTION
                 "The number of Bursty Errored Seconds (BESs)
                 encountered by a DS1 interface in the previous 24
                 hour interval. Invalid 15 minute intervals count
                 as 0."
          ::= { dsx1FarEndTotalEntry 9 }

     dsx1FarEndTotalDMs OBJECT-TYPE
          SYNTAX PerfTotalCount
          MAX-ACCESS read-only
          STATUS current
          DESCRIPTION
                 "The number of Degraded Minutes (DMs) encountered
                 by a DS1 interface in the previous 24 hour
                 interval.  Invalid 15 minute intervals count as
                 0."
          ::= { dsx1FarEndTotalEntry 10 }

     -- The DS1 Fractional Table
     dsx1FracTable OBJECT-TYPE
          SYNTAX  SEQUENCE OF Dsx1FracEntry
          MAX-ACCESS  not-accessible
          STATUS  deprecated
          DESCRIPTION
                 "This table is deprecated in favour of using
                 ifStackTable.

                 The table was mandatory for systems dividing a DS1
                 into channels containing different data streams
                 that are of local interest.  Systems which are
                 indifferent to data content, such as CSUs, need
                 not implement it.

                 The DS1 fractional table identifies which DS1
                 channels associated with a CSU are being used to
                 support a logical interface, i.e., an entry in the
                 interfaces table from the Internet-standard MIB.

                 For example, consider an application managing a
                 North American ISDN Primary Rate link whose
                 division is a 384 kbit/s H1 _B_ Channel for Video,


                 a second H1 for data to a primary routing peer,
                 and 12 64 kbit/s H0 _B_ Channels. Consider that
                 some subset of the H0 channels are used for voice
                 and the remainder are available for dynamic data
                 calls.

                 We count a total of 14 interfaces multiplexed onto
                 the DS1 interface. Six DS1 channels (for the sake
                 of the example, channels 1..6) are used for Video,
                 six more (7..11 and 13) are used for data, and the
                 remaining 12 are are in channels 12 and 14..24.

                 Let us further imagine that ifIndex 2 is of type
                 DS1 and refers to the DS1 interface, and that the
                 interfaces layered onto it are numbered 3..16.

                 We might describe the allocation of channels, in
                 the dsx1FracTable, as follows:
               dsx1FracIfIndex.2. 1 = 3  dsx1FracIfIndex.2.13 = 4
               dsx1FracIfIndex.2. 2 = 3  dsx1FracIfIndex.2.14 = 6
               dsx1FracIfIndex.2. 3 = 3  dsx1FracIfIndex.2.15 = 7
               dsx1FracIfIndex.2. 4 = 3  dsx1FracIfIndex.2.16 = 8
               dsx1FracIfIndex.2. 5 = 3  dsx1FracIfIndex.2.17 = 9
               dsx1FracIfIndex.2. 6 = 3  dsx1FracIfIndex.2.18 = 10
               dsx1FracIfIndex.2. 7 = 4  dsx1FracIfIndex.2.19 = 11
               dsx1FracIfIndex.2. 8 = 4  dsx1FracIfIndex.2.20 = 12
               dsx1FracIfIndex.2. 9 = 4  dsx1FracIfIndex.2.21 = 13
               dsx1FracIfIndex.2.10 = 4  dsx1FracIfIndex.2.22 = 14
               dsx1FracIfIndex.2.11 = 4  dsx1FracIfIndex.2.23 = 15
               dsx1FracIfIndex.2.12 = 5  dsx1FracIfIndex.2.24 = 16

                 For North American (DS1) interfaces, there are 24
                 legal channels, numbered 1 through 24.

                 For G.704 interfaces, there are 31 legal channels,
                 numbered 1 through 31.  The channels (1..31)
                 correspond directly to the equivalently numbered
                 time-slots."
          ::= { ds1 13 }

     dsx1FracEntry OBJECT-TYPE
          SYNTAX  Dsx1FracEntry
          MAX-ACCESS  not-accessible
          STATUS  deprecated
          DESCRIPTION
             "An entry in the DS1 Fractional table."
         INDEX   { dsx1FracIndex, dsx1FracNumber }
         ::= { dsx1FracTable 1 }


     Dsx1FracEntry ::=
         SEQUENCE {
             dsx1FracIndex        INTEGER,
             dsx1FracNumber       INTEGER,
             dsx1FracIfIndex      INTEGER
         }

     dsx1FracIndex OBJECT-TYPE
         SYNTAX  INTEGER (1..'7fffffff'h)
         MAX-ACCESS  read-only
         STATUS  deprecated
         DESCRIPTION
            "The index value which uniquely identifies  the
            DS1  interface  to which this entry is applicable
            The interface identified by a  particular
            value  of  this  index is the same interface as
            identified by the same value  an  dsx1LineIndex
            object instance."
        ::= { dsx1FracEntry 1 }

     dsx1FracNumber OBJECT-TYPE
         SYNTAX  INTEGER (1..31)
         MAX-ACCESS  read-only
         STATUS  deprecated
         DESCRIPTION
            "The channel number for this entry."
        ::= { dsx1FracEntry 2 }

     dsx1FracIfIndex OBJECT-TYPE
         SYNTAX  INTEGER (1..'7fffffff'h)
         MAX-ACCESS  read-write
         STATUS  deprecated
         DESCRIPTION
            "An index value that uniquely identifies an
            interface.  The interface identified by a particular
            value of this index is the same  interface
            as  identified by the same value an ifIndex
            object instance. If no interface is currently using
            a channel, the value should be zero.  If a
            single interface occupies more  than  one  time
            slot,  that ifIndex value will be found in multiple
            time slots."
        ::= { dsx1FracEntry 3 }

      -- Ds1 TRAPS

     ds1Traps OBJECT IDENTIFIER ::= { ds1 15 }


     dsx1LineStatusChange NOTIFICATION-TYPE
         OBJECTS { dsx1LineStatus,
                   dsx1LineStatusLastChange }
         STATUS  current
         DESCRIPTION
                 "A dsx1LineStatusChange trap is sent when the
                 value of an instance dsx1LineStatus changes. It
                 can be utilized by an NMS to trigger polls.  When
                 the line status change results from a higher level
                 line status change (i.e. ds3), then no traps for
                 the ds1 are sent."
          ::= { ds1Traps 0 1 }

     -- conformance information
     ds1Conformance OBJECT IDENTIFIER ::= { ds1 14 }

     ds1Groups      OBJECT IDENTIFIER ::= { ds1Conformance 1 }
     ds1Compliances OBJECT IDENTIFIER ::= { ds1Conformance 2 }

     -- compliance statements

     ds1Compliance MODULE-COMPLIANCE
         STATUS  current
         DESCRIPTION
                 "The compliance statement for T1 and E1
                 interfaces."
         MODULE  -- this module
             MANDATORY-GROUPS { ds1NearEndConfigGroup,
                                ds1NearEndStatisticsGroup }

             GROUP       ds1FarEndGroup
             DESCRIPTION
                 "Implementation of this group is optional for all
                 systems that attach to a DS1 Interface."

             GROUP       ds1NearEndOptionalConfigGroup
             DESCRIPTION
                 "Implementation of this group is optional for all
                 systems that attach to a DS1 Interface."

             GROUP       ds1DS2Group
             DESCRIPTION
                 "Implementation of this group is mandatory for all
                 systems that attach to a DS2 Interface."

             GROUP       ds1TransStatsGroup


             DESCRIPTION
                 "This group is the set of statistics appropriate
                 for all systems which attach to a DS1 Interface
                 running transparent or unFramed lineType."

             GROUP       ds1ChanMappingGroup
             DESCRIPTION
                 "This group is the set of objects for mapping a
                 DS3 Channel (ds1ChannelNumber) to ifIndex.

                 Implementation of this group is mandatory for
                 systems which support the channelization of DS3s
                 into DS1s."

             OBJECT dsx1LineType
             MIN-ACCESS read-only
             DESCRIPTION
                 "The ability to set the line type is not
                 required."

             OBJECT dsx1LineCoding
             MIN-ACCESS read-only
             DESCRIPTION
                 "The ability to set the line coding is not
                 required."

             OBJECT dsx1SendCode
             MIN-ACCESS read-only
             DESCRIPTION
                 "The ability to set the send code is not
                 required."

             OBJECT dsx1LoopbackConfig
             MIN-ACCESS read-only
             DESCRIPTION
                 "The ability to set loopbacks is not required."

             OBJECT dsx1SignalMode
             MIN-ACCESS read-only
             DESCRIPTION
                 "The ability to set the signal mode is not
                 required."

             OBJECT dsx1TransmitClockSource
             MIN-ACCESS read-only
             DESCRIPTION
                 "The ability to set the transmit clock source is


                 not required."

             OBJECT dsx1Fdl
             MIN-ACCESS read-only
             DESCRIPTION
                 "The ability to set the FDL is not required."

             OBJECT dsx1LineLength
             MIN-ACCESS read-only
             DESCRIPTION
                 "The ability to set the line length is not
                 required."

             OBJECT dsx1Channelization
             MIN-ACCESS read-only
             DESCRIPTION
                 "The ability to set the channelization is not
                 required."
         ::= { ds1Compliances 1 }

     ds1MibT1PriCompliance MODULE-COMPLIANCE
         STATUS current
         DESCRIPTION
                 "Compliance statement for using this MIB for ISDN
                 Primary Rate interfaces on T1 lines."
         MODULE
             MANDATORY-GROUPS { ds1NearEndConfigGroup,
                                ds1NearEndStatisticsGroup }
             OBJECT dsx1LineType
                 SYNTAX INTEGER {
                     dsx1ESF(2)   -- Intl Spec would be G704(2)
                                  -- or I.431(4)
                 }
                 MIN-ACCESS read-only
                 DESCRIPTION
                     "Line type for T1 ISDN Primary Rate
                      interfaces."

             OBJECT dsx1LineCoding
                 SYNTAX INTEGER {
                     dsx1B8ZS(2)
                 }
                 MIN-ACCESS read-only
                 DESCRIPTION
                     "Type of Zero Code Suppression for
                      T1 ISDN Primary Rate interfaces."

             OBJECT dsx1SignalMode


                 SYNTAX INTEGER {
                     none(1), -- if there is no signaling channel
                     messageOriented(4)
                 }
                 MIN-ACCESS read-only
                 DESCRIPTION
                     "Possible signaling modes for
                      T1 ISDN Primary Rate interfaces."

             OBJECT dsx1TransmitClockSource
                 SYNTAX INTEGER {
                     loopTiming(1)
                 }
                 MIN-ACCESS read-only
                 DESCRIPTION
                     "The transmit clock is derived from
                      received clock on ISDN Primary Rate
                      interfaces."

             OBJECT dsx1Fdl
                 MIN-ACCESS read-only
                 DESCRIPTION
                     "Facilities Data Link usage on T1 ISDN
                      Primary Rate interfaces.
                      Note: Eventually dsx1Att-54016(4) is to be
                            used here since the line type is ESF."

             OBJECT dsx1Channelization
                 MIN-ACCESS read-only
                 DESCRIPTION
                     "The ability to set the channelization
                      is not required."
         ::= { ds1Compliances 2 }

     ds1MibE1PriCompliance MODULE-COMPLIANCE
         STATUS current
         DESCRIPTION
                 "Compliance statement for using this MIB for ISDN
                 Primary Rate interfaces on E1 lines."
         MODULE
             MANDATORY-GROUPS { ds1NearEndConfigGroup,
                                ds1NearEndStatisticsGroup }
             OBJECT dsx1LineType
                 SYNTAX INTEGER {
                     dsx1E1CRC(5)
                 }
                 MIN-ACCESS read-only


                 DESCRIPTION
                     "Line type for E1 ISDN Primary Rate
                      interfaces."

             OBJECT dsx1LineCoding
                 SYNTAX INTEGER {
                     dsx1HDB3(3)
                 }
                 MIN-ACCESS read-only
                 DESCRIPTION
                     "Type of Zero Code Suppression for
                      E1 ISDN Primary Rate interfaces."

             OBJECT dsx1SignalMode
                 SYNTAX INTEGER {
                     messageOriented(4)
                 }
                 MIN-ACCESS read-only
                 DESCRIPTION
                     "Signaling on E1 ISDN Primary Rate interfaces
                      is always message oriented."

             OBJECT dsx1TransmitClockSource
                 SYNTAX INTEGER {
                     loopTiming(1)
                 }
                 MIN-ACCESS read-only
                 DESCRIPTION
                     "The transmit clock is derived from received
                      clock on ISDN Primary Rate interfaces."

             OBJECT dsx1Fdl
                 MIN-ACCESS read-only
                 DESCRIPTION
                     "Facilities Data Link usage on E1 ISDN
                      Primary Rate interfaces.
                      Note: There is a 'M-Channel' in E1,
                            using National Bit Sa4 (G704,
                            Table 4a). It is used to implement
                            management features between ET
                            and NT.  This is different to
                            FDL in T1, which is used to carry
                            control signals and performance
                            data.  In E1, control and status
                            signals are carried using National
                            Bits Sa5, Sa6 and A (RAI Ind.).
                      This indicates that only the other(1) or
                      eventually the dsx1Fdl-none(8) bits should


                      be set in this object for E1 PRI."

             OBJECT dsx1Channelization
                 MIN-ACCESS read-only
                 DESCRIPTION
                 "The ability to set the channelization is not
                 required."
         ::= { ds1Compliances 3 }

     ds1Ds2Compliance MODULE-COMPLIANCE
         STATUS current
         DESCRIPTION
                 "Compliance statement for using this MIB for DS2
                 interfaces."
         MODULE
             MANDATORY-GROUPS { ds1DS2Group }

             OBJECT dsx1Channelization
                 MIN-ACCESS read-only
                 DESCRIPTION
                 "The ability to set the channelization is not
                 required."
         ::= { ds1Compliances 4 }

     -- units of conformance

     ds1NearEndConfigGroup  OBJECT-GROUP
         OBJECTS { dsx1LineIndex,
                   dsx1TimeElapsed,
                   dsx1ValidIntervals,
                   dsx1LineType,
                   dsx1LineCoding,
                   dsx1SendCode,
                   dsx1CircuitIdentifier,
                   dsx1LoopbackConfig,
                   dsx1LineStatus,
                   dsx1SignalMode,
                   dsx1TransmitClockSource,
                   dsx1Fdl,
                   dsx1InvalidIntervals,
                   dsx1LineLength,
                   dsx1LoopbackStatus,
                   dsx1Ds1ChannelNumber,
                   dsx1Channelization }
         STATUS  current
         DESCRIPTION
                 "A collection of objects providing configuration


                 information applicable to all DS1 interfaces."
         ::= { ds1Groups 1 }

     ds1NearEndStatisticsGroup OBJECT-GROUP
         OBJECTS { dsx1CurrentIndex,
                   dsx1CurrentESs,
                   dsx1CurrentSESs,
                   dsx1CurrentSEFSs,
                   dsx1CurrentUASs,
                   dsx1CurrentCSSs,
                   dsx1CurrentPCVs,
                   dsx1CurrentLESs,
                   dsx1CurrentBESs,
                   dsx1CurrentDMs,
                   dsx1CurrentLCVs,
                   dsx1IntervalIndex,
                   dsx1IntervalNumber,
                   dsx1IntervalESs,
                   dsx1IntervalSESs,
                   dsx1IntervalSEFSs,
                   dsx1IntervalUASs,
                   dsx1IntervalCSSs,
                   dsx1IntervalPCVs,
                   dsx1IntervalLESs,
                   dsx1IntervalBESs,
                   dsx1IntervalDMs,
                   dsx1IntervalLCVs,
                   dsx1IntervalValidData,
                   dsx1TotalIndex,
                   dsx1TotalESs,
                   dsx1TotalSESs,
                   dsx1TotalSEFSs,
                   dsx1TotalUASs,
                   dsx1TotalCSSs,
                   dsx1TotalPCVs,
                   dsx1TotalLESs,
                   dsx1TotalBESs,
                   dsx1TotalDMs,
                   dsx1TotalLCVs }
         STATUS  current
         DESCRIPTION
                 "A collection of objects providing statistics
                 information applicable to all DS1 interfaces."
         ::= { ds1Groups 2 }

     ds1FarEndGroup  OBJECT-GROUP
         OBJECTS { dsx1FarEndCurrentIndex,
                   dsx1FarEndTimeElapsed,


                   dsx1FarEndValidIntervals,
                   dsx1FarEndCurrentESs,
                   dsx1FarEndCurrentSESs,
                   dsx1FarEndCurrentSEFSs,
                   dsx1FarEndCurrentUASs,
                   dsx1FarEndCurrentCSSs,
                   dsx1FarEndCurrentLESs,
                   dsx1FarEndCurrentPCVs,
                   dsx1FarEndCurrentBESs,
                   dsx1FarEndCurrentDMs,
                   dsx1FarEndInvalidIntervals,
                   dsx1FarEndIntervalIndex,
                   dsx1FarEndIntervalNumber,
                   dsx1FarEndIntervalESs,
                   dsx1FarEndIntervalSESs,
                   dsx1FarEndIntervalSEFSs,
                   dsx1FarEndIntervalUASs,
                   dsx1FarEndIntervalCSSs,
                   dsx1FarEndIntervalLESs,
                   dsx1FarEndIntervalPCVs,
                   dsx1FarEndIntervalBESs,
                   dsx1FarEndIntervalDMs,
                   dsx1FarEndIntervalValidData,
                   dsx1FarEndTotalIndex,
                   dsx1FarEndTotalESs,
                   dsx1FarEndTotalSESs,
                   dsx1FarEndTotalSEFSs,
                   dsx1FarEndTotalUASs,
                   dsx1FarEndTotalCSSs,
                   dsx1FarEndTotalLESs,
                   dsx1FarEndTotalPCVs,
                   dsx1FarEndTotalBESs,
                   dsx1FarEndTotalDMs }
         STATUS  current
         DESCRIPTION
                 "A collection of objects providing remote
                 configuration and statistics information."
         ::= { ds1Groups 3 }

     ds1DeprecatedGroup OBJECT-GROUP
         OBJECTS { dsx1IfIndex,
                   dsx1FracIndex,
                   dsx1FracNumber,
                   dsx1FracIfIndex }
         STATUS  deprecated
         DESCRIPTION
                 "A collection of obsolete objects that may be
                 implemented for backwards compatibility."


         ::= { ds1Groups 4 }

     ds1NearEndOptionalConfigGroup OBJECT-GROUP
         OBJECTS { dsx1LineStatusLastChange,
                   dsx1LineStatusChangeTrapEnable }

         STATUS    current
         DESCRIPTION
                 "A collection of objects that may be implemented
                 on DS1 and DS2 interfaces."
         ::= { ds1Groups 5 }

     ds1DS2Group OBJECT-GROUP
         OBJECTS { dsx1LineIndex,
                   dsx1LineType,
                   dsx1LineCoding,
                   dsx1SendCode,
                   dsx1LineStatus,
                   dsx1SignalMode,
                   dsx1TransmitClockSource,
                   dsx1Channelization }
         STATUS   current
         DESCRIPTION
                 "A collection of objects providing information
                 about DS2 (6,312 kbps) and E2 (8,448 kbps)
                 systems."
         ::= { ds1Groups 6 }

     ds1TransStatsGroup OBJECT-GROUP
         OBJECTS { dsx1CurrentESs,
                   dsx1CurrentSESs,
                   dsx1CurrentUASs,
                   dsx1IntervalESs,
                   dsx1IntervalSESs,
                   dsx1IntervalUASs,
                   dsx1TotalESs,
                   dsx1TotalSESs,
                   dsx1TotalUASs }
         STATUS   current
         DESCRIPTION
                      "A collection of objects which are the
                 statistics which can be collected from a ds1
                 interface that is running transparent or unframed
                 lineType.  Statistics not in this list should
                 return noSuchInstance."
         ::= { ds1Groups 7 }

     ds1NearEndOptionalTrapGroup NOTIFICATION-GROUP


         NOTIFICATIONS { dsx1LineStatusChange }
         STATUS    current
         DESCRIPTION
                 "A collection of notifications that may be
                 implemented on DS1 and DS2 interfaces."
         ::= { ds1Groups 8 }

     ds1ChanMappingGroup OBJECT-GROUP
         OBJECTS { dsx1ChanMappedIfIndex }
         STATUS    current
         DESCRIPTION
                 "A collection of objects that give an mapping of
                 DS3 Channel (ds1ChannelNumber) to ifIndex."
         ::= { ds1Groups 9 }

END

PPP-LCP-MIB DEFINITIONS ::= BEGIN

          IMPORTS
               Counter
                    FROM RFC1155-SMI
               ifIndex, transmission
                    FROM RFC1213-MIB
               OBJECT-TYPE
                    FROM RFC-1212;

               --  PPP MIB

               ppp  OBJECT IDENTIFIER ::= { transmission 23 }

               pppLcp OBJECT IDENTIFIER ::= { ppp 1 }


               -- The individual groups within the PPP-LCP-MIB

               pppLink      OBJECT IDENTIFIER ::= { pppLcp 1 }
               pppLqr       OBJECT IDENTIFIER ::= { pppLcp 2 }
               pppTests     OBJECT IDENTIFIER ::= { pppLcp 3 }

          -- 4.1.  PPP Link Group

          --
          -- The PPP Link Group. Implementation of this
          -- group is mandatory for all PPP entities.
          --

          -- The following object reflect the values of the option
          -- parameters used in the PPP Link Control Protocol
          --   pppLinkStatusLocalMRU
          --   pppLinkStatusRemoteMRU
          --   pppLinkStatusLocalToPeerACCMap
          --   pppLinkStatusPeerToLocalACCMap
          --   pppLinkStatusLocalToRemoteProtocolCompression
          --   pppLinkStatusRemoteToLocalProtocolCompression
          --   pppLinkStatusLocalToRemoteACCompression
          --   pppLinkStatusRemoteToLocalACCompression
          --   pppLinkStatusTransmitFcsSize
          --   pppLinkStatusReceiveFcsSize
          --
          -- These values are not available until after the PPP Option
          -- negotiation has completed, which is indicated by the link
          -- reaching the open state (i.e., ifOperStatus is set to
          -- up).
          --
          -- Therefore, when ifOperStatus is not up
          -- the contents of these objects is undefined. The value
          -- returned when accessing the objects is an implementation
          -- dependent issue.

          pppLinkStatusTable   OBJECT-TYPE
               SYNTAX    SEQUENCE OF PppLinkStatusEntry
               ACCESS    not-accessible
               STATUS    mandatory
               DESCRIPTION
                         "A table containing PPP-link specific variables
                         for this PPP implementation."
               ::= { pppLink 1 }


          pppLinkStatusEntry   OBJECT-TYPE
               SYNTAX    PppLinkStatusEntry
               ACCESS    not-accessible
               STATUS    mandatory
               DESCRIPTION
                         "Management information about a particular PPP
                         Link."
               INDEX     { ifIndex }
               ::= { pppLinkStatusTable 1 }

          PppLinkStatusEntry ::= SEQUENCE {
               pppLinkStatusPhysicalIndex
                    INTEGER,
               pppLinkStatusBadAddresses
                    Counter,
               pppLinkStatusBadControls
                    Counter,
               pppLinkStatusPacketTooLongs
                    Counter,
               pppLinkStatusBadFCSs
                    Counter,
               pppLinkStatusLocalMRU
                    INTEGER,
               pppLinkStatusRemoteMRU
                    INTEGER,
               pppLinkStatusLocalToPeerACCMap
                    OCTET STRING,
               pppLinkStatusPeerToLocalACCMap
                    OCTET STRING,
               pppLinkStatusLocalToRemoteProtocolCompression
                    INTEGER,
               pppLinkStatusRemoteToLocalProtocolCompression
                    INTEGER,
               pppLinkStatusLocalToRemoteACCompression
                    INTEGER,
               pppLinkStatusRemoteToLocalACCompression
                    INTEGER,
               pppLinkStatusTransmitFcsSize
                    INTEGER,
               pppLinkStatusReceiveFcsSize
                    INTEGER
               }
          pppLinkStatusPhysicalIndex   OBJECT-TYPE
               SYNTAX    INTEGER(0..2147483647)
               ACCESS    read-only
               STATUS    mandatory
               DESCRIPTION


                         "The value of ifIndex that identifies the
                         lower-level interface over which this PPP Link
                         is operating. This interface would usually be
                         an HDLC or RS-232 type of interface. If there
                         is no lower-layer interface element, or there
                         is no ifEntry for the element, or the element
                         can not be identified, then the value of this
                         object is 0.  For example, suppose that PPP is
                         operating over a serial port. This would use
                         two entries in the ifTable. The PPP could be
                         running over `interface' number 123 and the
                         serial port could be running over `interface'
                         number 987.  Therefore, ifSpecific.123 would
                         contain the OBJECT IDENTIFIER ppp
                         pppLinkStatusPhysicalIndex.123 would contain
                         987, and ifSpecific.987 would contain the
                         OBJECT IDENTIFIER for the serial-port's media-
                         specific MIB."
               ::= { pppLinkStatusEntry 1 }

          pppLinkStatusBadAddresses   OBJECT-TYPE
               SYNTAX    Counter
               ACCESS    read-only
               STATUS    mandatory
               DESCRIPTION
                         "The number of packets received with an
                         incorrect Address Field. This counter is a
                         component of the ifInErrors variable that is
                         associated with the interface that represents
                         this PPP Link."
               REFERENCE
                         "Section 3.1, Address Field, of RFC1331."
               ::= { pppLinkStatusEntry 2 }

          pppLinkStatusBadControls   OBJECT-TYPE
               SYNTAX    Counter
               ACCESS    read-only
               STATUS    mandatory
               DESCRIPTION
                         "The number of packets received on this link
                         with an incorrect Control Field. This counter
                         is a component of the ifInErrors variable that
                         is associated with the interface that
                         represents this PPP Link."
               REFERENCE
                         "Section 3.1, Control Field, of RFC1331."


               ::= { pppLinkStatusEntry 3 }

          pppLinkStatusPacketTooLongs   OBJECT-TYPE
               SYNTAX    Counter
               ACCESS    read-only
               STATUS    mandatory
               DESCRIPTION
                         "The number of received packets that have been
                         discarded because their length exceeded the
                         MRU. This counter is a component of the
                         ifInErrors variable that is associated with the
                         interface that represents this PPP Link. NOTE,
                         packets which are longer than the MRU but which
                         are successfully received and processed are NOT
                         included in this count."
               ::= { pppLinkStatusEntry 4 }

          pppLinkStatusBadFCSs   OBJECT-TYPE
               SYNTAX    Counter
               ACCESS    read-only
               STATUS    mandatory
               DESCRIPTION
                         "The number of received packets that have been
                         discarded due to having an incorrect FCS. This
                         counter is a component of the ifInErrors
                         variable that is associated with the interface
                         that represents this PPP Link."
               ::= { pppLinkStatusEntry 5 }

          pppLinkStatusLocalMRU   OBJECT-TYPE
               SYNTAX    INTEGER(1..2147483648)
               ACCESS    read-only
               STATUS    mandatory
               DESCRIPTION
                         "The current value of the MRU for the local PPP
                         Entity. This value is the MRU that the remote
                         entity is using when sending packets to the
                         local PPP entity. The value of this object is
                         meaningful only when the link has reached the
                         open state (ifOperStatus is up)."
               ::= { pppLinkStatusEntry 6 }

          pppLinkStatusRemoteMRU   OBJECT-TYPE
               SYNTAX    INTEGER(1..2147483648)


               ACCESS    read-only
               STATUS    mandatory
               DESCRIPTION
                         "The current value of the MRU for the remote
                         PPP Entity. This value is the MRU that the
                         local entity is using when sending packets to
                         the remote PPP entity. The value of this object
                         is meaningful only when the link has reached
                         the open state (ifOperStatus is up)."
               ::= { pppLinkStatusEntry 7 }

          pppLinkStatusLocalToPeerACCMap   OBJECT-TYPE
               SYNTAX    OCTET STRING (SIZE (4))
               ACCESS    read-only
               STATUS    mandatory
               DESCRIPTION
                         "The current value of the ACC Map used for
                         sending packets from the local PPP entity to
                         the remote PPP entity. The value of this object
                         is meaningful only when the link has reached
                         the open state (ifOperStatus is up)."
               ::= { pppLinkStatusEntry 8 }

          pppLinkStatusPeerToLocalACCMap   OBJECT-TYPE
               SYNTAX    OCTET STRING (SIZE (4))
               ACCESS    read-only
               STATUS    mandatory
               DESCRIPTION
                         "The ACC Map used by the remote PPP entity when
                         transmitting packets to the local PPP entity.
                         The value of this object is meaningful only
                         when the link has reached the open state
                         (ifOperStatus is up)."
               ::= { pppLinkStatusEntry 9 }

          pppLinkStatusLocalToRemoteProtocolCompression
               OBJECT-TYPE
               SYNTAX    INTEGER {
                         enabled(1),
                         disabled(2)
                    }
               ACCESS    read-only
               STATUS    mandatory
               DESCRIPTION
                         "Indicates whether the local PPP entity will


                         use Protocol Compression when transmitting
                         packets to the remote PPP entity. The value of
                         this object is meaningful only when the link
                         has reached the open state (ifOperStatus is
                         up)."
               ::= { pppLinkStatusEntry 10 }

          pppLinkStatusRemoteToLocalProtocolCompression
               OBJECT-TYPE
               SYNTAX    INTEGER {
                         enabled(1),
                         disabled(2)
                    }
               ACCESS    read-only
               STATUS    mandatory
               DESCRIPTION
                         "Indicates whether the remote PPP entity will
                         use Protocol Compression when transmitting
                         packets to the local PPP entity. The value of
                         this object is meaningful only when the link
                         has reached the open state (ifOperStatus is
                         up)."
               ::= { pppLinkStatusEntry 11 }

          pppLinkStatusLocalToRemoteACCompression   OBJECT-TYPE
               SYNTAX    INTEGER {
                         enabled(1),
                         disabled(2)
                    }
               ACCESS    read-only
               STATUS    mandatory
               DESCRIPTION
                         "Indicates whether the local PPP entity will
                         use Address and Control Compression when
                         transmitting packets to the remote PPP entity.
                         The value of this object is meaningful only
                         when the link has reached the open state
                         (ifOperStatus is up)."
               ::= { pppLinkStatusEntry 12 }

          pppLinkStatusRemoteToLocalACCompression   OBJECT-TYPE
               SYNTAX    INTEGER {
                         enabled(1),
                         disabled(2)
                    }


               ACCESS    read-only
               STATUS    mandatory
               DESCRIPTION
                         "Indicates whether the remote PPP entity will
                         use Address and Control Compression when
                         transmitting packets to the local PPP entity.
                         The value of this object is meaningful only
                         when the link has reached the open state
                         (ifOperStatus is up)."
               ::= { pppLinkStatusEntry 13 }

          pppLinkStatusTransmitFcsSize   OBJECT-TYPE
               SYNTAX    INTEGER (0..128)
               ACCESS    read-only
               STATUS    mandatory
               DESCRIPTION
                         "The size of the Frame Check Sequence (FCS) in
                         bits that the local node will generate when
                         sending packets to the remote node. The value
                         of this object is meaningful only when the link
                         has reached the open state (ifOperStatus is
                         up)."
               ::= { pppLinkStatusEntry 14 }

          pppLinkStatusReceiveFcsSize   OBJECT-TYPE
               SYNTAX    INTEGER (0..128)
               ACCESS    read-only
               STATUS    mandatory
               DESCRIPTION
                         "The size of the Frame Check Sequence (FCS) in
                         bits that the remote node will generate when
                         sending packets to the local node. The value of
                         this object is meaningful only when the link
                         has reached the open state (ifOperStatus is
                         up)."
               ::= { pppLinkStatusEntry 15 }

          pppLinkConfigTable   OBJECT-TYPE
               SYNTAX    SEQUENCE OF PppLinkConfigEntry
               ACCESS    not-accessible
               STATUS    mandatory
               DESCRIPTION
                         "A table containing the LCP configuration
                         parameters for this PPP Link. These variables
                         represent the initial configuration of the PPP


                         Link. The actual values of the parameters may
                         be changed when the link is brought up via the
                         LCP options negotiation mechanism."
               ::= { pppLink 2 }

          pppLinkConfigEntry   OBJECT-TYPE
               SYNTAX    PppLinkConfigEntry
               ACCESS    not-accessible
               STATUS    mandatory
               DESCRIPTION
                         "Configuration information about a particular
                         PPP Link."
               INDEX     { ifIndex }
               ::= { pppLinkConfigTable 1 }

          PppLinkConfigEntry ::= SEQUENCE {
               pppLinkConfigInitialMRU
                    INTEGER,
               pppLinkConfigReceiveACCMap
                    OCTET STRING,
               pppLinkConfigTransmitACCMap
                    OCTET STRING,
               pppLinkConfigMagicNumber
                    INTEGER,
               pppLinkConfigFcsSize
                    INTEGER
               }

          pppLinkConfigInitialMRU   OBJECT-TYPE
               SYNTAX    INTEGER(0..2147483647)
               ACCESS    read-write
               STATUS    mandatory
               DESCRIPTION
                         "The initial Maximum Receive Unit (MRU) that
                         the local PPP entity will advertise to the
                         remote entity. If the value of this variable is
                         0 then the local PPP entity will not advertise
                         any MRU to the remote entity and the default
                         MRU will be assumed. Changing this object will
                         have effect when the link is next restarted."
               REFERENCE
                         "Section 7.2, Maximum Receive Unit of RFC1331."
               DEFVAL    { 1500 }
               ::= { pppLinkConfigEntry 1 }


          pppLinkConfigReceiveACCMap   OBJECT-TYPE
               SYNTAX    OCTET STRING (SIZE (4))
               ACCESS    read-write
               STATUS    mandatory
               DESCRIPTION
                         "The Asynchronous-Control-Character-Map (ACC)
                         that the local PPP entity requires for use on
                         its receive side. In effect, this is the ACC
                         Map that is required in order to ensure that
                         the local modem will successfully receive all
                         characters. The actual ACC map used on the
                         receive side of the link will be a combination
                         of the local node's pppLinkConfigReceiveACCMap
                         and the remote node's
                         pppLinkConfigTransmitACCMap. Changing this
                         object will have effect when the link is next
                         restarted."
               REFERENCE
                         "Section 7.3, page 4, Async-Control-Character-
                         Map of RFC1331."
               DEFVAL    { 'ffffffff'h }
               ::= { pppLinkConfigEntry 2 }

          pppLinkConfigTransmitACCMap   OBJECT-TYPE
               SYNTAX    OCTET STRING (SIZE (4))
               ACCESS    read-write
               STATUS    mandatory
               DESCRIPTION
                         "The Asynchronous-Control-Character-Map (ACC)
                         that the local PPP entity requires for use on
                         its transmit side. In effect, this is the ACC
                         Map that is required in order to ensure that
                         all characters can be successfully transmitted
                         through the local modem.  The actual ACC map
                         used on the transmit side of the link will be a
                         combination of the local node's
                         pppLinkConfigTransmitACCMap and the remote
                         node's pppLinkConfigReceiveACCMap. Changing
                         this object will have effect when the link is
                         next restarted."
               REFERENCE
                         "Section 7.3, page 4, Async-Control-Character-
                         Map of RFC1331."
               DEFVAL    { 'ffffffff'h }
               ::= { pppLinkConfigEntry 3 }


          pppLinkConfigMagicNumber   OBJECT-TYPE
               SYNTAX    INTEGER {false (1), true (2)}
               ACCESS    read-write
               STATUS    mandatory
               DESCRIPTION
                         "If true(2) then the local node will attempt to
                         perform Magic Number negotiation with the
                         remote node. If false(1) then this negotiation
                         is not performed. In any event, the local node
                         will comply with any magic number negotiations
                         attempted by the remote node, per the PPP
                         specification. Changing this object will have
                         effect when the link is next restarted."
               REFERENCE
                         "Section 7.6, Magic Number, of RFC1331."
               DEFVAL    { false }
               ::= { pppLinkConfigEntry 4 }

          pppLinkConfigFcsSize   OBJECT-TYPE
               SYNTAX    INTEGER (0..128)
               ACCESS    read-write
               STATUS    mandatory
               DESCRIPTION
                         "The size of the FCS, in bits, the local node
                         will attempt to negotiate for use with the
                         remote node. Regardless of the value of this
                         object, the local node will comply with any FCS
                         size negotiations initiated by the remote node,
                         per the PPP specification. Changing this object
                         will have effect when the link is next
                         restarted."
               DEFVAL    { 16 }
               ::= { pppLinkConfigEntry 5 }

          -- 4.2.  PPP LQR Group

               --
               -- The PPP LQR Group.
               -- Implementation of this group is mandatory for all
               -- PPP implementations that implement LQR.
               --

          pppLqrTable   OBJECT-TYPE
               SYNTAX    SEQUENCE OF PppLqrEntry
               ACCESS    not-accessible


               STATUS    mandatory
               DESCRIPTION
                         "Table containing the LQR parameters and
                         statistics for the local PPP entity."
               ::= { pppLqr 1 }

          pppLqrEntry   OBJECT-TYPE
               SYNTAX    PppLqrEntry
               ACCESS    not-accessible
               STATUS    mandatory
               DESCRIPTION
                         "LQR information for a particular PPP link. A
                         PPP link will have an entry in this table if
                         and only if LQR Quality Monitoring has been
                         successfully negotiated for said link."
               INDEX     { ifIndex }
               ::= { pppLqrTable 1 }

          PppLqrEntry ::= SEQUENCE {
               pppLqrQuality
                    INTEGER,
               pppLqrInGoodOctets
                    Counter,
               pppLqrLocalPeriod
                    INTEGER,
               pppLqrRemotePeriod
                    INTEGER,
               pppLqrOutLQRs
                    Counter,
               pppLqrInLQRs
                    Counter
          }

          pppLqrQuality   OBJECT-TYPE
               SYNTAX    INTEGER {
                         good(1),
                         bad(2),
                         not-determined(3)
                    }
               ACCESS    read-only
               STATUS    mandatory
               DESCRIPTION
                         "The current quality of the link as declared by
                         the local PPP entity's Link-Quality Management
                         modules. No effort is made to define good or
                         bad, nor the policy used to determine it. The


                         not-determined value indicates that the entity
                         does not actually evaluate the link's quality.
                         This value is used to disambiguate the
                         `determined to be good' case from the `no
                         determination made and presumed to be good'
                         case."
               ::= { pppLqrEntry 1 }

          pppLqrInGoodOctets   OBJECT-TYPE
               SYNTAX    Counter
               ACCESS    read-only
               STATUS    mandatory
               DESCRIPTION
                         "The LQR InGoodOctets counter for this link."
               REFERENCE
                         "Section 2.2, Counters, of RFC1333."
               ::= { pppLqrEntry 2 }

          pppLqrLocalPeriod   OBJECT-TYPE
               SYNTAX    INTEGER(1..2147483648)
               ACCESS    read-only
               STATUS    mandatory
               DESCRIPTION
                         "The LQR reporting period, in hundredths of a
                         second that is in effect for the local PPP
                         entity."
               REFERENCE
                         "Section 2.5, Configuration Option Format, of
                         RFC1333."
               ::= { pppLqrEntry 3 }

          pppLqrRemotePeriod   OBJECT-TYPE
               SYNTAX    INTEGER(1..2147483648)
               ACCESS    read-only
               STATUS    mandatory
               DESCRIPTION
                         "The LQR reporting period, in hundredths of a
                         second, that is in effect for the remote PPP
                         entity."
               REFERENCE
                         "Section 2.5, Configuration Option Format, of
                         RFC1333."
               ::= { pppLqrEntry 4 }


          pppLqrOutLQRs   OBJECT-TYPE
               SYNTAX    Counter
               ACCESS    read-only
               STATUS    mandatory
               DESCRIPTION
                         "The value of the OutLQRs counter on the local
                         node for the link identified by ifIndex."
               REFERENCE
                         "Section 2.2, Counters, of RFC1333."
               ::= { pppLqrEntry 5 }

          pppLqrInLQRs   OBJECT-TYPE
               SYNTAX    Counter
               ACCESS    read-only
               STATUS    mandatory
               DESCRIPTION
                         "The value of the InLQRs counter on the local
                         node for the link identified by ifIndex."
               REFERENCE
                         "Section 2.2, Counters, of RFC1333."
               ::= { pppLqrEntry 6 }

          --
          -- The PPP LQR Configuration table.
          --

          pppLqrConfigTable   OBJECT-TYPE
               SYNTAX    SEQUENCE OF PppLqrConfigEntry
               ACCESS    not-accessible
               STATUS    mandatory
               DESCRIPTION
                         "Table containing the LQR Configuration
                         parameters for the local PPP entity."
               ::= { pppLqr 2 }

          pppLqrConfigEntry   OBJECT-TYPE
               SYNTAX    PppLqrConfigEntry
               ACCESS    not-accessible
               STATUS    mandatory
               DESCRIPTION
                         "LQR configuration information for a particular
                         PPP link."
               INDEX     { ifIndex }
               ::= { pppLqrConfigTable 1 }


          PppLqrConfigEntry ::= SEQUENCE {
               pppLqrConfigPeriod
                    INTEGER,
               pppLqrConfigStatus
                    INTEGER
          }

          pppLqrConfigPeriod   OBJECT-TYPE
               SYNTAX    INTEGER(0..2147483647)
               ACCESS    read-write
               STATUS    mandatory
               DESCRIPTION
                         "The LQR Reporting Period that the local PPP
                         entity will attempt to negotiate with the
                         remote entity, in units of hundredths of a
                         second. Changing this object will have effect
                         when the link is next restarted."
               REFERENCE
                         "Section 2.5, Configuration Option Format, of
                         RFC1333."
               DEFVAL    { 0 }
               ::= { pppLqrConfigEntry 1 }

          pppLqrConfigStatus   OBJECT-TYPE
               SYNTAX    INTEGER {disabled (1), enabled (2)}
               ACCESS    read-write
               STATUS    mandatory
               DESCRIPTION
                         "If enabled(2) then the local node will attempt
                         to perform LQR negotiation with the remote
                         node. If disabled(1) then this negotiation is
                         not performed. In any event, the local node
                         will comply with any magic number negotiations
                         attempted by the remote node, per the PPP
                         specification. Changing this object will have
                         effect when the link is next restarted.
                         Setting this object to the value disabled(1)
                         has the effect of invalidating the
                         corresponding entry in the pppLqrConfigTable
                         object. It is an implementation-specific matter
                         as to whether the agent removes an invalidated
                         entry from the table. Accordingly, management
                         stations must be prepared to receive tabular
                         information from agents that corresponds to
                         entries not currently in use."
               REFERENCE
                         "Section 7.6, Magic Number, of RFC1331."


               DEFVAL    { enabled }
               ::= { pppLqrConfigEntry 2 }

          -- 4.3.  PPP LQR Extensions Group

          --
          -- The PPP LQR Extensions Group.
          -- Implementation of this group is optional.
          --
          -- The intent of this group is to allow external
          -- implementation of the policy mechanisms that
          -- are used to declare a link to be "bad" or not.
          --
          -- It is not practical to examine the MIB objects
          -- which are used to generate LQR packets since
          -- LQR policies tend to require synchronization of
          -- the values of all data used to determine Link
          -- Quality; i.e. the values of the relevant counters
          -- must all be taken at the same instant in time.
          --

          pppLqrExtnsTable   OBJECT-TYPE
               SYNTAX    SEQUENCE OF PppLqrExtnsEntry
               ACCESS    not-accessible
               STATUS    mandatory
               DESCRIPTION
                         "Table containing additional LQR information
                         for the local PPP entity."
               ::= { pppLqr 3 }

          pppLqrExtnsEntry   OBJECT-TYPE
               SYNTAX    PppLqrExtnsEntry
               ACCESS    not-accessible
               STATUS    mandatory
               DESCRIPTION
                         "Extended LQR information for a particular PPP
                         link. Assuming that this group has been
                         implemented, a PPP link will have an entry in
                         this table if and only if LQR Quality
                         Monitoring has been successfully negotiated for
                         said link."
               INDEX     { ifIndex }
               ::= { pppLqrExtnsTable 1 }

          PppLqrExtnsEntry ::= SEQUENCE {


               pppLqrExtnsLastReceivedLqrPacket
                    OCTET STRING(SIZE(68))
          }

          pppLqrExtnsLastReceivedLqrPacket   OBJECT-TYPE
               SYNTAX    OCTET STRING(SIZE(68))
               ACCESS    read-only
               STATUS    mandatory
               DESCRIPTION
                         "This object contains the most recently
                         received LQR packet.  The format of the packet
                         is as described in the LQM Protocol
                         specificiation. All fields of the packet,
                         including the `save' fields, are stored in this
                         object.

                         The LQR packet is stored in network byte order.
                         The LAP-B and PPP headers are not stored in
                         this object; the first four octets of this
                         variable contain the Magic-Number field, the
                         second four octets contain the LastOutLQRs
                         field and so on. The last four octets of this
                         object contain the SaveInOctets field of the
                         LQR packet."
               REFERENCE
                         "Section 2.6, Packet Format, of RFC1333"
               ::= { pppLqrExtnsEntry 1 }

          -- 4.4.  PPP Tests

          -- The extensions to the interface table in RFC1229 define a
          -- table through which the network manager can instruct the
          -- managed object to perform various tests of the interface. This
          -- is the ifExtnsTestTable.

          -- The PPP MIB defines two such tests.

          -- 4.4.1.  PPP Echo Test

          -- The PPP Echo Test is defined as

               pppEchoTest    OBJECT IDENTIFIER ::= { pppTests 1 }

          -- Invoking this test causes a PPP Echo Packet to be sent on the
          -- line. ifExtnsTestResult returns success(2) if the echo
          -- response came back properly. It returns failed(7) if the
          -- response did not properly return. The definition of "proper"


          -- in this context is left to the discretion of the implementor.

          -- 4.4.2.  PPP Discard Test

          -- The PPP Discard Test is defined as

               pppDiscardTest OBJECT IDENTIFIER ::= { pppTests 2 }

          -- Invoking this test causes a PPP Discard Packet to be sent on
          -- the line. ifExtnsTestResult returns success(2) if the discard
          -- packet was successfully transmitted and failed(7) if an error
          -- was detected on transmission. The definition of "transmission
          -- error" in this context is left to the discretion of the
          -- implementor.

END

PPP-BRIDGE-NCP-MIB DEFINITIONS ::= BEGIN

          IMPORTS
               Counter
                    FROM RFC1155-SMI
               ifIndex
                    FROM RFC1213-MIB
               OBJECT-TYPE
                    FROM RFC-1212
               ppp
                    FROM PPP-LCP-MIB;

               pppBridge OBJECT IDENTIFIER ::= { ppp 4 }

          --
          -- The PPP Bridge NCP Group.
          -- Implementation of this group is mandatory for all
          -- PPP implementations that support MAC Bridging  over
          -- PPP (RFC1220).
          --

          -- The following object reflect the values of the option
          -- parameters used in the PPP Link Control Protocol
          --   pppBridgeLocalToRemoteTinygramCompression
          --   pppBridgeRemoteToLocalTinygramCompression
          --   pppBridgeLocalToRemoteLanId
          --   pppBridgeRemoteToLocalLanId
          --
          -- These values are not available until after the PPP Option


          -- negotiation has completed, which is indicated by the link
          -- reaching the open state (i.e. pppBridgeOperStatus is set to
          -- opened).
          --
          -- Therefore, when pppBridgeOperStatus is not opened
          -- the contents of these objects is undefined. The value
          -- returned when accessing the objects is an implementation
          -- dependent issue.

          pppBridgeTable   OBJECT-TYPE
               SYNTAX    SEQUENCE OF PppBridgeEntry
               ACCESS    not-accessible
               STATUS    mandatory
               DESCRIPTION
                         "Table containing the parameters and statistics
                         for the local PPP entity that are related to
                         the operation of Bridging over the PPP."
               ::= { pppBridge 1 }

          pppBridgeEntry   OBJECT-TYPE
               SYNTAX    PppBridgeEntry
               ACCESS    not-accessible
               STATUS    mandatory
               DESCRIPTION
                         "Bridging information for a particular PPP
                         link."
               INDEX     { ifIndex }
               ::= { pppBridgeTable 1 }

          PppBridgeEntry ::= SEQUENCE {
               pppBridgeOperStatus
                    INTEGER,
               pppBridgeLocalToRemoteTinygramCompression
                    INTEGER,
               pppBridgeRemoteToLocalTinygramCompression
                    INTEGER,
               pppBridgeLocalToRemoteLanId
                    INTEGER,
               pppBridgeRemoteToLocalLanId
                    INTEGER
          }

          pppBridgeOperStatus   OBJECT-TYPE
               SYNTAX    INTEGER {opened(1), not-opened(2)}
               ACCESS    read-only


               STATUS    mandatory
               DESCRIPTION
                         "The operational status of the Bridge network
                         protocol. If the value of this object is up
                         then the finite state machine for the Bridge
                         network protocol has reached the Opened state."
               ::= { pppBridgeEntry 1 }

          pppBridgeLocalToRemoteTinygramCompression   OBJECT-TYPE
               SYNTAX    INTEGER { false(1), true(2) }
               ACCESS    read-only
               STATUS    mandatory
               DESCRIPTION
                         "Indicates whether the local node will perform
                         Tinygram Compression when sending packets to
                         the remote entity. If false then the local
                         entity will not perform Tinygram Compression.
                         If true then the local entity will perform
                         Tinygram Compression. The value of this object
                         is meaningful only when the link has reached
                         the open state (pppBridgeOperStatus is
                         opened)."
               REFERENCE
                         "Section 6.7, Tinygram Compression Option, of
                         RFC1220"
               ::= { pppBridgeEntry 2 }

          pppBridgeRemoteToLocalTinygramCompression   OBJECT-TYPE
               SYNTAX    INTEGER { false(1), true(2) }
               ACCESS    read-only
               STATUS    mandatory
               DESCRIPTION
                         "If false(1) then the remote entity is not
                         expected to perform Tinygram Compression. If
                         true then the remote entity is expected to
                         perform Tinygram Compression. The value of this
                         object is meaningful only when the link has
                         reached the open state (pppBridgeOperStatus is
                         opened)."
               REFERENCE
                         "Section 6.7, Tinygram Compression Option, of
                         RFC1220"
               ::= { pppBridgeEntry 3 }


          pppBridgeLocalToRemoteLanId   OBJECT-TYPE
               SYNTAX    INTEGER { false(1), true(2) }
               ACCESS    read-only
               STATUS    mandatory
               DESCRIPTION
                         "Indicates whether the local node will include
                         the LAN Identification field in transmitted
                         packets or not. If false(1) then the local node
                         will not transmit this field, true(2) means
                         that the field will be transmitted. The value
                         of this object is meaningful only when the link
                         has reached the open state (pppBridgeOperStatus
                         is opened)."
               REFERENCE
                         "Section 6.8, LAN Identification Option, of
                         RFC1220"
               ::= { pppBridgeEntry 4 }

          pppBridgeRemoteToLocalLanId   OBJECT-TYPE
               SYNTAX    INTEGER { false(1), true(2) }
               ACCESS    read-only
               STATUS    mandatory
               DESCRIPTION
                         "Indicates whether the remote node has
                         indicated that it will include the LAN
                         Identification field in transmitted packets or
                         not. If false(1) then the field will not be
                         transmitted, if true(2) then the field will be
                         transmitted. The value of this object is
                         meaningful only when the link has reached the
                         open state (pppBridgeOperStatus is opened)."
               REFERENCE
                         "Section 6.8, LAN Identification Option, of
                         RFC1220"
               ::= { pppBridgeEntry 5 }

          --
          -- The PPP Bridge Configuration table
          --

          pppBridgeConfigTable   OBJECT-TYPE
               SYNTAX    SEQUENCE OF PppBridgeConfigEntry
               ACCESS    not-accessible
               STATUS    mandatory
               DESCRIPTION
                         "Table containing the parameters and statistics


                         for the local PPP entity that are related to
                         the operation of Bridging over the PPP."
               ::= { pppBridge 2 }

          pppBridgeConfigEntry   OBJECT-TYPE
               SYNTAX    PppBridgeConfigEntry
               ACCESS    not-accessible
               STATUS    mandatory
               DESCRIPTION
                         "Bridging Configuration information for a
                         particular PPP link."
               INDEX     { ifIndex }
               ::= { pppBridgeConfigTable 1 }

          PppBridgeConfigEntry ::= SEQUENCE {
               pppBridgeConfigAdminStatus
                    INTEGER,
               pppBridgeConfigTinygram
                    INTEGER,
               pppBridgeConfigRingId
                    INTEGER,
               pppBridgeConfigLineId
                    INTEGER,
               pppBridgeConfigLanId
                    INTEGER
          }

          pppBridgeConfigAdminStatus   OBJECT-TYPE
               SYNTAX    INTEGER { open(1), close(2) }
               ACCESS    read-write
               STATUS    mandatory
               DESCRIPTION
                         "The immediate desired status of the Bridging
                         network protocol. Setting this object to open
                         will inject an administrative open event into
                         the Bridging network protocol's finite state
                         machine. Setting this object to close will
                         inject an administrative close event into the
                         Bridging network protocol's finite state
                         machine."
               ::= { pppBridgeConfigEntry 1 }

          pppBridgeConfigTinygram   OBJECT-TYPE
               SYNTAX    INTEGER { false(1), true(2) }


               ACCESS    read-write
               STATUS    mandatory
               DESCRIPTION
                         "If false then the local BNCP entity will not
                         initiate the Tinygram Compression Option
                         Negotiation. If true then the local BNCP entity
                         will initiate negotiation of this option."
               REFERENCE
                         "Section 6.7, Tinygram Compression Option, of
                         RFC1220"
               DEFVAL    { true }
               ::= { pppBridgeConfigEntry 2 }

          pppBridgeConfigRingId   OBJECT-TYPE
               SYNTAX    INTEGER { false(1), true(2) }
               ACCESS    read-write
               STATUS    mandatory
               DESCRIPTION
                         "If false then the local PPP Entity will not
                         initiate a Remote Ring Identification Option
                         negotiation. If true then the local PPP entity
                         will intiate this negotiation. This MIB object
                         is relevant only if the interface is for 802.5
                         Token Ring bridging."
               REFERENCE
                         "Section 6.4, IEEE 802.5 Remote Ring
                         Identification Option, of RFC1220"
               DEFVAL    { false }
               ::= { pppBridgeConfigEntry 3 }

          pppBridgeConfigLineId   OBJECT-TYPE
               SYNTAX    INTEGER { false(1), true(2) }
               ACCESS    read-write
               STATUS    mandatory
               DESCRIPTION
                         "If false then the local PPP Entity is not to
                         initiate a Line Identification Option
                         negotiation. If true then the local PPP entity
                         will intiate this negotiation. This MIB object
                         is relevant only if the interface is for 802.5
                         Token Ring bridging."
               REFERENCE
                         "Section 6.5, IEEE 802.5 Line Identification
                         Option, of RFC1220"
               DEFVAL    { false }
               ::= { pppBridgeConfigEntry 4 }


          pppBridgeConfigLanId   OBJECT-TYPE
               SYNTAX    INTEGER { false(1), true(2) }
               ACCESS    read-write
               STATUS    mandatory
               DESCRIPTION
                         "If false then the local BNCP entity will not
                         initiate the LAN Identification Option
                         Negotiation. If true then the local BNCP entity
                         will initiate negotiation of this option."
               REFERENCE
                         "Section 6.8, LAN Identification Option, of
                         RFC1220"
               DEFVAL    { false }
               ::= { pppBridgeConfigEntry 5 }

          --
          -- The PPP Bridge Media Status Table
          --

          pppBridgeMediaTable   OBJECT-TYPE
               SYNTAX    SEQUENCE OF PppBridgeMediaEntry
               ACCESS    not-accessible
               STATUS    mandatory
               DESCRIPTION
                         "Table identifying which MAC media types are
                         enabled for the Bridging NCPs."
               ::= { pppBridge 3 }

          pppBridgeMediaEntry   OBJECT-TYPE
               SYNTAX    PppBridgeMediaEntry
               ACCESS    not-accessible
               STATUS    mandatory
               DESCRIPTION
                         "Status of a specific MAC Type for a specific
                         PPP Link."
               INDEX     { ifIndex, pppBridgeMediaMacType }
               ::= { pppBridgeMediaTable 1 }

          PppBridgeMediaEntry ::= SEQUENCE {
               pppBridgeMediaMacType
                    INTEGER,
               pppBridgeMediaLocalStatus
                    INTEGER,
               pppBridgeMediaRemoteStatus
                    INTEGER


          }

          pppBridgeMediaMacType   OBJECT-TYPE
               SYNTAX    INTEGER(0..2147483647)
               ACCESS    read-only
               STATUS    mandatory
               DESCRIPTION
                         "The MAC type for which this entry in the
                         pppBridgeMediaTable is providing status
                         information. Valid values for this object are
                         defined in Section 6.6 MAC Type Support
                         Selection of RFC1220 (Bridging Point-to-Point
                         Protocol)."
               REFERENCE
                         "Section 6.6, MAC Type Support Selection, of
                         RFC1212."
               ::= { pppBridgeMediaEntry 1 }

          pppBridgeMediaLocalStatus   OBJECT-TYPE
               SYNTAX    INTEGER { accept(1), dont-accept(2) }
               ACCESS    read-only
               STATUS    mandatory
               DESCRIPTION
                         "Indicates whether the local PPP Bridging
                         Entity will accept packets of the protocol type
                         identified in pppBridgeMediaMacType on the PPP
                         link identified by ifIndex or not. If this
                         object is accept then any packets of the
                         indicated MAC type will be received and
                         properly processed. If this object is dont-
                         accept then received packets of the indicated
                         MAC type will not be properly processed."
               REFERENCE
                         "Section 6.6, MAC Type Support Selection, of
                         RFC1212."
               ::= { pppBridgeMediaEntry 2 }

          pppBridgeMediaRemoteStatus   OBJECT-TYPE
               SYNTAX    INTEGER { accept(1), dont-accept(2) }
               ACCESS    read-only
               STATUS    mandatory
               DESCRIPTION
                         "Indicates whether the local PPP Bridging
                         Entity believes that the remote PPP Bridging
                         Entity will accept packets of the protocol type
                         identified in pppBridgeMediaMacType on the PPP


                         link identified by ifIndex or not."
               REFERENCE
                         "Section 6.6, MAC Type Support Selection, of
                         RFC1212."
               ::= { pppBridgeMediaEntry 3 }

          --
          -- The PPP Bridge Media Configuration Table
          --

          pppBridgeMediaConfigTable   OBJECT-TYPE
               SYNTAX    SEQUENCE OF PppBridgeMediaConfigEntry
               ACCESS    not-accessible
               STATUS    mandatory
               DESCRIPTION
                         "Table identifying which MAC media types are
                         enabled for the Bridging NCPs."
               ::= { pppBridge 4 }

          pppBridgeMediaConfigEntry   OBJECT-TYPE
               SYNTAX    PppBridgeMediaConfigEntry
               ACCESS    not-accessible
               STATUS    mandatory
               DESCRIPTION
                         "Status of a specific MAC Type for a specific
                         PPP Link."
               INDEX     { ifIndex, pppBridgeMediaConfigMacType }
               ::= { pppBridgeMediaConfigTable 1 }

          PppBridgeMediaConfigEntry ::= SEQUENCE {
               pppBridgeMediaConfigMacType
                    INTEGER,
               pppBridgeMediaConfigLocalStatus
                    INTEGER
          }

          pppBridgeMediaConfigMacType   OBJECT-TYPE
               SYNTAX    INTEGER(0..2147483647)
               ACCESS    read-write
               STATUS    mandatory
               DESCRIPTION
                         "The MAC type for which this entry in the
                         pppBridgeMediaConfigTable is providing status
                         information. Valid values for this object are


                         defined in Section 6.6 MAC Type Support
                         Selection of RFC1220 (Bridging Point-to-Point
                         Protocol)."
               REFERENCE
                         "Section 6.6, MAC Type Support Selection, of
                         RFC1212."
               ::= { pppBridgeMediaConfigEntry 1 }

          pppBridgeMediaConfigLocalStatus   OBJECT-TYPE
               SYNTAX    INTEGER { accept(1), dont-accept(2) }
               ACCESS    read-write
               STATUS    mandatory
               DESCRIPTION
                         "Indicates whether the local PPP Bridging
                         Entity should accept packets of the protocol
                         type identified in pppBridgeMediaConfigMacType
                         on the PPP link identified by ifIndex or not.
                         Setting this object to the value dont-accept
                         has the affect of invalidating the
                         corresponding entry in the
                         pppBridgeMediaConfigTable object. It is an
                         implementation-specific matter as to whether
                         the agent removes an invalidated entry from the
                         table. Accordingly, management stations must be
                         prepared to receive tabular information from
                         agents that corresponds to entries not
                         currently in use. Changing this object will
                         have effect when the link is next restarted."
               REFERENCE
                         "Section 6.6, MAC Type Support Selection, of
                         RFC1212."
               ::= { pppBridgeMediaConfigEntry 2 }

END

PDN-HEADER-MIB DEFINITIONS ::= BEGIN

IMPORTS
     enterprises
         FROM RFC1155-SMI;

--     Copyright (C) 1994-2004, Paradyne.  All rights reserved.
--
--     Title: Paradyne Top Level Enterprise Definitions
--
-- =========================================================
-- PdnHeader Version: 8/17/2005
-- =========================================================
--
--     This file may be freely copied and distributed as
--     long as no changes are made to it.
--

pdyn                 OBJECT IDENTIFIER ::= { enterprises 1795 }
pdn-products         OBJECT IDENTIFIER ::= { pdyn 1 }
pdn-mgmt             OBJECT IDENTIFIER ::= { pdyn 2 }

--
--  The NMS/pdnP products subtrees are used for enterprise OIDs
--

-- ========== NMS products ==========

paradyneNMS-products      OBJECT IDENTIFIER ::= { pdn-products 13 }

-- nms-6800-products      OBJECT IDENTIFIER ::= { paradyneNMS-products }

nms-6700-products         OBJECT IDENTIFIER ::= { paradyneNMS-products 2 }

nms-dce-products          OBJECT IDENTIFIER ::= { paradyneNMS-products 3 }

nms-gem-products          OBJECT IDENTIFIER ::= { paradyneNMS-products 4 }
gem-aac-341               OBJECT IDENTIFIER ::= { nms-gem-products 1 }

nms-logical-products      OBJECT IDENTIFIER ::= { paradyneNMS-products 5 }
iso-physical              OBJECT IDENTIFIER ::= { nms-logical-products 1 }
iso-link                  OBJECT IDENTIFIER ::= { nms-logical-products 2 }
iso-network               OBJECT IDENTIFIER ::= { nms-logical-products 3 }
access-router               OBJECT IDENTIFIER ::= { iso-network 1 }
iso-transport             OBJECT IDENTIFIER ::= { nms-logical-products 4 }
iso-session               OBJECT IDENTIFIER ::= { nms-logical-products 5 }
iso-presentation          OBJECT IDENTIFIER ::= { nms-logical-products 6 }
iso-application           OBJECT IDENTIFIER ::= { nms-logical-products 7 }
chassis-manager             OBJECT IDENTIFIER ::= { iso-application 1 }

-- ========== PDN products ==========

paradyne-products         OBJECT IDENTIFIER ::= { pdn-products 14 }

pdn-cellRelay-products   OBJECT IDENTIFIER ::= { paradyne-products 1 }

-- 3000/9000/7000 Series
pdn-snmp-products        OBJECT IDENTIFIER ::= { paradyne-products 2 }

csu                       OBJECT IDENTIFIER ::= { pdn-snmp-products 1 }
t1-3150                     OBJECT IDENTIFIER ::= { csu 1 }
t1-3151                     OBJECT IDENTIFIER ::= { csu 2 }

dsu-csu                   OBJECT IDENTIFIER ::= { pdn-snmp-products 2 }
t1-3160                     OBJECT IDENTIFIER ::= { dsu-csu 1 }
t1-3164                     OBJECT IDENTIFIER ::= { dsu-csu 2 }
t1-3165                     OBJECT IDENTIFIER ::= { dsu-csu 3 }
t1-3161                     OBJECT IDENTIFIER ::= { dsu-csu 4 }
e1-3172                     OBJECT IDENTIFIER ::= { dsu-csu 5 }
e1-3174                     OBJECT IDENTIFIER ::= { dsu-csu 6 }
t1-3162                     OBJECT IDENTIFIER ::= { dsu-csu 7 }
t1-3166                     OBJECT IDENTIFIER ::= { dsu-csu 8 }

ntu                       OBJECT IDENTIFIER ::= { pdn-snmp-products 3 }
e1-3350                     OBJECT IDENTIFIER ::= { ntu 1 }
e1-3360                     OBJECT IDENTIFIER ::= { ntu 2 }
e1-3364                     OBJECT IDENTIFIER ::= { ntu 3 }
e1-3365                     OBJECT IDENTIFIER ::= { ntu 4 }

dev9XXX                   OBJECT IDENTIFIER ::= { pdn-snmp-products 4 }
fr-96XX                   OBJECT IDENTIFIER ::= { dev9XXX 1 }
fr-9620                     OBJECT IDENTIFIER ::= { fr-96XX 1 }
fr-2slot                    OBJECT IDENTIFIER ::= { fr-96XX 2 }
fr-naf                      OBJECT IDENTIFIER ::= { fr-96XX 3 }
fr-nac                      OBJECT IDENTIFIER ::= { fr-96XX 4 }
fr-9624                     OBJECT IDENTIFIER ::= { fr-96XX 5 }
fr-9626                     OBJECT IDENTIFIER ::= { fr-96XX 6 }
fr-9623                     OBJECT IDENTIFIER ::= { fr-96XX 7 }
fr-9624-OS                  OBJECT IDENTIFIER ::= { fr-96XX 8 }

bonaire                   OBJECT IDENTIFIER ::= { dev9XXX 2 }
bonaire-1slot               OBJECT IDENTIFIER ::= { bonaire 1 }
bonaire-2slot               OBJECT IDENTIFIER ::= { bonaire 2 }
bonaire-naf                 OBJECT IDENTIFIER ::= { bonaire 3 }
bonaire-nac                 OBJECT IDENTIFIER ::= { bonaire 4 }

t1-916X                   OBJECT IDENTIFIER ::= { dev9XXX 3 }
t1-1slot                    OBJECT IDENTIFIER ::= { t1-916X 1 }
t1-9162                     OBJECT IDENTIFIER ::= { t1-916X 2 }
t1-9165                     OBJECT IDENTIFIER ::= { t1-916X 3 }
t1-nac                      OBJECT IDENTIFIER ::= { t1-916X 4 }
t1-9262                     OBJECT IDENTIFIER ::= { t1-916X 5 }
t1-9265                     OBJECT IDENTIFIER ::= { t1-916X 6 }
t1-9161                     OBJECT IDENTIFIER ::= { t1-916X 7 }
t1-9261                     OBJECT IDENTIFIER ::= { t1-916X 8 }

t1fr-912X                 OBJECT IDENTIFIER ::= { dev9XXX 4 }
t1fr-9121                   OBJECT IDENTIFIER ::= { t1fr-912X 1 }
t1fr-2slot                  OBJECT IDENTIFIER ::= { t1fr-912X 2 }
t1fr-naf                    OBJECT IDENTIFIER ::= { t1fr-912X 3 }
t1fr-nac                    OBJECT IDENTIFIER ::= { t1fr-912X 4 }
t1fr-9124                   OBJECT IDENTIFIER ::= { t1fr-912X 5 }
t1fr-9124-NNI               OBJECT IDENTIFIER ::= { t1fr-912X 6 }
t1fr-9126                   OBJECT IDENTIFIER ::= { t1fr-912X 7 }
t1fr-9128                   OBJECT IDENTIFIER ::= { t1fr-912X 8 }
t1fr-9124-II                OBJECT IDENTIFIER ::= { t1fr-912X 9 }
t1fr-9124-L                 OBJECT IDENTIFIER ::= { t1fr-912X 10 }
t1fr-9123                   OBJECT IDENTIFIER ::= { t1fr-912X 11 }
t1fr-9124-OS                OBJECT IDENTIFIER ::= { t1fr-912X 12 }

atm-95XX                  OBJECT IDENTIFIER ::= { dev9XXX 5 }
atm-9580                    OBJECT IDENTIFIER ::= { atm-95XX 1 }
atm-9520-ilm                OBJECT IDENTIFIER ::= { atm-95XX 2 }
atm-9520                    OBJECT IDENTIFIER ::= { atm-95XX 3 }

msa-919X                  OBJECT IDENTIFIER ::= { dev9XXX 6 }
msa-9192                    OBJECT IDENTIFIER ::= { msa-919X 1 }
msa-9195                    OBJECT IDENTIFIER ::= { msa-919X 2 }
msa-9292                    OBJECT IDENTIFIER ::= { msa-919X 3 }
msa-9295                    OBJECT IDENTIFIER ::= { msa-919X 4 }

int-98XX                  OBJECT IDENTIFIER ::= { dev9XXX 7 }
int-9820                    OBJECT IDENTIFIER ::= { int-98XX 1 }
int-9820-C                  OBJECT IDENTIFIER ::= { int-98XX 2 }
int-9820-8M                 OBJECT IDENTIFIER ::= { int-98XX 3 }
int-9820-45M                OBJECT IDENTIFIER ::= { int-98XX 4 }

nni-9XXX                  OBJECT IDENTIFIER ::= { dev9XXX 8 }
nni-9110                    OBJECT IDENTIFIER ::= { nni-9XXX 1 }

msdsl-9XXX                OBJECT IDENTIFIER ::= { dev9XXX 9 }
msdsl-9723                  OBJECT IDENTIFIER ::= { msdsl-9XXX 1 }
msdsl-9783                  OBJECT IDENTIFIER ::= { msdsl-9XXX 2 }
msdsl-9720                  OBJECT IDENTIFIER ::= { msdsl-9XXX 3 }
msdsl-9788                  OBJECT IDENTIFIER ::= { msdsl-9XXX 4 }

isdn-9XXX                 OBJECT IDENTIFIER ::= { dev9XXX 10 }
isdn-9664                   OBJECT IDENTIFIER ::= { isdn-9XXX 1 }

rtr-9XXX                  OBJECT IDENTIFIER ::= { dev9XXX 11 }
rtr-9783                    OBJECT IDENTIFIER ::= { rtr-9XXX 1 }
rtr-9720                    OBJECT IDENTIFIER ::= { rtr-9XXX 2 }
rtr-9788                    OBJECT IDENTIFIER ::= { rtr-9XXX 3 }
rtr-9126                    OBJECT IDENTIFIER ::= { rtr-9XXX 4 }
rtr-9123                    OBJECT IDENTIFIER ::= { rtr-9XXX 5 }
rtr-9623                    OBJECT IDENTIFIER ::= { rtr-9XXX 6 }

t1-7XXX                   OBJECT IDENTIFIER ::= { dev9XXX 12 }
t1-7123                     OBJECT IDENTIFIER ::= { t1-7XXX 1 }
 
dev7XXX                   OBJECT IDENTIFIER ::= { pdn-snmp-products 5 }
dds-76XX                    OBJECT IDENTIFIER ::= { dev7XXX 1 }
dds-7610                      OBJECT IDENTIFIER ::= { dds-76XX 1 }
dds-7612                      OBJECT IDENTIFIER ::= { dds-76XX 2 }
dds-7613                      OBJECT IDENTIFIER ::= { dds-76XX 3 }
t1-71XX                     OBJECT IDENTIFIER ::= { dev7XXX 2 }
t1-7110                       OBJECT IDENTIFIER ::= { t1-71XX 1 }
t1-7112                       OBJECT IDENTIFIER ::= { t1-71XX 2 }

-- 3600 Series
pdn-36xx-products        OBJECT IDENTIFIER ::= { paradyne-products 3 }

-- ACCULINK Access Controller
pdn-aac-products         OBJECT IDENTIFIER ::= { paradyne-products 4 }
aac-34                    OBJECT IDENTIFIER ::= { pdn-aac-products 1 }

aac-34X                   OBJECT IDENTIFIER ::= { pdn-aac-products 2 }
aac-FL                      OBJECT IDENTIFIER ::= { aac-34X 1 }
aac-UE                      OBJECT IDENTIFIER ::= { aac-34X 2 }
aac-FP                      OBJECT IDENTIFIER ::= { aac-34X 3 }
aac-300                     OBJECT IDENTIFIER ::= { aac-34X 4 }

aac-cards                 OBJECT IDENTIFIER ::= { pdn-aac-products 3 }
aac-frs                     OBJECT IDENTIFIER ::= { aac-cards 1 }
aac-ipc                     OBJECT IDENTIFIER ::= { aac-cards 2 }
aac-atm                     OBJECT IDENTIFIER ::= { aac-cards 3 }

aac-4X                    OBJECT IDENTIFIER ::= { pdn-aac-products 4 }
aac-4XFL                    OBJECT IDENTIFIER ::= { aac-4X 1 }
aac-4XUE                    OBJECT IDENTIFIER ::= { aac-4X 2 }
aac-4XFP                    OBJECT IDENTIFIER ::= { aac-4X 3 }
aac-4X300                   OBJECT IDENTIFIER ::= { aac-4X 4 }

-- Common
pdn-common-products      OBJECT IDENTIFIER ::= { paradyne-products 5 }
pdn-testOIDs               OBJECT IDENTIFIER ::= { pdn-common-products 1 }
pdnLoopbackTest            OBJECT IDENTIFIER ::= { pdn-testOIDs 1 }
pdnBertTest                OBJECT IDENTIFIER ::= { pdn-testOIDs 2 }
pdnPingTest                OBJECT IDENTIFIER ::= { pdn-testOIDs 3 }
pdnTraceRouteTest          OBJECT IDENTIFIER ::= { pdn-testOIDs 4 }
pdnBlertTest	           OBJECT IDENTIFIER ::= { pdn-testOIDs 5 }

-- Eagle
pdn-eagle-products       OBJECT IDENTIFIER ::= { paradyne-products 6 }

-- Access Router
pdn-ar-products          OBJECT IDENTIFIER ::= { paradyne-products 7 }
ar-541                      OBJECT IDENTIFIER ::= { pdn-ar-products 1 }
ar-611                      OBJECT IDENTIFIER ::= { pdn-ar-products 2 }
ar-621                      OBJECT IDENTIFIER ::= { pdn-ar-products 3 }
ar-641                      OBJECT IDENTIFIER ::= { pdn-ar-products 4 }
ar-712                      OBJECT IDENTIFIER ::= { pdn-ar-products 5 }
ar-722                      OBJECT IDENTIFIER ::= { pdn-ar-products 6 }
ar-928                      OBJECT IDENTIFIER ::= { pdn-ar-products 7 }
ar-711                      OBJECT IDENTIFIER ::= { pdn-ar-products 8 }

-- Access Server
pdn-as-products          OBJECT IDENTIFIER ::= { paradyne-products 8 }
as-4                        OBJECT IDENTIFIER ::= { pdn-as-products 1 }
as-8                        OBJECT IDENTIFIER ::= { pdn-as-products 2 }
as-24                       OBJECT IDENTIFIER ::= { pdn-as-products 3 }

-- xDSL
pdn-xdsl-products        OBJECT IDENTIFIER ::= { paradyne-products 9 }
xdsl-5100                   OBJECT IDENTIFIER ::= { pdn-xdsl-products 1 }
xdsl-unused1                OBJECT IDENTIFIER ::= { pdn-xdsl-products 2 }
xdsl-8800-old               OBJECT IDENTIFIER ::= { pdn-xdsl-products 3 }
xdsl-unused2                OBJECT IDENTIFIER ::= { pdn-xdsl-products 4 }
xdsl-8600-old               OBJECT IDENTIFIER ::= { pdn-xdsl-products 5 }
xdsl-ipc                    OBJECT IDENTIFIER ::= { pdn-xdsl-products 6 }
xdsl-8100                     OBJECT IDENTIFIER ::= { xdsl-ipc 1 }
xdsl-8200                     OBJECT IDENTIFIER ::= { xdsl-ipc 2 }
xdsl-chassis                OBJECT IDENTIFIER ::= { pdn-xdsl-products 8 }
xdsl-8600                     OBJECT IDENTIFIER ::= { xdsl-chassis 1 }
xdsl-8800                     OBJECT IDENTIFIER ::= { xdsl-chassis 2 }
xdsl-8610                     OBJECT IDENTIFIER ::= { xdsl-chassis 3 }
xdsl-8810                     OBJECT IDENTIFIER ::= { xdsl-chassis 4 }
xdsl-8820                     OBJECT IDENTIFIER ::= { xdsl-chassis 5 }
xdsl-8610-X                   OBJECT IDENTIFIER ::= { xdsl-chassis 6 }
xdsl-8810-X                   OBJECT IDENTIFIER ::= { xdsl-chassis 7 }
xdsl-8820-X                   OBJECT IDENTIFIER ::= { xdsl-chassis 8 }
xdsl-8620                     OBJECT IDENTIFIER ::= { xdsl-chassis 9 }
xdsl-remote                 OBJECT IDENTIFIER ::= { pdn-xdsl-products 9 }
xdsl-5446                     OBJECT IDENTIFIER ::= { xdsl-remote 1 }
xdsl-7914                     OBJECT IDENTIFIER ::= { xdsl-remote 2 }
xdsl-5246                     OBJECT IDENTIFIER ::= { xdsl-remote 3 }
xdsl-5216                     OBJECT IDENTIFIER ::= { xdsl-remote 4 }
xdsl-5170                     OBJECT IDENTIFIER ::= { xdsl-remote 5 }
xdsl-5171                     OBJECT IDENTIFIER ::= { xdsl-remote 6 }
xdsl-5546                     OBJECT IDENTIFIER ::= { xdsl-remote 7 }
xdsl-5620                     OBJECT IDENTIFIER ::= { xdsl-remote 8 }
xdsl-6310                     OBJECT IDENTIFIER ::= { xdsl-remote 9 }
xdsl-7975                     OBJECT IDENTIFIER ::= { xdsl-remote 10 }
xdsl-7976                     OBJECT IDENTIFIER ::= { xdsl-remote 11 }
xdsl-7974                     OBJECT IDENTIFIER ::= { xdsl-remote 12 }
xdsl-7986                     OBJECT IDENTIFIER ::= { xdsl-remote 13 }
xdsl-7985                     OBJECT IDENTIFIER ::= { xdsl-remote 14 }
xdsl-7984                     OBJECT IDENTIFIER ::= { xdsl-remote 15 }
xdsl-6341                     OBJECT IDENTIFIER ::= { xdsl-remote 16 }
xdsl-6342                     OBJECT IDENTIFIER ::= { xdsl-remote 17 }
xdsl-6331                     OBJECT IDENTIFIER ::= { xdsl-remote 18 }
xdsl-6332                     OBJECT IDENTIFIER ::= { xdsl-remote 19 }
xdsl-6371                     OBJECT IDENTIFIER ::= { xdsl-remote 20 }
xdsl-6372                     OBJECT IDENTIFIER ::= { xdsl-remote 21 }
xdsl-6321                     OBJECT IDENTIFIER ::= { xdsl-remote 23 }
xdsl-6322                     OBJECT IDENTIFIER ::= { xdsl-remote 24 }
xdsl-6341R2                   OBJECT IDENTIFIER ::= { xdsl-remote 25 }
xdsl-6342R2                   OBJECT IDENTIFIER ::= { xdsl-remote 26 }
xdsl-6331R2                   OBJECT IDENTIFIER ::= { xdsl-remote 27 }
xdsl-6332R2                   OBJECT IDENTIFIER ::= { xdsl-remote 28 }
xdsl-6371R2                   OBJECT IDENTIFIER ::= { xdsl-remote 29 }
xdsl-6372R2                   OBJECT IDENTIFIER ::= { xdsl-remote 30 }
xdsl-6321R2                   OBJECT IDENTIFIER ::= { xdsl-remote 31 }
xdsl-6322R2                   OBJECT IDENTIFIER ::= { xdsl-remote 32 }
xdsl-6328                     OBJECT IDENTIFIER ::= { xdsl-remote 33 } -- unused
xdsl-6329                     OBJECT IDENTIFIER ::= { xdsl-remote 34 } -- unused
xdsl-6301R2                   OBJECT IDENTIFIER ::= { xdsl-remote 35 }
xdsl-6302R2                   OBJECT IDENTIFIER ::= { xdsl-remote 36 }
xdsl-6350                     OBJECT IDENTIFIER ::= { xdsl-remote 38 }
xdsl-6351                     OBJECT IDENTIFIER ::= { xdsl-remote 39 }
xdsl-6385                     OBJECT IDENTIFIER ::= { xdsl-remote 40 }
xdsl-7994                     OBJECT IDENTIFIER ::= { xdsl-remote 41 }
xdsl-7995                     OBJECT IDENTIFIER ::= { xdsl-remote 42 }
xdsl-7996                     OBJECT IDENTIFIER ::= { xdsl-remote 43 }
xdsl-cards                    OBJECT IDENTIFIER ::= { pdn-xdsl-products 10 }
card-mcc                      OBJECT IDENTIFIER ::= { xdsl-cards 1 }
card-adsl                     OBJECT IDENTIFIER ::= { xdsl-cards 2 } -- unused
card-radsl                    OBJECT IDENTIFIER ::= { xdsl-cards 3 }
card-sdsl                     OBJECT IDENTIFIER ::= { xdsl-cards 4 } -- unused
card-vdsl                     OBJECT IDENTIFIER ::= { xdsl-cards 5 } -- unused
card-8774                     OBJECT IDENTIFIER ::= { xdsl-cards 6 }
card-8540                     OBJECT IDENTIFIER ::= { xdsl-cards 7 }
card-8775                     OBJECT IDENTIFIER ::= { xdsl-cards 8 }
card-8776                     OBJECT IDENTIFIER ::= { xdsl-cards 9 }
card-8786                     OBJECT IDENTIFIER ::= { xdsl-cards 10 }
card-8946                     OBJECT IDENTIFIER ::= { xdsl-cards 11 }
card-8510                     OBJECT IDENTIFIER ::= { xdsl-cards 12 }
card-8310                     OBJECT IDENTIFIER ::= { xdsl-cards 13 }
card-e1-sdsl                  OBJECT IDENTIFIER ::= { xdsl-cards 14 }
card-mcc2                     OBJECT IDENTIFIER ::= { xdsl-cards 15 }
card-8785                     OBJECT IDENTIFIER ::= { xdsl-cards 16 }
card-8784                     OBJECT IDENTIFIER ::= { xdsl-cards 17 }
card-8312                     OBJECT IDENTIFIER ::= { xdsl-cards 18 }
card-8344                     OBJECT IDENTIFIER ::= { xdsl-cards 19 }
card-mcc-plus                 OBJECT IDENTIFIER ::= { xdsl-cards 20 }
card-mcp                      OBJECT IDENTIFIER ::= { xdsl-cards 21 }
card-8334                     OBJECT IDENTIFIER ::= { xdsl-cards 22 }
card-xxxx                     OBJECT IDENTIFIER ::= { xdsl-cards 23 }
card-8343                     OBJECT IDENTIFIER ::= { xdsl-cards 24 }
card-8333                     OBJECT IDENTIFIER ::= { xdsl-cards 25 }
card-8719                     OBJECT IDENTIFIER ::= { xdsl-cards 26 }
card-8747                     OBJECT IDENTIFIER ::= { xdsl-cards 27 }
card-8777                     OBJECT IDENTIFIER ::= { xdsl-cards 28 }
card-8779                     OBJECT IDENTIFIER ::= { xdsl-cards 29 }
card-8021                     OBJECT IDENTIFIER ::= { xdsl-cards 30 }
card-8022                     OBJECT IDENTIFIER ::= { xdsl-cards 31 }
card-8373                     OBJECT IDENTIFIER ::= { xdsl-cards 32 }
card-8374                     OBJECT IDENTIFIER ::= { xdsl-cards 33 }
card-8323                     OBJECT IDENTIFIER ::= { xdsl-cards 34 }
card-8324                     OBJECT IDENTIFIER ::= { xdsl-cards 35 }
card-8023                     OBJECT IDENTIFIER ::= { xdsl-cards 36 }
card-8024                     OBJECT IDENTIFIER ::= { xdsl-cards 37 }
card-8335                     OBJECT IDENTIFIER ::= { xdsl-cards 38 }
card-8365                     OBJECT IDENTIFIER ::= { xdsl-cards 39 }
card-83xx                     OBJECT IDENTIFIER ::= { xdsl-cards 40 }
card-8314                     OBJECT IDENTIFIER ::= { xdsl-cards 41 }
card-8328                     OBJECT IDENTIFIER ::= { xdsl-cards 42 }
card-8329                     OBJECT IDENTIFIER ::= { xdsl-cards 43 }
card-8303                     OBJECT IDENTIFIER ::= { xdsl-cards 44 }
card-8304                     OBJECT IDENTIFIER ::= { xdsl-cards 45 }
card-8025                     OBJECT IDENTIFIER ::= { xdsl-cards 46 }
card-8026                     OBJECT IDENTIFIER ::= { xdsl-cards 47 }
card-8027                     OBJECT IDENTIFIER ::= { xdsl-cards 48 }
card-8028                     OBJECT IDENTIFIER ::= { xdsl-cards 49 }
card-8379                     OBJECT IDENTIFIER ::= { xdsl-cards 50 }
card-8312-ReachDSL            OBJECT IDENTIFIER ::= { xdsl-cards 51 }
card-8314-ReachDSL            OBJECT IDENTIFIER ::= { xdsl-cards 52 }
card-8385                     OBJECT IDENTIFIER ::= { xdsl-cards 53 }
card-8395                     OBJECT IDENTIFIER ::= { xdsl-cards 54 }
card-8396                     OBJECT IDENTIFIER ::= { xdsl-cards 55 }
card-8797                     OBJECT IDENTIFIER ::= { xdsl-cards 56 }
card-8799                     OBJECT IDENTIFIER ::= { xdsl-cards 57 }
card-8355                     OBJECT IDENTIFIER ::= { xdsl-cards 58 }
card-mcp8900                  OBJECT IDENTIFIER ::= { xdsl-cards 59 }
card-8375                     OBJECT IDENTIFIER ::= { xdsl-cards 60 }
xdsl-ports                  OBJECT IDENTIFIER ::= { pdn-xdsl-products 11 }
port-dsl                      OBJECT IDENTIFIER ::= { xdsl-ports 1 }
port-mvl                      OBJECT IDENTIFIER ::= { xdsl-ports 2 }
port-eth10                    OBJECT IDENTIFIER ::= { xdsl-ports 3 }
port-eth100                   OBJECT IDENTIFIER ::= { xdsl-ports 4 }
port-oc3                      OBJECT IDENTIFIER ::= { xdsl-ports 5 }
port-ds3                      OBJECT IDENTIFIER ::= { xdsl-ports 6 }
port-sar                      OBJECT IDENTIFIER ::= { xdsl-ports 7 }
port-hdlc                     OBJECT IDENTIFIER ::= { xdsl-ports 8 }
port-e3                       OBJECT IDENTIFIER ::= { xdsl-ports 9 }
port-ds1                      OBJECT IDENTIFIER ::= { xdsl-ports 10 }
port-e1                       OBJECT IDENTIFIER ::= { xdsl-ports 11 }
port-ima                      OBJECT IDENTIFIER ::= { xdsl-ports 12 }
port-reachDsl                 OBJECT IDENTIFIER ::= { xdsl-ports 13 }
port-reachDslV3		      OBJECT IDENTIFIER ::= { xdsl-ports 14 }
port-adsl-r		      OBJECT IDENTIFIER ::= { xdsl-ports 15 }
xdsl-slots                  OBJECT IDENTIFIER ::= { pdn-xdsl-products 12 }
slot-std                      OBJECT IDENTIFIER ::= { xdsl-slots 1 }
xdsl-components             OBJECT IDENTIFIER ::= { pdn-xdsl-products 13 }
comp-powerA                   OBJECT IDENTIFIER ::= { xdsl-components 1 }
comp-powerB                   OBJECT IDENTIFIER ::= { xdsl-components 2 }
comp-fan                      OBJECT IDENTIFIER ::= { xdsl-components 3 }
comp-mgmt                     OBJECT IDENTIFIER ::= { xdsl-components 4 }
comp-atm                      OBJECT IDENTIFIER ::= { xdsl-components 5 }
comp-pld                      OBJECT IDENTIFIER ::= { xdsl-components 6 }
comp-sensor                   OBJECT IDENTIFIER ::= { xdsl-components 7 }

-- SME  -begin

xdsl-sme	       	OBJECT IDENTIFIER ::= { pdn-xdsl-products 14 }

sme-scp-cards		 OBJECT IDENTIFIER ::= { xdsl-sme 1}
sme-scp-8412-card	  OBJECT IDENTIFIER ::= { sme-scp-cards 1}
sme-scp-8413-card	  OBJECT IDENTIFIER ::= { sme-scp-cards 2}
sme-scp-8414-card	  OBJECT IDENTIFIER ::= { sme-scp-cards 3}
sme-scp-8416-card	  OBJECT IDENTIFIER ::= { sme-scp-cards 4}
sme-scp-8417-card	  OBJECT IDENTIFIER ::= { sme-scp-cards 5}
sme-scp-8418-card	  OBJECT IDENTIFIER ::= { sme-scp-cards 6}
sme-scp-8411-card	  OBJECT IDENTIFIER ::= { sme-scp-cards 7}
sme-scp-8429-card	  OBJECT IDENTIFIER ::= { sme-scp-cards 8}
sme-scp-8415-card	  OBJECT IDENTIFIER ::= { sme-scp-cards 9}

sme-childcards		 OBJECT IDENTIFIER ::= { xdsl-sme 2}
sme-t1e1-uplink-child	  OBJECT IDENTIFIER ::= { sme-childcards 1}
sme-t3e3-uplink-child	  OBJECT IDENTIFIER ::= { sme-childcards 2}
sme-ether-uplink-child	  OBJECT IDENTIFIER ::= { sme-childcards 3}
sme-int-splitter	  OBJECT IDENTIFIER ::= { sme-childcards 4}

sme-ports		 OBJECT IDENTIFIER ::= { xdsl-sme 3}
sme-reachDsl-port	  OBJECT IDENTIFIER ::= { sme-ports 1}
sme-adsl-a-port		  OBJECT IDENTIFIER ::= { sme-ports 2}
sme-adsl-b-port		  OBJECT IDENTIFIER ::= { sme-ports 3}
sme-shdsl-port		  OBJECT IDENTIFIER ::= { sme-ports 4}
sme-t1e1-port		  OBJECT IDENTIFIER ::= { sme-ports 5}
sme-oc3-port		  OBJECT IDENTIFIER ::= { sme-ports 6}
sme-rs232-port		  OBJECT IDENTIFIER ::= { sme-ports 7}
sme-eth-port		  OBJECT IDENTIFIER ::= { sme-ports 8}
sme-ds3-port              OBJECT IDENTIFIER ::= { sme-ports 9}
sme-pots-port             OBJECT IDENTIFIER ::= { sme-ports 10}
sme-adsl-r-port           OBJECT IDENTIFIER ::= { sme-ports 11}

sme-portcards		 OBJECT IDENTIFIER ::= { xdsl-sme 4}
sme-8965-card	  	  OBJECT IDENTIFIER ::= { sme-portcards 1}
sme-8955-card	  	  OBJECT IDENTIFIER ::= { sme-portcards 2}
sme-8985-card	  	  OBJECT IDENTIFIER ::= { sme-portcards 3}
sme-8995-card	  	  OBJECT IDENTIFIER ::= { sme-portcards 4}
sme-8968-card	  	  OBJECT IDENTIFIER ::= { sme-portcards 5}
sme-8915-card	  	  OBJECT IDENTIFIER ::= { sme-portcards 6}
sme-8975-card	  	  OBJECT IDENTIFIER ::= { sme-portcards 7}
sme-8922-card	  	  OBJECT IDENTIFIER ::= { sme-portcards 8}
sme-8997-card	  	  OBJECT IDENTIFIER ::= { sme-portcards 9}
sme-8922-card-ip  	  OBJECT IDENTIFIER ::= { sme-portcards 10}
sme-8995-B2-card-ip  	  OBJECT IDENTIFIER ::= { sme-portcards 11}
sme-8997-B2-card-ip  	  OBJECT IDENTIFIER ::= { sme-portcards 12}

sme-chassis		 OBJECT IDENTIFIER ::= { xdsl-sme 5}
sme-chassis-8820	 OBJECT IDENTIFIER ::= { sme-chassis 1} -- atm
sme-chassis-8620	 OBJECT IDENTIFIER ::= { sme-chassis 2} -- atm
sme-chassis-8820-ip	 OBJECT IDENTIFIER ::= { sme-chassis 3} -- ip
sme-chassis-8620-ip	 OBJECT IDENTIFIER ::= { sme-chassis 4} -- ip

sme-components		 OBJECT IDENTIFIER ::= { xdsl-sme 6}
sme-comp-fan		 OBJECT IDENTIFIER ::= { sme-components 1}
sme-comp-pld		 OBJECT IDENTIFIER ::= { sme-components 2}
sme-comp-sensor		 OBJECT IDENTIFIER ::= { sme-components 3}
sme-comp-powersupply	 OBJECT IDENTIFIER ::= { sme-components 4}
sme-comp-sfp		 OBJECT IDENTIFIER ::= { sme-components 5}


sme-container		 OBJECT IDENTIFIER ::= { xdsl-sme 7}

-- SME -end

-- Compression
pdn-comp-products        OBJECT IDENTIFIER ::= { paradyne-products 10 }
comp-9028                   OBJECT IDENTIFIER ::= { pdn-comp-products 1 }

-- PTC
pdn-ptc-products         OBJECT IDENTIFIER ::= { paradyne-products 11 }
xdsl-xdsl                   OBJECT IDENTIFIER ::= { pdn-ptc-products 1 }

-- DSL Router Endpoint (not used?)
pdnDslEndpoint           OBJECT IDENTIFIER ::= { paradyne-products 12 }

-- (reserved)
reserved13               OBJECT IDENTIFIER ::= { paradyne-products 13 }
reserved14               OBJECT IDENTIFIER ::= { paradyne-products 14 }

-- CellSaver
pdn-cellsaver            OBJECT IDENTIFIER ::= { paradyne-products 15 }
cellsaver-9510              OBJECT IDENTIFIER ::= { pdn-cellsaver 1 }
cellsaver-9550              OBJECT IDENTIFIER ::= { pdn-cellsaver 2 }

-- Cornet
pdn-cornet              OBJECT IDENTIFIER ::= { paradyne-products 16 }
cornet-xxxx                 OBJECT IDENTIFIER ::= { pdn-cornet 1 }

--
-- IP Stackable  i.e. Speedway/Bitstorm and GranDSLAM IP
--    ips refers to IP Stackable
--
ip-stackable            OBJECT IDENTIFIER ::= { paradyne-products 17 }
ips-stack                 OBJECT IDENTIFIER ::= { ip-stackable 1 }
ips-4800                    OBJECT IDENTIFIER ::= { ips-stack 1 }
ips-2600                    OBJECT IDENTIFIER ::= { ips-stack 2 }
ips-4200                    OBJECT IDENTIFIER ::= { ips-stack 3 }

ips-chassis               OBJECT IDENTIFIER ::= { ip-stackable 2 }
ips-4821                    OBJECT IDENTIFIER ::= { ips-chassis 1 }
ips-2611                    OBJECT IDENTIFIER ::= { ips-chassis 2 }
ips-2621                    OBJECT IDENTIFIER ::= { ips-chassis 3 }
ips-4219                    OBJECT IDENTIFIER ::= { ips-chassis 4 }
ips-4229                    OBJECT IDENTIFIER ::= { ips-chassis 5 }
ips-2671                    OBJECT IDENTIFIER ::= { ips-chassis 6 }
ips-4279                    OBJECT IDENTIFIER ::= { ips-chassis 7 }
ips-2620                    OBJECT IDENTIFIER ::= { ips-chassis 8 }
ips-2631                    OBJECT IDENTIFIER ::= { ips-chassis 9 }
ips-4239                    OBJECT IDENTIFIER ::= { ips-chassis 10 }
ips-4214                    OBJECT IDENTIFIER ::= { ips-chassis 11 }
ips-4224                    OBJECT IDENTIFIER ::= { ips-chassis 12 }
ips-4234                    OBJECT IDENTIFIER ::= { ips-chassis 13 }
ips-4274                    OBJECT IDENTIFIER ::= { ips-chassis 14 }
ips-2614                    OBJECT IDENTIFIER ::= { ips-chassis 15 }
ips-2624                    OBJECT IDENTIFIER ::= { ips-chassis 16 }
ips-2634                    OBJECT IDENTIFIER ::= { ips-chassis 17 }
ips-2674                    OBJECT IDENTIFIER ::= { ips-chassis 18 }

ips-fixed-cards           OBJECT IDENTIFIER ::= { ip-stackable 3 }
ips-24port-adsl-main-card          OBJECT IDENTIFIER ::= { ips-fixed-cards 1 }
ips-24port-adsl-child-card         OBJECT IDENTIFIER ::= { ips-fixed-cards 2 }
ips-maui-card                      OBJECT IDENTIFIER ::= { ips-fixed-cards 3 }
ips-pots-splitter-child-card       OBJECT IDENTIFIER ::= { ips-fixed-cards 4 }
ips-24port-reachDsl-main-card      OBJECT IDENTIFIER ::= { ips-fixed-cards 5 }
ips-24port-reachDsl-child-card     OBJECT IDENTIFIER ::= { ips-fixed-cards 6 }
ips-24port-shdsl-main-card         OBJECT IDENTIFIER ::= { ips-fixed-cards 7 }
ips-24port-shdsl-child-card        OBJECT IDENTIFIER ::= { ips-fixed-cards 8 }
ips-48port-adsl-main-card          OBJECT IDENTIFIER ::= { ips-fixed-cards 9 }

ips-pluggable-cards       OBJECT IDENTIFIER ::= { ip-stackable 4 }
ips-mgmt-no-wan                 OBJECT IDENTIFIER ::= { ips-pluggable-cards 1 }
ips-mgmt-with-v35x21-wan        OBJECT IDENTIFIER ::= { ips-pluggable-cards 2 }
ips-mgmt-with-t1e1-mlppp-wan    OBJECT IDENTIFIER ::= { ips-pluggable-cards 3 }
ips-mgmt-with-t1e1-ima-wan      OBJECT IDENTIFIER ::= { ips-pluggable-cards 4 }

ips-ports                 OBJECT IDENTIFIER ::= { ip-stackable 5 }
ips-rs232-dte-port          OBJECT IDENTIFIER ::= { ips-ports 1 }
ips-rs232-dce-port          OBJECT IDENTIFIER ::= { ips-ports 2 }
ips-v35-dte-port            OBJECT IDENTIFIER ::= { ips-ports 3 }
ips-adsl-port               OBJECT IDENTIFIER ::= { ips-ports 4 }
ips-ethernet-port           OBJECT IDENTIFIER ::= { ips-ports 5 }
ips-t1e1-port               OBJECT IDENTIFIER ::= { ips-ports 6 }
ips-adsl-a-port             OBJECT IDENTIFIER ::= { ips-ports 7 }
ips-reachDsl-port           OBJECT IDENTIFIER ::= { ips-ports 8 }
ips-shdsl-port              OBJECT IDENTIFIER ::= { ips-ports 9 }
ips-adsl-b-port             OBJECT IDENTIFIER ::= { ips-ports 10 }

ips-components            OBJECT IDENTIFIER ::= { ip-stackable 6 }
ips-fan                     OBJECT IDENTIFIER ::= { ips-components 1 }
                            -- Probably should use ips-speed-sensor
ips-temperature-sensor      OBJECT IDENTIFIER ::= { ips-components 2 }
ips-processor               OBJECT IDENTIFIER ::= { ips-components 3 }
ips-pld                     OBJECT IDENTIFIER ::= { ips-components 4 }
ips-speed-sensor            OBJECT IDENTIFIER ::= { ips-components 5 }
ips-alarm-relay-contact     OBJECT IDENTIFIER ::= { ips-components 6 }

ips-dot1dBasePortCircuit OBJECT IDENTIFIER ::= { ip-stackable 7 }
                           -- Priority Interworking Groups (PIWGs)
ips-piwg-1                 OBJECT IDENTIFIER ::= { ips-dot1dBasePortCircuit 1 }
ips-piwg-2                 OBJECT IDENTIFIER ::= { ips-dot1dBasePortCircuit 2 }
ips-piwg-3                 OBJECT IDENTIFIER ::= { ips-dot1dBasePortCircuit 3 }
ips-piwg-4                 OBJECT IDENTIFIER ::= { ips-dot1dBasePortCircuit 4 }
ips-piwg-5                 OBJECT IDENTIFIER ::= { ips-dot1dBasePortCircuit 5 }
ips-piwg-6                 OBJECT IDENTIFIER ::= { ips-dot1dBasePortCircuit 6 }
ips-piwg-7                 OBJECT IDENTIFIER ::= { ips-dot1dBasePortCircuit 7 }
ips-piwg-8                 OBJECT IDENTIFIER ::= { ips-dot1dBasePortCircuit 8 }


--
-- New Tree for EtherLoop
--

etherloop             OBJECT IDENTIFIER ::= { paradyne-products 18 }
eloop-shelf             OBJECT IDENTIFIER ::= { etherloop 1 }
eloop-2400                OBJECT IDENTIFIER ::= { eloop-shelf 1 }

eloop-unit            OBJECT IDENTIFIER ::= { etherloop 2 }
eloop-2461              OBJECT IDENTIFIER ::= { eloop-unit 1 }

eloop-modem-stick     OBJECT IDENTIFIER ::= { etherloop 3 }

eloop-intf-card       OBJECT IDENTIFIER ::= { etherloop 4 }

eloop-switch-card     OBJECT IDENTIFIER ::= { etherloop 5 }

--
-- ATM Stackable  i.e. 4200
--    atm-stk refers to ATM Stackable
--
atm-stackable          OBJECT IDENTIFIER ::= { paradyne-products 19 }

atmstk-stack            OBJECT IDENTIFIER ::= { atm-stackable 1 }
atmstk-4200                OBJECT IDENTIFIER ::= { atmstk-stack 1 }

atmstk-chassis          OBJECT IDENTIFIER ::= { atm-stackable 2 }
atmstk-4216                OBJECT IDENTIFIER ::= { atmstk-chassis 1 }
atmstk-4218                OBJECT IDENTIFIER ::= { atmstk-chassis 2 }
atmstk-4210                OBJECT IDENTIFIER ::= { atmstk-chassis 3 }
atmstk-4211                OBJECT IDENTIFIER ::= { atmstk-chassis 4 }
atmstk-4212                OBJECT IDENTIFIER ::= { atmstk-chassis 5 }
atmstk-4213                OBJECT IDENTIFIER ::= { atmstk-chassis 6 }
atmstk-4221                OBJECT IDENTIFIER ::= { atmstk-chassis 7 }
atmstk-4222                OBJECT IDENTIFIER ::= { atmstk-chassis 8 }
atmstk-4223                OBJECT IDENTIFIER ::= { atmstk-chassis 9 }
atmstk-4231                OBJECT IDENTIFIER ::= { atmstk-chassis 10 }
atmstk-4232                OBJECT IDENTIFIER ::= { atmstk-chassis 11 }
atmstk-4233                OBJECT IDENTIFIER ::= { atmstk-chassis 12 }

atmstk-cards            OBJECT IDENTIFIER ::= { atm-stackable 3 }
atmstk-24Port-main-reach   OBJECT IDENTIFIER ::= { atmstk-cards 1 }
atmstk-24Port-main-adsl-a  OBJECT IDENTIFIER ::= { atmstk-cards 2 }
atmstk-24Port-main-adsl-b  OBJECT IDENTIFIER ::= { atmstk-cards 3 }

atmstk-child-cards      OBJECT IDENTIFIER ::= { atm-stackable 4 }
atmstk-4201-t1-uplink       OBJECT IDENTIFIER ::= { atmstk-child-cards 1 }
atmstk-4202-e1-uplink       OBJECT IDENTIFIER ::= { atmstk-child-cards 2 }
atmstk-4203-t1e1-ima-uplink OBJECT IDENTIFIER ::= { atmstk-child-cards 3 }
atmstk-oc3-uplink           OBJECT IDENTIFIER ::= { atmstk-child-cards 4 }
atmstk-splitter             OBJECT IDENTIFIER ::= { atmstk-child-cards 5 }
atmstk-24Port-ext           OBJECT IDENTIFIER ::= { atmstk-child-cards 6 }

atmstk-ports     	OBJECT IDENTIFIER ::= { atm-stackable 5 }
atmstk-reachDsl-port       OBJECT IDENTIFIER ::= { atmstk-ports 1 }
atmstk-t1e1-port     	   OBJECT IDENTIFIER ::= { atmstk-ports 2 }
atmstk-rs232-dce-port      OBJECT IDENTIFIER ::= { atmstk-ports 3 }
atmstk-ethernet-port       OBJECT IDENTIFIER ::= { atmstk-ports 4 }
atmstk-ADSL-annexa-port    OBJECT IDENTIFIER ::= { atmstk-ports 5 }
atmstk-ADSL-annexb-port    OBJECT IDENTIFIER ::= { atmstk-ports 6 }

atmstk-components     	OBJECT IDENTIFIER ::= { atm-stackable 6 }
atmstk-comp-fan       	   OBJECT IDENTIFIER ::= { atmstk-components 1 }
atmstk-comp-temp-sensor    OBJECT IDENTIFIER ::= { atmstk-components 2 }
atmstk-comp-pld            OBJECT IDENTIFIER ::= { atmstk-components 3 }

--
-- New tree for JetStream
--

jetstream	          	OBJECT IDENTIFIER ::= { paradyne-products 20 }
js-cpx		             	OBJECT IDENTIFIER ::= { jetstream 1 }
js-cpx1     	        		OBJECT IDENTIFIER ::= { js-cpx 1 }

--
--  The NMS/pdn mgmt subtrees are used for MIB objects
--

-- ========== NMS mgmt ==========

paradyneNMS           OBJECT IDENTIFIER ::= { pdn-mgmt 23 }

-- nms-6800           OBJECT IDENTIFIER ::= { paradyneNMS 1 thru 4}
nms-6700              OBJECT IDENTIFIER ::= { paradyneNMS 5 }

-- ========== pdn mgmt ==========

paradyne              OBJECT IDENTIFIER ::= { pdn-mgmt 24 }

-- ===============================================================

pdn-cellRelay        OBJECT IDENTIFIER ::= { paradyne 1 } 

-- ===============================================================

pdn-common           OBJECT IDENTIFIER ::= { paradyne 2 }
pdn-frontPanel       OBJECT IDENTIFIER ::= { pdn-common 1 }
pdn-chassis          OBJECT IDENTIFIER ::= { pdn-common 2 } -- unused
pdn-callDir          OBJECT IDENTIFIER ::= { pdn-common 3 }
pdn-devStatus        OBJECT IDENTIFIER ::= { pdn-common 4 }
pdn-devID            OBJECT IDENTIFIER ::= { pdn-common 5 }
pdn-interfaces       OBJECT IDENTIFIER ::= { pdn-common 6 }
-- ifMap                  OBJECT IDENTIFIER ::= { pdn-interfaces 1 }
-- dds                    OBJECT IDENTIFIER ::= { pdn-interfaces 2 }
-- portUsage              OBJECT IDENTIFIER ::= { pdn-interfaces 3 }
-- voice                  OBJECT IDENTIFIER ::= { pdn-interfaces 4 }
ent-ds1                   OBJECT IDENTIFIER ::= { pdn-interfaces 5 }
-- devDS1Tests              OBJECT IDENTIFIER ::= { ent-ds1 1 }
-- ds1PerfStats             OBJECT IDENTIFIER ::= { ent-ds1 4 }
-- pdnDs1Ext                OBJECT IDENTIFIER ::= { ent-ds1 5 }
--syncPort                  OBJECT IDENTIFIER ::= { pdn-interfaces 6 }
-- syncDataPortConfigTbl    OBJECT IDENTIFIER ::= { syncPort 1 }
-- devSyncPortTest          OBJECT IDENTIFIER ::= { syncPort 2 }
-- edlPerfStats             OBJECT IDENTIFIER ::= { syncPort 4 }
crossConnect              OBJECT IDENTIFIER ::= { pdn-interfaces 7 }
-- devDs1FracTable          OBJECT IDENTIFIER ::= { crossConnect 1 }
-- devSyncDataPortAssignTbl OBJECT IDENTIFIER ::= { crossConnect 2 }
-- pvcXconnect              OBJECT IDENTIFIER ::= { crossConnect 3 }
xdsl                      OBJECT IDENTIFIER ::= { pdn-interfaces 8 }
-- xdsl                     OBJECT IDENTIFIER ::= { xdsl 1 }
-- dhcp                     OBJECT IDENTIFIER ::= { xdsl 2 }
-- pdsl                     OBJECT IDENTIFIER ::= { xdsl 3 }
pdnFrameRelay             OBJECT IDENTIFIER ::= { pdn-interfaces 9 }
-- frame-relay-clear-stat   OBJECT IDENTIFIER ::= { pdnFrameRelay 1 }
-- frNetDcp                 OBJECT IDENTIFIER ::= { pdnFrameRelay 2 }
-- devPVCTest               OBJECT IDENTIFIER ::= { pdnFrameRelay 3 }
-- ocuPort                OBJECT IDENTIFIER ::= { pdn-interfaces 10 }
pdnAtm                    OBJECT IDENTIFIER ::= { pdn-interfaces 11 }
-- devAtmSlv                OBJECT IDENTIFIER ::= { pdnAtm 1 }
-- devAtmPVCTest            OBJECT IDENTIFIER ::= { pdnAtm 2 }
-- devAtmStatsMIB           OBJECT IDENTIFIER ::= { pdnAtm 3 }
-- devAtmSCM                OBJECT IDENTIFIER ::= { pdnAtm 4 }
-- pdnAtmExtMIB             OBJECT IDENTIFIER ::= { pdnAtm 5 }
-- pdnAtmM4ExtMIB           OBJECT IDENTIFIER ::= { pdnAtm 6 }
-- pdnAtmCesExtMIB          OBJECT IDENTIFIER ::= { pdnAtm 7 }
pdnIfExt                  OBJECT IDENTIFIER ::= { pdn-interfaces 12 }
-- pdnIfExtConfig           OBJECT IDENTIFIER ::= { pdnIfExt 1 }
-- pdnIfExtTestConfig       OBJECT IDENTIFIER ::= { pdnIfExt 2 }
-- pdnIfExtEncapConfig      OBJECT IDENTIFIER ::= { pdnIfExt 3 }
pdnSonetMIB               OBJECT IDENTIFIER ::= { pdn-interfaces 13 }
pdnDs3MIB                 OBJECT IDENTIFIER ::= { pdn-interfaces 14 }
pdnmsdsl                  OBJECT IDENTIFIER ::= { pdn-interfaces 15 }
-- pdnShdsl                 OBJECT IDENTIFIER ::= { pdnmsdsl 1 }
pdnIsdn                   OBJECT IDENTIFIER ::= { pdn-interfaces 16 }
pdnMgmtLink               OBJECT IDENTIFIER ::= { pdn-interfaces 17 }
pdnDiagPortal             OBJECT IDENTIFIER ::= { pdn-interfaces 18 }
-- pdnSpectrumMgmt           OBJECT IDENTIFIER ::= { pdn-interfaces 19 }
pdnReachDSL             OBJECT IDENTIFIER ::= { pdn-interfaces 20 }
-- pdnMgmtIpMIB              OBJECT IDENTIFIER ::= { pdn-interfaces 21 }
--rs232ExtPort                  OBJECT IDENTIFIER ::= { pdn-interfaces 22 }
-- rs232PortExtMIBObject    OBJECT IDENTIFIER ::= { rs232ExtPort 1 }
-- rs232ExtPortGroups         OBJECT IDENTIFIER ::= { rs232ExtPort 2 }
-- pdnHdsl2ShdslLineMIB    OBJECT IDENTIFIER ::= { pdn-interfaces 23 }
-- pdnAdslLineExtMIB       OBJECT IDENTIFIER ::= { pdn-interfaces 24 }
pdnDs0                     OBJECT IDENTIFIER ::= { pdn-interfaces 25 }
-- pdnDsx0MIB               OBJECT IDENTIFIER ::= { pdnDs0 1 }
-- pdnHdlcMIB              OBJECT IDENTIFIER ::= { pdn-interfaces 26 }
-- pdnIfDevIwfMIB          OBJECT IDENTIFIER ::= { pdn-interfaces 27 }
-- pdnPppLcpExtMIB         OBJECT IDENTIFIER ::= { pdn-interfaces 28 }
-- pdnPppBridgeMIB         OBJECT IDENTIFIER ::= { pdn-interfaces 29 }
-- pdnPppMlMIB             OBJECT IDENTIFIER ::= { pdn-interfaces 30 }
-- pdnAdslSeltMIB          OBJECT IDENTIFIER ::= { pdn-interfaces 31 }
-- pdnPppoeExtMIB          OBJECT IDENTIFIER ::= { pdn-interfaces 32 }
-- pdnDslAtmBondMIB        OBJECT IDENTIFIER ::= { pdn-interfaces 33 }

pdn-devConfig        OBJECT IDENTIFIER ::= { pdn-common 7 }
-- pdn-security      OBJECT IDENTIFIER ::= { pdn-common 8 }
pdn-traps            OBJECT IDENTIFIER ::= { pdn-common 9 }
-- pdn-control       OBJECT IDENTIFIER ::= { pdn-common 10 }
pdn-ipInjection      OBJECT IDENTIFIER ::= { pdn-common 11 }
pdn-ip               OBJECT IDENTIFIER ::= { pdn-common 12 }
 pdn-rmon            OBJECT IDENTIFIER ::= { pdn-common 13 }
pdn-fileXfer         OBJECT IDENTIFIER ::= { pdn-common 14 } 
pdn-feature          OBJECT IDENTIFIER ::= { pdn-common 15 }
pdn-diagnostics      OBJECT IDENTIFIER ::= { pdn-common 16 }
-- diagTestMIBObjects    OBJECT IDENTIFIER ::= { pdn-diagnostics 1  }
-- diagTestMIBTraps      OBJECT IDENTIFIER ::= { pdn-diagnostics 2 }

pdn-dns              OBJECT IDENTIFIER ::= { pdn-common 17 }
-- pdnDNSMIBObjects      OBJECT IDENTIFIER ::= { pdn-dns 1 }
-- pdnDNSMIBTraps        OBJECT IDENTIFIER ::= { pdn-dns 2 }

pdn-ether            OBJECT IDENTIFIER ::= { pdn-common 18 }
-- pdnPortConfigMIBObjects  OBJECT IDENTIFIER ::= { pdn-ether 1 }
-- pdnPortConfigMIBTraps    OBJECT IDENTIFIER ::= { pdn-ether 2 }


pdn-socket           OBJECT IDENTIFIER ::= { pdn-common 19 }
-- devSocketStatsMIBObjects  OBJECT IDENTIFIER ::= { pdn-socket 1 }
-- devSocketStatsMIBTraps    OBJECT IDENTIFIER ::= { pdn-socket 2 }


pdn-time             OBJECT IDENTIFIER ::= { pdn-common 20 }
-- devTimeMIBObjects       OBJECT IDENTIFIER ::= { pdn-time 1 }
-- devTimeMIBTraps         OBJECT IDENTIFIER ::= { pdn-time 2 }


pdn-bridge           OBJECT IDENTIFIER ::= { pdn-common 21 }
-- pdnBridgeGenericMIBObjects OBJECT IDENTIFIER ::= { pdn-bridge 1 }
-- pdnBridgeMIBTraps OBJECT IDENTIFIER ::= { pdn-bridge 2 }

pdn-domain           OBJECT IDENTIFIER ::= { pdn-common 22 }
-- pdnDomainMIBObjects   OBJECT IDENTIFIER ::= { pdn-domain 1 }
-- pdnDomainMIBTraps     OBJECT IDENTIFIER ::= { pdn-domain 2 }

pdn-filter           OBJECT IDENTIFIER ::= { pdn-common 23 }
-- sysDevFilterMIBObjects OBJECT IDENTIFIER ::= { pdn-filter 1 }
-- sysDevFilterMIBTraps   OBJECT IDENTIFIER ::= { pdn-filter 2 }
-- pdn-filter-v2          OBJECT IDENTIFIER ::= { pdn-filter 10 }
-- pdnIpSpecFilterMIB     OBJECT IDENTIFIER ::= { pdn-filter 11 }
-- pdnFilterProtocols     OBJECT IDENTIFIER ::= { pdn-filter 12 }

pdn-dslam            OBJECT IDENTIFIER ::= { pdn-common 24 }
-- sysDevDslamMIBObjects OBJECT IDENTIFIER ::= { pdn-dslam 1 }
-- sysDevDslamMIBTraps   OBJECT IDENTIFIER ::= { pdn-dslam 2 }

pdn-radius           OBJECT IDENTIFIER ::= { pdn-common 25 }
-- sysDevRadiusMIBObjects OBJECT IDENTIFIER ::= { pdn-radius 1 }
-- sysDevRadiusMIBTraps   OBJECT IDENTIFIER ::= { pdn-radius 2 }


pdn-inet             OBJECT IDENTIFIER ::= { pdn-common 26 }
-- pdnInetMIBObjects   OBJECT IDENTIFIER ::= { pdn-inet 1 }
-- pdnInetMIBTraps     OBJECT IDENTIFIER ::= { pdn-inet 2 }


-- pdn-arp              OBJECT IDENTIFIER ::= { pdn-common 27 }
-- pdnNetToMediaGenericMIBObjects  OBJECT IDENTIFIER ::= { pdn-arp 1 }
-- pdnNetToMediaMIBTraps           OBJECT IDENTIFIER ::= { pdn-arp 2 }

pdn-devStats         OBJECT IDENTIFIER ::= { pdn-common 28 }
-- devStatsMIBObjects    OBJECT IDENTIFIER ::= { pdn-devStats 1 }
-- devStatsMIBTraps      OBJECT IDENTIFIER ::= { pdn-devStats 2 }

pdn-dhcp             OBJECT IDENTIFIER ::= { pdn-common 29 }
pdn-nat              OBJECT IDENTIFIER ::= { pdn-common 30 }
pdn-syslog           OBJECT IDENTIFIER ::= { pdn-common 31 }
pdn-dialControl      OBJECT IDENTIFIER ::= { pdn-common 32 }

pdn-devNetTiming     OBJECT IDENTIFIER ::= { pdn-common 33 }
-- pdnDevNetTimingMIB            OBJECT IDENTIFIER ::= { pdn-devTiming 1 }
-- pdnDevNetTimingMIBObjects     OBJECT IDENTIFIER ::= { pdnDevNetTimingMIB 1 }
-- pdnDevNetTimingMIBTraps       OBJECT IDENTIFIER ::= { pdnDevNetTimingMIB 2 }
-- pdnDevNetTimingMIBConformance OBJECT IDENTIFIER ::= { pdnDevNetTimingMIB 3 }

pdnIPSec             OBJECT IDENTIFIER ::= { pdn-common 34 }
mpeEntitySensor      OBJECT IDENTIFIER ::= { pdn-common 35 }
-- pdnStackable	     OBJECT IDENTIFIER ::= { pdn-common 36 }
pdnUplinkTagging     OBJECT IDENTIFIER ::= { pdn-common 37 }
pdnSpectrumMgr       OBJECT IDENTIFIER ::= { pdn-common 38 }
pdn-dot1q            OBJECT IDENTIFIER ::= { pdn-common 39 } 
pdnLinkFaultMgmt     OBJECT IDENTIFIER ::= { pdn-common 40 } 
pdnEntityRedundancy  OBJECT IDENTIFIER ::= { pdn-common 41 } 
pdnLinkLoadSharing   OBJECT IDENTIFIER ::= { pdn-common 42 } 
pdnAtmBridgeIwfMIB   OBJECT IDENTIFIER ::= { pdn-common 43 } 
pdnMpdExt   	     OBJECT IDENTIFIER ::= { pdn-common 44 } 
pdnEntitySensorExtMIB OBJECT IDENTIFIER ::= { pdn-common 45 } 
pdnVlanMIB            OBJECT IDENTIFIER ::= { pdn-common 46 } 
--pdnIgmpStdExtMIB      OBJECT IDENTIFIER ::= { pdn-common 47 } 
--pdnIpMcastMIB         OBJECT IDENTIFIER ::= { pdn-common 48 } 
-- pdnProtoSpecFilterMIB  OBJECT IDENTIFIER ::= { pdn-common 49 } 
pdnCpIwf         	OBJECT IDENTIFIER ::= { pdn-common 50 } 
-- pdnCpIwfMIB  	OBJECT IDENTIFIER ::= { pdn-common 51 } 
-- pdnCpIwfAtmMIB  	OBJECT IDENTIFIER ::= { pdn-common 52 } 
-- pdnCpIwfIpMIB  	OBJECT IDENTIFIER ::= { pdn-common 53 } 

pdnMtau         	OBJECT IDENTIFIER ::= { pdn-common 55 } 
-- pdnMtauMIB  	        OBJECT IDENTIFIER ::= { pdnMtau 1 } 

-- pdnTcMIB             OBJECT IDENTIFIER ::= { pdn-common 56 }
-- pdnDhcpMIB           OBJECT IDENTIFIER ::= { pdn-common 57 }
-- pdnBridgeExtMib      OBJECT IDENTIFIER ::= { pdn-common 58 }
-- pdnPppoaoeIwfMIB     OBJECT IDENTIFIER ::= { pdn-common 59 }
-- ===============================================================

pdn-snmp         OBJECT IDENTIFIER ::= { paradyne 3 }
ent-9XXX              OBJECT IDENTIFIER ::= { pdn-snmp 1 }
ent-96XX              OBJECT IDENTIFIER ::= { ent-9XXX 1 } -- unused
ent-bonaire           OBJECT IDENTIFIER ::= { ent-9XXX 2 } -- unused
ent-91XX              OBJECT IDENTIFIER ::= { ent-9XXX 3 } -- unused

-- ===============================================================

pdn-36xx             OBJECT IDENTIFIER ::= { paradyne 4 } -- unused

pdn-aac              OBJECT IDENTIFIER ::= { paradyne 5 } -- unused

pdn-eagle            OBJECT IDENTIFIER ::= { paradyne 6 } -- unused

pdn-ar               OBJECT IDENTIFIER ::= { paradyne 7 } -- unused

pdn-as               OBJECT IDENTIFIER ::= { paradyne 8 } -- unused

-- ===============================================================

pdn-xdsl             OBJECT IDENTIFIER ::= { paradyne 9 }
ent-5100                OBJECT IDENTIFIER ::= { pdn-xdsl 1 }
-- xdslIfConfigMIBObjects        OBJECT IDENTIFIER ::= { pdn-xdsl 2 }
ent-8800                OBJECT IDENTIFIER ::= { pdn-xdsl 3 } 
-- sysDevStats            OBJECT IDENTIFIER ::= { ent-8800 1 } 
-- sysDevConfig           OBJECT IDENTIFIER ::= { ent-8800 2 } 
-- sysDevFilter           OBJECT IDENTIFIER ::= { ent-8800 3 } 
-- diagTests              OBJECT IDENTIFIER ::= { ent-8800 4 } 
-- pdnDot1dBridge         OBJECT IDENTIFIER ::= { ent-8800 5 } 
-- pdnDomain              OBJECT IDENTIFIER ::= { ent-8800 6 } 
-- sysDevRadiusAuth       OBJECT IDENTIFIER ::= { ent-8800 7 } 
-- sysDevUserAccount      OBJECT IDENTIFIER ::= { ent-8800 8 } 
-- xdslIfConfigMIBTraps          OBJECT IDENTIFIER ::= { pdn-xdsl 4 }
ent-8600                OBJECT IDENTIFIER ::= { pdn-xdsl 5 } -- unused
pdn-sle                 OBJECT IDENTIFIER ::= { pdn-xdsl 6 }

-- ===============================================================

pdn-comp             OBJECT IDENTIFIER ::= { paradyne 10 }
ent-9028                OBJECT IDENTIFIER ::= { pdn-comp 1 } -- unused

-- ===============================================================

pdn-ptc              OBJECT IDENTIFIER ::= { paradyne 11 }
ent-ptc                 OBJECT IDENTIFIER ::= { pdn-ptc 1 } -- unused

-- ===============================================================

pdn-mpe              OBJECT IDENTIFIER ::= { paradyne 12 }

mpe-mib2         OBJECT IDENTIFIER ::= { pdn-mpe 4 }
-- mpeMib2MIBObjects OBJECT IDENTIFIER ::= { mpe-mib2 1 }
-- mpeMib2MIBTraps   OBJECT IDENTIFIER ::= { mpe-mib2 2 }


mpe-devHealth    OBJECT IDENTIFIER ::= { pdn-mpe 7 }
-- mpeDevHealthAndStatusMIBObjects  OBJECT IDENTIFIER ::= { mpe-devHealth  1 }
-- mpeDevHealthAndStatusMIBTraps    OBJECT IDENTIFIER ::= { mpe-devHealth  2 }

-- mpeDevControl    OBJECT IDENTIFIER ::= { pdn-mpe 10 }
-- mpeDevControlMIBObjects      OBJECT IDENTIFIER ::= { mpe-devControl 1  }
-- mpeDevControlMIBTraps        OBJECT IDENTIFIER ::= { mpe-devControl 2  }

mpe-bridge         OBJECT IDENTIFIER ::= { pdn-mpe 21 }
-- mpePdnBridgeGenericMIBObjects OBJECT IDENTIFIER ::= { mpe-bridge 1 }
-- mpePdnBridgeMIBTraps OBJECT IDENTIFIER ::= { mpe-bridge 2 }

mpe-domain       OBJECT IDENTIFIER ::= { pdn-mpe 22 }
-- mpePdnDomainMIBObjects   OBJECT IDENTIFIER ::= { mpe-domain 1 }
-- mpePdnDomainMIBTraps     OBJECT IDENTIFIER ::= { mpe-domain 2 }

mpe-filter         OBJECT IDENTIFIER ::= { pdn-mpe 23 }
-- mpeSysDevFilterMIBObjects OBJECT IDENTIFIER ::= { mpe-filter 1 }
-- mpeSysDevFilterMIBTraps   OBJECT IDENTIFIER ::= { mpe-filter 2 }

--mpe-dslam         OBJECT IDENTIFIER ::= { pdn-mpe 24 }
-- mpeSysDevDslamMIBObjects OBJECT IDENTIFIER ::= { mpe-dslam 1 }
-- mpeSysDevDslamMIBTraps   OBJECT IDENTIFIER ::= { mpe-dslam 2 }

mpe-arp            OBJECT IDENTIFIER ::= { pdn-mpe 27 }
-- mpePdnNetToMediaGenericMIBObjects      OBJECT IDENTIFIER ::= { mpe-arp 1 } 
-- mpePdnNetToMediaGenericMIBTraps        OBJECT IDENTIFIER ::= { mpe-arp 2 }

mpe-devStats     OBJECT IDENTIFIER ::= { pdn-mpe 28 }
-- mpeDevStatsMIBObjects    OBJECT IDENTIFIER ::= { mpe-devStats 1 }
-- mpeDevStatsMIBTraps      OBJECT IDENTIFIER ::= { mpe-devStats 2 }

mpe-devConfig     OBJECT IDENTIFIER ::= { pdn-mpe 29 }
-- mpeDevConfigMIB            OBJECT IDENTIFIER ::= { mpe-devConfig 1 }
-- mpeDevConfigMIBObjects     OBJECT IDENTIFIER ::= { mpeDevConfigMIB 1 }
-- mpeDevConfigMIBTraps       OBJECT IDENTIFIER ::= { mpeDevConfigMIB 2 }
-- mpeDevConfigMIBConformance OBJECT IDENTIFIER ::= { mpeDevConfigMIB 3 }

mpe-atm     OBJECT IDENTIFIER ::= { pdn-mpe 30 }
-- mpeAtmConfMIB             OBJECT IDENTIFIER ::= { mpe-atm 1 }
-- mpeAtmConfMIBObjects      OBJECT IDENTIFIER ::= { mpeAtmConfMIB 1 }
-- mpeAtmConfMIBTraps        OBJECT IDENTIFIER ::= { mpeAtmConfMIB 2 }
-- mpeAtmConfMIBConformance  OBJECT IDENTIFIER ::= { mpeAtmConfMIB 3 }

-- ===============================================================

pdn-experimental     OBJECT IDENTIFIER ::= { paradyne 13 }

-- ===============================================================

pdn-ietf-drafts      OBJECT IDENTIFIER ::= { paradyne 14 }
-- draft-ietf-frnetmib-frsi-00  OBJECT IDENTIFER ::= { pdn-ietf-drafts 1 }
-- draft-ietf-atommib-sonetaps-mib-08 OBJECT IDENTIFER ::= { pdn-ietf-drafts 2 }
-- pdnSfp            OBJECT IDENTIFER ::= { pdn-ietf-drafts 3 }
-- pPPoE-01          OBJECT IDENTIFER ::= { pdn-ietf-drafts 4 }

-- ===============================================================

cellsaver-mibs       OBJECT IDENTIFIER ::= { paradyne 15 }
-- cellsaver-common          OBJECT IDENTIFER ::= { cellsaver-mibs 1 }
-- mib-9510                  OBJECT IDENTIFER ::= { cellsaver-mibs 2 }
-- mib-9550                  OBJECT IDENTIFER ::= { cellsaver-mibs 3 }

-- ===============================================================

cornet-mibs          OBJECT IDENTIFIER ::= { paradyne 16 }
-- cornet-common       OBJECT IDENTIFER ::= { cornet-mibs 1 }
-- mib-xxxx            OBJECT IDENTIFER ::= { cornet-mibs 2 }

-- ===============================================================

ip-stackable-mibs      OBJECT IDENTIFIER ::= { paradyne 17 }
-- ip-stackable-common OBJECT IDENTIFIER ::= { ip-stackable-mibs 1 }
-- mib-xxxx            OBJECT IDENTIFIER ::= { ip-stackable-mibs 2 }

-- ===============================================================

etherloop-mibs		OBJECT IDENTIFIER ::= { paradyne 18 }

atmstk-mibs			OBJECT IDENTIFIER ::= { paradyne 19 }

-- ===============================================================

jetstream-mibs		OBJECT IDENTIFIER ::= { paradyne 20 }

js-common		        OBJECT IDENTIFIER ::= { jetstream-mibs 1 }
js-varbind-dn		        OBJECT IDENTIFIER ::= { js-common 1 }

js-cpx1-mib				OBJECT IDENTIFIER ::= { jetstream-mibs 2 }


END

-- ===================================================================
-- ==                                                               ==
-- ==  Paradyne Textual Conventions.                                ==
-- ==                                                               ==
-- ==  Paradyne Networks was acquired by Zhone Technologies on      ==
-- ==  September 1, 2005.                                           ==
-- ==                                                               ==
-- ==          Copyright (C) 2005 Zhone Technologies, Inc.          ==
-- ==                                                               ==
-- ===================================================================



PDN-TC DEFINITIONS ::=  BEGIN

IMPORTS 
   MODULE-IDENTITY, Integer32
      FROM SNMPv2-SMI
   TEXTUAL-CONVENTION
      FROM SNMPv2-TC 
   pdn-common
      FROM PDN-HEADER-MIB;

pdnTcMIB MODULE-IDENTITY
   LAST-UPDATED "200509080000Z"  -- September 8, 2005
   ORGANIZATION "Paradyne Networks
                 MIB Working Group
                 Other information about group editing the MIB."
   CONTACT-INFO "Paradyne Networks, Inc.
                 8545 126th Avenue North
                 Largo, FL 33773
                 www.paradyne.com

                 General Comments to: mibwg_team@paradyne.com
    
                 Editor(s)
                    Wayne Jadoo
                    Kevin Baughman
                    Rajesh Raghavan
                    Sue Alfano
                    Jesus Pinto
                    Clay Sikes"

   DESCRIPTION  "This MIB Module provides some generic Textual
                 conventions for Paradyne enterprise MIB Modules.


                 =====================================================
                 ==                                                 ==
                 ==   Copyright (C) 2005 Zhone Technologies, Inc.   ==
                 ==                                                 ==
                 ====================================================="


   REVISION     "200509080000Z"  -- September 8, 2005
   DESCRIPTION   "Added PdnTestAndIncrDerivedIndexTC to support table
                  indices derived from or related to a TestAndIncr
                  operation.
                  Clay Sikes"

   REVISION     "200409140000Z"  -- September 14, 2003
   DESCRIPTION  "Changed enumerated list for PdnPPPState to start 
                 from 0.  Although SMIv2 allows a - to + range,
                 the SNMP Research MIB tools have a problem with
                 starting from 0.
                 Clay Sikes."

   REVISION     "200409100000Z"  -- September 10, 2003
   DESCRIPTION  "Converted to a `full' SMIv2 TC MIB to correct
                 libsmi issues
                 Clay Sikes."

   REVISION     "200409060000Z"  -- September 6, 2003
   DESCRIPTION  "Added PdnPPPState to present the state machine's 
                 state for various PPP entities such as LCP, NCP, and 
                 ML PPP.
                 Clay Sikes"

   REVISION     "200311190000Z"  -- November 19, 2003
   DESCRIPTION  "Added TEXTUAL-CONVENTION TblCmd to command actions on
                 databases or mib tables (e.g, clear database).
                 Jesus Pinto"

   REVISION     "200208130000Z"  -- August 13, 2002
   DESCRIPTION  "Added TC for ContactState. 
                 Jesus Pinto"

   REVISION     "200205070000Z"  -- May 7, 2002
   DESCRIPTION  "Added new enum to NTPMode, removed reference to 
                 DisplayString (MIB compile doesn't allow definition
                 in TC to use syntax from another TC).
                 Sue Alfano"

   REVISION     "200009210000Z"  -- September 21, 2000
   DESCRIPTION  "Added TC for TimeOfDay.
                 Rajesh Raghavan"

   REVISION     "199910270000Z"  -- October 27, 1999
   DESCRIPTION  "Converted back to smiv2.
                 Kevin Baughman"
 
   REVISION     "199910070000Z"  -- October 7, 1999
   DESCRIPTION  "Imported PDN-HEADER-HEADER mib and added TC for 
                 SnmpAdminString.
                 Wayne Jadoo"

   REVISION     "199910040000Z"  -- October 4, 1999
   DESCRIPTION  "Removed TC for Tadddress, MacAddress and TruthValue 
                 DateAndTime and SnmpAdminString and moved to rfc1901v1.mib.
                 Wayne Jadoo"

   REVISION     "199909280000Z"  -- September 28, 1999
   DESCRIPTION  "Added TC for TAddress , MacAddress and TruthValue.
                 Wayne Jadoo"

   REVISION     "199909270000Z"  -- September 27, 1999
   DESCRIPTION  "Commented out textual conventions so to be compatible
                 to SNMP-V1 .
                 Wayne Jadoo"

   REVISION     "199908250000Z"  -- August 25, 1999
   DESCRIPTION  "Initial version.
                 Wayne Jadoo"

   ::= { pdn-common 56 }


-- ==========================================================

VnidMode ::= TEXTUAL-CONVENTION
     STATUS       current
     DESCRIPTION
	"This object describes the configuration mode
  	for VNIDs and ports. "

     SYNTAX INTEGER { implicit(1), explicit(2), notagging(3) }

ClientState ::= TEXTUAL-CONVENTION
     STATUS current
     DESCRIPTION
       " The configuration type for a client."
     SYNTAX INTEGER { static(1), dynamic(2)}

VnidTaggingState ::=  TEXTUAL-CONVENTION
     STATUS current
     DESCRIPTION
        " This object indicates whether VNID tagging 
        is activated or de-activated."
     SYNTAX	INTEGER { enabled(1), disabled(2)}

VnidRange ::= TEXTUAL-CONVENTION
     DISPLAY-HINT "d"
     STATUS current
     DESCRIPTION
        " The valid range for VNID IDs"
     SYNTAX Integer32( 2..4000 )

SwitchState ::= TEXTUAL-CONVENTION
     STATUS current
     DESCRIPTION
        " This object indicates whether an object state is 
        in the enabled or disabled state "
     SYNTAX INTEGER { enabled(1), disabled(2)}

TblCmd ::= TEXTUAL-CONVENTION
	STATUS current
	DESCRIPTION
	"This convention can be used to command a database
	(e.g, mib table) to perform an action (e.g, clear)"
	SYNTAX INTEGER
	{
		noCmd (1),
		clear (2)
	}

ResetStates ::= TEXTUAL-CONVENTION
     STATUS current
     DESCRIPTION
        "This object defines the enumerations
        of values that can be applied to the reset
        object"
     SYNTAX INTEGER { 
                      noOp(1), 
		      reset(2), 
		      resetToFactoryDefaults(3), 
		      resetToNewActiveConfig(4) 
     }

ResultTypes ::=  TEXTUAL-CONVENTION
     STATUS current
     DESCRIPTION
        "This object defines the enumerations
        for the result of an operation "
     SYNTAX INTEGER {
                none(1),
                success(2),
                failure(3),
                inProgress(4)
     }

InitiatorTypes ::=  TEXTUAL-CONVENTION
     STATUS current
     DESCRIPTION
        "This object defines the enumerations
        for the result of an operation "
     SYNTAX INTEGER {
             noop(1),
             telnet(2),
             console(3),
             snmp(4)
           }

NTPMode ::= TEXTUAL-CONVENTION
     STATUS current
     DESCRIPTION
           "This object describes the mode in which NTP/SNTP will operate."
     SYNTAX INTEGER {
                  unicast(1),
                  broadcast(2),
                  multicast(3)
          }

DNSServerType ::= TEXTUAL-CONVENTION
    STATUS  current
    DESCRIPTION
           "This object describes the DNS server Type"
	SYNTAX  INTEGER {
                  primary(1),
                  secondary(2)
                 }


MibOidType ::=  TEXTUAL-CONVENTION
    STATUS  current
    DESCRIPTION
        "This Object describes the type of a mib object
              Scalar - Single Instance Object
              Table - Multi-instance Object
              Mib - A Mib.
                 Section - A Section Within A MIB"
    SYNTAX INTEGER {
                    scalar (1),
                    table (2),
                    mib (3),
                    section (4)
                 }

SocketType ::=  TEXTUAL-CONVENTION
    STATUS  current
    DESCRIPTION
           "This object describes the type of socket"
    SYNTAX INTEGER {
                    unknown(1),
                    stream(2),
                    datagram(3),
                    rawProtocol(4),
                    reliableMessageDelivery(5),
                    sequencedPacket(6)
                   }


SocketFamily ::=  TEXTUAL-CONVENTION
     STATUS  current
     DESCRIPTION
            "This object describes the socket Family"
     SYNTAX  INTEGER {
                           unknown(1),
                           unix(2),
                           darpaInternet(3),
                           darpaIMP(4),
                           pUP(5),
                           cHAOSFamily(6),
                           xeroxNovell(7),
                           nBS(8),
                           eCMA(9),
                           dATAKIT(10),
                           cCITT(11),
                           sNA(12),
                           dECnet(13),
                           directDataLinkInterface(14),
                           dECLAT(15),
                           nSCHyperChannel(16),
                           appleTalk(17),
                           netqorkInterfaceTap(18),
                           iEEE8020ISO8802(19),
                           oSI(20),
                           x25(21),
                           oSIAFI47IDI4(22),
                           uSGovermentOSI(23)
                   }

SocketState ::=  TEXTUAL-CONVENTION
       STATUS  current
       DESCRIPTION
              "This object describes the state of a stream socket"
       SYNTAX INTEGER {
                          closed (1),
                          listen (2),
                          sYNSent(3),
                          sYNRCVD(4),
                          established(5),
                          closeWait(6),
                          fINWait(7),
                          closing(8),
                          lastAck(9),
                          fINWait2(10),
                          timeWait(11)
                 }

DomainName ::=  TEXTUAL-CONVENTION
       STATUS  current
       DESCRIPTION
            "The domain name space is a tree structure.  Each node and 
            leaf on the tree corresponds to a resource set (which may be 
            empty).  The domain system makes no distinctions between the 
            uses of the interior nodes and leaves, and this memo uses the 
            term 'node' to refer to both. Each node has a label, which is 
            zero to 63 octets in length.  Brother nodes may not have the 
            same label, although the same label can be used for nodes 
            which are not brothers.  One label is reserved, and that is
            the null (i.e., zero length) label used for the root.
            The domain name of a node is the list of the labels on the 
            path from the node to the root of the tree.  By convention, 
            the labels that compose a domain name are printed or read 
            left to right, from the most specific (lowest, farthest from 
            the root) to the least specific (highest, closest to the 
            root).
 
            Internally, programs that manipulate domain names should 
            represent them as sequences of labels, where each label is a 
            length octet followed by  an octet string.  Because all domain 
            names end at the root, which has a null string for a label, 
            these internal representations can use a length byte of zero 
            to terminate a domain name.
 
            By convention, domain names can be stored with arbitrary case, but
            domain name comparisons for all present domain functions are done in 
            a case-insensitive manner, assuming an ASCII character set, and a 
            high order zero bit.  This means that you are free to create a node 
            with label 'A' or a node with label 'a', but not both as brothers; 
            you could refer to either using 'a' or 'A'.  When you receive a 
            domain name or label, you should preserve its case.  The rationale 
            for this  choice is that we may someday need to add full binary 
            domain names for  new services; existing services would not be 
            changed.
 
            When a user needs to type a domain name, the length of each label is
            omitted and the labels are separated by dots ('.').  Since a complete
            domain name ends with the root label, this leads to a printed form 
            which ends in a dot.  We use this property to distinguish between:
 
            character string which represents a complete domain name
            (often called 'absolute').  For example, 'poneria.ISI.EDU.'
 
           - a character string that represents the starting labels of a
           domain name which is incomplete, and should be completed by
           local software using knowledge of the local domain (often
           called 'relative').  For example, 'poneria' used in the
           ISI.EDU domain.
 
           Relative names are either taken relative to a well known 
           origin, or to a list of domains used as a search list.  Relative 
           names appear mostly at the user interface, where their interpretation 
           varies  from implementation to implementation, and in master files, 
           where they  are  relative to a single origin domain name.  The most 
           common interpretation uses the root '.' as either the single origin 
           or as one of the members of the search list, so a multi-label relative 
           name is often one where the trailing dot has been omitted to save 
           typing.
 
           To simplify implementations, the total number of octets that represent  a
           domain name (i.e., the sum of all label octets and label lengths) is
           limited to 255.
 
           A domain is identified by a domain name, and consists of that part of
           the domain name space that is at or below the domain name which
           specifies the domain.  A domain is a subdomain of another domain if it
           is contained within that domain.  This relationship can be tested by
           seeing if the subdomain's name ends with the containing domain's name.
           For example, A.B.C.D is a subdomain of B.C.D, C.D, D, and  '.' "
        SYNTAX OCTET STRING (SIZE (1..64))

   SnmpAdminString ::= TEXTUAL-CONVENTION
        DISPLAY-HINT "255a"
        STATUS       current
        DESCRIPTION "An octet string containing administrative
           information, preferably in human-readable form.
 
           To facilitate internationalization, this
           information is represented using the ISO/IEC
           IS 10646-1 character set, encoded as an octet
           string using the UTF-8 transformation format
           described in [RFC2044].
 
           Since additional code points are added by
           amendments to the 10646 standard from time
           to time, implementations must be prepared to
           encounter any code point from 0x00000000 to
           0x7fffffff.
 
           The use of control codes should be avoided.
 
           When it is necessary to represent a newline,
           the control code sequence CR LF should be used.
 
 
           The use of leading or trailing white space should
           be avoided.
 
           For code points not directly supported by user
           interface hardware or software, an alternative
           means of entry and display, such as hexadecimal,
           may be provided.
 
           For information encoded in 7-bit US-ASCII,
           the UTF-8 encoding is identical to the
           US-ASCII encoding.
 
           Note that when this TC is used for an object that
           is used or envisioned to be used as an index, then
           a SIZE restriction must be specified so that the
           number of sub-identifiers for any object instance
           does not exceed the limit of 128, as defined by
           [RFC1905].
                "
    SYNTAX OCTET STRING (SIZE (0..255))

InetAddressType ::= TEXTUAL-CONVENTION
  STATUS       current
  DESCRIPTION
    "This object describes the type of address configured 
     for a interface"
  SYNTAX INTEGER { primary (1), secondary (2) }

ManagementType ::= TEXTUAL-CONVENTION
	STATUS current
	DESCRIPTION
	"This object is used to specify the type of
	management. This can be either Inband
	Management or OutBand Management."
	SYNTAX INTEGER
	{
		inband  (1),
		outband (2)
	}

ContactState ::= TEXTUAL-CONVENTION
	STATUS current
	DESCRIPTION
	"This convension can be used to indicate the
	state of a switch, door, connector, etc. that
	can be by nature opened or closed."
	SYNTAX INTEGER
	{
		open  (1),
		close (2)
	}

IdslClockMode ::= TEXTUAL-CONVENTION
	STATUS current
	DESCRIPTION
    "This object indicates the network clock mode set
    for the secondary network clock. IDSL portcards with a
    port configured as an NT will be set to
    portCardDriveClockOnboard(4), both driving the backplane
    and using the clock for the other Local Timing transceivers
    on the card. Port cards with only LT ports configured will
    receive a clock from the backplane using portCardSinkClock(2).
    portCardDriveClock(3) will drive the backplane alone."
   SYNTAX INTEGER 
   {
      triState(1),
      portCardSinkClock(2),
      portCardDriveClock(3),
      portCardDriveClockOnboard(4)
   }

TimeOfDay ::= TEXTUAL-CONVENTION
    DISPLAY-HINT "1d:1d"
    STATUS	current
    DESCRIPTION
	"A time of day specification

	field	octets	contents	range
	-----	------	--------	-----
	  1	   1	hour		0..23
	  2	   2	minutes		0..59"

    SYNTAX	OCTET STRING(SIZE(2))

DayOfWeek ::= TEXTUAL-CONVENTION
    STATUS	current
    DESCRIPTION
	"This object indicates the day of the week, with
	an additional option 'Daily' to work with interfaces
	that use this convention to schedule events."
    SYNTAX	INTEGER { sunday(1), monday(2), tuesday(3), wednesday(4),
			thursday(5), friday(6), saturday(7), daily(8) }

PdnPPPState ::= TEXTUAL-CONVENTION
   STATUS       current
   DESCRIPTION  "State of the PPP Entity State Machine.  Examples of 
                 PPP entities are LCP, NCP, and ML PPP."
   REFERENCE   "RFC1661, Section 4.2, `State Transition Table'."
   SYNTAX       INTEGER {
                   initial(1),
                   starting(2),
                   closed(3),
                   stopped(4),
                   closing(5),
                   stopping(6),
                   reqSend(7),
                   ackRcvd(8),
                   ackSent(9),     
                   opened(10)
                }

PdnTestAndIncrDerivedIndexTC ::= TEXTUAL-CONVENTION
   DISPLAY-HINT "d"
   STATUS       current
   DESCRIPTION  "An index for a table entry, where a `get next index'
                 object whose syntax is a TestAndIncr textual 
                 convention is used to determine the value for the next
                 unused index for a table entry.  This syntax was 
                 chosen to correspond to the TestAndIncr textual
                 convention."
   SYNTAX       Integer32(0..2147483647)



-- =========
-- == END ==
-- =========
END


-- ===============================================================
-- Copyright (C) 2002 Paradyne Corporation.
-- Enterprise device control mib (mpe support)
-- This MIB contains objects that is used to perform
-- various operations on a device.
PDN-MPE-DEVICE-CONTROL-MIB DEFINITIONS ::= BEGIN



IMPORTS
ResetStates 
FROM PDN-TC
IpAddress, Integer32, Counter32, TimeTicks, 
NOTIFICATION-TYPE,
OBJECT-IDENTITY, OBJECT-TYPE,
MODULE-IDENTITY
FROM SNMPv2-SMI
OBJECT-GROUP, NOTIFICATION-GROUP
FROM SNMPv2-CONF
entPhysicalIndex
FROM ENTITY-MIB
pdn-mpe
FROM PDN-HEADER-MIB
RowStatus,
DisplayString
FROM SNMPv2-TC
;

mpeDevControl MODULE-IDENTITY
	LAST-UPDATED  	"200204290000Z"
   	ORGANIZATION    "Paradyne Corporation
		         MIB Working Group"

   	CONTACT-INFO    "Paradyne Corporation
		         8545 126th Avenue North
		         Largo, FL 33733
		         www.paradyne.com

		         General Comments to: mibwg_team@paradyne.com

		         Editors
                         Prakash Easwar
		         Rajesh Raghaven
		         Kathy Wilson
			 Aamir Shaikh"

	DESCRIPTION	"This MIB Module allows a user to reset a device
			in the DSLAM, as well as perform various operations
			related to the storage and retrieval of firmware
			and configuration files on devices."

	REVISION	"0204290000Z"
	DESCRIPTION	"Aamir Shaikh
	o  Adding mpeDevControlExtendedSelfTest object"

 	REVISION	"200204090905Z"
	DESCRIPTION	"Kathy Wilson
	o  Add mpeDevFileXferFileFormat object"

	REVISION	"200011211800Z"
	DESCRIPTION	"Delete CCM objects and traps"

	REVISION	"200010261400Z"
	DESCRIPTION	"Combine the mpeCCMResync objects"

	REVISION	"200010181830Z"
	DESCRIPTION	"Addition of mpeCCMAutoBackupType object"

	REVISION	"200010061800Z"
	DESCRIPTION	"Initial conversion to SMIv2"


	::= { pdn-mpe 10 }

mpeDevControlMIBObjects     OBJECT IDENTIFIER ::= { mpeDevControl 1 }
mpeDevControlMIBTraps       OBJECT IDENTIFIER ::= { mpeDevControl 2 }
mpeDevControlMIBGroups	    OBJECT IDENTIFIER ::= { mpeDevControl 3 }
mpeDevHwControl             OBJECT IDENTIFIER ::= { mpeDevControlMIBObjects 1 }
mpeDevFileXferConfig        OBJECT IDENTIFIER ::= { mpeDevControlMIBObjects 2 }
mpeDevFirmwareControl       OBJECT IDENTIFIER ::= { mpeDevControlMIBObjects 3 }
mpeDevTestControl	    OBJECT IDENTIFIER ::= { mpeDevControlMIBObjects 4 }

mpeDevControlMIBTrapsV2		OBJECT-IDENTITY
	STATUS 	current
	DESCRIPTION	"The traps for the device control MIB."
	::= { mpeDevControlMIBTraps 0 }

-- Device Reset Object
-- Used to reset (warm boot) the device.

mpeDevControlTable OBJECT-TYPE
   SYNTAX  SEQUENCE OF DevControlEntry
   MAX-ACCESS  not-accessible
   STATUS  current
    DESCRIPTION
         "A table that contains generic information about
           Card Control."
    ::= { mpeDevHwControl  1 }

mpeDevControlEntry OBJECT-TYPE
   SYNTAX  DevControlEntry
   MAX-ACCESS  not-accessible
   STATUS  current
   DESCRIPTION
         "A list of information for device Control."
   INDEX  { entPhysicalIndex }
    ::= { mpeDevControlTable 1 }

DevControlEntry ::=
    SEQUENCE {
              mpeDevControlReset                    ResetStates
             }

mpeDevControlReset OBJECT-TYPE
    SYNTAX  ResetStates
    MAX-ACCESS  read-create
    STATUS  current
    DESCRIPTION
        "Writing the value reset (2) to this object 
         initiates a Hardware power-on reset of the device. 
         Writing the value resetToFactoryDefaults (3) causes the device to re-configure 
         itself with factory defaults. Writing the value (4) causes the device
	 to re-configure itself with a previously loaded active configuration. 
	 The value read from this object is noOp(1)."
     ::= { mpeDevControlEntry 1 }

--
-- Device reset and put it in extended selftest mode 
--

mpeDevControlSelfTestTable OBJECT-TYPE
   SYNTAX  SEQUENCE OF DevControlSelfTestEntry
   MAX-ACCESS  not-accessible
   STATUS  current
    DESCRIPTION
         "A table containing information to control device specific Self-Test
	  operations."
    ::= { mpeDevHwControl  2 }

mpeDevControlSelfTestEntry OBJECT-TYPE
   SYNTAX  DevControlSelfTestEntry
   MAX-ACCESS  not-accessible
   STATUS  current
   DESCRIPTION
         "A list of objects for performing Self-Test operations."
   INDEX  { entPhysicalIndex }
    ::= { mpeDevControlSelfTestTable 1 }

DevControlSelfTestEntry ::=
    SEQUENCE {
              	mpeDevControlExtendedSelfTest	    INTEGER
             }

mpeDevControlExtendedSelfTest OBJECT-TYPE
    SYNTAX  INTEGER {
                     noOp(1),
                     enableExtendSelfTestAndReset(2)
                    }
    MAX-ACCESS  read-write
    STATUS  current
    DESCRIPTION
        "This object is used to start the extended Power-On Self-Test
	 test.  Writing the value enableExtendSelfTestAndReset(2) to this
	 object resets the device and puts it into extended Power-On 
	 Self-Test mode.  During device initialization, the extended
	 Self-Test would be carried out first and then the device would
	 carry out its normal boot operation. The value read from this
	 object is noOp(1). Writing back the same value, noOp(1) will not
	 start the test. Note that if extended Self-Test fails for some
	 reason, after re-initialization, the value of this object will 
	 default to enableExtendSelfTestAndReset(2) again unless the 
	 manager explicitly chooses not to do so."

     ::= { mpeDevControlSelfTestEntry 1 }

--
-- Perform Device specific tests
--

mpeDevControlTestTable OBJECT-TYPE
   SYNTAX  SEQUENCE OF MpeDevControlTestEntry
   MAX-ACCESS  not-accessible
   STATUS  current
    DESCRIPTION
         "A table that contains configuration information to perform
	  device specific tests."
    ::= { mpeDevTestControl  3 }

mpeDevControlTestEntry OBJECT-TYPE
   SYNTAX  MpeDevControlTestEntry
   MAX-ACCESS  not-accessible
   STATUS  current
   DESCRIPTION
         "A list of configuration information for device specific tests."
   INDEX  { entPhysicalIndex }
    ::= { mpeDevControlTestTable 1 }

MpeDevControlTestEntry ::=
    SEQUENCE {
              	mpeDevControlTestType 	    INTEGER,
		mpeDevControlTestStatus     INTEGER,
		mpeDevControlTestCmd 	    INTEGER
             }

mpeDevControlTestType OBJECT-TYPE
    SYNTAX  INTEGER {
                     lampTest(1)
                    }
    MAX-ACCESS  read-write
    STATUS  current
    DESCRIPTION
        "This object is used to specify the type of the test to start."

     ::= { mpeDevControlTestEntry 1 }

mpeDevControlTestStatus OBJECT-TYPE
    SYNTAX  INTEGER {
                      active(1),
	              inactive(2)
                    }
    MAX-ACCESS  read-only
    STATUS  current
    DESCRIPTION
        "The test status on the device. This object indicates whether
         the indexed test is currently active(1) or inactive(2)."

     ::= { mpeDevControlTestEntry 2 }

mpeDevControlTestCmd OBJECT-TYPE
    SYNTAX  INTEGER {
                    start  (1),
	            stop   (2)
                    }
    MAX-ACCESS  read-write
    STATUS  current
    DESCRIPTION
        "Used to start or stop the indexed test.
         When read, the value returned will be the next logical command."

     ::= { mpeDevControlTestEntry 3 }

-- =======================================================
--
--  The Paradyne File Transfer Group  (J.Strain)
-- =======================================================

mpeDevFileXferConfigTable OBJECT-TYPE
    SYNTAX  SEQUENCE OF MpeDevFileXferConfigEntry
    MAX-ACCESS  not-accessible
    STATUS  current
    DESCRIPTION
           "The Paradyne  FileXfer Client Config Table."
    ::= { mpeDevFileXferConfig  1 }

mpeDevFileXferConfigEntry OBJECT-TYPE
    SYNTAX  MpeDevFileXferConfigEntry
    MAX-ACCESS  not-accessible
    STATUS  current
    DESCRIPTION

       " Use of the File Tranfer MIB could be used with other MIBS in
              the following manner:
                  a) Use another MIB/means to verify available space /make room
                     for a file to be transfered to this device
                  b) Use this MIB to download the file
                  c) Use another MIB/means to select the file you want to make 
                     active
                                        if your selecting firmware for example.
                  d) Use another MIB/means to reset the device.

        A management station wishing to initiate a file transfer needs to
                         create an entry in this table. To do so, you must
       first identify the entPhysicalIndex of the device you intend to
       do the transfer with.  You should
       then create the associated instance of the row status
       It must also, either in the same
       or in successive PDUs, create an instance of
       mpeDevFileXferFileName, mpeDevFileXferFileType, 
.      mpeDevFileXferServerIpAddress,
       mpeDevFileXferOperation.

       It should also modify the default values for the other
       configuration objects if the defaults are not appropriate.

       Once the appropriate instance of all the configuration
       objects have been created, either by an explicit SNMP
       set request or by default, the row status should be set
       to active to initiate the request. Note that this entire
       procedure may be initiated via a single set request which
       specifies a row status of createAndGo as well as specifies
       valid values for the non-defaulted configuration objects.

       Once the MpeDevFileXferConfigEntry request has been created (i.e. the
       mpeDevFileXferRowStatus has been made active), the entry
       cannot be modified - the only operation possible
       after this is to delete the row.

       Once the request completes, the management station should
       retrieve the values of the status objects of interest, and
       should then delete the entry.  In order to prevent old
       entries from clogging the table, entries could be aged out,
       but an entry will never be deleted within 5 minutes of
       completing.  "
    INDEX   { entPhysicalIndex }
    ::= { mpeDevFileXferConfigTable  1 }

MpeDevFileXferConfigEntry ::=
    SEQUENCE {

    mpeDevFileXferFileName
        DisplayString,

    mpeDevFileXferCopyProtocol
        INTEGER,

    mpeDevFileXferFileType
        INTEGER,

    mpeDevFileXferServerIpAddress
        IpAddress,

    mpeDevFileXferUserName
        DisplayString,

    mpeDevFileXferUserPassword
        DisplayString,

    mpeDevFileXferOperation
        INTEGER,

    mpeDevFileXferPktsSent
        Counter32,

    mpeDevFileXferPktsRecv
        Counter32,

    mpeDevFileXferOctetsSent
        Counter32,

    mpeDevFileXferOctetsRecv
        Counter32,

    mpeDevFileXferOwnerString
        OCTET STRING,

    mpeDevFileXferStatus
        INTEGER,

    mpeDevFileXferErrorStatus
        Integer32,

    mpeDevFileXferSendEvent
        INTEGER,

    mpeDevFileXferRowStatus
        RowStatus,
		
    mpeDevFileXferXferTime
	TimeTicks,	
		
    mpeDevFileXferFileFormat
	INTEGER	
    }

mpeDevFileXferFileName OBJECT-TYPE
    SYNTAX  DisplayString
    MAX-ACCESS  read-create
    STATUS  current
    DESCRIPTION
           "This object contains the name of the filetransfer file."
    ::= { mpeDevFileXferConfigEntry  1 }

mpeDevFileXferCopyProtocol OBJECT-TYPE
    SYNTAX   INTEGER {
                         tftp(1),
                         ftp(2)
                                                }
    MAX-ACCESS  read-create
    STATUS  current
        DESCRIPTION
          "The transfer protocol that should be used to copy the file
           across the network. If the file transfer is to occur locally on the 
           SNMP agent, the method of transfer is left upto the implementation, 
           and is not restricted to the protocols below."

--    DEFVAL  { tftp }
    ::= { mpeDevFileXferConfigEntry  2 }

mpeDevFileXferFileType OBJECT-TYPE
    SYNTAX  INTEGER {
                                firmware(1),
                                config(2)
                                }

    MAX-ACCESS  read-create
    STATUS  current
    DESCRIPTION
           "Specifies the type of file your want to transfer."
    ::= { mpeDevFileXferConfigEntry  3 }

mpeDevFileXferServerIpAddress OBJECT-TYPE
    SYNTAX  IpAddress
    MAX-ACCESS  read-create
    STATUS  current
    DESCRIPTION
           "This object contains the file transfer server's IP address. "
    ::= { mpeDevFileXferConfigEntry  4 }

mpeDevFileXferUserName OBJECT-TYPE
    SYNTAX  DisplayString
    MAX-ACCESS  read-create
    STATUS  current
    DESCRIPTION
           "This object contains the username if a username is needed
        to login to the server."
    ::= { mpeDevFileXferConfigEntry  5 }

mpeDevFileXferUserPassword OBJECT-TYPE
    SYNTAX  DisplayString
    MAX-ACCESS  read-create
    STATUS  current
    DESCRIPTION
           "This object contains the password if a password is needed
            to login to the server. This object will return null on a read 
            operation."
    ::= { mpeDevFileXferConfigEntry  6 }

mpeDevFileXferOperation OBJECT-TYPE
    SYNTAX  INTEGER {
                                get(1),
                                put(2)
                                        }
    MAX-ACCESS  read-create
    STATUS  current
    DESCRIPTION
           "This object contains the operation the file transfer wants to 
perform."
    ::= { mpeDevFileXferConfigEntry  7 }

mpeDevFileXferPktsSent OBJECT-TYPE
    SYNTAX  Counter32
    MAX-ACCESS  read-only
    STATUS  current
    DESCRIPTION
           "This object contains the the number of packets sent to the
        server at the time of interrogation."
    ::= { mpeDevFileXferConfigEntry  8 }

mpeDevFileXferPktsRecv OBJECT-TYPE
    SYNTAX  Counter32
    MAX-ACCESS  read-only
    STATUS  current
    DESCRIPTION
           "This object contains the the number of packets received from the
        server at the time of interrogation."
    ::= { mpeDevFileXferConfigEntry  9 }

mpeDevFileXferOctetsSent OBJECT-TYPE
    SYNTAX  Counter32
    MAX-ACCESS  read-only
    STATUS  current
    DESCRIPTION
           "This object contains the the number of octets sent to the
        server at the time of interrogation."
    ::= { mpeDevFileXferConfigEntry  10 }

mpeDevFileXferOctetsRecv OBJECT-TYPE
    SYNTAX  Counter32
    MAX-ACCESS  read-only
    STATUS  current
    DESCRIPTION
           "This object contains the the number of octets received from the
        server at the time of interrogation."
    ::= { mpeDevFileXferConfigEntry  11 }

mpeDevFileXferOwnerString OBJECT-TYPE
    SYNTAX   OCTET STRING (SIZE(0..255))
    MAX-ACCESS  read-create
    STATUS  current
    DESCRIPTION
           "The entity which currently has the 'ownership'
        required to invoke the operation on this index."
    ::= { mpeDevFileXferConfigEntry  12 }

mpeDevFileXferStatus OBJECT-TYPE
    SYNTAX  INTEGER {
                 none(1),
                 success(2),
                 failure(3),
                 inprogress(4)
               }
    MAX-ACCESS  read-only
    STATUS  current
    DESCRIPTION
           "This object contains the status of the file transfer."
    ::= { mpeDevFileXferConfigEntry  13 }

mpeDevFileXferErrorStatus OBJECT-TYPE
    SYNTAX  Integer32
    MAX-ACCESS  read-only
    STATUS  current
    DESCRIPTION
           "This object contains the reason code of the failure determined in 
mpeDevFileXferStatus.
        The reason code are specific to the file transfer protocol.

        Please refer to the file transfer protocols respective RFC for 
clarification
        of the error code value meanings.

        TFTP Error Codes from rfc 1350
        FTP Error Codes from rfc 959"

    ::= { mpeDevFileXferConfigEntry  14 }

mpeDevFileXferSendEvent OBJECT-TYPE
    SYNTAX INTEGER {
    active(1),
    inactive(2)
    }
    MAX-ACCESS read-create
    STATUS current
    DESCRIPTION
        "This object indicates whether or not to send the 
         mpeDevFileXferEvent event trap ."
    ::= { mpeDevFileXferConfigEntry  15 }

mpeDevFileXferRowStatus OBJECT-TYPE
    SYNTAX  RowStatus
    MAX-ACCESS  read-create
    STATUS  current
    DESCRIPTION
           "This object is used to create
     a new row or delete an
     existing row in this table."
    ::= { mpeDevFileXferConfigEntry  16 }

mpeDevFileXferXferTime OBJECT-TYPE
    SYNTAX  TimeTicks 
    MAX-ACCESS  read-only
    STATUS  current
    DESCRIPTION
        "This object indicates the elapsed time 
		(in hundredths of a second) of the file transfer."
    ::= { mpeDevFileXferConfigEntry 17 }

mpeDevFileXferFileFormat OBJECT-TYPE
    SYNTAX  INTEGER {
                      ascii(1),
                      binary(2)
                    }
    MAX-ACCESS  read-create
    STATUS  current
    DESCRIPTION
           "This object contains the file representation type. A
	   file representation type of ascii implies an ASCII,
	   non-print text file. A file representation type of 
	   binary implies an binary image file. The default file
	   representation type is binary(2)."

--    DEFVAL  { binary }
    ::= { mpeDevFileXferConfigEntry  18 }


-- ====================================================================
--
-- Firmware Control Table
--
-- This table is used to control and provide information concerning
-- firmware/executable images.
--
-- ====================================================================

mpeDevFirmwareControlTable OBJECT-TYPE
    SYNTAX SEQUENCE OF DevFirmwareControlEntry
    MAX-ACCESS  not-accessible
    STATUS  current
    DESCRIPTION
        "A list of the current Firmware Releases and their associated
         status.  Each Firmware Release will be indexed by a number
         from 1 to N.  The user will be able to view the Firmware
         Release String and Operational Status of the release (valid
                 or invalid) and activate a valid Firmware Release by changing
                 the Administration Status to active."
    ::= { mpeDevFirmwareControl 1 }

mpeDevFirmwareControlEntry OBJECT-TYPE
    SYNTAX  DevFirmwareControlEntry
    MAX-ACCESS  not-accessible
    STATUS  current
    DESCRIPTION
        "The Device Firmware Release entry."
    INDEX  { entPhysicalIndex, mpeDevFirmwareControlIndex }
    ::= { mpeDevFirmwareControlTable 1 }

DevFirmwareControlEntry ::=
    SEQUENCE {
    mpeDevFirmwareControlIndex
    Integer32,
    mpeDevFirmwareControlRelease
        DisplayString,
    mpeDevFirmwareControlOperStatus
        INTEGER,
    mpeDevFirmwareControlAdminStatus
        INTEGER
    }

mpeDevFirmwareControlIndex OBJECT-TYPE
    SYNTAX Integer32
    MAX-ACCESS read-only
    STATUS current
    DESCRIPTION
        "This object is used to index the Firmware table (range 1 to N)."
::= { mpeDevFirmwareControlEntry 1 }

mpeDevFirmwareControlRelease OBJECT-TYPE
    SYNTAX  DisplayString (SIZE (1..16))
    MAX-ACCESS  read-only
    STATUS  current
    DESCRIPTION
    "This object indicates the Software Release for
     this Firmware. If the Software Firmware is Operational Status
     is invalid, the Software Revision Number will be blank."
::= { mpeDevFirmwareControlEntry 2 }

mpeDevFirmwareControlOperStatus OBJECT-TYPE
    SYNTAX INTEGER {
    valid(1),
    invalid(2),
    unknown(3)
    }
    MAX-ACCESS read-only
    STATUS current
    DESCRIPTION
     "This object indicates whether or not the indexed
     Firmware entry contains a valid(1) or invalid(2) Firmware."
::= { mpeDevFirmwareControlEntry 3 }

mpeDevFirmwareControlAdminStatus OBJECT-TYPE
    SYNTAX INTEGER {
    active(1),
    inactive(2)
    }
    MAX-ACCESS read-create
    STATUS current
    DESCRIPTION
        "This object indicates whether or not the indexed
     Firmware entry is active(1) or inactive(2).
     Writing active(1) will activate that software release
     and cause the unit to reset (response may timeout).
     Writing active(1) to a Firmware entry whose
     mpeDevFirmwareControlOperStatus is invalid will return BAD VALUE.
     Writing inactive(2) will always return BAD VALUE."
::= { mpeDevFirmwareControlEntry 4 }

--
--      File Transfer Traps
--

mpeDevFileXferEvent NOTIFICATION-TYPE
	OBJECTS {  mpeDevFileXferStatus , mpeDevFileXferErrorStatus,
                                mpeDevFileXferOperation, mpeDevFileXferFileType,
                                mpeDevFileXferFileName }
	STATUS		current
   	DESCRIPTION
     		"This trap is to communicate a couple of things about
      		the completion of a file transfer.

                mpeDevFileXferStatus       - Did it complete successfully or not.
                mpeDevFileXferErrorStatus  - If not, what was the error code.
                mpeDevFileXferOperation    - What operation was performed?.
                mpeDevFileXferFileType     - Was it a firmware xfer or config?
                mpeDevFileXferFileName     - The name of the file transfered.
         	"

 ::= { mpeDevControlMIBTrapsV2 1 }

mpeDevHwControlGroup	OBJECT-GROUP
	OBJECTS		{ mpeDevControlReset,
		  	  mpeDevControlExtendedSelfTest  }
	STATUS		current
	DESCRIPTION	"Objects necessary to implement minimal hardware 
			control"
 ::= { mpeDevControlMIBGroups 1 }

mpeDevFileXferConfigGroup	OBJECT-GROUP
	OBJECTS		{ mpeDevFileXferFileName,
			  mpeDevFileXferCopyProtocol,
			  mpeDevFileXferFileType,
			  mpeDevFileXferServerIpAddress,
			  mpeDevFileXferUserName,
			  mpeDevFileXferUserPassword,
			  mpeDevFileXferOperation,
			  mpeDevFileXferPktsSent,
			  mpeDevFileXferPktsRecv,
			  mpeDevFileXferOctetsSent,
			  mpeDevFileXferOctetsRecv,
			  mpeDevFileXferOwnerString,
			  mpeDevFileXferStatus,
			  mpeDevFileXferErrorStatus,
			  mpeDevFileXferSendEvent,
			  mpeDevFileXferRowStatus,
			  mpeDevFileXferXferTime, 
			  mpeDevFileXferFileFormat }
	STATUS		current
	DESCRIPTION	"Object group used to implement file transfer 
			functionality"
  ::= { mpeDevControlMIBGroups 2 }

mpeDevFirmwareControlGroup	OBJECT-GROUP
	OBJECTS		{ mpeDevFirmwareControlIndex,
		 	  mpeDevFirmwareControlRelease,
			  mpeDevFirmwareControlOperStatus,
			  mpeDevFirmwareControlAdminStatus }
	STATUS		current
	DESCRIPTION	"Object group used to manage firmware releases on 
			devices"
  ::= { mpeDevControlMIBGroups 3 }

mpeDevTestControlGroup		OBJECT-GROUP
	OBJECTS       { mpeDevControlTestType,
			mpeDevControlTestStatus,
			mpeDevControlTestCmd
             	      }
	STATUS       current
	DESCRIPTION  "Objects necessary to implement device specific tests"
  ::= { mpeDevControlMIBGroups 4 }

mpeDevFileXferEventGroup	NOTIFICATION-GROUP
	NOTIFICATIONS	{ mpeDevFileXferEvent }
	STATUS		current
	DESCRIPTION	"Notifications associated with 
			mpeDevFileXferConfigGroup"
  ::= { mpeDevControlMIBGroups 5 }

END

PDN-MPE-HEALTH-AND-STATUS-MIB DEFINITIONS ::= BEGIN

-- Last-Updated: 6/16/00

-- Enterprise Health and Status  MIB (mpe support)
-- Copyright (C) 2000 Paradyne Corporation.
--
-- Created by : Wayne Jadoo / Prakash Easwar

IMPORTS
DisplayString
  FROM SNMPv2-TC
OBJECT-TYPE
  FROM RFC-1212
entPhysicalIndex
  FROM ENTITY-MIB  
mpe-devHealth
  FROM PDN-HEADER-MIB
TRAP-TYPE
  FROM RFC-1215
;

mpeDevHealthAndStatusMIBObjects  OBJECT IDENTIFIER ::= { mpe-devHealth  1 }
mpeDevHealthAndStatusMIBTraps    OBJECT IDENTIFIER ::= { mpe-devHealth  2 }

 -- groups for Paradyne  health and Status MIB

mpeDevHealthAndStatusTable OBJECT-TYPE
  SYNTAX  SEQUENCE OF MpeDevHealthAndStatusEntry
  ACCESS  not-accessible
  STATUS  mandatory
  DESCRIPTION
    "A table that contains information about an Entity's health."
::= { mpeDevHealthAndStatusMIBObjects 1 }

mpeDevHealthAndStatusEntry OBJECT-TYPE
  SYNTAX  MpeDevHealthAndStatusEntry
  ACCESS  not-accessible
  STATUS  mandatory
  DESCRIPTION
    "A list of information for an entity's health."
  INDEX  { entPhysicalIndex }
::= { mpeDevHealthAndStatusTable 1 }

MpeDevHealthAndStatusEntry ::=
  SEQUENCE 
  {
     mpeDevSelfTestResults DisplayString
  }

mpeDevSelfTestResults OBJECT-TYPE
  SYNTAX  DisplayString (SIZE (0..255))
  ACCESS  read-only
  STATUS  mandatory
  DESCRIPTION
    "Self-test results. Self-test (or power-up test) results
     summarizes the test results of each CCA, where each CCA test
     result is separated by a semi-colon. Refer to device-specific 
     user documentation for a complete description of the self test
     codes and messages."
::= { mpeDevHealthAndStatusEntry  1 }

-- Traps for Device failure 

mpeSelfTestFailure TRAP-TYPE
  ENTERPRISE  mpeDevHealthAndStatusMIBTraps
  VARIABLES { mpeDevSelfTestResults }
  DESCRIPTION
    "This trap signifies that the sending protocol's
     device has failed self test.
     The variable binding for this trap would be the selfTest
     devSelfTestResults object of the Health and Status MIB. The
     exact format of this display string will be well-documented
     in the Operational Specifications of the device."
::= 1

END

PDN-MPE-MIB2-MIB DEFINITIONS ::= BEGIN

-- Last-Updated: 1/28/2002

-- Enterprise mib-2 mib (mpe support)
-- Copyright (C) 2000 Paradyne Corporation.

-- Created by : Prakash Easwar

 IMPORTS
 DisplayString
 FROM SNMPv2-TC
 TimeTicks
 FROM RFC1155-SMI
 OBJECT-TYPE
 FROM RFC-1212
 TRAP-TYPE
 FROM RFC-1215
 entPhysicalIndex
 FROM ENTITY-MIB 
 mpe-mib2
 FROM PDN-HEADER-MIB
 ;

--Test
mpeMib2MIBObjects OBJECT IDENTIFIER ::= { mpe-mib2 1 }
mpeMib2MIBTraps   OBJECT IDENTIFIER ::= { mpe-mib2 2 }

mpeSystem OBJECT IDENTIFIER ::= { mpeMib2MIBObjects 1 }

-- the Enterprise System group

mpeSystemsTable OBJECT-TYPE
    SYNTAX  SEQUENCE OF MpeSystemsEntry
    ACCESS  not-accessible
    STATUS  mandatory
    DESCRIPTION
            "A table that contains general information about an Entity ."
    ::= { mpeSystem 1 }

mpeSystemsEntry OBJECT-TYPE
    SYNTAX  MpeSystemsEntry
    ACCESS  not-accessible
    STATUS  mandatory
    DESCRIPTION
            "A list of system information about an Entity  ."
              INDEX  { entPhysicalIndex }
   ::= { mpeSystemsTable 1 }

MpeSystemsEntry ::=
    SEQUENCE {
        mpeSysDescr    DisplayString (SIZE (0..255)),
        mpeSysObjectID OBJECT IDENTIFIER,
        mpeSysUpTime   TimeTicks,
        mpeSysContact  DisplayString (SIZE (0..255)),
        mpeSysName     DisplayString (SIZE (0..255)),
        mpeSysLocation DisplayString (SIZE (0..255)),
        mpeSysServices INTEGER (0..127)
   }

mpeSysDescr OBJECT-TYPE
    SYNTAX  DisplayString (SIZE (0..255))
    ACCESS  read-only
    STATUS  mandatory
    DESCRIPTION
            "A textual description of the entity.  This value
            should include the full name and version
            identification of the system's hardware type,
            software operating-system, and networking
            software.  It is mandatory that this only contain
            printable ASCII characters."
    ::= { mpeSystemsEntry 1 }

mpeSysObjectID OBJECT-TYPE
    SYNTAX  OBJECT IDENTIFIER
    ACCESS  read-only
    STATUS  mandatory
    DESCRIPTION
            "The vendor's authoritative identification of the
            network management subsystem contained in the
            entity.  This value is allocated within the SMI
            enterprises subtree (1.3.6.1.4.1) and provides an
            easy and unambiguous means for determining `what
            kind of box' is being managed.  For example, if
            vendor `Flintstones, Inc.' was assigned the
            subtree 1.3.6.1.4.1.4242, it could assign the
            identifier 1.3.6.1.4.1.4242.1.1 to its `Fred
            Router'."
    ::= { mpeSystemsEntry 2 }

mpeSysUpTime OBJECT-TYPE
    SYNTAX  TimeTicks
    ACCESS  read-only
    STATUS  mandatory
    DESCRIPTION
            "The time (in hundredths of a second) since the
            network management portion of the system was last
            re-initialized."
    ::= { mpeSystemsEntry  3 }

mpeSysContact OBJECT-TYPE
    SYNTAX  DisplayString (SIZE (0..255))
    ACCESS  read-write
    STATUS  mandatory
    DESCRIPTION
            "The textual identification of the contact person
            for this managed node, together with information
            on how to contact this person."
    ::= { mpeSystemsEntry  4 }

mpeSysName OBJECT-TYPE
    SYNTAX  DisplayString (SIZE (0..255))
    ACCESS  read-write
    STATUS  mandatory
    DESCRIPTION
            "An administratively-assigned name for this
            managed node.  By convention, this is the node's
            fully-qualified domain name."
    ::= { mpeSystemsEntry  5 }

mpeSysLocation OBJECT-TYPE
    SYNTAX  DisplayString (SIZE (0..255))
    ACCESS  read-write
    STATUS  mandatory
    DESCRIPTION
            "The physical location of this node (e.g.,
            `telephone closet, 3rd floor')."
    ::= { mpeSystemsEntry  6 }
          
mpeSysServices OBJECT-TYPE
    SYNTAX  INTEGER (0..127)
    ACCESS  read-only
    STATUS  mandatory
    DESCRIPTION
      "A value which indicates the set of services that
       this entity primarily offers.

       The value is a sum.  This sum initially takes the
       value zero, Then, for each layer, L, in the range
       1 through 7, that this node performs transactions
       for, 2 raised to (L - 1) is added to the sum.  For
       example, a node which performs primarily routing
       functions would have a value of 4 (2^(3-1)).  In
       contrast, a node which is a host offering
       application services would have a value of 72
       (2^(4-1) + 2^(7-1)).  Note that in the context of
       the Internet suite of protocols, values should be
       calculated accordingly:

       layer  functionality
         1  physical (e.g., repeaters)
         2  datalink/subnetwork (e.g., bridges)
         3  internet (e.g., IP gateways)
         4  end-to-end  (e.g., IP hosts)
         7  applications (e.g., mail relays)

       For systems including OSI protocols, layers 5 and
       6 may also be counted."
   ::= { mpeSystemsEntry 7 }

END

-- ===============================================================
-- Copyright (C) 2003 Paradyne Corporation.
-- ===============================================================

PDN-MPE-DSLAM-SYSTEM-MIB DEFINITIONS ::= BEGIN

IMPORTS
   NOTIFICATION-TYPE,
   OBJECT-TYPE,
   MODULE-IDENTITY,
   Integer32,
   TimeTicks
	FROM SNMPv2-SMI
   OBJECT-GROUP, NOTIFICATION-GROUP,
   MODULE-COMPLIANCE
	FROM SNMPv2-CONF
   TruthValue, TEXTUAL-CONVENTION
	FROM SNMPv2-TC
   SnmpAdminString
        FROM SNMP-FRAMEWORK-MIB
   ContactState
	FROM PDN-TC
   entPhysicalIndex,
   entPhysicalEntry
	FROM ENTITY-MIB
   pdn-mpe
	FROM PDN-HEADER-MIB
   mpeSysObjectID
        FROM PDN-MPE-MIB2-MIB

;

mpe-dslam	 MODULE-IDENTITY
   LAST-UPDATED    "200306060000Z"  -- June 6, 2003
   ORGANIZATION    "Paradyne Corporation
		    MIB Working Group"

   CONTACT-INFO    "Paradyne Corporation
		    8545 126th Avenue North
		    Largo, FL 33733
		    www.paradyne.com

		    General Comments to: mibwg_team@paradyne.com

		    Editors
                    Prakash Easwar
                    Jesus Pinto
		    Dragana Gough
                    Clay Sikes"

  DESCRIPTION
   "The mpe dslam MIB. This MIB is written specifically to
   extend entPhysicalTable." 

   REVISION "200306060000Z"  -- June 6, 2003
   DESCRIPTION "Jesus Pinto and Clay Sikes
               Removed the entPhysicalIndex as an object in the
               mpeAlarmRelayInputStateChanged notification. This
               object was redundant in that it's the instance
               part of the mpeAlarmRelayState object."

   REVISION "200304250000Z"  -- April 25, 2003
   DESCRIPTION "Jesus Pinto and Clay Sikes
               Change mpeAlarmRelayInputState to mpeAlarmRelayState
               and changed it from a read-only object to a read-
               write object. This should give ultimate flexibility."

   REVISION "200304180000Z"  -- April 18, 2003
   DESCRIPTION "Jesus Pinto and Clay Sikes
               Needed objects to read Alarm Relay Input State. The
               addition of mpeEntPhysicalExtAlarmRelayInputContactState
               below was not a good idea as it implied a dense augments.
               mpeEntPhysicalExtAlarmRelayInputContactState was deprecated.

               Added a new table, mpeAlarmRelayTable to hold alarm
               relay objects where the table implies a sparse augments.
               Deprecated mpeAlarmRrelayEquipmentIndex, 
               mpeAlarmRelayInputContactState, and the
               mpeAlarmRelayInputcontactStateChanged trap they were
               designed for to discourage use in new projects. Added a new 
               trap, mpeAlarmRelayInputStateChanged, as a replacement that
               uses objects defined in or related to the mpeAlarmRelayTable.

               The mpeAlarmRelayTable allows Alarm Relay Input state to be
               read and has a direct relationship with the objects defined
               for the mpeAlarmRelayInputStateChanged trap. Since this table
               is indexed the entPhysicalIndex, it is extremely flexible in 
               that it can apply to a Single Management Entity / Single 
               Logical Entity, a chassis, or what ever level of granularity 
               is desired in the implementation."

   REVISION "200303201500Z"  -- March 20, 2003
   DESCRIPTION "Added new notifications to complement the
		entConfigChange notification defined in RFC2737."

   REVISION "200303070000Z"  -- March 7, 2003
   DESCRIPTION "Added mpeEntPhysicalExtAlarmRelayInputContactState."

   REVISION "200210250000Z"  -- October 25, 2002
   DESCRIPTION "Added mpeEntPhysicalExtTable and cleaned up some
                MIB compiler warnings."

   REVISION "200208150000Z"
   DESCRIPTION "Added mpeAlarmRelayEquipIndex, 
                Added mpeAlarmRelayInputContactState,
		Added mpeAlarmRelayInputContactStateChanged trap."

   REVISION "200202210000Z"
   DESCRIPTION "Added mpeDeviceFailureCleared Trap."

   REVISION "200201280000Z"
   DESCRIPTION "Added table to extend entityPhysicalTable by
		one object that would specify state of the alarm." 

   REVISION "200001220000Z"
   DESCRIPTION "Initial Release" 

   ::= { pdn-mpe 24 }

mpeSysDevDslamMIBObjects OBJECT IDENTIFIER ::= { mpe-dslam 1 }
mpeSysDevDslamMIBTraps   OBJECT IDENTIFIER ::= { mpe-dslam 2 }
mpeEntExtAlarms          OBJECT IDENTIFIER ::= { mpeSysDevDslamMIBObjects 1}
mpeAlarmRelay            OBJECT IDENTIFIER ::= { mpeSysDevDslamMIBObjects 2}
mpeEntExtMibObjects      OBJECT IDENTIFIER ::= { mpeSysDevDslamMIBObjects 3}
mpeSysDevDslamMIBNotifications   OBJECT IDENTIFIER ::= { mpeSysDevDslamMIBTraps 0 }



-- =========================================================================
-- Textual Conventions
-- =========================================================================


MpeEntExtAdminStatus ::= TEXTUAL-CONVENTION
    STATUS      current
    DESCRIPTION "Values to support the desired state of the entity.
                These values were selected to correspond to the syntax of
                the ifAdminStatus in the IF-MIB."
    SYNTAX INTEGER {
        up(1),       -- The Administrator considers the entity to be in
                     -- the 'up' or 'operational' state.
        down(2),     -- The Administrator considers the entity to be in 
                     -- the 'down' or non-operational' state. Generally
                     -- in this state, alarms or traps should not be reported.
        testing(3)   -- The Administrator considers the entity to be in
                     -- a state where the entity is under going some sort
                     -- of tests.
    }

MpeEntExtOperStatus ::= TEXTUAL-CONVENTION
    STATUS      current
    DESCRIPTION "Values to support the current operational state of the 
                entity. These values were selected to correspond to the
                syntax of the ifOperStatus in the IF-MIB."
    SYNTAX INTEGER {
        up(1),            -- The entity is operational.
        down(2),          -- The entity is non-operational.
        testing(3),       -- The entity is in some test mode.
        unknown(4),       -- The entity is in an 'unknown' state.
        dormant(5),       -- The entity is in a 'dormant' state.
        notPresent(6),    -- The entity was present, but is currently
                          -- not present.
        reserved1(7)      -- Not used, but reserved.
    }


-- =========================================================================
-- MIB Objects
-- =========================================================================

--
--ALARM objects
--

mpeEntExtAlarmTable OBJECT-TYPE
    SYNTAX SEQUENCE OF MpeEntExtAlarmEntry
    MAX-ACCESS not-accessible
    STATUS current
    DESCRIPTION
        "This table lists the alarm states of the objects
	listed in the entity-MIB entPhysicalTable."
    ::= { mpeEntExtAlarms 1 }

mpeEntExtAlarmEntry OBJECT-TYPE
    SYNTAX MpeEntExtAlarmEntry
    MAX-ACCESS not-accessible
    STATUS current
    DESCRIPTION
        "An mpeEntExtAlarmTable entry indicates the 
        alarm state of the physical entity."
    AUGMENTS { entPhysicalEntry }
    ::= { mpeEntExtAlarmTable 1 }

MpeEntExtAlarmEntry ::= SEQUENCE {
    mpeEntExtAlarm TruthValue
    }

mpeEntExtAlarm OBJECT-TYPE
    SYNTAX TruthValue
    MAX-ACCESS read-only
    STATUS current
    DESCRIPTION
        "This variable indicates the alarm state of the
	 physical entity."
    ::= { mpeEntExtAlarmEntry 1 }

-- 
-- AlarmRelay objects. For the purpose of being used
-- as VarBinds for the AlarmRelayInputContact trap.
--
mpeAlarmRelayEquipIndex OBJECT-TYPE
    SYNTAX Integer32
    MAX-ACCESS accessible-for-notify
    STATUS deprecated
    DESCRIPTION
        "This variable is the index of the equipment whose
	alarms are being relayed. It is a integer number
	starting from 1 until the max number of physical
	connectors the DSLAM device has to support relay.

        NOTE: This object has been deprecated. Please consider using
              the mpeAlarmRelayTable and mpeAlarmRelayInputStateChanged
              objects."
    ::= { mpeAlarmRelay 1 }

mpeAlarmRelayInputContactState OBJECT-TYPE
    SYNTAX ContactState
    MAX-ACCESS accessible-for-notify
    STATUS deprecated
    DESCRIPTION
        "This variable indicates the alarm state of the
	 Input Contact (open/closed).

        NOTE: This object has been deprecated. Please consider using
              the mpeAlarmRelayTable and mpeAlarmRelayInputStateChanged
              objects."
    ::= { mpeAlarmRelay 2 }


-- =========================================================================
-- Alarm Relay Table
-- =========================================================================

mpeAlarmRelayTable OBJECT-TYPE
    SYNTAX      SEQUENCE OF MpeAlarmRelayEntry
    MAX-ACCESS  not-accessible
    STATUS      current
    DESCRIPTION "This table holds objects that relate to Alarm Relay
                input or output."
    ::= { mpeAlarmRelay 3 }

mpeAlarmRelayEntry OBJECT-TYPE
    SYNTAX      MpeAlarmRelayEntry
    MAX-ACCESS  not-accessible
    STATUS      current
    DESCRIPTION "An entry in this table is a sparse augmentation of the
                entPhysicalEntry. As such, it is indexed by the 
                entPhysicalIndex and not an augmentation of the
                entPhysicalTable."
    INDEX       { entPhysicalIndex }
    ::= { mpeAlarmRelayTable 1 }

MpeAlarmRelayEntry ::=
    SEQUENCE {
        mpeAlarmRelayState   ContactState
}

mpeAlarmRelayState OBJECT-TYPE
    SYNTAX      ContactState
    MAX-ACCESS  read-write
    STATUS      current
    DESCRIPTION "This object is used to read or write the state an alarm 
                relay input or output."
    ::= { mpeAlarmRelayEntry 1 }



-- =========================================================================
-- Augmentation of entPhysicalTable
-- =========================================================================

mpeEntPhysicalExtTable OBJECT-TYPE
    SYNTAX      SEQUENCE OF MpeEntPhysicalExtEntry
    MAX-ACCESS  not-accessible
    STATUS      current
    DESCRIPTION "This table contains entity information that is not defined 
                in the standard ENTITY-MIB."
    ::= { mpeEntExtMibObjects 1 }


mpeEntPhysicalExtEntry OBJECT-TYPE
    SYNTAX      MpeEntPhysicalExtEntry
    MAX-ACCESS  not-accessible
    STATUS      current
    DESCRIPTION "An entry extends the entPhysicalEntry defined in the 
                ENTITY-MIB."
    AUGMENTS    { entPhysicalEntry }
    ::= { mpeEntPhysicalExtTable 1 }

MpeEntPhysicalExtEntry ::=
    SEQUENCE {
        mpeEntPhysicalExtUpTime      TimeTicks,
        mpeEntPhysicalExtLocation    SnmpAdminString,
        mpeEntPhysicalExtAdminStatus MpeEntExtAdminStatus,
        mpeEntPhysicalExtOperStatus  MpeEntExtOperStatus
    }

mpeEntPhysicalExtUpTime OBJECT-TYPE
    SYNTAX      TimeTicks
    MAX-ACCESS   read-only
    STATUS      current
    DESCRIPTION "The time (in hundredths of a second --just like the
                sysUpTime) since the entity was last re-initialized."
    ::= { mpeEntPhysicalExtEntry 1 }

mpeEntPhysicalExtLocation OBJECT-TYPE
    SYNTAX      SnmpAdminString
    MAX-ACCESS  read-write
    STATUS      current
    DESCRIPTION "This object allows the manager to enter the location of 
                the physical entity where applicable. For example, in a 
                stack, chassis or units may be in different locations. In 
                this case, it would be logical for the manager to set this 
                object to the location of the associated chassis. 

                Where the location doesn't make sense, it is recommended 
                that the object return a zero-length string."
    ::= { mpeEntPhysicalExtEntry 2 }

mpeEntPhysicalExtAdminStatus OBJECT-TYPE
    SYNTAX      MpeEntExtAdminStatus
    MAX-ACCESS  read-write
    STATUS      current
    DESCRIPTION "The desired state of the entity."
    ::= { mpeEntPhysicalExtEntry 3 }

mpeEntPhysicalExtOperStatus OBJECT-TYPE
    SYNTAX      MpeEntExtOperStatus
    MAX-ACCESS  read-only
    STATUS      current
    DESCRIPTION "The current operational state of the entity."
    ::= { mpeEntPhysicalExtEntry 4 }



-- =========================================================================
--Traps
-- =========================================================================

mpeCcn NOTIFICATION-TYPE
  OBJECTS { entPhysicalIndex }
  STATUS current
  DESCRIPTION
    "This trap signifies a Configuration change  or 
     software upgrade in the xDSL card. This trap 
     is of 'warning' class"
::= { mpeSysDevDslamMIBTraps 7 }

mpeDeviceFailure NOTIFICATION-TYPE
  OBJECTS { entPhysicalIndex }
  STATUS current
  DESCRIPTION
    "This trap signifies that the sending protocol's
     device has failed and the failure was not a result
     of a device test. 
     Note there are no variable bindings for this trap"
::= { mpeSysDevDslamMIBTraps 15 }
 
mpeDeviceFailureCleared NOTIFICATION-TYPE
  OBJECTS { entPhysicalIndex }
  STATUS current
  DESCRIPTION
    "This trap signifies that the sending protocol's
     device has failed but now it is operational.
     Failure was not a result
     of a device test." 
::= { mpeSysDevDslamMIBTraps 16 }
 
mpeNonSupportedMCC NOTIFICATION-TYPE
  OBJECTS { mpeSysObjectID }
  STATUS current
  DESCRIPTION
    "AN has detected MCC firmware release too low to support
     this device"
::= { mpeSysDevDslamMIBTraps 20 }

mpeNonSupportedChassis NOTIFICATION-TYPE
  OBJECTS { mpeSysObjectID }
  STATUS current
  DESCRIPTION
    "AN in slot xx has been installed in a chassis that cannot
     support one or more of its features. "
::= { mpeSysDevDslamMIBTraps 21 }


mpeAlarmRelayInputContactStateChanged NOTIFICATION-TYPE
  OBJECTS { mpeAlarmRelayEquipIndex, mpeAlarmRelayInputContactState }
  STATUS deprecated
  DESCRIPTION
    "This trap signifies that the state of the InputContact Alarm
     has changed since last time.
     NOTE: This object has been deprecated. Please consider using
           the mpeAlarmRelayInputStateChanged notification."
::= { mpeSysDevDslamMIBTraps 22 }

mpeEntPhysicalExtEntityCreated NOTIFICATION-TYPE
  OBJECTS { entPhysicalIndex }
  STATUS current
  DESCRIPTION " This trap signifies that an instance of this entity has
		been created in the entPhysicalTable.

		This trap is generated in addition to the entConfigChange 
		notification defined in RFC2737."

::= { mpeSysDevDslamMIBTraps 23 }

mpeEntPhysicalExtEntityDeleted NOTIFICATION-TYPE
  OBJECTS { entPhysicalIndex }
  STATUS current
  DESCRIPTION " This trap signifies that an instance of this entity has
		been deleted from the entPhysicalTable.

		This trap is generated in addition to the entConfigChange
		notification defined in RFC2737."	

::= { mpeSysDevDslamMIBTraps 24 }

mpeEntPhysicalExtEntityChanged NOTIFICATION-TYPE
  OBJECTS { entPhysicalIndex }
  STATUS current
  DESCRIPTION " This trap signifies that an instance of this entity has
		been modified in the entPhysicalTable as a result of a
		change in any of the objects in that table.

		This trap is generated in addition to the entConfigChange 
		notification defined in RFC2737."

::= { mpeSysDevDslamMIBTraps 25 }

mpeAlarmRelayInputStateChanged NOTIFICATION-TYPE
  OBJECTS { mpeAlarmRelayState }
  STATUS current
  DESCRIPTION
    "This trap signifies that the state of the Alarm Relay Input
     has changed."
::= { mpeSysDevDslamMIBNotifications 26 }


-- =========================================================================
--CONFORMANCE
-- =========================================================================

mpeSysDevDslamConformance  OBJECT IDENTIFIER ::= { mpe-dslam 3 }

mpeSysDevDslamGroups OBJECT IDENTIFIER
    ::= { mpeSysDevDslamConformance 1 }

mpeSysDevDslamCompliances OBJECT IDENTIFIER
    ::= { mpeSysDevDslamConformance 2 }

mpeSysDevDslamDeprecatedGroup OBJECT IDENTIFIER
    ::= { mpeSysDevDslamConformance 3 }

-- =========================================================================
-- COMPLIANCE statements
-- =========================================================================

mpeSysDevDslamAlarmCompliances MODULE-COMPLIANCE
  STATUS current
  DESCRIPTION
    "The compliance statement for entities and their
    alarms states."
  MODULE -- this module
  GROUP mpeSysDevDslamAlarmStateGroup
	DESCRIPTION "The conditional objects in the group"
        OBJECT mpeEntExtAlarm
        DESCRIPTION
           "Write access is not required."

  ::= { mpeSysDevDslamCompliances 1 }

mpeSysDevDslamAlarmStateGroup OBJECT-GROUP
  OBJECTS {
     mpeEntExtAlarm
  }
  STATUS current
  DESCRIPTION
    "The collection of objects which are used
    to describe alarm states for equipments
    physically connected to a DSLAM device."
::= { mpeSysDevDslamGroups 1 }

mpeEntityExtNotificationGroup NOTIFICATION-GROUP
  NOTIFICATIONS {
      mpeCcn,
      mpeDeviceFailure,
      mpeDeviceFailureCleared,
      mpeNonSupportedMCC,
      mpeNonSupportedChassis,
      mpeEntPhysicalExtEntityCreated,
      mpeEntPhysicalExtEntityDeleted,
      mpeEntPhysicalExtEntityChanged,
      mpeAlarmRelayInputStateChanged
  }
  STATUS current
  DESCRIPTION
    "The collection of objects which are used
    to notify that trap conditions are met."
::= { mpeSysDevDslamGroups 2 }

mpeSysDevDslamAlarmRelayGroup OBJECT-GROUP
  OBJECTS {
     mpeAlarmRelayState
  }
  STATUS current
  DESCRIPTION
    "The collection of objects which are used
    for Alarm Relay objects."
::= { mpeSysDevDslamGroups 3 }

mpeEntPhysicalExtGroup OBJECT-GROUP
  OBJECTS {
    mpeEntPhysicalExtUpTime,
    mpeEntPhysicalExtLocation,
    mpeEntPhysicalExtAdminStatus,
    mpeEntPhysicalExtOperStatus
  }
  STATUS current
  DESCRIPTION
    "The collection of objects which are used
    in extending the entPhysicalTable."
::= { mpeSysDevDslamGroups 4 }


------------------------
-- Deprecated Objects --
------------------------
mpeDslamDeprecatedObjectsGroup OBJECT-GROUP
  OBJECTS {
    mpeAlarmRelayEquipIndex,
    mpeAlarmRelayInputContactState
  }
  STATUS deprecated
  DESCRIPTION
    "The collection of objects that have been deprecated."
::= { mpeSysDevDslamDeprecatedGroup 1 }

mpeDslamDeprecatedNotificationsGroup NOTIFICATION-GROUP
  NOTIFICATIONS {
    mpeAlarmRelayInputContactStateChanged
  }
  STATUS deprecated
  DESCRIPTION
    "The collection of traps/notifications that have been deprecated."
::= { mpeSysDevDslamDeprecatedGroup 2 }



END

-- ======================================================================
-- ==                                                                  ==
-- ==        Copyright (C) 2005 Paradyne Networks, Inc.                ==
-- ==                                                                  ==
-- ======================================================================


PDN-ARP-MIB DEFINITIONS ::= BEGIN

IMPORTS
   SwitchState, VnidRange
      FROM PDN-TC
   MacAddress, TruthValue, RowStatus
      FROM SNMPv2-TC
   IpAddress, OBJECT-TYPE, MODULE-IDENTITY, NOTIFICATION-TYPE,
   Integer32, Unsigned32
      FROM SNMPv2-SMI
   MODULE-COMPLIANCE, OBJECT-GROUP, NOTIFICATION-GROUP
      FROM SNMPv2-CONF
   ifIndex
      FROM IF-MIB
   ipNetToMediaIfIndex, ipNetToMediaEntry, ipNetToMediaPhysAddress
      FROM IP-MIB
   pdn-common
      FROM PDN-HEADER-MIB;

pdn-arp MODULE-IDENTITY
   LAST-UPDATED "200507190000Z"  -- July 19, 2005
   ORGANIZATION "Paradyne Networks, Inc.
                 MIB Working Group"
   CONTACT-INFO "Paradyne Corporation
                 8545 126th Avenue North
                 Largo, FL 33733
                 www.paradyne.com

                 General Comments to: mibwg_team@paradyne.com

                 Editors
                    Wayne Jadoo
                    Prakash Easwar
                    Dragana Gough
                    Clay Sikes"

  DESCRIPTION
     "This MIB contains objects that are used to configure
      ARP entries and display ARP information.

      =================================================================
      ==                                                             ==
      ==          Copyright (C) 2005 Paradyne Networks, Inc.         ==
      ==                                                             ==
      ================================================================="


   REVISION    "200507190000Z"  -- July 19, 2005
   DESCRIPTION "Clean up formatting and eliminated tabs.  Added missing
                periods. 
                Corrected SMIv2 issues identified by libsmi including:
                   1.  INTEGER objects that were not enumerations, were 
                       changed to Integer32.  
                   2.  Reworked the conformance.  Had to change the OID 
                       structure because the MODULE-COMPLIANCE section
                       was missing resulting in `group-unref' issues.
                   3.  The OID for unauthorizedUserEvent was change
                       such that the second-to-the-last number is now
                       `0' to satisfy SMIv2.
                   4.  Masked the warning that 
                       pdnNetTo8023MediaConfigVnidId should be 
                       non-accessible.
                   5.  Changed the import for ifIndex to be the IF-MIB.
                   6.  Change the import for ipNetToMedia objects to be
                       the IP-MIB.

                Added the pdnNetToMediaParamsAprTable to support 
                periodic sending of ARP requests.

                Noticed several inconsistencies with respect to ranges
                specified in the syntax clause and where was described
                in the description text.  These inconsistencies were
                not touched as in doing so could cause over-the-wire
                issues.
                Clay Sikes"

   REVISION    "200208020000Z"
   DESCRIPTION "Added vlan to ipNetToMediaConfig for the BitStorm 4800
                (Speedway product's R2.0 release."
   REVISION    "200204180000Z"
   DESCRIPTION "Added utl to ipNetToMediaConfig for the BitStorm 4800
                (Speedway) product."

   REVISION    "200112310000Z"
   DESCRIPTION "Added ipNetToMediaExtTable to extend ipNetToMediaTable adding
                NHR filed to it. 
                Added ipNetToMediaConfig objects (mux/basic and default nhr)
                Added ipNetToMediaLimit table."

   REVISION    "200101150000Z"
   DESCRIPTION "pdnNetTo8023Media MAC Address set to read-write to add ARP 
                entries other needed variables are index variables."

   REVISION    "200005020000Z"
   DESCRIPTION "Updated MIB file to add history." 

   ::= { pdn-common 27 }



pdnNetToMediaGenericMIBObjects  OBJECT IDENTIFIER ::= { pdn-arp 1 }
pdnNetToMediaMIBTraps           OBJECT IDENTIFIER ::= { pdn-arp 2 }
pdnNetToMediaMIBNotifications   OBJECT IDENTIFIER ::= { pdnNetToMediaMIBTraps 0 }
pdnNetToMediaParams             OBJECT IDENTIFIER ::= { pdnNetToMediaGenericMIBObjects 1 }
pdnNetToMediaConfig             OBJECT IDENTIFIER ::= { pdnNetToMediaGenericMIBObjects 2 }
pdnNetTo8023MediaConfig         OBJECT IDENTIFIER ::= { pdnNetToMediaGenericMIBObjects 3 }
pdnNetToMediaConformance        OBJECT IDENTIFIER ::= { pdnNetToMediaGenericMIBObjects 4 }


-- =================================================
-- == The ARP Parameters Configuration  group
-- =================================================

pdnNetToMediaParamsCompEntryTimeout OBJECT-TYPE
   SYNTAX      Integer32(0..99999)
   MAX-ACCESS  read-write
   STATUS      current
   DESCRIPTION "Complete Entry Timeout is the length of time that 
                a complete entry remains in the ARP table before 
                removal.  A complete entry is one for which there is 
                a MAC address -- i.e. a node has responded to the
                ARP request.  If an entry gets this old without being
                referenced, it will be removed from the table.  The 
                range for this parameter is 1  to 200000 minutes."
   DEFVAL { 20 }
   ::= { pdnNetToMediaParams 1 }

pdnNetToMediaParamsIncompEntryTimeout OBJECT-TYPE
   SYNTAX      Integer32(0..99999) 
   MAX-ACCESS  read-write
   STATUS      current
   DESCRIPTION "Incomplete Entry Timeout is the length of time that 
                an incomplete entry remains in the ARP table before 
                removal.  An incomplete entry is one for which there 
                is no MAC address -- i.e. an ARP request has been made,
                but no response has been received.  This is also the 
                amount of time that a packet will remain in the system 
                while waiting for address resolution.  The range 
                for this parameter is  1 to  255  minutes."
   DEFVAL { 3 }
   ::= { pdnNetToMediaParams 2 }
        
pdnNetToMediaParamsDefRouteEntryTimeout OBJECT-TYPE
   SYNTAX      Integer32(0..99999) 
   MAX-ACCESS  read-write
   STATUS      current 
   DESCRIPTION "Default Route Entry Timeout is the length of time 
                a default route entry will remain in the ARP table. 
                If default route gets this old without being referenced,
                an ARP request will be sent to the next hop router.
                If no response is received, it will be removed from 
                the ARP table and the card will switch to the next 
                reachable default route with the highest preference. 
                The range for this parameter is 1  to  20  minutes."
   DEFVAL { 1 }
   ::= { pdnNetToMediaParams 3 }


-- =======================================
-- == ARP Periodic Request (APR) Table
-- =======================================
pdnNetToMediaParamsAprTable OBJECT-TYPE
   SYNTAX      SEQUENCE OF PdnNetToMediaParamsAprEntry
   MAX-ACCESS  not-accessible
   STATUS      current
   DESCRIPTION "The ARP Periodic Request Table.
                This table allows timers which control the rate in 
                which ARP requests are periodically sent to IP 
                addresses to be configured and displayed."
   ::= { pdnNetToMediaParams 4 }

pdnNetToMediaParamsAprEntry OBJECT-TYPE
   SYNTAX      PdnNetToMediaParamsAprEntry
   MAX-ACCESS  not-accessible
   STATUS      current
   DESCRIPTION "An entry in the ARP Periodic Request Table.
                Each entry represents an IP address to send an ARP
                request to."
   INDEX       {  pdnNetToMediaParamsAprIpAddr }
   ::= { pdnNetToMediaParamsAprTable 1 }

PdnNetToMediaParamsAprEntry ::=
   SEQUENCE {
      pdnNetToMediaParamsAprIpAddr       IpAddress,
      pdnNetToMediaParamsAprRowStatus    RowStatus,
      pdnNetToMediaParamsAprReqPeriod    Unsigned32,
      pdnNetToMediaParamsAprTimeToNext   Unsigned32
   }

pdnNetToMediaParamsAprIpAddr OBJECT-TYPE
   SYNTAX      IpAddress
   MAX-ACCESS  not-accessible
   STATUS      current
   DESCRIPTION "Identifies the IP address to periodically send an ARP
                request to and is used to identify corresponding rows
                in the table."
   ::= { pdnNetToMediaParamsAprEntry 1 }

pdnNetToMediaParamsAprRowStatus OBJECT-TYPE
   SYNTAX      RowStatus
   MAX-ACCESS  read-create
   STATUS      current
   DESCRIPTION "This object allows create, change, and delete operations
                on the table."
   ::= { pdnNetToMediaParamsAprEntry 2 }

pdnNetToMediaParamsAprReqPeriod OBJECT-TYPE
   SYNTAX      Unsigned32(1..1440)
   UNITS       "minutes"
   MAX-ACCESS  read-create
   STATUS      current
   DESCRIPTION "Configures the period, in minutes, that ARP requests
                are periodically sent.  The range is from one request
                every minute to one request every day (1440 minutes)."
   ::= { pdnNetToMediaParamsAprEntry 3 }

pdnNetToMediaParamsAprTimeToNext OBJECT-TYPE
   SYNTAX      Unsigned32
   UNITS       "minutes"
   MAX-ACCESS  read-only
   STATUS      current
   DESCRIPTION "Indicates the time, in minutes, remaining before the
                next ARP request will be sent."
   ::= { pdnNetToMediaParamsAprEntry 4 }


-- ===========================================================
-- == The ARP Entry Configuration Table for 802.3 Media Cards
-- ===========================================================

pdnNetToMediaConfigTable OBJECT-TYPE
   SYNTAX      SEQUENCE OF PdnNetToMediaConfigEntry
   MAX-ACCESS  not-accessible
   STATUS      current 
   DESCRIPTION "A table displaying information about ARP entries."      
   ::= { pdnNetToMediaConfig 1 }

pdnNetToMediaConfigEntry OBJECT-TYPE
   SYNTAX      PdnNetToMediaConfigEntry
   MAX-ACCESS  not-accessible
   STATUS      current
   DESCRIPTION "A list of information for each ARP entry in the 
                ARP table to be displayed."
   INDEX       { ifIndex, pdnNetToMediaConfigIpAddr }
   ::= { pdnNetToMediaConfigTable 1 }

PdnNetToMediaConfigEntry ::=
   SEQUENCE {
      pdnNetToMediaConfigIpAddr     IpAddress,
      pdnNetToMediaConfigMacAddr    MacAddress,
      pdnNetToMediaConfigMin        Integer32,
      pdnNetToMediaConfigFlags      Integer32,
      pdnNetToMediaConfigTrailer    SwitchState,
      pdnNetToMediaConfigPerm       TruthValue,
      pdnNetToMediaConfigRowStatus  RowStatus
   }
          
pdnNetToMediaConfigIpAddr OBJECT-TYPE
   SYNTAX       IpAddress
   MAX-ACCESS   not-accessible
   STATUS       current
   DESCRIPTION" This objects corresponds to an IP Address of a
                Host or Client."
   ::= { pdnNetToMediaConfigEntry 1 }

pdnNetToMediaConfigMacAddr OBJECT-TYPE
   SYNTAX      MacAddress
   MAX-ACCESS  read-create
   STATUS      current
   DESCRIPTION "This object corresponds to a MAC Address of a Host 
                or Client."
   ::= { pdnNetToMediaConfigEntry 2 }

pdnNetToMediaConfigMin OBJECT-TYPE
   SYNTAX      Integer32(0..99999)
   MAX-ACCESS  read-only
   STATUS      current
   DESCRIPTION "This objects displays the number of minutes since an 
                ARP entry was last used." 
   ::= { pdnNetToMediaConfigEntry 3 }

pdnNetToMediaConfigFlags OBJECT-TYPE
   SYNTAX      Integer32 
   MAX-ACCESS  read-only
   STATUS      current
   DESCRIPTION "This object contains multiple information for an entry.
                The information can be interpreted as follows: 
                   0x0004  -- permanent entry 
                   0x0008  -- publish entry (respond for other host) 
                   0x0010  -- has requested trailers 
                   0x0020  -- Proxy ARP entry 
                   0x0040  -- Subnetted Proxy ARP entry 
                   0x0100  -- ARP For Default Gateway."
   ::= { pdnNetToMediaConfigEntry 4 }

pdnNetToMediaConfigTrailer OBJECT-TYPE
   SYNTAX      SwitchState
   MAX-ACCESS  read-create
   STATUS      current
   DESCRIPTION "This object is used to specify whether 
                or not trailer encapsulation should be 
                enabled or disabled."
   ::= { pdnNetToMediaConfigEntry 5 }

pdnNetToMediaConfigPerm OBJECT-TYPE
   SYNTAX  TruthValue 
   MAX-ACCESS  read-create
   STATUS  current
   DESCRIPTION "This object is used to specify whether 
                or not an entry should be stored permanently
                in Non-volatile storage.  If the value is 
                'true' (1) a permanent entry is added to 
                non-volatile storage." 
   ::= { pdnNetToMediaConfigEntry 6 }

pdnNetToMediaConfigRowStatus OBJECT-TYPE
   SYNTAX  RowStatus 
   MAX-ACCESS  read-create
   STATUS  current
   DESCRIPTION "This object is used to create or delete a row in this
                table." 
::= { pdnNetToMediaConfigEntry 7 }


-- ===========================================================
-- == The ARP Entry Configuration Table for 802.3 Media Cards
-- ===========================================================

pdnNetTo8023MediaConfigTable OBJECT-TYPE
   SYNTAX  SEQUENCE OF PdnNetTo8023MediaConfigEntry
   MAX-ACCESS  not-accessible
   STATUS  current
   DESCRIPTION "A table displaying  information about ARP entries."
   ::= { pdnNetTo8023MediaConfig 1 }

pdnNetTo8023MediaConfigEntry OBJECT-TYPE
   SYNTAX      PdnNetTo8023MediaConfigEntry
   MAX-ACCESS  not-accessible
   STATUS      current
   DESCRIPTION "A list of information for each ARP entry in the 
                ARP table to be displayed."
   INDEX       { ifIndex,
                 pdnNetTo8023MediaConfigIpAddr, 
                 pdnNetTo8023MediaConfigVnidId }
   ::= { pdnNetTo8023MediaConfigTable 1 }

PdnNetTo8023MediaConfigEntry ::=
   SEQUENCE {
      pdnNetTo8023MediaConfigIpAddr     IpAddress,
      pdnNetTo8023MediaConfigVnidId     VnidRange,
      pdnNetTo8023MediaConfigMacAddr    MacAddress,
      pdnNetTo8023MediaConfigMin        Integer32,
      pdnNetTo8023MediaConfigFlags      Integer32,
      pdnNetTo8023MediaConfigTrailer    SwitchState,
      pdnNetTo8023MediaConfigPerm       TruthValue,
      pdnNetTo8023MediaConfigRowStatus  RowStatus
   }

pdnNetTo8023MediaConfigIpAddr OBJECT-TYPE
   SYNTAX  IpAddress
   MAX-ACCESS  not-accessible
   STATUS  current
   DESCRIPTION "This objects corresponds to an IP Address of a
                Host or Client."
   ::= { pdnNetTo8023MediaConfigEntry 1 }

pdnNetTo8023MediaConfigVnidId    OBJECT-TYPE
   SYNTAX  VnidRange
   MAX-ACCESS  read-only
   STATUS  current
   DESCRIPTION "The VNID Id number of the virtual network for which this 
                entry contains management information."
   ::= { pdnNetTo8023MediaConfigEntry 2 }

pdnNetTo8023MediaConfigMacAddr OBJECT-TYPE
   SYNTAX      MacAddress
   MAX-ACCESS  read-create
   STATUS      current
   DESCRIPTION "This object corresponds to a MAC Address of a Host 
                or Client."
   ::= { pdnNetTo8023MediaConfigEntry 3 }

pdnNetTo8023MediaConfigMin OBJECT-TYPE
   SYNTAX  Integer32(0..99999)
   MAX-ACCESS  read-only
   STATUS  current
   DESCRIPTION "This objects displays the number of
                minutes since an ARP entry was last 
                used." 
   ::= { pdnNetTo8023MediaConfigEntry 4 }

pdnNetTo8023MediaConfigFlags OBJECT-TYPE
   SYNTAX      Integer32 
   MAX-ACCESS  read-only
   STATUS      current
   DESCRIPTION "This object contains multiple information
                for an entry.  The information can be
                interpreted as follows: 
                   0x0004  -- permanent entry 
                   0x0008  -- publish entry (respond for other host) 
                   0x0010  -- has requested trailers 
                   0x0020  -- Proxy ARP entry 
                   0x0040  -- Subnetted Proxy ARP entry 
                   0x0100  -- ARP For Default Gateway." 
   ::= { pdnNetTo8023MediaConfigEntry 5 }

pdnNetTo8023MediaConfigTrailer OBJECT-TYPE
   SYNTAX      SwitchState
   MAX-ACCESS  read-create
   STATUS      current
   DESCRIPTION "This object is used to specify whether 
                or not trailer encapsulation should be 
                enabled or disabled." 
   ::= { pdnNetTo8023MediaConfigEntry 6 }

pdnNetTo8023MediaConfigPerm OBJECT-TYPE
   SYNTAX      TruthValue 
   MAX-ACCESS  read-create
   STATUS      current
   DESCRIPTION "This object is used to specify whether 
                or not an entry should be stored permanently
                in Non-volatile storage.  If the value is 
                'true' (1) a permanent entry is added to 
                non-volatile storage." 
   ::= { pdnNetTo8023MediaConfigEntry 7 }

pdnNetTo8023MediaConfigRowStatus OBJECT-TYPE
   SYNTAX      RowStatus 
   MAX-ACCESS  read-create
   STATUS      current
   DESCRIPTION "This object is used to create or delete a row in this
                table." 
   ::= { pdnNetTo8023MediaConfigEntry 8 }


-- ========================
-- == groups for ARP MIB
-- ========================

pdnNetToMediaClearAllArp  OBJECT-TYPE
   SYNTAX      INTEGER {
                  noop (1),
                  clear (2)
               }
   MAX-ACCESS  read-write
   STATUS      current
   DESCRIPTION "Setting this object to a value of 'clear' will remove 
                all entries from the ARP table."
   ::= { pdnNetToMediaConfig 2 }


-- ==============
-- == Proxy ARP 
-- ==============

pdnNetToMediaProxyArpTable  OBJECT-TYPE
   SYNTAX      SEQUENCE OF PdnNetToMediaProxyArpEntry
   MAX-ACCESS  not-accessible
   STATUS      current 
   DESCRIPTION "This table is used to enable or disable
                proxy ARP for the specified interface. "
   ::= { pdnNetToMediaConfig 3 }

pdnNetToMediaProxyArpEntry OBJECT-TYPE
   SYNTAX      PdnNetToMediaProxyArpEntry
   MAX-ACCESS  not-accessible
   STATUS      current
   DESCRIPTION "This is an entry that allows user to enable or disable
                proxy ARP for the specified interface."
   INDEX       { ifIndex }
   ::= { pdnNetToMediaProxyArpTable 1 }

PdnNetToMediaProxyArpEntry ::=
   SEQUENCE {
      pdnNetToMediaProxyArpStatus  INTEGER
   }

pdnNetToMediaProxyArpStatus   OBJECT-TYPE
   SYNTAX      INTEGER  { 
                  disable (1), 
                  enable (2) 
               }
   MAX-ACCESS  read-create
   STATUS      current
   DESCRIPTION "Setting this object to a value 'enable' will enable
                proxy ARP for the interface identified by IfIndex.
                The value 'disable' will disable proxy ARP for
                the interface. "
   ::= { pdnNetToMediaProxyArpEntry 1 }


-- ==============================================
-- == this group is used to configure proxy ARP
-- ==============================================

ipNetToMediaConfig OBJECT IDENTIFIER ::= { pdnNetToMediaConfig 4 }


ipNetToMediaForwardingMode   OBJECT-TYPE
   SYNTAX      INTEGER  { 
                  basic (1), 
                  mux (2), 
                  sms (3), 
                  ult(4), 
                  vlan(5) 
               }
   MAX-ACCESS  read-write
   STATUS      current 
   DESCRIPTION "Setting this object to a value 'basic' will configure 
                bridge to run in basic (transparent) mode.  Setting the 
                value to mux(2), will set bridge to run in
                mux forwarding mode.  For more information about 
                transparent vs. forwarding mode refer to RFC1483 that 
                defines bridge functionality and the mib RFC1493 that
                defines mib needed to support different bridge 
                functionality.

                Setting the value to ult(4), will enable Uplink Tagging.
                The Uplink Tagging Feature was added for the BitStorm 
                4800 and implements a portion of the IEEE 802.3Q VLAN 
                standard to provide tagged Ethernet frames on the uplink 
                port with a one-to-one mapping of ingress ADSL 
                (subscriber) link to the LAN identifier carried in the 
                Ethernet tag header.  See Speedway (4800) R1.1 Requirements 
                for detail. vlan(5) enables general VLAN support."

   ::= { ipNetToMediaConfig 1 }

ipNetToMediaDefaultNHR   OBJECT-TYPE
   SYNTAX      IpAddress
   MAX-ACCESS  read-write
   STATUS      current
   DESCRIPTION "Setting this address will configure default NHR for the
                system."
   ::= { ipNetToMediaConfig 2 }


-- ======================================================================
-- == this table is designed to augment ipNetToMediaTable from RFC1213
-- == new element is ipNetToMediaNHR
-- ======================================================================

-- ==============================================
-- == Extension to ip address translation table
-- ==============================================

ipNetToMediaExtTable OBJECT-TYPE
   SYNTAX      SEQUENCE OF IpNetToMediaExtEntry
   MAX-ACCESS  not-accessible
   STATUS      current
   DESCRIPTION "The IP Address Translation table used for mapping
                from IP addresses to physical addresses."
   ::= { ipNetToMediaConfig 3 }

ipNetToMediaExtEntry OBJECT-TYPE
   SYNTAX      IpNetToMediaExtEntry
   MAX-ACCESS  not-accessible
   STATUS      current
   DESCRIPTION "Each entry contains one IpAddress to `physical'
                address equivalence."
   AUGMENTS   { ipNetToMediaEntry }
   ::= { ipNetToMediaExtTable 1 }

IpNetToMediaExtEntry ::=
   SEQUENCE {
      ipNetToMediaNHR     IpAddress
   }

ipNetToMediaNHR OBJECT-TYPE
   SYNTAX      IpAddress 
   MAX-ACCESS  read-create
   STATUS      current
   DESCRIPTION "This object is used to configure nhr for the interface
                using proxy ARP."
::= { ipNetToMediaExtEntry 1 }


-- ==================================
-- == Proxy ARP configuration table
-- ==================================

ipNetToMediaLimitTable OBJECT-TYPE
   SYNTAX      SEQUENCE OF IpNetToMediaLimitEntry
   MAX-ACCESS  not-accessible
   STATUS      current
   DESCRIPTION "This table is used for to configure max number 
                of IP addresses allowed on that interface."
   ::= { ipNetToMediaConfig 4 }

ipNetToMediaLimitEntry OBJECT-TYPE
   SYNTAX      IpNetToMediaLimitEntry
   MAX-ACCESS  not-accessible
   STATUS      current
   DESCRIPTION "Each entry contains number of IP addresses allowed 
                on that interface."
   INDEX       { ipNetToMediaIfIndex }
   ::= { ipNetToMediaLimitTable 1 }

IpNetToMediaLimitEntry ::=
   SEQUENCE {
      ipNetToMediaLimitEnabled       TruthValue,
      ipNetToMediaMaxIPAddresses     Integer32
}

ipNetToMediaLimitEnabled OBJECT-TYPE
   SYNTAX      TruthValue
   MAX-ACCESS  read-create
   STATUS      current
   DESCRIPTION "This object is used to enable/disable limiting number of
                ip addresses on interfaces using proxy ARP."
   ::= { ipNetToMediaLimitEntry 1 }

ipNetToMediaMaxIPAddresses OBJECT-TYPE
   SYNTAX  Integer32(0..99999)
   MAX-ACCESS  read-create
   STATUS  current
   DESCRIPTION "This object is used to configure number of
                ip addresses allowed on interfaces using proxy ARP."
   ::= { ipNetToMediaLimitEntry 2 }


-- =============================================================
-- == NOTIFICATIONS
-- =============================================================

unauthorizedUserEvent NOTIFICATION-TYPE
   OBJECTS { 
               ipNetToMediaIfIndex, 
               ipNetToMediaPhysAddress 
   } 
   STATUS      current
   DESCRIPTION "This trap is to communicate that on the interface
                where security authorization (MAC or IP to port) is
                enabled, frame arrived that is not authorized for that 
                interface."
   ::= { pdnNetToMediaMIBNotifications 1 }




-- ======================================================================
-- ==                  Conformance Information                         ==
-- ======================================================================

pdnNetToMediaCompliances OBJECT IDENTIFIER ::= { pdnNetToMediaConformance 1 }
pdnNetToMediaGroups      OBJECT IDENTIFIER ::= { pdnNetToMediaConformance 2 }


-- ===========================
-- == Compliance Statements ==
-- ===========================

pdnNetToMediaCompliance MODULE-COMPLIANCE
   STATUS      current
   DESCRIPTION "The compliance statement for the entities which
                implement the PDN-ARP-MIB."
   MODULE      -- this module
   -- No mandatory groups are specified

   --
   -- Optional Groups
   --

   GROUP       pdnNetToMediaParamsGroup
   DESCRIPTION "This group is only required for implementations that
                need to configure the ARP table."

   GROUP       pdnNetToMediaConfigGroup
   DESCRIPTION "This group is only required for implementations that
                need to be able to add ARP table entries."

   GROUP       pdnNetToMedia8023ConfigGroup
   DESCRIPTION "This group is only required for implementations that
                need to be able to add 802.3 ARP table entries."

   GROUP       pdnNetToMediaClearGroup
   DESCRIPTION "This group is only required for implementations that
                need to be able to clear all ARP entries from a table."

   GROUP       pdnNetToMediaProxyArpGroup
   DESCRIPTION "This group is only required for implementations that
                need to be able to set all proxy ARP entries."

   GROUP       pdnNetToMediaConfigProxyArpGroup
   DESCRIPTION "This group is only required for implementations that
                need to allow the setting of some proxy ARP entries."

   GROUP       pdnNetToMediaExtGroup
   DESCRIPTION "This group is only required for implementations that
                need to allow the configuration of a next-hop router."

   GROUP       pdnNetToMediaLimitGroup
   DESCRIPTION "This group is only required for implementations that
                need to allow the configuration of limits for proxy
                ARP."

   GROUP       pdnNetToMediaUnauthorizedUserEventGroup
   DESCRIPTION "This group is only required for implementations that
                need generate notifications of unauthorized user
                events."

   GROUP       pdnNetToMediaParamsAprConfigGroup
   DESCRIPTION "This group is only required for implementations that
                need to configure a timer to send ARP requests to IP 
                addresses periodically."

   GROUP       pdnNetToMediaParamsAprTimeToNextGroup
   DESCRIPTION "This group is only required for implementations that
                need to configure a timer to send ARP requests to IP
                addresses periodically and that need to display the
                amount of time remaining until the next ARP request
                gets sent to a particular IP address."

   ::= { pdnNetToMediaCompliances 1 }


-- ==========================
-- == Units of Conformance ==
-- ==========================

pdnNetToMediaObjGroups   OBJECT IDENTIFIER ::= { pdnNetToMediaGroups 1 }
pdnNetToMediaNtfyGroups  OBJECT IDENTIFIER ::= { pdnNetToMediaGroups 2 }



-- ===================
-- == Object Groups ==
-- ===================

pdnNetToMediaParamsGroup    OBJECT-GROUP
   OBJECTS {
               pdnNetToMediaParamsCompEntryTimeout,
               pdnNetToMediaParamsIncompEntryTimeout,
               pdnNetToMediaParamsDefRouteEntryTimeout
   }
   STATUS      current
   DESCRIPTION "A collection of objects providing way to configure ARP table
                entries."
   ::= { pdnNetToMediaObjGroups 1 }

pdnNetToMediaConfigGroup    OBJECT-GROUP
   OBJECTS {
               pdnNetToMediaConfigMacAddr,
               pdnNetToMediaConfigMin,
               pdnNetToMediaConfigFlags,
               pdnNetToMediaConfigTrailer,
               pdnNetToMediaConfigPerm,
               pdnNetToMediaConfigRowStatus
   }
   STATUS      current
   DESCRIPTION "A collection of objects providing way to add ARP table
                entries."
   ::= { pdnNetToMediaObjGroups 2 }

pdnNetToMedia8023ConfigGroup    OBJECT-GROUP
   OBJECTS {
               pdnNetTo8023MediaConfigVnidId,
               pdnNetTo8023MediaConfigMacAddr,
               pdnNetTo8023MediaConfigMin,
               pdnNetTo8023MediaConfigFlags,
               pdnNetTo8023MediaConfigTrailer,
               pdnNetTo8023MediaConfigPerm,
               pdnNetTo8023MediaConfigRowStatus
   }
   STATUS      current
   DESCRIPTION "A collection of objects providing way to add 802.3 ARP table
                entries."
   ::= { pdnNetToMediaObjGroups 3 }

pdnNetToMediaClearGroup OBJECT-GROUP
   OBJECTS {
               pdnNetToMediaClearAllArp
   }
   STATUS      current
   DESCRIPTION "A collection of objects that allows to clear all arp entries 
                from a table."
   ::= { pdnNetToMediaObjGroups 4 }

pdnNetToMediaProxyArpGroup OBJECT-GROUP
   OBJECTS { 
               pdnNetToMediaProxyArpStatus
   }
   STATUS      current
   DESCRIPTION "A collection of objects that allows to set all proxy
                ARP entries."
   ::= { pdnNetToMediaObjGroups 5 }

pdnNetToMediaConfigProxyArpGroup OBJECT-GROUP
   OBJECTS {
               ipNetToMediaForwardingMode,
               ipNetToMediaDefaultNHR
   } 
   STATUS      current
   DESCRIPTION "A collection of objects that allows to set some proxy
                ARP entries."
   ::= { pdnNetToMediaObjGroups 6 }

pdnNetToMediaExtGroup OBJECT-GROUP
   OBJECTS {
               ipNetToMediaNHR
   }
   STATUS      current
   DESCRIPTION "A collection of objects that allows to set some proxy
                ARP entries."
   ::= { pdnNetToMediaObjGroups 7 }

pdnNetToMediaLimitGroup OBJECT-GROUP
   OBJECTS {
               ipNetToMediaLimitEnabled,
               ipNetToMediaMaxIPAddresses
   }
   STATUS      current
   DESCRIPTION "A collection of objects that allows to set some proxy 
                ARP entries."
   ::= { pdnNetToMediaObjGroups 8 }

pdnNetToMediaParamsAprConfigGroup OBJECT-GROUP
   OBJECTS {
               pdnNetToMediaParamsAprRowStatus,
               pdnNetToMediaParamsAprReqPeriod
   }
   STATUS      current
   DESCRIPTION "A collection of objects to configure a timer to send
                ARP request to IP addresses periodically."
   ::= { pdnNetToMediaObjGroups 9 }

pdnNetToMediaParamsAprTimeToNextGroup OBJECT-GROUP
   OBJECTS {
               pdnNetToMediaParamsAprTimeToNext
   }
   STATUS      current
   DESCRIPTION "Object to display the amount of time remaining until the
                next ARP request gets sent for a particular IP address."
   ::= { pdnNetToMediaObjGroups 10 }



-- =========================
-- == Notification Groups ==
-- =========================

pdnNetToMediaUnauthorizedUserEventGroup NOTIFICATION-GROUP
   NOTIFICATIONS {
               unauthorizedUserEvent
   }
   STATUS      current
   DESCRIPTION "Unauthorized user event group."
   ::= { pdnNetToMediaNtfyGroups 1 }




-- =========
-- == END == 
-- =========
END

PDN-ATMSTATS-MIB DEFINITIONS ::= BEGIN

IMPORTS
	MODULE-IDENTITY , OBJECT-TYPE, Integer32, Gauge32, Counter32
		FROM SNMPv2-SMI
	TimeInterval,RowStatus
		FROM SNMPv2-TC
	ifIndex
		FROM IF-MIB
   pdnAtm
		FROM PDN-HEADER-MIB
	atmVclVpi, atmVclVci
		FROM ATM-MIB;


-- ===============================================================
--
--   ATM Stats Group
--
--  Release: 1.0  05/26/99 (Initial Release)
--
--  Last Updated: 04/06/2004
--
--
    pdnAtmStatsMIB MODULE-IDENTITY
		LAST-UPDATED "200404060000Z"
		ORGANIZATION "Paradyne Networks
					  MIB Working Group"
		CONTACT-INFO
				      "Paradyne Networks
					   331 Newman Springs Road
		               Red Bank, NJ 07701
					   www.paradyne.com

					   General Comments to: mibwg_team@eng.paradyne.com"

		DESCRIPTION
		"This MIB Module supports ATM Statistics "

		REVISION "0203280000Z"
		DESCRIPTION  "D. Martinez
			1. Added objects to count the number of cells discarded due to
				congestion."

        REVISION "0203280000Z"
	         DESCRIPTION " D.GOUGH Added pdnAtmStatTable to count HEC and OCD errors 
		 per interface."

        REVISION "200004130000Z"
		DESCRIPTION "Z. Pan
			o	added pdnAtmVclCurrTable - a current 15 minute cells stats
			 	 and  pdnAtmVclHistTable - 96 -  15 minute history cells stats"

        REVISION "9905260000Z"
		DESCRIPTION "J. Strain
			o  Initial - VPL and VCL Stats Table"
	::= {  pdnAtm 3 }

pdnAtmVplStat OBJECT IDENTIFIER ::= { pdnAtmStatsMIB  1 }
pdnAtmVclStat OBJECT IDENTIFIER ::= { pdnAtmStatsMIB  2 }
pdnAtmStat OBJECT IDENTIFIER ::= { pdnAtmStatsMIB  3 }

-- ===============================================================
--
-- The following 2 tables were taken from draft-ietf-atommib-atm2-12.txt.
--			1) Atm VPL Statistics Table
--			2) Atm VCL Statistics Table
--
-- The following changes  were made to the VCL table:
--	  1)  This additional object 'pdnAtmVclStatRowStatus' is used to allow the
--		user to dynamically select the VCL's
--		the user would like to collect statistics on.
--	  2)  Added pdnAtmVclStatTotalOutDiscards.
--
-- The following changes  were made to the VPL table:
--	  1)  Added pdnAtmVplStatTotalOutDiscards.
--				
-- The following changes were made by D. Gough
-- 	1)Added pdnAtmStatTable to count HEC and OCD errors per interface
-- ===============================================================
--
--                   Definitions of Supplemental Managed Objects
--                               for ATM Management
--
--                                  March 13, 1998
-- 
-- 						Original Authors
-- 
--                               Faye Ly  (editor)
--                               3Com Corporation
--                                 fayely@3com.com
-- 
-- 
--                              Michael Noto  (editor)
--                          Network Equipment Technologies
--                                mike_noto@net.com
-- 
-- 
--                              Andrew Smith  (editor)
--                                 Extreme Networks
--                           ansmith@extremenetworks.com
-- 
-- 
--                          Ethan Mickey Spiegel  (editor)
--                                  Cisco Systems
--                                mspiegel@cisco.com
-- 
-- 
--                               Kaj Tesink  (editor)
--                           Bell Communications Research
--                               kaj@cc.bellcore.com
-- 
-- 
-- ===============================================================

-- ===============================================================
--	
--			Atm VPL Statistics Table
--
-- ===============================================================

              pdnAtmVplStatTable   OBJECT-TYPE
                  SYNTAX       SEQUENCE OF PdnAtmVplStatEntry
                  MAX-ACCESS   not-accessible
                  STATUS       current
                  DESCRIPTION
                      "This table contains all statistic counters per
                      VPL.  It is used to monitor the usage of the VPL
                      in terms of incoming cells and outgoing cells."
                  ::= { pdnAtmVplStat 1 }
 
              pdnAtmVplStatEntry    OBJECT-TYPE
                  SYNTAX       PdnAtmVplStatEntry
                  MAX-ACCESS   not-accessible
                  STATUS       current
                  DESCRIPTION
                      "Each entry in this table represents a VPL."
                  INDEX { pdnAtmVplStatIfIndex, pdnAtmVplStatVpi }
                  ::= { pdnAtmVplStatTable 1 }
 
              PdnAtmVplStatEntry ::=
                  SEQUENCE {
                      pdnAtmVplStatIfIndex           Integer32,
                      pdnAtmVplStatVpi               Integer32,
                      pdnAtmVplStatTotalCellIns      Counter32,
                      pdnAtmVplStatClp0CellIns       Counter32,
                      pdnAtmVplStatTotalDiscards     Counter32,
                      pdnAtmVplStatClp0Discards      Counter32,
                      pdnAtmVplStatTotalCellOuts     Counter32,
                      pdnAtmVplStatClp0CellOuts      Counter32,
                      pdnAtmVplStatTaggedOuts        Counter32,
                      pdnAtmVplStatTotalOutDiscards  Counter32
              }

              pdnAtmVplStatIfIndex OBJECT-TYPE
                  SYNTAX  Integer32
                  MAX-ACCESS  read-only
                  STATUS current
                  DESCRIPTION
                      "A unique value for each interface.  Its value
                      ranges between 1 and the value of ifNumber.  The
                      value for each interface must remain constant at
                      least from one re-initialization of the entity's
                      network management system to the next re-
                      initialization."
                  ::= { pdnAtmVplStatEntry 1 }

              pdnAtmVplStatVpi OBJECT-TYPE
                  SYNTAX   Integer32
                  MAX-ACCESS   read-only
	              STATUS   current
                  DESCRIPTION
                      "The VPI value of the VPL."
                  ::= { pdnAtmVplStatEntry 2 }
 
              pdnAtmVplStatTotalCellIns OBJECT-TYPE
                  SYNTAX   Counter32
                  MAX-ACCESS   read-only
                  STATUS   current
                  DESCRIPTION
                      "The total number of valid ATM cells received by
 
                      this VPL including both CLP=0 and CLP=1 cells.
                      The cells are counted prior to the application of
                      the traffic policing."
                  ::= { pdnAtmVplStatEntry 3 }
 
              pdnAtmVplStatClp0CellIns OBJECT-TYPE
                  SYNTAX   Counter32
                  MAX-ACCESS   read-only
                  STATUS   current
                  DESCRIPTION
                      "The number of valid ATM cells received by this
                      VPL with CLP=0.  The cells are counted prior to
                      the application of the traffic policing."
                  ::= { pdnAtmVplStatEntry 4 }
 
              pdnAtmVplStatTotalDiscards OBJECT-TYPE
                  SYNTAX   Counter32
                  MAX-ACCESS   read-only
                  STATUS   current
                  DESCRIPTION
                      "The total number of valid ATM cells discarded by
                      the traffic policing entity.  This includes cells
                      originally received with CLP=0 and CLP=1."
                  ::= { pdnAtmVplStatEntry 5 }
 
              pdnAtmVplStatClp0Discards OBJECT-TYPE
                  SYNTAX   Counter32
                  MAX-ACCESS   read-only
                  STATUS   current
                  DESCRIPTION
                      "The total number of valid ATM cells received with
                      CLP=0 an  discarded by the traffic policing
                      entity."
                  ::= { pdnAtmVplStatEntry 6 }
 
              pdnAtmVplStatTotalCellOuts OBJECT-TYPE
                  SYNTAX   Counter32
                  MAX-ACCESS   read-only
                  STATUS   current
                  DESCRIPTION
                      "The total number of valid ATM cells transmitted
                      by this VPL.  This includes both CLP=0 and CLP=1
                      cells."
                  ::= { pdnAtmVplStatEntry 7 }
 
 
              pdnAtmVplStatClp0CellOuts OBJECT-TYPE
                  SYNTAX   Counter32
                  MAX-ACCESS   read-only
                  STATUS   current
                  DESCRIPTION
                      "The total number of valid ATM cells transmitted
                      with CLP=0 by this VPL."
                  ::= { pdnAtmVplStatEntry 8 }
 
              pdnAtmVplStatTaggedOuts OBJECT-TYPE
                  SYNTAX   Counter32
                  MAX-ACCESS   read-only
                  STATUS   current
                  DESCRIPTION
                      "The total number of valid ATM cells tagged by the
                      traffic policing entity from CLP=0 to CLP=1 and
                      transmitted by this VPL."
                  ::= { pdnAtmVplStatEntry 9 }

              pdnAtmVplStatTotalOutDiscards OBJECT-TYPE
                  SYNTAX   Counter32
                  MAX-ACCESS   read-only
                  STATUS   current
                  DESCRIPTION
                      "The total number of ATM cells discarded due 
                      to congestion."
                  ::= { pdnAtmVplStatEntry 10 }

-- ===============================================================
--	
--			Atm VCL Statistics Table
--
-- ===============================================================
 
              pdnAtmVclStatTable   OBJECT-TYPE
                  SYNTAX   SEQUENCE OF PdnAtmVclStatEntry
                  MAX-ACCESS   not-accessible
                  STATUS   current
                  DESCRIPTION
                      "This table contains all statistic counters per
                      VCL.  It is used to monitor the usage of the VCL
                      in terms of incoming cells and outgoing cells."
                  ::= { pdnAtmVclStat 2 }
 
              pdnAtmVclStatEntry    OBJECT-TYPE
                  SYNTAX   PdnAtmVclStatEntry
                  MAX-ACCESS   not-accessible
                  STATUS   current
                  DESCRIPTION
                      "Each entry in this table represents a VCL."
                  INDEX {  pdnAtmVclStatIfIndex, pdnAtmVclStatVpi, pdnAtmVclStatVci }
                  ::= { pdnAtmVclStatTable 1 }
 
              PdnAtmVclStatEntry ::=
                  SEQUENCE {
                      pdnAtmVclStatIfIndex           Integer32,
                      pdnAtmVclStatVpi               Integer32,
                      pdnAtmVclStatVci               Integer32,
                      pdnAtmVclStatTotalCellIns      Counter32,
                      pdnAtmVclStatClp0CellIns       Counter32,
                      pdnAtmVclStatTotalDiscards     Counter32,
                      pdnAtmVclStatClp0Discards      Counter32,
                      pdnAtmVclStatTotalCellOuts     Counter32,
                      pdnAtmVclStatClp0CellOuts      Counter32,
                      pdnAtmVclStatTaggedOuts        Counter32,
                      pdnAtmVclStatRowStatus       	 RowStatus,
                      pdnAtmVclStatTotalOutDiscards  Counter32
                  }
 
              pdnAtmVclStatIfIndex OBJECT-TYPE
                  SYNTAX  Integer32
                  MAX-ACCESS  read-only
                  STATUS current
                  DESCRIPTION
                      "A unique value for each interface.  Its value
                      ranges between 1 and the value of ifNumber.  The
                      value for each interface must remain constant at
                      least from one re-initialization of the entity's
                      network management system to the next re-
                      initialization."
                  ::= { pdnAtmVclStatEntry 1 }
 
              pdnAtmVclStatVpi OBJECT-TYPE
                  SYNTAX     Integer32
                  MAX-ACCESS     read-only
                  STATUS     current
                  DESCRIPTION
                      "The VPI value of the VCL."
                  ::= { pdnAtmVclStatEntry 2 }

              pdnAtmVclStatVci OBJECT-TYPE
                  SYNTAX     Integer32
                  MAX-ACCESS     read-only
                  STATUS     current
                  DESCRIPTION
                      "The VCI value of the VCL."
                  ::= { pdnAtmVclStatEntry 3 }
 
              pdnAtmVclStatTotalCellIns OBJECT-TYPE
                  SYNTAX   Counter32
                  MAX-ACCESS   read-only
                  STATUS   current
                  DESCRIPTION
                      "The total number of valid ATM cells received by
                      this VCL including both CLP=0 and CLP=1 cells.
                      The cells are counted prior to the application of
                      the traffic policing."
                  ::= { pdnAtmVclStatEntry 4 }
 
              pdnAtmVclStatClp0CellIns OBJECT-TYPE
			      SYNTAX   Counter32
                  MAX-ACCESS   read-only
                  STATUS   current
                  DESCRIPTION
                      "The number of valid ATM cells received by this
                      VCL with CLP=0.  The cells are counted prior to
                      the application of the traffic policing."
                  ::= { pdnAtmVclStatEntry 5 }
 
              pdnAtmVclStatTotalDiscards OBJECT-TYPE
                  SYNTAX   Counter32
                  MAX-ACCESS   read-only
                  STATUS   current
                  DESCRIPTION
                      "The total number of valid ATM cells discarded by
                      the traffic policing entity.  This includes cells
                      originally received with CLP=0 and CLP=1."
                  ::= { pdnAtmVclStatEntry 6 }
 
              pdnAtmVclStatClp0Discards OBJECT-TYPE
                  SYNTAX   Counter32
                  MAX-ACCESS   read-only
                  STATUS   current
                  DESCRIPTION
                      "The total number of valid ATM cells received with
                      CLP=0 an  discarded by the traffic policing
                      entity."
                  ::= { pdnAtmVclStatEntry 7 }
 
              pdnAtmVclStatTotalCellOuts OBJECT-TYPE
                  SYNTAX   Counter32
                  MAX-ACCESS   read-only
                  STATUS   current
                  DESCRIPTION
                      "The total number of valid ATM cells transmitted
                      by this VCL.  This includes both CLP=0 and CLP=1
                      cells."
                  ::= { pdnAtmVclStatEntry 8 }
 
              pdnAtmVclStatClp0CellOuts OBJECT-TYPE
                  SYNTAX   Counter32
                  MAX-ACCESS   read-only
                  STATUS   current
                  DESCRIPTION
                      "The total number of valid ATM cells transmitted
                      with CLP=0 by this VCL."
                  ::= { pdnAtmVclStatEntry 9 }
 
              pdnAtmVclStatTaggedOuts OBJECT-TYPE
                  SYNTAX   Counter32
                  MAX-ACCESS   read-only
                  STATUS   current
                  DESCRIPTION
                      "The total number of valid ATM cells tagged by the
                      traffic policing entity from CLP=0 to CLP=1 and
                      transmitted by this VCL."
                  ::= { pdnAtmVclStatEntry 10 }


			pdnAtmVclStatRowStatus OBJECT-TYPE
				    SYNTAX  RowStatus
				    MAX-ACCESS  read-write
				    STATUS current
				    DESCRIPTION
			           "This object is used to create a new row
						 or delete an existing row in this table. When a new
						row is added, statistics are collected for the
						VCL. Statistics collection is terminated by deletion of the
						row."
				    ::= { pdnAtmVclStatEntry  11 }

              pdnAtmVclStatTotalOutDiscards OBJECT-TYPE
                  SYNTAX   Counter32
                  MAX-ACCESS   read-only
                  STATUS   current
                  DESCRIPTION
                      "The total number of ATM cells discarded due 
                      to congestion."
                  ::= { pdnAtmVclStatEntry 12 }

-- ===============================================================
--
-- ATM VCL current and historical fifteen-minute interval statistics 
-- pdnAtmfVclCurrTable and pdnAtmVclHistTable
--  ZPan.

-- Current fifteen-minute interval statistics per VCL

pdnAtmVclCurrTable OBJECT-TYPE
     SYNTAX    SEQUENCE OF    PdnAtmVclCurrEntry
     MAX-ACCESS     not-accessible
     STATUS    current
     DESCRIPTION
          "This table maintains per-TP statistics for the
          fifteen-minute interval currently being collected."
     ::= { pdnAtmVclStat 3 }

pdnAtmVclCurrEntry OBJECT-TYPE
     SYNTAX    PdnAtmVclCurrEntry
     MAX-ACCESS     not-accessible
     STATUS    current
     DESCRIPTION
          "An entry in this table for VCL termination points.
          Each VCL Termination Point automatically has
          an entry in this table associated with it."
     INDEX     { ifIndex, 
		 atmVclVpi,
		 atmVclVci }
     ::= { pdnAtmVclCurrTable 1 }

PdnAtmVclCurrEntry ::= SEQUENCE {
     pdnAtmVclCurrElapsedTime 	     TimeInterval,
     pdnAtmVclCurrTotalCellIns       Gauge32,
     pdnAtmVclCurrTotalInDiscards    Gauge32,
     pdnAtmVclCurrTotalCellOuts      Gauge32,
     pdnAtmVclCurrTotalOutDiscards   Gauge32
          }

pdnAtmVclCurrElapsedTime OBJECT-TYPE
     SYNTAX TimeInterval
     MAX-ACCESS read-only
     STATUS current
     DESCRIPTION
          "Amount of time, measured in seconds, that statistics
          for this entry (the current interval) have been counted."
     ::= { pdnAtmVclCurrEntry 1 }

pdnAtmVclCurrTotalCellIns OBJECT-TYPE
     SYNTAX    Gauge32
     MAX-ACCESS     read-only
     STATUS    current
     DESCRIPTION
          "The total number of valid ATM cells received by this VCL.
	       This number corresponds to that of toal cells recieved
           from CPE if this interface is a DSL ATM interface" 
     ::= { pdnAtmVclCurrEntry 2 }

pdnAtmVclCurrTotalInDiscards OBJECT-TYPE
     SYNTAX    Gauge32
     MAX-ACCESS     read-only
     STATUS    current
     DESCRIPTION
          "The number of discarded received cells."
     ::= { pdnAtmVclCurrEntry 3 }

pdnAtmVclCurrTotalCellOuts OBJECT-TYPE
     SYNTAX    Gauge32
     MAX-ACCESS     read-only
     STATUS    current
     DESCRIPTION
          "The number of cells that have been successfully sent.
	       This number corresponds to that of toal cells transmitted
           to CPE if this interface is a DSL ATM interface" 
     ::= { pdnAtmVclCurrEntry 4 }

pdnAtmVclCurrTotalOutDiscards OBJECT-TYPE
     SYNTAX    Gauge32
     MAX-ACCESS     read-only
     STATUS    current
     DESCRIPTION
          "The number of discarded transmitted cells since this interval."
     ::= { pdnAtmVclCurrEntry 5 }


-- History fifteen-minute interval statistics per VCL and time interval
-- These data are only recorded for permanent connections.

pdnAtmVclHistTable OBJECT-TYPE
     SYNTAX    SEQUENCE OF    PdnAtmVclHistEntry
     MAX-ACCESS     not-accessible
     STATUS    current
     DESCRIPTION
          "This table maintains per-interface statistics for previous
          fifteen-minute intervals."
     ::= { pdnAtmVclStat 4 }

pdnAtmVclHistEntry OBJECT-TYPE
     SYNTAX    PdnAtmVclHistEntry
     MAX-ACCESS     not-accessible
     STATUS    current
     DESCRIPTION
          "An entry in History Data table for VCL termination points.
          Each VCL Termination Point automatically has
          an entry in this table associated with it."
     INDEX     { ifIndex,
		     atmVclVpi,
		     atmVclVci,
	         pdnAtmVclHistIndex }
     ::= { pdnAtmVclHistTable 1 }

PdnAtmVclHistEntry ::= SEQUENCE {
     pdnAtmVclHistIndex            Integer32,
     pdnAtmVclHistElapsedTime      TimeInterval,
     pdnAtmVclHistTotalCellIns     Gauge32,
     pdnAtmVclHistTotalInDiscards  Gauge32,
     pdnAtmVclHistTotalCellOuts    Gauge32,
     pdnAtmVclHistTotalOutDiscards Gauge32
          }

pdnAtmVclHistIndex OBJECT-TYPE
     SYNTAX    Integer32 (1..96)
     MAX-ACCESS     not-accessible
     STATUS    current
     DESCRIPTION
          "A number between 1 and 96, which identifies the interval
          for which the set of statistics in this entry was
          collected.
          The interval identified by 1 is the most recently completed
          15 minute interval, and the interval identified by N is the
          interval immediately preceding the one identified by N-1."
     ::= { pdnAtmVclHistEntry 1 }

pdnAtmVclHistElapsedTime OBJECT-TYPE
     SYNTAX    TimeInterval
     MAX-ACCESS     read-only
     STATUS    current
     DESCRIPTION
          "Amount of Time, measured in units of 0.01 second, that
 	   statistics for this entry(the current interval) have been
	   counted."
     ::= { pdnAtmVclHistEntry 2 }

pdnAtmVclHistTotalCellIns OBJECT-TYPE
     SYNTAX    Gauge32
     MAX-ACCESS     read-only
     STATUS    current
     DESCRIPTION
          "The total number of valid ATM cells received by this VCL
	   during this interval.
	   This number corresponds to that of toal cells recieved
           from CPE if this interface is a DSL ATM interface" 
     ::= { pdnAtmVclHistEntry 3 }

pdnAtmVclHistTotalInDiscards OBJECT-TYPE
     SYNTAX    Gauge32
     MAX-ACCESS     read-only
     STATUS    current
     DESCRIPTION
          "The number of discarded received cells during this interval."
     ::= { pdnAtmVclHistEntry 4 }

pdnAtmVclHistTotalCellOuts OBJECT-TYPE
     SYNTAX    Gauge32
     MAX-ACCESS     read-only
     STATUS    current
     DESCRIPTION
          "The number of cells that have been successfully sent during
	       this interval.
	       This number corresponds to that of toal cells transmitted
           to CPE if this interface is a DSL ATM interface" 
     ::= { pdnAtmVclHistEntry 5 }

pdnAtmVclHistTotalOutDiscards OBJECT-TYPE
     SYNTAX    Gauge32
     MAX-ACCESS     read-only
     STATUS    current
     DESCRIPTION
          "The number of discarded transmitted cells during this interval."
     ::= { pdnAtmVclHistEntry 6 }

-- ===============================================================

-- ===============================================================
--	
--			Atm Statistics Table
--
-- ===============================================================

              pdnAtmStatTable   OBJECT-TYPE
                  SYNTAX       SEQUENCE OF PdnAtmStatEntry
                  MAX-ACCESS   not-accessible
                  STATUS       current
                  DESCRIPTION
                      "This table contains all statistic counters per
                      interface.  It is used to monitor the errors 
                      in terms of incoming cells."
                  ::= { pdnAtmStat 1 }
 
              pdnAtmStatEntry    OBJECT-TYPE
                  SYNTAX       PdnAtmStatEntry
                  MAX-ACCESS   not-accessible
                  STATUS       current
                  DESCRIPTION
                      "Each entry in this table represents a error count
		       per interface."
                  INDEX { ifIndex }
                  ::= { pdnAtmStatTable 1 }
 
              PdnAtmStatEntry ::=
                  SEQUENCE {
                      pdnAtmStatHECErrors         Counter32,
                      pdnAtmStatLCDErrors         Counter32	
              }

              pdnAtmStatHECErrors OBJECT-TYPE
                  SYNTAX   Counter32
                  MAX-ACCESS   read-only
                  STATUS   current
                  DESCRIPTION
                      "The total number of ATM cells discarded on 
		      this interface due to a HEC violation."
                  ::= { pdnAtmStatEntry 1 }

              pdnAtmStatLCDErrors OBJECT-TYPE
                  SYNTAX   Counter32
                  MAX-ACCESS   read-only
                  STATUS   current
                  DESCRIPTION
                      "The total number of Loss of Cell Delineataion
		      events (LCD) that occured on this interface."
                  ::= { pdnAtmStatEntry 2 }

END

PDN-CONFIG-MIB DEFINITIONS ::= BEGIN

IMPORTS
    ifIndex, ipAdEntAddr
        FROM RFC1213-MIB
    ifName
        FROM IF-MIB
    entPhysicalSerialNum
        FROM ENTITY-MIB
    Gauge
        FROM RFC1155-SMI
    DateAndTime, DisplayString 
        FROM SNMPv2-TC
    TRAP-TYPE
        FROM RFC-1215
    OBJECT-TYPE
        FROM RFC-1212
    pdn-devConfig
        FROM PDN-HEADER-MIB;

-- ===============================================================
--
-- Device Configuration
--
-- Version 1.0.14
--
-- Updated 07/13/04 Sue Alfano - Added devConfigOUI object, devConfigIpAddrChange trap.
--
-- Updated 02/05/04 Vic Sperry -  Added devConfigClockAutoSwitchback object
--				  that allows a customer to configure how a
--				  failed-then-recovered clock source is used.
--
-- Updated 01/09/04 Jesus Pinto - Added devCurrentClockSrcSelection object
--				  that indicates current selection of clksrc
--				  among configured choices (prim,second,etc.).
--				- Expanded list of devCfgWhichSrc to include
--				  a tertiary source.
--
-- Updated 10/11/03 Sue Alfano - Added devCfgClkRate devCurrClkSrcSelection object
--                               added new enum, external2, to devCfgClkSource.
--
-- Updated 03/07/02 Mohan Mohankumar - changed the description for the object
--				       devConfigTrapEnable to include support
--				       for path Trap and Latency Trap.
--
-- Updated 12/13/01 Dragana Gough - added new objects devConfigTestTimeout,
--				    devConfigTestDuration, devConfigComDiscTime,
--				    devConfigComInactivityTO, devConfigPortNumDisplayFormat,
--				    devConfigDateDisplayFormat, devAcceptRemoteResetFrame
--
-- 
-- Updated 12/04/01 Dragana Gough - updated DESCRIPTION filed for
--				    devConfigTimeOfDay
-- Updated 09/18/2000 Rob Steinberger - Added Usage Comments to 
--                                      devConfigChangeKeysTable
--
-- Updated 09/08/2000 Rob Steinberger - Added devConfigChangeKeysTable
--
-- Updated 05/19/2000 Rob Steinberger - Added dslNam and t3Nam card types
--
-- Updated 03/08/2000 Dragana Gough -updated devConfigTrapEnable documentation
--   to specify cases when the trap configuration is set per interface vs per 
--   entity.  Added Configuration change trap
--
-- Updated 02/10/2000 Dragana Gough -added bit field positions to devConfigTrapEnable
--   to enable disabling/enabling of linkUp and linkDown Traps
--
-- Updated 08/18/99 by J. Colom (jaime@paradyne.com)
--         (Added devConfigNetSyncRole 
--             Added devConfigTimeOfDay )
--
-- Updated 7/14/99 Jaime Colom - Adds dce6APM, sruAPM, ocu4APM, 
--   pktVoiceAPM, dpNAM, stNAM, ddsNAM, dualDsxNniNAM, t3NniNAM card 
--   types as well as acceptingAPM and failedAPM states.
--
-- Updated 7/29/98 Vince Ciletti - Adds 2 and 6 port OCU APM card types.
--
-- ==================================================================

devConfigArea OBJECT IDENTIFIER ::= { pdn-devConfig 1 }

devConfigAreaCopy OBJECT-TYPE
    SYNTAX  INTEGER {
        noOp(1),
        active-to-customer1(2),
        active-to-customer2(3),
        customer1-to-active(4),
        customer1-to-customer2(5),
        customer2-to-active(6),
        customer2-to-customer1(7),
        factory1-to-active(8),
        factory1-to-customer1(9),
        factory1-to-customer2(10),
        factory2-to-active(11),
        factory2-to-customer1(12),
        factory2-to-customer2(13),
        factory3-to-active(14),
        factory3-to-customer1(15),
        factory3-to-customer2(16),
        factory4-to-active(17),
        factory4-to-customer1(18),
        factory4-to-customer2(19),
        factory5-to-active(20),
        factory5-to-customer1(21),
        factory5-to-customer2(22),
        factory6-to-active(23),
        factory6-to-customer1(24),
        factory6-to-customer2(25),
        factory7-to-active(26),
        factory7-to-customer1(27),
        factory7-to-customer2(28),
        factory8-to-active(29),
        factory8-to-customer1(30),
        factory8-to-customer2(31),
        factory9-to-active(32),
        factory9-to-customer1(33),
        factory9-to-customer2(34)
    }
    ACCESS  read-write
    STATUS  mandatory
    DESCRIPTION
       "This object is used to copy the entire contents of one
        configuration area into another configuration area.  The
        supported number of factory configuration areas depends
        on the device model.  The value read from this object is
        always noOp(1)."
    ::= { devConfigArea 1 }

-- General device-wide configuration items

-- The Test Timeout group.  This group is used for configuring
-- timers associated with tests on the device.

devConfigTestTimer    OBJECT IDENTIFIER ::= { pdn-devConfig 2 }

devConfigTestTimeout OBJECT-TYPE
    SYNTAX  INTEGER {
        disable(1),    -- Tests will not be terminated
                       -- based on a timer.
        enable(2)      -- Tests will be terminated after
                       -- the duration specified by
                       -- devConfigTestDuration
    }
    ACCESS  read-write
    STATUS  mandatory
    DESCRIPTION
       "This object specifies whether tests are to be terminated
    after a defined duration.  If the value is enable(2), the
    duration is defined by devConfigTestDuration."
    ::= { devConfigTestTimer 1 }

devConfigTestDuration OBJECT-TYPE
    SYNTAX  INTEGER
    ACCESS  read-write
    STATUS  mandatory
    DESCRIPTION
       "This object specifies the duration that a test will be
    allowed to run before it is automatically terminated.
    Tests will only be terminated if devConfigTestTimeout
    is set to enable."
    ::= { devConfigTestTimer 2 }

-- The Clock Source group.

devConfigClockSrc    OBJECT IDENTIFIER ::= { pdn-devConfig 3 }

devConfigClockSrcTable OBJECT-TYPE
    SYNTAX  SEQUENCE OF DevConfigClockSrcEntry
    ACCESS  not-accessible
    STATUS  mandatory
    DESCRIPTION
        "The clock source table."
    ::= { devConfigClockSrc 1 }
 
devConfigClockSrcEntry OBJECT-TYPE
    SYNTAX  DevConfigClockSrcEntry
    ACCESS  not-accessible
    STATUS  mandatory
    DESCRIPTION
        "An entry in the clock source table."
    INDEX { devCfgClkWhichSrc }
    ::= { devConfigClockSrcTable 1 }
 
--
-- Layout of one entry in the devConfigClockSrcTable
--
 
DevConfigClockSrcEntry ::=
    SEQUENCE {
        devCfgClkWhichSrc    INTEGER,
        devCfgClkSource      INTEGER,
        devCfgClkIfIndex     INTEGER,
        devCfgClkRate        INTEGER
    }

devCfgClkWhichSrc OBJECT-TYPE
    SYNTAX  INTEGER {
        primary(1),     -- The primary master clock source
        secondary(2),   -- The secondary master clock source
	tertiary(3)     -- The Tertiary master clock source
    }
    ACCESS  read-only
    STATUS  mandatory
    DESCRIPTION
    "The clock source to which this entry is applicable."
    ::= { devConfigClockSrcEntry 1 }

devCfgClkSource OBJECT-TYPE
    SYNTAX  INTEGER {
        internal(1),    -- Master clock is the internal clock
        external(2),    -- Master clock is external clock source 1
        interface(3),   -- clock source is provided via an interface
        dbm(4),         -- clock source is provided via a backup module
        external2(5)    -- Master clock is external clock source 2
    }
    ACCESS  read-write
    STATUS  mandatory
    DESCRIPTION
       "This object is used to select the source for the master
        clock for the device.  The source selected provides
        synchronization for all the timing within the device,
        and the clocks for all of the external interfaces.

        If this object is interface(3), the specific interface
        used as the master clock source is specified using
        devCfgClkIfIndex.

        If this object is external(2), or external2(5), the clock
        rate can be specified using devCfgClkRate."
    ::= { devConfigClockSrcEntry 2 }

devCfgClkIfIndex OBJECT-TYPE
    SYNTAX  INTEGER
    ACCESS  read-write
    STATUS  mandatory
    DESCRIPTION
       "This object is used to select the interface to be used
        as the source for the master clock for the device, if
        devCfgClkSource is set to interface(3).  The interface
        selected provides synchronization for all the timing
        within the device, and the clocks for all of the
        external interfaces.
        NOTE:  if a synchronous data port is selected and the EDL
               is enabled for that synchronous data port, then the
               external device must provide a clock 8 Kbps less
               than the expected data port rate.  For example, if
               the data port rate is set at 64 Kbps, the external
               clock source needs to supply a 56 Kbps clock signal.

        If devCfgClkSource is not interface(3), the value of this
        object is meaningless."
    ::= { devConfigClockSrcEntry 3 }

devCfgClkRate OBJECT-TYPE
    SYNTAX  INTEGER {
        rate400Hz(1),
        rate8KHz(2),
        rate64KHz(3),
        rate1544KHz(4),
        rate2048KHz(5)
    }
    ACCESS  read-write
    STATUS  mandatory
    DESCRIPTION
       "This object is used to specify the clock signal
        rate associated with the external source selected by
        the devCfgClkSource object."
    ::= { devConfigClockSrcEntry 4 }

devCurrentClockSrcSelection OBJECT-TYPE
    SYNTAX  INTEGER ( 0 | 1..65535 )
    ACCESS  read-only
    STATUS  mandatory
    DESCRIPTION
        "The object is used to read the clock source that
	is currently selected by the device.
	
	This object will return a value that corresponds to
	a valid index in the devConfigClockSrcTable.

	For example if the secondary clock source is currently
	being selected by the device, then this object will
	return the value 'secondary (2)'. 

	The value of '0' will denote the default value (e.g, 
	local clock). The default value will be used in the
	case where the device is unable to select any of the
	configured clock sources.
	"
    ::= { devConfigClockSrc 2 }

devConfigClockSrcAutoSwitchback OBJECT-TYPE
    SYNTAX      INTEGER {
                    enabled(1),
                    disabled(2)
                }
    ACCESS      read-write
    STATUS      mandatory
    DESCRIPTION
        "This object controls whether or not the device is
         allowed to switch back to a failed clock source if
         the device detects that the clock source has
         recovered.

         If devConfigClockSrcAutoSwitchback is enabled, the
         device will always use the best clock source.

         If devConfigClockSrcAutoSwitchback is disabled, the
         device will switch away from a failed clock source,
         but will not switch back to the failed clock source,
         even if it has recovered, until this object has been
         manually changed to enabled.

         The intent of the disabled mode is to prevent the
         device from continuously switching away from and
         back to a marginal clock source, such as a port that
         is going up and down repeatedly.
	"
    DEFVAL      { disabled }
    ::= { devConfigClockSrc 3 }

-- The Trap Configuration group.

devConfigTrap    OBJECT IDENTIFIER ::= { pdn-devConfig 4 }

devConfigTrapEnable OBJECT-TYPE
    SYNTAX  INTEGER
    ACCESS  read-write
    STATUS  mandatory
    DESCRIPTION
       "Which trap types will be sent by the entity.  This
        object is a bit map represented as a sum, therefore,
        multiple trap types can be enabled simultaneously.
        This objects sets flag (enable/disable) value
        on entity level. If trap enable/disable flags are
        set per interface level by some other object
        this object will read 'enabled' if any one of the 
        interfaces is enabled. If any of the traps
        below are set to enabled by this object 
        it will enable that trap on all interfaces 
        on the entity.
        The various bit positions are:
            1  warmStart traps
            2  authenticationFailure traps
            4  enterpriseSpecific traps
            8  LinkUp trap
            16 LinkDown Trap
            32 path Trap
            64 Latency Trap."
    ::= { devConfigTrap 1 }

cCNTrapEnable OBJECT-TYPE
  SYNTAX  INTEGER
  ACCESS  read-write
  STATUS  mandatory
  DESCRIPTION
    " This object is used to enable or disable
      configuration change trap. It is a bit 
      sequence sum with only accepted values
      1 or 2. Setting the bit sequence to 2 
      would mean enabling the trap and 1 
      would mean disabling it."
  ::= { devConfigTrap 2 }

-- The Paradyne System Alarm group.

devConfigAlarm    OBJECT IDENTIFIER ::= { pdn-devConfig 5 }

devConfigAlarmRelayCutoff OBJECT-TYPE
    SYNTAX  INTEGER {
        noOp(1),
        off(2)
    }
    ACCESS  read-write
    STATUS  mandatory
    DESCRIPTION
       "Writing off(2) to this object will turn off the System
        Alarm Relay.  Reading this object will always return
        noOp(1)."
    ::= { devConfigAlarm 6 }

-- The Paradyne Card Type table.

-- This table is used by multi-slot devices.  It shows what
-- type of card has been configured to occupy each slot in
-- the chassis, and what card type is actually present in the
-- chassis.  If the configured and actual card types do not
-- match, this table allows the actual card type to be accepted,
-- which will change the configuration information for the card.

devConfigCardType    OBJECT IDENTIFIER ::= { pdn-devConfig 6 }

devConfigCardTypeTable OBJECT-TYPE
    SYNTAX  SEQUENCE OF DevConfigCardTypeEntry
    ACCESS  not-accessible
    STATUS  mandatory
    DESCRIPTION
       "The Paradyne Card Type Table."
    ::= { devConfigCardType 7 }

devConfigCardTypeEntry OBJECT-TYPE
    SYNTAX  DevConfigCardTypeEntry
    ACCESS  not-accessible
    STATUS  mandatory
    DESCRIPTION
       "An entry in the Paradyne Card Type Table."
    INDEX  { devCfgCardSlot }
    ::= { devConfigCardTypeTable 1 }

-- Layout of one entry in the devConfigCardTypeTable

DevConfigCardTypeEntry ::=
    SEQUENCE {
    devCfgCardSlot      INTEGER,
    devCfgCardConfig    INTEGER,
    devCfgCardActual    INTEGER,
    devCfgCardAction    INTEGER
    }


devCfgCardSlot OBJECT-TYPE
    SYNTAX  INTEGER
    ACCESS  read-only
    STATUS  mandatory
    DESCRIPTION
       "The slot number which this card occupies in the chassis."
    ::= { devConfigCardTypeEntry 1 }

devCfgCardConfig OBJECT-TYPE
    SYNTAX  INTEGER {
        emptySlot(1),          -- an empty slot
        unsupportedAPM(2),     -- an unrecognized APM
        t1NAM(3),              -- a 1T1/1DSX NAM
        syncDataAPM(4),        -- a synchronous data port APM
        voiceFxsAPM(5),        -- an FXS Voice APM
        voiceEmAPM(6),         -- an E&M Voice APM
        voiceFxoAPM(7),        -- an FXO Voice APM
        dsxAPM(8),             -- an DSX-1 APM
        t1NoDsxNAM(9),         -- a 2T1 with No DSX NAM
        misconfiguredAPM(10),  -- a misconfigured APM
        ocu2APM(11),           -- a 2 port OCU APM
        ocu6APM(12),           -- a 6 port OCU APM
        dce6APM(13),           -- a 6-port DCE APM 
        sruAPM(14),           -- a 5-port SubRate APM
        ocu4APM(15),           -- a 4-port Office Channel Unit APM
        pktVoiceAPM(16),       -- a Packet Voice APM  
        acceptingAPM(17),      -- Accepting State
        failedAPM(18),         -- APM position has failed card
        dpNAM(19),             -- Data Port NAM
        stNAM(20),             -- S/T ISDN NAM
        ddsNAM(21),            -- DDS NAM
        dualDsxNniNAM(22),     -- Dual Dsx-1 NNI NAM
        t3NniNAM(23),          -- T3 NNI NAM
        t3NAM(24),             -- T3 NAM
        dslNAM(25)             -- DSL NAM
    }
    ACCESS  read-only
    STATUS  mandatory
    DESCRIPTION
       "The type of card which has been configured for this slot."
    ::= { devConfigCardTypeEntry 2 }

devCfgCardActual OBJECT-TYPE
    SYNTAX  INTEGER {
        emptySlot(1),         -- an empty slot
        unsupportedAPM(2),    -- an unrecognized APM
        t1NAM(3),             -- a T1 NAM
        syncDataAPM(4),       -- a synchronous data port APM
        voiceFxsAPM(5),       -- an FXS Voice APM
        voiceEmAPM(6),        -- an E&M Voice APM
        voiceFxoAPM(7),       -- an FXO Voice APM
        voiceDsxAPM(8),       -- an DSX-1 APM
        t1NoDsxNAM(9),        -- a 2T1 with No DSX NAM
        misconfigured(10),    -- a misconfigured APM
        ocu2APM(11),          -- a 2 port OCU APM
        ocu6APM(12),          -- a 6 port OCU APM
        dce6APM(13),          -- a 6-port DCE APM 
        sruAPM(14),          -- a 5-port SubRate APM
        ocu4APM(15),          -- a 4-port Office Channel Unit APM
        pktVoiceAPM(16),      -- a Packet Voice APM  
        acceptingAPM(17),     -- Accepting State
        failedAPM(18),        -- APM position has failed card
        dpNAM(19),            -- Data Port NAM
        stNAM(20),            -- S/T ISDN NAM
        ddsNAM(21),           -- DDS NAM
        dualDsxNniNAM(22),    -- Dual Dsx-1 NNI NAM
        t3NniNAM(23),         -- T3 NNI NAM
        t3NAM(24),            -- T3 NAM
        dslNAM(25)            -- DSL NAM
    }
    ACCESS  read-only
    STATUS  mandatory
    DESCRIPTION
       "The type of card which is present in this slot."
    ::= { devConfigCardTypeEntry 3 }

devCfgCardAction OBJECT-TYPE
    SYNTAX  INTEGER {
        noOp(1),
        accept(2)
    }
    ACCESS  read-write
    STATUS  mandatory
    DESCRIPTION
       "Writing accept(2) to this object changes the configured
        card type to match the type of card currently present
        in the slot.  Reading this object always returns noOp(1)."
    ::= { devConfigCardTypeEntry 4 }

-- The Paradyne Device Network Synchronization group.

devConfigNetSync    OBJECT IDENTIFIER ::= { pdn-devConfig 7 }

devConfigNetSyncRole OBJECT-TYPE
    SYNTAX  INTEGER {
        none(1),
        tributary(2),
        controller(3)
    }
    ACCESS  read-write
    STATUS  mandatory
    DESCRIPTION
       "Network Time Synchronization role item for a device in the network.
          none       - Device will ignore network time synchronization messages.
          tributary  - Update the network reference time each time the device  
                       receives an update massage.
          controller - The device will generate the synchronization message and
                       Time of Day clock will be the same as the Network
                       Reference Time."
    DEFVAL  { tributary }
    ::= { devConfigNetSync 1 }

-- The Paradyne Device Configuration Time group.

devConfigTime    OBJECT IDENTIFIER ::= { pdn-devConfig 8 }

devConfigTimeOfDay OBJECT-TYPE
    SYNTAX  DateAndTime
    ACCESS  read-write
    STATUS  mandatory
    DESCRIPTION
    "This is standard definition of Device Time of Day
     (DateAndTime) SYNTAX. The only difference is
     that our group is defining timezone filed (8)
     optional.

     Display format-> 2d-1d-1d,1d:1d:1d.1d,1a1d:1d
	    Fields description
            field  octets  contents                  range
            -----  ------  --------                  -----
              1      1-2   year*                     0..65536
              2       3    month                     1..12
              3       4    day                       1..31
              4       5    hour                      0..23
              5       6    minutes                   0..59
              6       7    seconds                   0..60
                           (use 60 for leap-second)
              7       8    deci-seconds              0..9
              8       9    direction from UTC        '+' / '-'
              9      10    hours from UTC*           0..13
             10      11    minutes from UTC          0..59

            * Notes:
            - the value of year is in network-byte order
            - daylight saving time in New Zealand is +13

            For example, Tuesday May 26, 1992 at 1:30:15 PM EDT would be
            displayed as:

                             1992-5-26,13:30:15.0,-4:0

	    Timezone information (fileds 8-10)
	    is optional.
            Note that if only local time is known, then timezone
            information (fields 8-10) is not present."
    ::= { devConfigTime 1 }

-- The Paradyne Device Configuration Change Key Group

devConfigChangeKeys OBJECT IDENTIFIER ::= { pdn-devConfig 9 }

--
-- Configuration Change Keys Table
--
-- This table contains a set of keys specific to each non-volatile
-- database on the device.  The keys are ensured to change each time
-- there is a change to the database that they represent.
--
-- Example of Use:
--
--   1) Database Discovery
--      This MIB can be used to discover the various non-volatile
--      databases on a device.  Each database has a unique key.
--
--      The discovery process consists of walking devConfigChangeKeysDbKey.
--      Each response corresponds to a different database type.  The NMS
--      only needs to be concerned with the databases that affect them.
--      Each of the "interesting" database keys should be stored for later
--      reference.
--
--   2) Database monitoring
--         After discovery, the NMS can check the database keys of the
--         databases of interest to it either at specific intervals or
--         based on configuration change traps.  When using trap directed,
--         polling, a default polling interval should still apply in case
--         a trap is lost in the transmission process.
--         
--         Checking the keys consists of performing a get operation on
--         devConfigChangeKeysDbKey for the specific database(s) of interest.  
--         If the key has changed from that previously stored, the database
--         has changed.  The new key should be stored for future reference.
--

devConfigChangeKeysTable OBJECT-TYPE
    SYNTAX  SEQUENCE OF DevConfigChangeKeysEntry
    ACCESS  not-accessible
    STATUS  mandatory
    DESCRIPTION
       "The Paradyne Configuration Change Key Table. This table
        is in place to allow a Network Manager to know when the
        configuration on the device changes.  Configuration can
        be found in several databases that may each have a
        unique access method.  For this reason, the keys are
        in the form of a table."
    ::= { devConfigChangeKeys 1 }

devConfigChangeKeysEntry OBJECT-TYPE
    SYNTAX  DevConfigChangeKeysEntry
    ACCESS  not-accessible
    STATUS  mandatory
    DESCRIPTION
       "An entry in the Paradyne Configuration Change Key Table."
    INDEX  { devConfigChangeKeysDbType }
    ::= { devConfigChangeKeysTable 1 }

DevConfigChangeKeysEntry ::=
    SEQUENCE {
    devConfigChangeKeysDbType   INTEGER,
    devConfigChangeKeysDbKey    Gauge
    }

devConfigChangeKeysDbType OBJECT-TYPE
    SYNTAX  INTEGER {
              generalConfig(1),
              rmonAlarm(2),
              rmonUserHistory(3),
              routerConfig(4)
            }
    ACCESS  read-only
    STATUS  mandatory
    DESCRIPTION
       "The type of database that is being keyed.  If a specific
        type is not supported by the device, noSuchName should be
        returned."
    ::= { devConfigChangeKeysEntry 1 }

devConfigChangeKeysDbKey OBJECT-TYPE
    SYNTAX  Gauge
    ACCESS  read-only
    STATUS  mandatory
    DESCRIPTION
       "A unique value that will change each time the database is
        altered.  Effort should be made to increase the number of
        times the database can change without seeing the same
        key."
    ::= { devConfigChangeKeysEntry 2 }

-- The General Configuration group.

devConfiguration    OBJECT IDENTIFIER ::= { pdn-devConfig 10 }

	devConfigComDiscTime OBJECT-TYPE
	     SYNTAX  INTEGER
	     ACCESS  read-write
	     STATUS  mandatory
	     DESCRIPTION
		"This object is used to specify how long
		 to wait before disconnecting. Inactivity
		 is defined as no keyboard activity within
		 a given period of time. The time is kept
		 in seconds. The default is 300 seconds."
	    ::= { devConfiguration 1  }

        devConfigPortNumDisplayFormat OBJECT-TYPE
	    SYNTAX INTEGER {
		       sle(1),
		       unitport(2),
		       name(3)
		}
	    ACCESS read-write 
	    STATUS mandatory
	    DESCRIPTION
	       "This object is used to set display format for the
		port numbers. The default is unit/port number.
		sle(1) - this method is to use Single Logical Entity
			 interface numbers. For example, if sle is  
			 confiugred the sle numbers range from 1 to
			 384 for a stack of 8 units
			 with 48 ports each.
		unitport(2) - this method uses unitnumber/portnumber
			      For previous example the numbers would
			      be from 1/1 to  8/48.
		name(3) - This method allowes user to assign character
			  strings (names) to each interface and to view
			  the interfaces by names."
            ::= { devConfiguration 2 }


	devConfigDateDisplayFormat OBJECT-TYPE
	    SYNTAX INTEGER {
		    ddmmyy(1),
		    mmddyy(2)  
		}
	    ACCESS read-write
	    STATUS mandatory
	    DESCRIPTION
	      "This object is used to specify which format
	       will date be displayed in.The default is 'mmddyy'"
	    ::= { devConfiguration 3 }

       devAcceptRemoteResetFrame OBJECT-TYPE
	   SYNTAX INTEGER {
		    enable(1),
		    disable(2)
		 }
	   ACCESS read-write
	   STATUS mandatory
	   DESCRIPTION
	     "This object is used to enable/disable 
	      acceptance of remote reset frame which
	      would result in hardware reset.
	      The default setting is disabled."
	  ::= { devConfiguration 4 }

       devConfigOUI OBJECT-TYPE
           SYNTAX  DisplayString (SIZE (0..6))
           ACCESS  read-only
           STATUS  mandatory
           DESCRIPTION
             "This object is the Organizationally Unique Identifier (OUI)
              defined in ANSI/IEEE Std 802 and used to generate a 48 bit 
              universal LAN MAC address to identify LAN and MAN stations
              uniquely.  The OUI is represented as a six hexadecimal digit
              value using all upper-case letters and including any leading
              zeros.  The value of this object for Paradyne products
              appears as 00E039.

              If the OUI is unknown or non-existent, devConfigOUI will be
              set to a zero-length string."

           ::= { devConfiguration 5 }

--TRAP Group

cCN TRAP-TYPE
  ENTERPRISE devConfigTrap 
  VARIABLES { ifIndex }
  DESCRIPTION
    "This trap signifies a Configuration change  or 
     software upgrade. This trap 
     is of 'warning' class"
 ::= 7

devConfigIpAddrChange TRAP-TYPE
  ENTERPRISE devConfigTrap
  VARIABLES { devConfigOUI, entPhysicalSerialNum, ipAdEntAddr, ifName }
  DESCRIPTION
    "This trap signifies that an IP address change has occurred."
 ::= 8

END

-- =================================================================
-- ==                                                             ==
-- ==  Paradyne Extension to the BRIDGE-MIB.                      ==
-- ==                                                             ==
-- ==  Paradyne Networks was acquired by Zhone Technologies on    ==
-- ==  September 1, 2005.                                         ==
-- ==                                                             ==
-- ==         Copyright (C) 2005 Zhone Technologies, Inc.         ==
-- ==                                                             ==
-- =================================================================


PDN-CONTROL-MIB DEFINITIONS ::= BEGIN

IMPORTS
SwitchState 
	FROM PDN-TC
RowStatus, DisplayString 
	FROM SNMPv2-TC
ifIndex 
	FROM IF-MIB
Integer32, Counter32, IpAddress, TimeTicks, NOTIFICATION-TYPE, OBJECT-IDENTITY,
OBJECT-TYPE, MODULE-IDENTITY 
	FROM SNMPv2-SMI
MODULE-COMPLIANCE, OBJECT-GROUP, NOTIFICATION-GROUP 
	FROM SNMPv2-CONF 
entPhysicalIndex 
	FROM ENTITY-MIB
pdn-common 
	FROM PDN-HEADER-MIB;


pdnControl MODULE-IDENTITY
	LAST-UPDATED 	"200510180000Z"  -- October 18, 2005
	ORGANIZATION 	"Paradyne Networks
                         MIB Working Group
                         Other information about group editing the MIB module."
	CONTACT-INFO 	"Paradyne Networks, Inc.
			 8545 126th Avenue North
			 Largo, FL 33773
			 www.paradyne.com

			 General Comments to: mibwg_team@paradyne.com"

	DESCRIPTION	"This MIB Module allow a user to reset a device
			in the DSLAM, as well as perform various operations
			related to the storage and retrieval of firmware
			and configuration files on devices.

                        ================================================
                        ==                                            ==
                        == Copyright (C) 2005 Zhone Technologies, Inc ==
                        ==                                            ==
                        ================================================"

        REVISION        "200510180000Z"  -- October 18, 2005
        DESCRIPTION     "Added pdnCCMMode to support a configurable
                         Configuration Change Management Mode.
                         Clay Sikes"

        REVISION        "200412140000Z"  -- December 14, 2004
        DESCRIPTION     "Cleaned up errors from MIB compiler.
                         Added pdnDevFileXferErrorStatusText object and added
                         the object to the pdnDevFileXferEvent notification.
                         Clay Sikes"

	REVISION	"200112040000Z"  -- December 4, 2001
	DESCRIPTION	"Added pdnDevFileXferApply. 
                         Dragana Gough"

	REVISION	"200111140000Z"  -- November 14, 2001
	DESCRIPTION	"Added group definition, switched RowStatus and 
                         XferTime positions in the table.  Added 
                         pdnDevFileXferSessionIDNext singular object.
                         Dragana Gough"

	REVISION	"200111120000Z"  -- November 12, 2001
	DESCRIPTION	"Added new FTP transfer table that is indexed by session 
                         ID and contains three new objects(different from 
                         devFileXferConfigTable): 
                            pdnDevFileXferSessionID, 
                            pdnDevFileXferifIndex, 
                            pdnDevFileXferUserAccount.

                        Added new objects to pdnCCMAutoBackup Group:
                           pdnCCMAutoBackupFilename, 
                           pdnCCMAutoBackupAppendTimeStampToFilename, 
                           pdnCCMAutoBackupServerIpAddress,
		           pdnCCMAutoBackupUserName, 
                           pdnCCMAutoBackupUserPassword, 
                           pdnCCMAutoBackupUserAccount,
                           pdnCCMAutoBackupCopyProtocol.

		        Added new objects to pdnConfigChangeManagement group:
		           pdnCCMOperation. 
                        Dragana Gough"

	REVISION	"200106130000Z"  -- June 13, 2001
	DESCRIPTION	"Changed the description for devAutoFwStatus and 
                         devIsAutoFwEnabled of pdnAutoFwGroup.
                         Mohan Mohankumar"

	REVISION	"200105030000Z"  -- May 3, 2001
	DESCRIPTION	"Added Auto Firmware Download Group.
                         Mohan Mohankumar"

	REVISION	"200011200000Z"  -- November 20, 2000
	DESCRIPTION	"Conversion to SMIv2.
                         Addition of Configuration Change Management Objects and Traps.
                         Rajesh Raghavan"

	REVISION	"200003020000Z"  -- March 2, 2000
	DESCRIPTION	"Added devSNSwitchFirmwareTable for old service nodes.
                         Rajesh Gowda."

	REVISION	"200003010000Z"  -- March 1, 2000
	DESCRIPTION	"Added new ftp control group. 
                         J. Colom"

	REVISION	"199711310000Z"  -- December 31, 1997
	DESCRIPTION	"Completely removed devControlSLA.
                         Changed Enum values for devControlRMON. 
                         RAS"

	REVISION	"199711200000Z"  -- December 23, 1997
	DESCRIPTION	"Added devControlRMON and devControlLatency groups.
                         Added global comments.
                         Added Enum values to devControlTestStatus.
                         Modified comments on devControlTestCommand. 
                         RAS."

	::= { pdn-common 10 }
	


-- =============================================================================
-- ==                  MIB Objects                                            ==
-- =============================================================================

	     
--
-- Device Reset Object
--
-- Used to reset (warm boot) the device.
--
devHWControlReset OBJECT-TYPE
    SYNTAX  INTEGER {
        noOp(1),
        reset(2)
            }
    MAX-ACCESS  read-write
    STATUS current 
    DESCRIPTION
        "Writing the value reset(2) to this object initiates a
         Hardware power-on reset of the device.  
         The value read from this object is noOp(1)."
    ::= { pdnControl 1 }

-- ====================================================================
--
-- Test Table
--
-- This table controls device level tests.
--
devControlTestTable OBJECT-TYPE
    SYNTAX SEQUENCE OF DevControlTestEntry
    MAX-ACCESS  not-accessible
    STATUS current 
    DESCRIPTION
        "A list of Device tests that may be run."
    ::= { pdnControl 2 }

devControlTestEntry OBJECT-TYPE
    SYNTAX  DevControlTestEntry
    MAX-ACCESS  not-accessible
    STATUS current 
    DESCRIPTION
        "The device Test Table."
    INDEX  { devControlTest }
    ::= { devControlTestTable 1 }

DevControlTestEntry ::=
    SEQUENCE {
    devControlTest
        INTEGER,
    devControlTestStatus
        INTEGER,
    devControlTestCmd
        INTEGER
    }

devControlTest OBJECT-TYPE
    SYNTAX INTEGER {
        lampTest (1),
        v35DTELpbkTest (2)
    }
    MAX-ACCESS not-accessible
    STATUS current
    DESCRIPTION
        "An index into the test table that indicates which test 
         the row involves."
::= { devControlTestEntry 1 }

devControlTestStatus OBJECT-TYPE
    SYNTAX  INTEGER {
        active(1),
        inactive(2)
    }
    MAX-ACCESS  read-only
    STATUS current 
    DESCRIPTION
        "The test status on the device. This object indicates whether
         the indexed test is currently active(1) or inactive(2)."
::= { devControlTestEntry 2 }

devControlTestCmd OBJECT-TYPE
    SYNTAX INTEGER {
        start  (1),
        stop   (2)
    }
    MAX-ACCESS read-create
    STATUS current
    DESCRIPTION
        "Used to start or stop the indexed test.
         When read, the value returned will be the next logical command."
::= { devControlTestEntry 3 }

-- ====================================================================
--
-- Download Control Table
--
-- This table is used to control and provide information concerning
-- downloaded executable images. 
--
devControlDownLoadTable OBJECT-TYPE
    SYNTAX SEQUENCE OF DevControlDownLoadEntry
    MAX-ACCESS  not-accessible
    STATUS current 
    DESCRIPTION
        "A list of the current Download Releases and their associated status.
	 Each Download Release will be indexed by a number from 1 to N.
	 The user will be able to view the Download Release String and 
	 Operational Status of the release (valid or invalid) and 
	 activate a valid Download Release by changing the 
	 Administration Status to active."
    ::= { pdnControl 3 }

devControlDownLoadEntry OBJECT-TYPE
    SYNTAX  DevControlDownLoadEntry
    MAX-ACCESS  not-accessible
    STATUS current 
    DESCRIPTION
        "The Device DownLoad Release entry."
    INDEX  { devControlDownLoadIndex }
    ::= { devControlDownLoadTable 1 }

DevControlDownLoadEntry ::=
    SEQUENCE {
    devControlDownLoadIndex
	Integer32,
    devControlDownLoadRelease
        DisplayString,
    devControlDownLoadOperStatus
        INTEGER,
    devControlDownLoadAdminStatus
        INTEGER
    }

devControlDownLoadIndex OBJECT-TYPE
    SYNTAX Integer32
    MAX-ACCESS not-accessible
    STATUS current
    DESCRIPTION
        "This object is used to index the download table (range 1 to N)."
::= { devControlDownLoadEntry 1 }

devControlDownLoadRelease OBJECT-TYPE
    SYNTAX  DisplayString (SIZE (1..16))
    MAX-ACCESS  read-only
    STATUS current 
    DESCRIPTION
  	"This object indicates the Software Release for 
	 this Download. If the Software Download is Operational Status
	 is invalid, the Software Revision Number will be blank."
::= { devControlDownLoadEntry 2 }

devControlDownLoadOperStatus OBJECT-TYPE
    SYNTAX INTEGER {
	valid(1),
	invalid(2)
    }
    MAX-ACCESS read-only
    STATUS current
    DESCRIPTION
        "This object indicates whether or not the indexed 
	 download entry contains a valid(1) or invalid(2) download."
::= { devControlDownLoadEntry 3 }

devControlDownLoadAdminStatus OBJECT-TYPE
    SYNTAX INTEGER {
	active(1),
	inactive(2)
    }
    MAX-ACCESS read-create
    STATUS current
    DESCRIPTION
        "This object indicates whether or not the indexed 
	 download entry is active(1) or inactive(2). 
	 Writing active(1) will activate that software release
	 and cause the unit to reset (response may timeout).
	 Writing active(1) to a download entry whose 
	 devControlDownloadOperStatus is invalid will return BAD VALUE.
	 Writing inactive(2) will always return BAD VALUE."
::= { devControlDownLoadEntry 4 }

-- ====================================================================
--
-- The RMON Group
--
-- This group is a collection of items that control the RMON process.
--
devControlRMON    OBJECT IDENTIFIER ::= { pdnControl 4}

devControlRMONAdminStatus OBJECT-TYPE
    SYNTAX  INTEGER {
        enabled(1),
        disabled(2)
    }
    MAX-ACCESS  read-write
    STATUS current 
    DESCRIPTION
        "The desired state of the RMON process.  If set to enabled(1), the 
         RMON process will perform the collection tasks it is set up to do.  
         If it is disabled(2), RMON will not perform collection."
    ::= { devControlRMON 1 }

-- ====================================================================
--
--  Objects that switch banks in the Service Nodes(ASN).
--  devSNSwitchFirmwareTable is deprecated by devFirmwareControl
--  group in sle_devControl.mib (Atlantis 4.0 onwards)

devSNSwitchFirmwareTable OBJECT-TYPE
    SYNTAX SEQUENCE OF DevSNSwitchFirmwareEntry
    MAX-ACCESS  not-accessible
    STATUS current 
    DESCRIPTION
        "A list of objects needed to switch bank
         and reset the Service Node (ASN)."
    ::= { pdnControl 5 }

devSNSwitchFirmwareEntry OBJECT-TYPE
    SYNTAX  DevSNSwitchFirmwareEntry
    MAX-ACCESS  not-accessible
    STATUS current 
    DESCRIPTION
        "The Service Node Switch Firmware table."
    INDEX  { devSNSwitchFirmwareIndex }
    ::= { devSNSwitchFirmwareTable 1 }

DevSNSwitchFirmwareEntry ::=
    SEQUENCE {
    devSNSwitchFirmwareIndex
        Integer32,
    devSNSwitchFirmwareBank
        INTEGER
    }

devSNSwitchFirmwareIndex OBJECT-TYPE
    SYNTAX Integer32
    MAX-ACCESS not-accessible
    STATUS current
    DESCRIPTION
        "An index into the Service Node switch firmware table that
         indicates which interface the row involves. This index
         corresponds to the entityPhysicalIndex of the entity MIB "
::= { devSNSwitchFirmwareEntry 1 }

devSNSwitchFirmwareBank OBJECT-TYPE
    SYNTAX  INTEGER {
        noOp(1),
        switch(2)
    }
    MAX-ACCESS  read-create
    STATUS current 
    DESCRIPTION
         "Writing the value switch(2) to this object will
          switch the banks to change the firmware being
          used on the service node. The firmware from the stand
          by (not active) bank will be used as the currently running
          firmware.  The value read from this object is noOp(1)."
::= { devSNSwitchFirmwareEntry 2 }

-- ====================================================================
--
-- The FTP Group
--
-- This group is a collection of items that control the FTP process
--
devControlFTP    OBJECT IDENTIFIER ::= { pdnControl 6}

devControlFTPRate OBJECT-TYPE
    SYNTAX  Integer32
    MAX-ACCESS  read-write
    STATUS current 
    DESCRIPTION
        "FTP max transfer rate in (Kbps)"
    ::= { devControlFTP 1 }


-- =======================================================
--
--  The Paradyne File Transfer Group  (J.Strain)
-- =======================================================
devFileXferMIBObjects OBJECT IDENTIFIER ::= { pdnControl 7}
devFileXferMIBTraps OBJECT IDENTIFIER ::= { pdnControl 8 }

devFileXferConfigTable OBJECT-TYPE
    SYNTAX  SEQUENCE OF DevFileXferConfigEntry
    MAX-ACCESS  not-accessible
    STATUS current 
    DESCRIPTION
           "The Paradyne  FileXfer Client Config Table."
    ::= { devFileXferMIBObjects 1 }

devFileXferConfigEntry OBJECT-TYPE
    SYNTAX  DevFileXferConfigEntry
    MAX-ACCESS  not-accessible
    STATUS current 
    DESCRIPTION

       " Use of the File Transfer MIB could be used with other MIBS in
              the following manner:
                  a) Use another MIB/means to verify available space /make room
                     for a file to be transferred to this device
                  b) Use this MIB to download the file
                  c) Use another MIB/means to select the file you want to make 
                     active
                                        if your selecting firmware for example.
                  d) Use another MIB/means to reset the device.

        A management station wishing to initiate a file transfer needs to
                         create an entry in this table. To do so, you must
       first identify the ifIndex of the device you intend to
       do the transfer with.  You should
       then create the associated instance of the row status
       It must also, either in the same
       or in successive PDUs, create an instance of
       devFileXferFileName, DevFileXferFileType, 
.      devFileXferServerIpAddress,
       devFileXferOperation.

       It should also modify the default values for the other
       configuration objects if the defaults are not appropriate.

       Once the appropriate instance of all the configuration
       objects have been created, either by an explicit SNMP
       set request or by default, the row status should be set
       to active to initiate the request. Note that this entire
       procedure may be initiated via a single set request which
       specifies a row status of createAndGo as well as specifies
       valid values for the non-defaulted configuration objects.

       Once the DevFileXferConfigEntry request has been created (i.e. the
       devFileXferRowStatus has been made active), the entry
       cannot be modified - the only operation possible
       after this is to delete the row.

       Once the request completes, the management station should
       retrieve the values of the status objects of interest, and
       should then delete the entry.  In order to prevent old
       entries from clogging the table, entries could be aged out,
       but an entry will never be deleted within 5 minutes of
       completing.  "
    INDEX   { ifIndex }
    ::= { devFileXferConfigTable  1 }

DevFileXferConfigEntry ::=
    SEQUENCE {

    devFileXferFileName
        DisplayString,

    devFileXferCopyProtocol
        INTEGER,

    devFileXferFileType
        INTEGER,

    devFileXferServerIpAddress
        IpAddress,

    devFileXferUserName
        DisplayString,

    devFileXferUserPassword
        DisplayString,

    devFileXferOperation
        INTEGER,

    devFileXferPktsSent
        Counter32,

    devFileXferPktsRecv
        Counter32,

    devFileXferOctetsSent
        Counter32,

    devFileXferOctetsRecv
        Counter32,

    devFileXferOwnerString
        OCTET STRING,

    devFileXferStatus
        INTEGER,

    devFileXferErrorStatus
        Integer32,

    devFileXferSendEvent
        INTEGER,

    devFileXferRowStatus
        RowStatus,
		
    devFileXferXferTime
		TimeTicks	
    }

devFileXferFileName OBJECT-TYPE
    SYNTAX  DisplayString
    MAX-ACCESS  read-create
    STATUS current 
    DESCRIPTION
           "This object contains the name of the file to be transferred."
    ::= { devFileXferConfigEntry  1 }

devFileXferCopyProtocol OBJECT-TYPE
    SYNTAX   INTEGER {
                         tftp(1),
                         ftp(2)
                                                }
    MAX-ACCESS  read-create
    STATUS current 
    DESCRIPTION
          "The transfer protocol that should be used to copy the file
           across the network. If the file transfer is to occur locally on the 
           SNMP agent, the method of transfer is left up to the implementation, 
           and is not restricted to the protocols below."

--    DEFVAL  { tftp }
    ::= { devFileXferConfigEntry  2 }

devFileXferFileType OBJECT-TYPE
    SYNTAX  INTEGER {
                                firmware(1),
                                config(2)
                                }

    MAX-ACCESS  read-create
    STATUS current 
    DESCRIPTION
           "Specifies the type of file your want to transfer."
    ::= { devFileXferConfigEntry  3 }

devFileXferServerIpAddress OBJECT-TYPE
    SYNTAX  IpAddress
    MAX-ACCESS  read-create
    STATUS current 
    DESCRIPTION
           "This object contains the file transfer server's IP address. "
    ::= { devFileXferConfigEntry  4 }

devFileXferUserName OBJECT-TYPE
    SYNTAX  DisplayString
    MAX-ACCESS  read-create
    STATUS current 
    DESCRIPTION
           "This object contains the user name if a user name is needed
        to login to the server."
    ::= { devFileXferConfigEntry  5 }

devFileXferUserPassword OBJECT-TYPE
    SYNTAX  DisplayString
    MAX-ACCESS  read-create
    STATUS current 
    DESCRIPTION
           "This object contains the password if a password is needed
            to login to the server. This object will return null on a read 
            operation."
    ::= { devFileXferConfigEntry  6 }

devFileXferOperation OBJECT-TYPE
    SYNTAX  INTEGER {
                                get(1),
                                put(2)
                                        }
    MAX-ACCESS  read-create
    STATUS current 
    DESCRIPTION
           "This object contains the operation the file transfer wants to 
perform."
    ::= { devFileXferConfigEntry  7 }

devFileXferPktsSent OBJECT-TYPE
    SYNTAX  Counter32
    MAX-ACCESS  read-only
    STATUS current 
    DESCRIPTION
           "This object contains the the number of packets sent to the
        server at the time of interrogation."
    ::= { devFileXferConfigEntry  8 }

devFileXferPktsRecv OBJECT-TYPE
    SYNTAX  Counter32
    MAX-ACCESS  read-only
    STATUS current 
    DESCRIPTION
           "This object contains the the number of packets received from the
        server at the time of interrogation."
    ::= { devFileXferConfigEntry  9 }

devFileXferOctetsSent OBJECT-TYPE
    SYNTAX  Counter32
    MAX-ACCESS  read-only
    STATUS current 
    DESCRIPTION
           "This object contains the the number of octets sent to the
        server at the time of interrogation."
    ::= { devFileXferConfigEntry  10 }

devFileXferOctetsRecv OBJECT-TYPE
    SYNTAX  Counter32
    MAX-ACCESS  read-only
    STATUS current 
    DESCRIPTION
           "This object contains the the number of octets received from the
        server at the time of interrogation."
    ::= { devFileXferConfigEntry  11 }

devFileXferOwnerString OBJECT-TYPE
    SYNTAX   OCTET STRING (SIZE(0..255))
    MAX-ACCESS  read-create
    STATUS current 
    DESCRIPTION
           "The entity which currently has the 'ownership'
        required to invoke the operation on this index."
    ::= { devFileXferConfigEntry  12 }

devFileXferStatus OBJECT-TYPE
    SYNTAX  INTEGER {
                 none(1),
                 success(2),
                 failure(3),
                 inprogress(4)
               }
    MAX-ACCESS  read-only
    STATUS current 
    DESCRIPTION
           "This object contains the status of the file transfer."
    ::= { devFileXferConfigEntry  13 }

devFileXferErrorStatus OBJECT-TYPE
    SYNTAX  Integer32
    MAX-ACCESS  read-only
    STATUS current 
    DESCRIPTION
           "This object contains the reason code of the failure determined in 
devFileXferStatus.
        The reason code are specific to the file transfer protocol.

        Please refer to the file transfer protocols respective RFC for 
clarification
        of the error code value meanings.

        TFTP Error Codes from rfc 1350
        FTP Error Codes from rfc 959"

    ::= { devFileXferConfigEntry  14 }

devFileXferSendEvent OBJECT-TYPE
    SYNTAX INTEGER {
    active(1),
    inactive(2)
    }
    MAX-ACCESS read-create
    STATUS current
    DESCRIPTION
        "This object indicates whether or not to send the 
         devFileXferEvent event trap ."
    ::= { devFileXferConfigEntry  15 }

devFileXferRowStatus OBJECT-TYPE
    SYNTAX  RowStatus
    MAX-ACCESS  read-create
    STATUS current 
    DESCRIPTION
           "This object is used to create
     a new row or delete an
     existing row in this table."
    ::= { devFileXferConfigEntry  16 }

devFileXferXferTime OBJECT-TYPE
    SYNTAX  TimeTicks 
    MAX-ACCESS  read-only
    STATUS current 
    DESCRIPTION
        "This object indicates the elapsed time 
		(in hundredths of a second) of the file transfer."
    ::= { devFileXferConfigEntry 17 }

-- ##########################################
-- Net file transfer table for accessing by 
-- session id 
--###########################################

pdnDevFileXferTable OBJECT-TYPE
    SYNTAX  SEQUENCE OF PdnDevFileXferEntry
    MAX-ACCESS  not-accessible
    STATUS current 
    DESCRIPTION
           "The Paradyne  FileXfer Image Client Config Table accessed by session id."
    ::= { devFileXferMIBObjects 2 }

pdnDevFileXferEntry OBJECT-TYPE
    SYNTAX  PdnDevFileXferEntry
    MAX-ACCESS  not-accessible
    STATUS current 
    DESCRIPTION

       " Use of the File Transfer MIB could be used with other MIBS in
              the following manner:
                  a) Use another MIB/means to verify available space /make room
                     for a file to be transferred to this device
                  b) Use this MIB to download the file
                  c) Use another MIB object/means to select the file you want to make 
                     active
                                        if your selecting firmware for example.
                  d) Use another MIB/means to reset the device.

        A management station wishing to initiate a file transfer needs to
                         create an entry in this table. To do so, you must
       first identify the session id of the session that   
       the transfer is done with.  This is done by setting SessionID
       to 0 on SET and when session is establish entering that session
       id into this object. You should
       then create the associated instance of the row status
       It must also, either in the same
       or in successive PDUs, create an instance of
       pdnDevFileXferFileName, pdnDevFileXferFileType, 
.      pdnDevFileXferServerIpAddress,
       pdnDevFileXferOperation.

       It should also modify the default values for the other
       configuration objects if the defaults are not appropriate.

       Once the appropriate instance of all the configuration
       objects have been created, either by an explicit SNMP
       set request or by default, the row status should be set
       to active to initiate the request. Note that this entire
       procedure may be initiated via a single set request which
       specifies a row status of createAndGo as well as specifies
       valid values for the non-defaulted configuration objects.

       Once the request completes, the management station should
       retrieve the values of the status objects of interest, and
       should then delete the entry.  In order to prevent old
       entries from clogging the table, entries could be aged out,
       but an entry will never be deleted within 5 minutes of
       completing.  "
    INDEX   { pdnDevFileXferSessionID }
    ::= { pdnDevFileXferTable  1 }

PdnDevFileXferEntry ::=
    SEQUENCE {

    pdnDevFileXferSessionID
        Integer32,

    pdnDevFileXferifIndex
        Integer32,

    pdnDevFileXferFileName
        DisplayString,

    pdnDevFileXferCopyProtocol
        INTEGER,

    pdnDevFileXferFileType
        INTEGER,

    pdnDevFileXferServerIpAddress
        IpAddress,

    pdnDevFileXferUserName
        DisplayString,

    pdnDevFileXferUserPassword
        DisplayString,

    pdnDevFileXferUserAccount
        DisplayString,

    pdnDevFileXferOperation
        INTEGER,

    pdnDevFileXferPktsSent
        Counter32,

    pdnDevFileXferPktsRecv
        Counter32,

    pdnDevFileXferOctetsSent
        Counter32,

    pdnDevFileXferOctetsRecv
        Counter32,

    pdnDevFileXferOwnerString
        OCTET STRING,

    pdnDevFileXferStatus
        INTEGER,

    pdnDevFileXferApply
        INTEGER,

    pdnDevFileXferErrorStatus
        Integer32,

    pdnDevFileXferSendEvent
        INTEGER,

    pdnDevFileXferXferTime
		TimeTicks,	

    pdnDevFileXferRowStatus
        RowStatus,

    pdnDevFileXferErrorStatusText
        DisplayString
    }

pdnDevFileXferSessionID OBJECT-TYPE
    SYNTAX Integer32
    MAX-ACCESS not-accessible
    STATUS current
    DESCRIPTION
	   "This object is the session id. This object is used
	    by FileXfer Table to identify the row
	    of this table.  When creating the new row
	    in the table the value of this object may be 
	    obtained by retrieving the value
	    of pdnDevFileXferSessionIDNext."
    ::= { pdnDevFileXferEntry 1 }

pdnDevFileXferifIndex OBJECT-TYPE
    SYNTAX Integer32
    MAX-ACCESS read-create
    STATUS current
    DESCRIPTION
	   "This object specifies the interface
	    number that corresponds to RFC1213.
	    It this object is not used the value
	    of this object should be zero."
    ::= { pdnDevFileXferEntry 2 }

pdnDevFileXferFileName OBJECT-TYPE
    SYNTAX  DisplayString
    MAX-ACCESS  read-create
    STATUS current 
    DESCRIPTION
           "This object contains the name of the file to be transferred."
    ::= { pdnDevFileXferEntry  3 }

pdnDevFileXferCopyProtocol OBJECT-TYPE
    SYNTAX   INTEGER {
                         tftp(1),
                         ftp(2)
                                                }
    MAX-ACCESS  read-create
    STATUS current 
    DESCRIPTION
          "The transfer protocol that should be used to copy the file
           across the network. If the file transfer is to occur locally on the 
           SNMP agent, the method of transfer is left up to the implementation, 
           and is not restricted to the protocols below."

--    DEFVAL  { tftp }
    ::= { pdnDevFileXferEntry  4 }

pdnDevFileXferFileType OBJECT-TYPE
    SYNTAX  INTEGER {
                                firmware(1),
                                config(2)
                                }

    MAX-ACCESS  read-create
    STATUS current 
    DESCRIPTION
           "Specifies the type of file your want to transfer."
    ::= { pdnDevFileXferEntry  5 }

pdnDevFileXferServerIpAddress OBJECT-TYPE
    SYNTAX  IpAddress
    MAX-ACCESS  read-create
    STATUS current 
    DESCRIPTION
           "This object contains the file transfer server's IP address. "
    ::= { pdnDevFileXferEntry  6 }

pdnDevFileXferUserName OBJECT-TYPE
    SYNTAX  DisplayString
    MAX-ACCESS  read-create
    STATUS current 
    DESCRIPTION
           "This object contains the user name if a user name is needed
        to login to the server."
    ::= { pdnDevFileXferEntry  7 }

pdnDevFileXferUserPassword OBJECT-TYPE
    SYNTAX  DisplayString
    MAX-ACCESS  read-create
    STATUS current 
    DESCRIPTION
           "This object contains the password if a password is needed
            to login to the server. This object will return null on a read 
            operation."
    ::= { pdnDevFileXferEntry  8 }

pdnDevFileXferUserAccount OBJECT-TYPE
    SYNTAX  DisplayString
    MAX-ACCESS  read-create
    STATUS current 
    DESCRIPTION
           "This object contains the name of the the user account information
	    that is stored on ftp server. Server  would contain user name and password
	    under this account name. This object will return null on a read 
            operation. The default value of this is a null string."
    ::= { pdnDevFileXferEntry  9 }

pdnDevFileXferOperation OBJECT-TYPE
    SYNTAX  INTEGER {
                                get(1),
                                put(2)
                                        }
    MAX-ACCESS  read-create
    STATUS current 
    DESCRIPTION
           "This object contains the operation the file transfer wants to 
            perform."
    ::= { pdnDevFileXferEntry  10 }

pdnDevFileXferPktsSent OBJECT-TYPE
    SYNTAX  Counter32
    MAX-ACCESS  read-only
    STATUS current 
    DESCRIPTION
           "This object contains the the number of packets sent to the
        server at the time of interrogation."
    ::= { pdnDevFileXferEntry  11 }

pdnDevFileXferPktsRecv OBJECT-TYPE
    SYNTAX  Counter32
    MAX-ACCESS  read-only
    STATUS current 
    DESCRIPTION
           "This object contains the the number of packets received from the
        server at the time of interrogation."
    ::= { pdnDevFileXferEntry  12 }

pdnDevFileXferOctetsSent OBJECT-TYPE
    SYNTAX  Counter32
    MAX-ACCESS  read-only
    STATUS current 
    DESCRIPTION
           "This object contains the the number of octets sent to the
        server at the time of interrogation."
    ::= { pdnDevFileXferEntry  13 }

pdnDevFileXferOctetsRecv OBJECT-TYPE
    SYNTAX  Counter32
    MAX-ACCESS  read-only
    STATUS current 
    DESCRIPTION
           "This object contains the the number of octets received from the
        server at the time of interrogation."
    ::= { pdnDevFileXferEntry  14 }

pdnDevFileXferOwnerString OBJECT-TYPE
    SYNTAX   OCTET STRING (SIZE(0..255))
    MAX-ACCESS  read-create
    STATUS current 
    DESCRIPTION
           "The entity which currently has the 'ownership'
        required to invoke the operation on this index."
    ::= { pdnDevFileXferEntry  15 }

pdnDevFileXferStatus OBJECT-TYPE
    SYNTAX  INTEGER {
                 none(1),
                 success(2),
                 failure(3),
                 inprogress(4)
               }
    MAX-ACCESS  read-only
    STATUS current 
    DESCRIPTION
           "This object contains the status of the file transfer."
    ::= { pdnDevFileXferEntry  16 }

pdnDevFileXferApply OBJECT-TYPE
    SYNTAX  INTEGER {
                 yes(1),
                 no(2)
               }
    MAX-ACCESS  read-create
    STATUS current 
    DESCRIPTION
           "This object is configured to specify if the 
	    firmware download will be applied immediately after 
	    file transfer or not."
    ::= { pdnDevFileXferEntry  17 }

pdnDevFileXferErrorStatus OBJECT-TYPE
    SYNTAX  Integer32
    MAX-ACCESS  read-only
    STATUS current 
    DESCRIPTION
           "This object contains the reason code of the failure determined in 
            devFileXferStatus.
            The reason code are specific to the file transfer protocol.
            Please refer to the file transfer protocols respective RFC for 
            clarification
            of the error code value meanings.
            TFTP Error Codes from rfc 1350
            FTP Error Codes from rfc 959"

    ::= { pdnDevFileXferEntry  18 }

pdnDevFileXferSendEvent OBJECT-TYPE
    SYNTAX INTEGER {
    active(1),
    inactive(2)
    }
    MAX-ACCESS read-create
    STATUS current
    DESCRIPTION
        "This object indicates whether or not to send the 
         pdnDevFileXferEvent event trap ."
    ::= { pdnDevFileXferEntry  19 }

pdnDevFileXferXferTime OBJECT-TYPE
    SYNTAX  TimeTicks 
    MAX-ACCESS  read-only
    STATUS current 
    DESCRIPTION
        "This object indicates the elapsed time 
		(in hundredths of a second) of the file transfer."
    ::= { pdnDevFileXferEntry 20 }

pdnDevFileXferRowStatus OBJECT-TYPE
    SYNTAX  RowStatus
    MAX-ACCESS  read-create
    STATUS current 
    DESCRIPTION
           "This object is used to create
     a new row or delete an
     existing row in this table."
    ::= { pdnDevFileXferEntry  21 }

pdnDevFileXferErrorStatusText OBJECT-TYPE
    SYNTAX     DisplayString
    MAX-ACCESS read-only
    STATUS     current
    DESCRIPTION
           "This object provides a textual interpretation of the
            pdnDevFileXferErrorStatus code.  This is important for
            those situations where FTP may fail and a standard error
            code doesn't apply.  In the situations where standard
            error codes apply, this object will make it easier for
            an operator to react to an FTP failure."
    ::= { pdnDevFileXferEntry 22 }

-- ====================================================================
--
-- Firmware Control Table
--
-- This table is used to control and provide information concerning
-- firmware/executable images.
--
-- ====================================================================
devFirmwareControlMIBObjects OBJECT IDENTIFIER ::= { pdnControl 9 }

devFirmwareControlTable OBJECT-TYPE
    SYNTAX SEQUENCE OF DevFirmwareControlEntry
    MAX-ACCESS  not-accessible
    STATUS  current
    DESCRIPTION
        "A list of the current Firmware Releases and their associated
         status.  Each Firmware Release will be indexed by a number
         from 1 to N.  The user will be able to view the Firmware
         Release String and Operational Status of the release (valid
                 or invalid) and activate a valid Firmware Release by changing
                 the Administration Status to active."
    ::= { devFirmwareControlMIBObjects 1 }

devFirmwareControlEntry OBJECT-TYPE
    SYNTAX  DevFirmwareControlEntry
    MAX-ACCESS  not-accessible
    STATUS  current
    DESCRIPTION
        "The Device Firmware Release entry."
    INDEX  { devFirmwareControlIndex }
    ::= { devFirmwareControlTable 1 }

DevFirmwareControlEntry ::=
    SEQUENCE {
    devFirmwareControlIndex
    	Integer32,
    devFirmwareControlRelease
        DisplayString,
    devFirmwareControlOperStatus
        INTEGER,
    devFirmwareControlAdminStatus
        INTEGER
    }

devFirmwareControlIndex OBJECT-TYPE
    SYNTAX Integer32
    MAX-ACCESS not-accessible
    STATUS current
    DESCRIPTION
        "This object is used to index the Firmware table (range 1 to N)."
::= { devFirmwareControlEntry 1 }

devFirmwareControlRelease OBJECT-TYPE
    SYNTAX  DisplayString (SIZE (1..16))
    MAX-ACCESS  read-only
    STATUS  current
    DESCRIPTION
    "This object indicates the Software Release for
     this Firmware. If the Software Firmware is Operational Status
     is invalid, the Software Revision Number will be blank."
::= { devFirmwareControlEntry 2 }

devFirmwareControlOperStatus OBJECT-TYPE
    SYNTAX INTEGER {
    valid(1),
    invalid(2),
    unknown(3)
    }
    MAX-ACCESS read-only
    STATUS current
    DESCRIPTION
     "This object indicates whether or not the indexed
     Firmware entry contains a valid(1) or invalid(2) Firmware."
::= { devFirmwareControlEntry 3 }

devFirmwareControlAdminStatus OBJECT-TYPE
    SYNTAX INTEGER {
    active(1),
    inactive(2)
    }
    MAX-ACCESS read-create
    STATUS current
    DESCRIPTION
        "This object indicates whether or not the indexed
     Firmware entry is active(1) or inactive(2).
     Writing active(1) will activate that software release
     and cause the unit to reset (response may timeout).
     Writing active(1) to a Firmware entry whose
     devFirmwareControlOperStatus is invalid will return BAD VALUE.
     Writing inactive(2) will always return BAD VALUE."
::= { devFirmwareControlEntry 4 }

-- ====================================================================
--
-- Configuration Change Management (CCM) Group
-- Modified 10/4/2000 by Rajesh Raghavan
--
-- Objects for controlling automated backup and restore of the 
-- configuration files of devices (cards) in the slots of the 
-- Paradyne DSLAM chassis.
--
-- ====================================================================
pdnConfigChangeMgmt OBJECT IDENTIFIER ::= { pdnControl 10 }

pdnCCMAutoBackup OBJECT IDENTIFIER ::= { pdnConfigChangeMgmt 1 }
  -- CCM Auto Backup Group

pdnCCMAutoBackupType OBJECT-TYPE
    SYNTAX	INTEGER { disabled(0), fixed(1), dynamic(2) }
    MAX-ACCESS  read-write
    STATUS	current
    DESCRIPTION
	"This object indicates whether automatic backup of device
	configuration files to the MCC Flash File System is disabled,
	performed according to a fixed schedule, or whether it occurs
	dynamically at a specified interval after the latest configuration
	change to a device."

  ::= { pdnCCMAutoBackup 1 }

pdnCCMAutoBackupFixedDay OBJECT-TYPE
    SYNTAX	BITS {  sunday(0), 
			monday(1), 
			tuesday(2), 
			wednesday(3), 
			thursday(4), 
			friday(5), 
			saturday(6) }
    MAX-ACCESS	read-write
    STATUS	current
    DESCRIPTION
	"This object indicates the days of the week on which fixed schedule
	automatic backups occur.  If all bits are set, backups occur daily."

  ::= { pdnCCMAutoBackup 2 }

pdnCCMAutoBackupFixedTime OBJECT-TYPE
    SYNTAX	Integer32 (0..1440)
    UNITS	"minutes"
    MAX-ACCESS	read-write
    STATUS	current
    DESCRIPTION
	"This object indicates the time of day, in minutes past midnight,
	 at which automatic backups on a fixed schedule occur."

  ::= { pdnCCMAutoBackup 3 }

pdnCCMAutoBackupDynamicTime OBJECT-TYPE
    SYNTAX	Integer32 (30..1440)
    UNITS	"minutes"
    MAX-ACCESS	read-write
    STATUS	current
    DESCRIPTION
	"This object indicates the interval (in minutes) after the most recent
	configuration change, when a card's configuration will be backed up
	to the MCC Flash File System, when automatic backups are occurring on
	a dynamic schedule.  The minimum interval is 30 minutes.
	The maximum interval is 24 hours (1440 minutes)."

  ::= { pdnCCMAutoBackup 4 }

pdnCCMAutoBackupAppendTimeStampToFilename OBJECT-TYPE
    SYNTAX	INTEGER {
			  enable(1),
			  disable(2)
			}
    MAX-ACCESS  read-write
    STATUS current 
    DESCRIPTION
	"This object indicates that  the time is to be appended to filename of the file 
	 stored to upon automated backup. The default value of this
	 object is disabled(2)."
  ::= { pdnCCMAutoBackup 5 }

pdnCCMAutoBackupFilename OBJECT-TYPE
    SYNTAX  DisplayString
    MAX-ACCESS  read-write
    STATUS current 
    DESCRIPTION
	"This is file name that the configuration will be stored to upon automated backup."
  ::= { pdnCCMAutoBackup 6 }

pdnCCMAutoBackupServerIpAddress OBJECT-TYPE
    SYNTAX	IpAddress
    MAX-ACCESS  read-write
    STATUS current 
    DESCRIPTION
	"This object is to configure Ip address of the server used to perform autobackup."
  ::= { pdnCCMAutoBackup 7 }

pdnCCMAutoBackupUserName OBJECT-TYPE
    SYNTAX      DisplayString
    MAX-ACCESS  read-write
    STATUS current 
    DESCRIPTION
	"This object user name used to start ftp session for automatic backup."
  ::= { pdnCCMAutoBackup 8 }

pdnCCMAutoBackupUserPassword OBJECT-TYPE
    SYNTAX      DisplayString
    MAX-ACCESS  read-write
    STATUS current 
    DESCRIPTION
	"This object user password that is paired with user name for ftp server login."
  ::= { pdnCCMAutoBackup 9 }

pdnCCMAutoBackupUserAccount OBJECT-TYPE
    SYNTAX      DisplayString
    MAX-ACCESS  read-write
    STATUS current 
    DESCRIPTION
	"This object is user account name that ftp server contains.
        Under this name ftp server stores UserName and UserPassword info.
	If this object is null(not configured) than the 
	pdnCCMAutoBackupUserName and pdnCCMAutoBackupUserPassword
	are used. The default is null string."
  ::= { pdnCCMAutoBackup 10 }

pdnCCMAutoBackupCopyProtocol OBJECT-TYPE
    SYNTAX   INTEGER {
                         tftp(1),
                         ftp(2)
                                                }
    MAX-ACCESS  read-write
    STATUS current 
    DESCRIPTION
          "The transfer protocol that should be used to copy the file
           across the network. If the file transfer is to occur locally on the 
           SNMP agent, the method of transfer is left up to the implementation, 
           and is not restricted to the protocols below."
--    DEFVAL  { tftp }
    ::= { pdnCCMAutoBackup 11 }

pdnCCMAutoRestore OBJECT-TYPE
    SYNTAX	SwitchState
    MAX-ACCESS	read-write
    STATUS	current
    DESCRIPTION
	"This object specifies whether the MCC Flash File System will restore
	stored configuration files to newly inserted cards in the DSLAM."

  ::= { pdnConfigChangeMgmt 2 }

pdnCCMResyncOperation OBJECT-TYPE
    SYNTAX  INTEGER { noOp(1), get(2), put(3) }
    MAX-ACCESS  read-write
    STATUS  current
    DESCRIPTION
	"This object contains the operation performed when ResyncState is 
	enabled.  The value 'get' retrieves configuration files from the
	MCC FFS to all the devices.  The value 'put' stores all the
	configuration files on the MCC FFS. Querying this object always
	retrieves the value noOp(1)"
    ::= { pdnConfigChangeMgmt 3 }

pdnCCMOperation OBJECT-TYPE
    SYNTAX INTEGER {
		     noOp   (1),
                     apply  (2),
		     save   (3),
		     reset  (4),
		     revert (5),
		     default(6)
		     }
    MAX-ACCESS read-write
    STATUS current
    DESCRIPTION
	" This object contains configuration options for operations performed
          to manage object. SAVE(3) operation is interpreted as copying
	  running configuration to database (NVRAM). APPLY(2) is operation
	  performed to make configuration parameters take in effect. RESET(4)
	  operation is designed to upload database (nvram),saved, configuration,
	  and make it running configuration. REVERT(5) is configuration option used
	  in a case of error upon set operation (before DD applies configuration
	  parameter(s)). It will effectively make previous applied configuration 
	  parameter set valid, running configuration. In some systems this will be an
	  internal (user transparent) operation in case of error detection by DD.
	  DEFAULT(6) will upload default parameters to running configuration without
	  changing saved configuration in a database (nvram).
	  Querying this object always retrieves the value noOp(1)."
    ::= { pdnConfigChangeMgmt 4 }

pdnCCMMode OBJECT-TYPE
    SYNTAX INTEGER {
                     combineApplySave  (1),
                     separateApplySave (2)
		     }
    MAX-ACCESS read-write
    STATUS current
    DESCRIPTION
	"This object defines the mode used for configuration changes.

         When set to combineApplySave(1), setting the pdnCCMOperation
         to apply(2) will result in both the application of the 
         configuration parameters and the running configuration will be
         copied to the database (NVRAM) as if pdnCCMOperation was set
         to apply(1) followed by save(3).  

         When set to separateApplySave(2), setting the pdnCCMOperation
         to apply(2) will not result in the running configuration being
         copied to the database (NVRAM). In order for the running 
         configuration to be copied to the database, the pdnCCMOperation
         must be set to save(3) separately."
    ::= { pdnConfigChangeMgmt 5 }


 
-- the following object(s) can be used in conjunction with various tables
-- to create new table entries

pdnDevFileXferSessionIDNext OBJECT-TYPE
    SYNTAX   	Integer32
    MAX-ACCESS  read-only
    STATUS 	current
    DESCRIPTION
	" This object contains an appropriate value to be
	  used for pdnDevFileXferTable.
	  The value of 0 indicates that no unassigned 
	  entries are available.  To obtain 
	  pdnDevFileXferSessionID value for the new entry 
	  the manager issues a management protocol retrieval 
	  operation to obtain a current value of this object.
	  After each retrieval, the agent should modify the value
	  to the next unassigned index.  "
    ::= { devFileXferMIBObjects 3 }


-- ====================================================================
--
-- Auto Firmware Download (AutoFw) Group
-- Added 5/3/2001 by Mohan Mohankumar
--
-- Objects for controlling automated Firmware download by MCC to the
-- other cards in the slots of the Paradyne DSLAM chassis.
--
-- ====================================================================

pdnAutoFw	OBJECT IDENTIFIER ::= { pdnControl 12 }

devIsAutoFwEnabled OBJECT-TYPE
    SYNTAX	SwitchState
    MAX-ACCESS  read-write
    STATUS current
    DESCRIPTION
        "Writing the value enabled(1) or disabled(2) to this object enables 
         or disables the Automatic Firmware download feature."
         
     ::= { pdnAutoFw 1 }

devAutoFwStatus OBJECT-TYPE
    SYNTAX  DisplayString (SIZE (1..255))
    MAX-ACCESS  read-only
    STATUS  current
    DESCRIPTION
    "This indicates the Status of Auto Firmware Download
     where each field is separated by a semi-colon.
     The get function will return the status of the latest 
     card downloaded."
     
     ::= { pdnAutoFw 2 }


-- =============================================================================
-- ==                  Trap/Notification Objects                              ==
-- =============================================================================

pdnControlMIBTrapsV2	OBJECT-IDENTITY
	STATUS current
	DESCRIPTION	"The traps for the device control MIB."
	::= { pdnControl 0 }
--
--      File Transfer Traps
--

devFileXferEvent NOTIFICATION-TYPE
	OBJECTS {  devFileXferStatus , devFileXferErrorStatus,
                                devFileXferOperation, devFileXferFileType,
                                devFileXferFileName }
   STATUS	current
   DESCRIPTION
     "This trap is to communicate a couple of things about
      the completion of a file transfer.

                devFileXferStatus       - Did it complete successfully or not.
                devFileXferErrorStatus  - If not, what was the error code.
                devFileXferOperation    - What operation was performed?.
                devFileXferFileType     - Was it a firmware xfer or config?
                devFileXferFileName     - The name of the file transferred.
         "

 ::= { pdnControlMIBTrapsV2 1 }

--
--	Configuration Change Management Traps
--	Added 8 Sep 2000 by Rajesh Raghavan
--

devAutoBackupFailEvent NOTIFICATION-TYPE
	OBJECTS { entPhysicalIndex }
	STATUS		current
	DESCRIPTION
	    "This trap indicates a condition exists, which prevents 
	    automated backup of a device's configuration to the 
	    Management Controller Card (MCC) Flash File System at a 
	    scheduled time."
 ::= { pdnControlMIBTrapsV2 2 }


devConfigRestoreFailEvent NOTIFICATION-TYPE
	OBJECTS { entPhysicalIndex }
	STATUS		current
	DESCRIPTION
	    "This trap is sent by a device to indicate that an incorrect
	    or incompatible configuration file is being downloaded to the
	    device from the MCC Flash File System."
 ::= { pdnControlMIBTrapsV2 3 }

devAutoFwEvent NOTIFICATION-TYPE
	OBJECTS { devAutoFwStatus }
	STATUS          current
    DESCRIPTION
    "This trap is to communicate the result of the Auto Firmware Download.
     The variable binding for this trap would be the devAutoFwStatus
     of pdnAutoFwGroup. The exact format of this display string will 
     be well-documented."
 ::= { pdnControlMIBTrapsV2 4 }

pdnDevFileXferEvent NOTIFICATION-TYPE
	OBJECTS {  pdnDevFileXferStatus , pdnDevFileXferErrorStatus,
                                pdnDevFileXferOperation, pdnDevFileXferFileType,
                                pdnDevFileXferFileName }
   STATUS	current
   DESCRIPTION
     "This trap is to communicate a couple of things about
      the completion of a file transfer.

                pdnDevFileXferStatus          - Did it complete successfully or not.
                pdnDevFileXferErrorStatus     - If not, what was the error code.
                pdnDevFileXferOperation       - What operation was performed?.
                pdnDevFileXferFileType        - Was it a firmware xfer or config?
                pdnDevFileXferFileName        - The name of the file transferred.
                pdnDevFileXferErrorStatusText - Textual interpretation of 
                                                the error code."
 ::= { pdnControlMIBTrapsV2 5 }



-- =============================================================================
-- ==                  Conformance Information                                ==
-- =============================================================================


pdnControlMIBGroups	  OBJECT IDENTIFIER ::= { pdnControl 11 }
pdnControlMIBCompliances  OBJECT IDENTIFIER ::= { pdnControl 13 }



-- ===========================
-- == Compliance Statements ==
-- ===========================
pdnControlMIBCompliance MODULE-COMPLIANCE
   STATUS      current
   DESCRIPTION "The compliance statement for SNMP entities that implement objects
                in this module."
   MODULE      -- This module
   -- No mandatory groups are specified

   GROUP       devResetGroup 
   DESCRIPTION "This group associates objects related to resetting the device."

   GROUP       devControlTestGroup
   DESCRIPTION "This group associates objects related to device level tests."

   GROUP       devControlDownloadGroup
   DESCRIPTION "This group associates objects related to the current download 
                releases and their associated status"

   GROUP       devControlRMONGroup
   DESCRIPTION "This group associates objects related to the desired state 
                of the RMON process."

   GROUP       devSNSwitchFirmwareGroup
   DESCRIPTION "This group associates objects needed to switch bank and 
                reset the service node."

   GROUP       devControlFTPGroup
   DESCRIPTION "This group associates objects relative to the FTP Max 
                Transfer Rate."

   GROUP       devFileXferMIBGroup
   DESCRIPTION "This group associates objects to file transfer 
                client configuration."

   GROUP       devFirmwareControlGroup
   DESCRIPTION "This group associates objects relative to current
                firmware releases and their associated status."

   GROUP       devConfigChangeMgmtGroup
   DESCRIPTION "This group associates objects used to manage 
                automatic backup and restore of device configuration 
                files."

   GROUP       devFileXferEventGroup
   DESCRIPTION "This group associates objects relative to notifications
                that are associated with the devFileXferConfigGroup."

   GROUP       devCCMEventGroup 
   DESCRIPTION "This group associates objects associated with 
                notifications indicating a failure occurred during
                an automated backup or restore of device configuration
                files."

   GROUP       pdnDevFileXferEventGroup
   DESCRIPTION "This group associates objects related to notifications
                that are associated with the pdnDevFileXferConfigGroup."

   GROUP       pdnDevFileXferMIBGroup
   DESCRIPTION "This group associates objects related to file transfer
                client objects."

   GROUP       devNextTableObjectMIBGroup
   DESCRIPTION "This group associates objects related to deciding the 
                next available position in the pdnDevFileXferTable."

   GROUP       pdnAutoFwGroup
   DESCRIPTION "This group associates objects related to auto firmware
                download and its associated status."

   GROUP       devAutoFwEventGroup
   DESCRIPTION "This group associates objects associated with notifications
                indicating the result of auto firmware download."

   GROUP       pdnDevFileXferErrorStatusTextGroup
   DESCRIPTION "This group associates objects for textual interpretation of
                FTP failure codes." 

   GROUP       pdnCCMModeGroup
   DESCRIPTION "This group associates objects for configuring the
                Configuration Change Management Mode."

   ::= { pdnControlMIBCompliances 1 }


-- ===========================
-- == Units of Conformance  ==
-- ===========================
-- N/A due to original OID structure.

-- ====================
-- == Object Groups  ==
-- ====================

devResetGroup		OBJECT-GROUP
	OBJECTS		{ devHWControlReset }
	STATUS		current
	DESCRIPTION	"Objects to initiate resets of a device"
  ::= { pdnControlMIBGroups 1 }

devControlTestGroup	OBJECT-GROUP
	OBJECTS		{ devControlTestStatus,
			  devControlTestCmd }
	STATUS		current
	DESCRIPTION	"Objects to control device level tests"
  ::= { pdnControlMIBGroups 2 }

devControlDownloadGroup	OBJECT-GROUP
	OBJECTS		{ devControlDownLoadRelease,
			  devControlDownLoadOperStatus,
			  devControlDownLoadAdminStatus }
	STATUS		current
	DESCRIPTION	"A list of the current Download Releases and
			their associated status."
  ::= { pdnControlMIBGroups 3 }

devControlRMONGroup	OBJECT-GROUP
	OBJECTS		{ devControlRMONAdminStatus }
	STATUS		current
	DESCRIPTION	"The desired state of the RMON process."
  ::= { pdnControlMIBGroups 4 }

devSNSwitchFirmwareGroup	OBJECT-GROUP
	OBJECTS		{ devSNSwitchFirmwareBank }
	STATUS		current
	DESCRIPTION	"Objects needed to switch bank and reset the
			Service Node."
  ::= { pdnControlMIBGroups 5 }

devControlFTPGroup	OBJECT-GROUP
	OBJECTS		{ devControlFTPRate }
	STATUS		current
	DESCRIPTION	"FTP Max Transfer Rate"
  ::= { pdnControlMIBGroups 6 }

devFileXferMIBGroup	OBJECT-GROUP
	OBJECTS		{ devFileXferFileName, devFileXferCopyProtocol,
			  devFileXferFileType, devFileXferServerIpAddress,
			  devFileXferUserName, devFileXferUserPassword,
			  devFileXferOperation,
			  devFileXferPktsSent, devFileXferPktsRecv,
			  devFileXferOctetsSent, devFileXferOctetsRecv,
			  devFileXferOwnerString,
			  devFileXferStatus, devFileXferErrorStatus,
			  devFileXferSendEvent, devFileXferRowStatus,
			  devFileXferXferTime }
	STATUS		current
	DESCRIPTION	"File Transfer Client Config Objects"
  ::= { pdnControlMIBGroups 7 }

devFirmwareControlGroup	OBJECT-GROUP
	OBJECTS		{ devFirmwareControlRelease,
			  devFirmwareControlOperStatus,
			  devFirmwareControlAdminStatus }
	STATUS		current
	DESCRIPTION 	"Current Firmware Releases and associated status."
  ::= { pdnControlMIBGroups 8 }

devConfigChangeMgmtGroup	OBJECT-GROUP
	OBJECTS		{ pdnCCMAutoBackupType,pdnCCMAutoBackupFixedDay,
	                  pdnCCMAutoBackupFixedTime, pdnCCMAutoBackupDynamicTime,
			  pdnCCMAutoBackupAppendTimeStampToFilename,
			  pdnCCMAutoBackupFilename, pdnCCMAutoBackupServerIpAddress,
			  pdnCCMAutoBackupUserName, pdnCCMAutoBackupUserPassword,
			  pdnCCMAutoBackupUserAccount, pdnCCMAutoBackupCopyProtocol,
			  pdnCCMAutoRestore, pdnCCMResyncOperation,
			  pdnCCMOperation }
	STATUS		current
	DESCRIPTION	"Object group used to manage automatic backup and 
			restore of device configuration files."
  ::= { pdnControlMIBGroups 9 }

devFileXferEventGroup	NOTIFICATION-GROUP
	NOTIFICATIONS	{ devFileXferEvent }
	STATUS		current
	DESCRIPTION	"Notifications associated with 
			devFileXferConfigGroup"
  ::= { pdnControlMIBGroups 10 }

devCCMEventGroup		NOTIFICATION-GROUP
	NOTIFICATIONS	{ devAutoBackupFailEvent, 
			  devConfigRestoreFailEvent }
	STATUS		current
	DESCRIPTION	"Notifications indicating a failure occurring during
			automated backup or restore of device configuration 
			files."
  ::= { pdnControlMIBGroups 11 }

pdnDevFileXferEventGroup	NOTIFICATION-GROUP
	NOTIFICATIONS	{ pdnDevFileXferEvent }
	STATUS		current
	DESCRIPTION	"Notifications associated with 
			pdnDevFileXferConfigGroup"
  ::= { pdnControlMIBGroups 16 }

pdnDevFileXferMIBGroup	OBJECT-GROUP
	OBJECTS		{ pdnDevFileXferifIndex,
			  pdnDevFileXferFileName, pdnDevFileXferCopyProtocol,
			  pdnDevFileXferFileType, pdnDevFileXferServerIpAddress,
			  pdnDevFileXferUserName, pdnDevFileXferUserPassword,
			  pdnDevFileXferUserAccount, pdnDevFileXferOperation,
			  pdnDevFileXferPktsSent, pdnDevFileXferPktsRecv,
			  pdnDevFileXferOctetsSent, pdnDevFileXferOctetsRecv,
			  pdnDevFileXferOwnerString,
			  pdnDevFileXferStatus, pdnDevFileXferApply, pdnDevFileXferErrorStatus,
			  pdnDevFileXferSendEvent, pdnDevFileXferXferTime,
			  pdnDevFileXferRowStatus }
	STATUS		current
	DESCRIPTION	"File Transfer Client Objects"
  ::= { pdnControlMIBGroups 14 }

 devNextTableObjectMIBGroup OBJECT-GROUP
	OBJECTS		 { pdnDevFileXferSessionIDNext }
	STATUS		 current
	DESCRIPTION	 " Group of singular objects that decided next
			   available object for mib tables."
  ::= { pdnControlMIBGroups 15 }

pdnAutoFwGroup	OBJECT-GROUP
	OBJECTS		{ devIsAutoFwEnabled, devAutoFwStatus }
	STATUS		current
	DESCRIPTION 	"Auto Firmware Download Feature and associated status."
  ::= { pdnControlMIBGroups 12 }

devAutoFwEventGroup		NOTIFICATION-GROUP
	NOTIFICATIONS	{ devAutoFwEvent }
	STATUS		current
	DESCRIPTION	"Notifications indicating the result of the Auto Firmware Download."
  ::= { pdnControlMIBGroups 13 }

pdnDevFileXferErrorStatusTextGroup  OBJECT-GROUP
    OBJECTS     { pdnDevFileXferErrorStatusText }
    STATUS      current
    DESCRIPTION "Objects for textual interpretation of FTP failure codes."
    ::= { pdnControlMIBGroups 17 }

pdnCCMModeGroup OBJECT-GROUP
    OBJECTS     { pdnCCMMode }
    STATUS      current
    DESCRIPTION "Objects for configuring the Configuration Change 
                 Management Mode."
    ::= { pdnControlMIBGroups 18 }


END

PDN-IFEXT-MIB DEFINITIONS ::= BEGIN

IMPORTS
	ifIndex
		FROM RFC1213-MIB
	Counter,IpAddress
		FROM RFC1155-SMI
	OBJECT-TYPE
		FROM RFC-1212
     	pdnIfExt
		FROM PDN-HEADER-MIB
	RowStatus
		FROM SNMPv2-TC
	;

-- ===============================================================
--
--   Extentions to the IF-MIB
--
--  Release: 1.5  01/02/2002 D.Gough
--  Release: 1.4  03/20/2000 D.Gough
--  Release: 1.3  03/02/2000 D.Gough
--  Release: 1.2  02/10/2000 D.Gough
--  Release: 1.1  10/12/99 F. Mota
--  Release: 1.0  05/26/99 (Initial Release) J.Strain
--
--  Last Updated: 01/02/2002 by D.Gough
--		  Updated pdnIfTable (marked as deprecated)
--  Last Updated: 03/20/2000 by D.Gough
--		  Updated pdnIfTable (interface configuration
--		  table)
--  Last Updated: 03/02/2000 by D.Gough
--	          Updated pdnAddressConfigIfTable
--		  and added pdnIfExtRouterID
--  Last Updated: 02/10/2000 by D.Gough
--		  Added pdnAddressConfigifTable
--  Last Updated: 10/12/99 by F. Mota (fmota@eng.paradyne.com)
--                (Added object pdnIfExtTotalUASs)
--
--
--	This MIB is intended to AUGMENT the ifEntry Table like ifTestEntry
--	and ifXEntry does.
--

pdnIfExtConfig OBJECT IDENTIFIER ::= { pdnIfExt  1 }
pdnIfExtTestConfig OBJECT IDENTIFIER   ::= { pdnIfExt  2 }

pdnIfExtTable OBJECT-TYPE
    SYNTAX  SEQUENCE OF PdnIfExtEntry
    ACCESS  not-accessible
    STATUS  mandatory
    DESCRIPTION
           "The Paradyne IF-MIB Table Augment."
    ::= { pdnIfExtConfig 1   }

pdnIfExtEntry OBJECT-TYPE
    SYNTAX  PdnIfExtEntry
    ACCESS  not-accessible
    STATUS  mandatory
    DESCRIPTION
           "An entry in the Paradyne If-MIB Interface Config Table."
    INDEX   { pdnIfExtIndex }
    ::= { pdnIfExtTable  1 }

PdnIfExtEntry ::=
    SEQUENCE {
    pdnIfExtIndex
        INTEGER,

    pdnIfExtInOctetRollovers
        Counter,

    pdnIfExtOutOctetRollovers
        Counter,

    pdnIfExtTotalUASs
        Counter
    }

pdnIfExtIndex OBJECT-TYPE
    SYNTAX  INTEGER
    ACCESS  read-only
    STATUS  mandatory
    DESCRIPTION
           "The index value which uniquely identifies the
            interface for which this entry contains information
            on interface tests.  The interface identified by a
            particular value of this index is the same interface
            as identified by the same value of ifIndex from the
            Interfaces table of MIB II (RFC 1213)."
    ::= { pdnIfExtEntry 1 }

pdnIfExtInOctetRollovers OBJECT-TYPE
    SYNTAX 	Counter
    ACCESS  read-only
    STATUS 	mandatory
    DESCRIPTION
			"The number of times that the associated instance of the ifInOctets
			 object has overflowed or incremented from the value 2^^32-1 to zero."
    ::= { pdnIfExtEntry 2 }

pdnIfExtOutOctetRollovers OBJECT-TYPE
    SYNTAX	Counter
    ACCESS  read-only
    STATUS 	mandatory
    DESCRIPTION
			"The number of times that the associated instance of the ifOutOctets 
			object has overflowed or incremented from the value 2^^32-1 to zero."
    ::= { pdnIfExtEntry 3 }

pdnIfExtTotalUASs OBJECT-TYPE
    SYNTAX	Counter
    ACCESS	read-only
    STATUS	mandatory
    DESCRIPTION
			"The number of Unavailable Seconds encountered by this interface."
    ::= { pdnIfExtEntry 4 }
-- ------------------------------------------------------
--
--   Interface Test Group
--
--  Release: 1.0  05/26/99 (Initial Release) J.Strain
--
--  Last Updated:
--
-- This Group extends the interface table for only those interfaces
-- where test are to be performed on them.
--
-- ------------------------------------------------------
 
 
pdnIfExtTestConfigTable OBJECT-TYPE
    SYNTAX  SEQUENCE OF PdnIfExtTestConfigEntry
    ACCESS  not-accessible
    STATUS  mandatory
    DESCRIPTION
           "The Paradyne Interface Test Table"
    ::= { pdnIfExtTestConfig 1 }
 
pdnIfExtTestConfigEntry OBJECT-TYPE
    SYNTAX  PdnIfExtTestConfigEntry
    ACCESS  not-accessible
    STATUS  mandatory
    DESCRIPTION
           "An entry in the Paradyne Interface Test Config Table."
    INDEX   { pdnIfExtTestConfigIfIndex }
    ::= { pdnIfExtTestConfigTable  1 }
 
PdnIfExtTestConfigEntry ::=
    SEQUENCE {
    pdnIfExtTestConfigIfIndex
        INTEGER,
 
    pdnIfExtTestConfigNearTimer
        INTEGER,
 
    pdnIfExtTestConfigFarTimer
        INTEGER
    }
 
pdnIfExtTestConfigIfIndex OBJECT-TYPE
    SYNTAX  INTEGER
    ACCESS  read-only
    STATUS  mandatory
    DESCRIPTION
           "The index value which uniquely identifies the
            interface for which this entry contains information
            on interface tests.  The interface identified by a
            particular value of this index is the same interface
            as identified by the same value of ifIndex from the
            Interfaces table of MIB II (RFC 1213)."
    ::= { pdnIfExtTestConfigEntry 1 }
 
pdnIfExtTestConfigNearTimer OBJECT-TYPE
    SYNTAX  INTEGER
    ACCESS  read-write
    STATUS  mandatory
    DESCRIPTION
           "This object is used to specify a near end timer primarily
            used as a timeout for a local loopback. The time is in seconds."
    ::= { pdnIfExtTestConfigEntry  2 }
 
pdnIfExtTestConfigFarTimer OBJECT-TYPE
    SYNTAX  INTEGER
    ACCESS  read-write
    STATUS  mandatory
    DESCRIPTION
           "This object is used to specify a far end timer, primarily
            used as a timeout from a far end initiated loopback.
			The time is in seconds."
    ::= { pdnIfExtTestConfigEntry  3 }

-- ------------------------------------------------------
--
--   Interface Address Configuration Group
--
--  Release:   02/10/2000 (Initial Release) D.Gough 
--
--  Last Updated: 03/20/2000 D.Gough
--
-- This Group allows configuration of interface  
--
-- ------------------------------------------------------
        pdnIfTable OBJECT-TYPE
	    SYNTAX  SEQUENCE OF PdnIfEntry
	    ACCESS  not-accessible
	    STATUS  deprecated
	    DESCRIPTION
	 	    " This table that contains additional  
		      interface configuration information. "
            ::= { pdnIfExtConfig 2 }

        pdnIfEntry OBJECT-TYPE
  	    SYNTAX   PdnIfEntry
	    ACCESS   not-accessible
	    STATUS   deprecated 
	    DESCRIPTION
	  	    " There will be one of these rows for each IP address
		    assigned ot an interface, and one for an unnumbered interface."
	    INDEX   { ifIndex, pdnIfAddr }
            ::= { pdnIfTable 1 }

        PdnIfEntry ::=
  	    SEQUENCE {
	     pdnIfAddr               IpAddress,
	     pdnIfAddrMask           IpAddress,
	     pdnIfStatus	           RowStatus
            }

        pdnIfAddr   OBJECT-TYPE
  	    SYNTAX	  IpAddress
	    ACCESS	  read-only
	    STATUS        deprecated
	    DESCRIPTION
	 	    " The value of this object specifies an 
		      interface IP Address. The value 0.0.0.0 means that
		      the interface is unnumbered."
            ::= { pdnIfEntry 1 }

        pdnIfAddrMask  OBJECT-TYPE
    	    SYNTAX	 IpAddress
	    ACCESS   read-write
	    STATUS   deprecated 
	    DESCRIPTION
		    " The value of this object specifies the
		      subnet mask associated with the corresponding
		      interface IP Address. The value of this
		      object along with corresponding interface IP
		      address, determines a subnet address for the interface."
            ::= { pdnIfEntry 2 }

        pdnIfStatus  OBJECT-TYPE
	    SYNTAX	RowStatus
	    ACCESS	read-write
	    STATUS 	deprecated
	    DESCRIPTION
		    " This object is used to create a new row or
		      delete an existing row in this table."
            ::= { pdnIfEntry 3 }

END

-- Copyright (C) 2003 Paradyne Corporation.        
PDN-IF-EXT-CONFIG-MIB DEFINITIONS ::= BEGIN

IMPORTS
	MODULE-IDENTITY, OBJECT-TYPE
	 FROM SNMPv2-SMI
	TEXTUAL-CONVENTION
	 FROM SNMPv2-TC
        ifIndex
	 FROM IF-MIB
        MODULE-COMPLIANCE, OBJECT-GROUP
	 FROM SNMPv2-CONF
        pdnIfExt
	 FROM PDN-HEADER-MIB
	pdnIfExtConfig
	 FROM PDN-IFEXT-MIB
        ;	

pdnIfExtEncapConfig MODULE-IDENTITY
	LAST-UPDATED "200312160900Z"
	ORGANIZATION "Paradyne Networks
		      MIB Working Group"

 	CONTACT-INFO "Paradyne Networks, Inc.
		      8545 126th Ave North
		      Largo, FL 33733
		      www.paradyne.com

		      General Comments to:
	mibwg_team@eng.paradyne.com

		      Editors
		      Dragana Gough,
		      Jesus Pinto" 

	DESCRIPTION
             "This Mib is created to facilitate  
	      configuration of interface related objects."

	REVISION "200312160900Z"
	DESCRIPTION " Jesus Pinto
            o Added LinkRole TEXTUAL-CONVENTION
	    o Added pdnIfXLinkConfigTable."

	REVISION "200111130000Z"
	DESCRIPTION " Dragana Gough
            o updated object name for
	      pdnIfMultiprotocolEncapConfigIPBridgedPDUs
	      to pdnIfMultiprotocolEncapConfigBridgedPDUs."

	REVISION "200111120000Z"
	DESCRIPTION " Dragana Gough
            o updated comment for
	      pdnIfMultiprotocolEncapConfigIPRoutedPDUs
	      to fix description field
	    o added new object
	      pdnIfMultiprotocolEncapConfigIPBridgedPDUs
	      to supported bridged pdus configuration"

	REVISION "200005110000Z"
	DESCRIPTION " Dragana Gough
	    o updated after mibwg meeting
	    o changed table name
	    o rearranged enum values in pdnIfExtConfigIPRoutedPDU
	    o define groups for compliance "

        REVISION "200005030000Z"
	DESCRIPTION " Dragana Gough
	    o changed enum names "

	REVISION "200005020000Z"
	DESCRIPTION " Dragana Gough
            o Initial Version "

	::= { pdnIfExt 3 }

--
-- Textual Conventions
--
-- Note: Although 'other' is a vague value, we want to leave it like
--	 that for now for flexibility. We'll refine that later.
--	 
PdnLinkRole ::= TEXTUAL-CONVENTION
	STATUS	current
	DESCRIPTION
		"Objects defined with this textual convention 	
		are used to indicate the usage of the link.

		uplink   (1) :  interface is used as uplink
		other    (2) :  interface is used for something other
			        than uplink (e.g, subtending).
		"

	SYNTAX  INTEGER { 
			uplink   (1),
			other    (2)
			}
	
--
--  Interface Configuration Group 
--
  pdnIfMultiprotocolEncapConfigTable  OBJECT-TYPE
    SYNTAX  SEQUENCE OF PdnIfMultiprotocolEncapConfigEntry 
    MAX-ACCESS  not-accessible
    STATUS current 
    DESCRIPTION
	    " This table that contains additional  
	      interface configuration information. "
    ::= { pdnIfExtEncapConfig 1 }

 pdnIfMultiprotocolEncapConfigEntry OBJECT-TYPE
    SYNTAX   PdnIfMultiprotocolEncapConfigEntry
    MAX-ACCESS   not-accessible
    STATUS  current 
    DESCRIPTION
	     " There will be one of these rows for each interface that 
	       supports RFC1483. "
    INDEX { ifIndex }
    ::= { pdnIfMultiprotocolEncapConfigTable 1 }

 PdnIfMultiprotocolEncapConfigEntry ::=
    SEQUENCE {
         pdnIfMultiprotocolEncapConfigIPRoutedPDUs	   INTEGER,
         pdnIfMultiprotocolEncapConfigBridgedPDUs	   INTEGER
            }

 pdnIfMultiprotocolEncapConfigIPRoutedPDUs   OBJECT-TYPE
     SYNTAX     INTEGER { none    (1), 
			  llcSnap (2),
			  vcBasedMultiplexing (3) 
			}
     MAX-ACCESS	read-write
     STATUS     current	
     DESCRIPTION
	"In the upstream direction user can configure the IP 
	routed PDUs in the LLC SNAP encapsulation or VC Based
	Multiplexing encapsulation (RFC1483). If neither is 
	configured 'none' is used. The direction is determined
	by the transmit direction. Initialy this object was
	developed for the endpoint use where the transmit direction
	is upstream. This object could be used for CO type equipment
	where the direction would be downstream."
     ::= { pdnIfMultiprotocolEncapConfigEntry 1 }

 pdnIfMultiprotocolEncapConfigBridgedPDUs   OBJECT-TYPE
     SYNTAX     INTEGER { none    (1), 
			  llcSnap (2),
			  vcBasedMultiplexing (3) 
			}
     MAX-ACCESS	read-write
     STATUS     current	
     DESCRIPTION
	 "In the transmit direction user can configure the IP
	 routed PDUs in the LLC SNAP encapsulation or VC Based
	 Multiplexing encapsulation (RFC1483). If neither is
	 configured 'none' is used."
     ::= { pdnIfMultiprotocolEncapConfigEntry 2 }

--
--  ifXLinkConfig Table
--
--  	This table allows configuration of interfaces
--	that are capable of switching roles at run-time.
--
--	Right now, the primary usage of this table is
--	to configure the uplink role among interfaces.
--

pdnIfXLinkConfigTable  OBJECT-TYPE
    SYNTAX      SEQUENCE OF PdnIfXLinkConfigEntry
    MAX-ACCESS  not-accessible
    STATUS 	current
    DESCRIPTION
	 "This table contains configuration information
	 for interfaces that are capable of switch roles
	 at run-time.
	"
    ::= { pdnIfExtConfig 3 }

pdnIfXLinkConfigEntry OBJECT-TYPE
    SYNTAX       PdnIfXLinkConfigEntry
    MAX-ACCESS   not-accessible
    STATUS       current 
    DESCRIPTION
	"An entry in this table represents an interface
      	that is capable of being used as an uplink.

	Typically, this table will contain entries only
	for interfaces that are capable of switching roles.
	"
    INDEX { ifIndex }	
    ::= { pdnIfXLinkConfigTable 1 }

PdnIfXLinkConfigEntry ::=
    SEQUENCE {
         	pdnIfXLinkConfigRole	PdnLinkRole
	     }

pdnIfXLinkConfigRole   OBJECT-TYPE
     SYNTAX     PdnLinkRole
     MAX-ACCESS	read-write
     STATUS     current	
     DESCRIPTION
	"This object allows users to configure the role
	(e.g., uplink) intended for this interface.
	"
     ::= { pdnIfXLinkConfigEntry 1 }

-- =============================================================================
-- ==                  Conformance Information                                ==
-- =============================================================================
pdnIfMultiprotocolEncapMIBConformance	OBJECT IDENTIFIER 
	::= {pdnIfExtEncapConfig 2 }

pdnIfMultiprotocolEncapMIBGroups	OBJECT IDENTIFIER 
	::= {pdnIfMultiprotocolEncapMIBConformance 1}

pdnIfMultiprotocolEncapCompliances      OBJECT IDENTIFIER 
	::= {pdnIfMultiprotocolEncapMIBConformance 2}

pdnIfXConfigMIBConformance		OBJECT IDENTIFIER
	::= {pdnIfExt 4}

pdnIfXConfigMIBGroups			OBJECT IDENTIFIER
	::= {pdnIfXConfigMIBConformance 1}


-- ===========================
-- == Compliance Statements ==
-- ===========================
pdnIfMultiprotocolEncapCompliance	MODULE-COMPLIANCE
   STATUS   current
   DESCRIPTION	
      " The compliance statement for SNMP entities which support
        RFC1483 Multiprotocol Encapsulation over ATM adaptation layer 5."

   MODULE -- this module

   GROUP pdnIfMultiprotocolEncapsulationOptionalGroup
   DESCRIPTION
    	"This optional group is used for the configuration of
      	interfaces that support RFC1483."
   OBJECT pdnIfMultiprotocolEncapConfigIPRoutedPDUs
   MIN-ACCESS  read-only
   DESCRIPTION 
	"Write access is not required. "

   OBJECT pdnIfMultiprotocolEncapConfigBridgedPDUs
   MIN-ACCESS  read-only
   DESCRIPTION 
	" Write access is not required. "

   GROUP pdnIfXLinkConfigOptionalGroup
   DESCRIPTION
	"This optional group is used for configuration of
	interfaces used as uplink or downlinks."
   OBJECT pdnIfXLinkConfigRole
   MIN-ACCESS read-only
   DESCRIPTION
	"Write access is not required."

   ::= { pdnIfMultiprotocolEncapCompliances 1 }

pdnIfMultiprotocolEncapsulationOptionalGroup   OBJECT-GROUP
   OBJECTS {
	    pdnIfMultiprotocolEncapConfigIPRoutedPDUs,
	    pdnIfMultiprotocolEncapConfigBridgedPDUs 
	   }
   STATUS  current
   DESCRIPTION
	"A collection of objects providing optional configuration information
	about multiprotocol interface link."
   ::= { pdnIfMultiprotocolEncapMIBGroups 1 }

pdnIfXLinkConfigOptionalGroup	OBJECT-GROUP
   OBJECTS {
	    pdnIfXLinkConfigRole
	   }
   STATUS  current
   DESCRIPTION
	"configuration information for this optional group."
   ::= { pdnIfXConfigMIBGroups 1 }

END

-- =========================================================================
-- ==                                                                     ==
-- ==         Copyright (C) 2005 Paradyne Networks, Inc.                  ==
-- ==                                                                     ==
-- =========================================================================


PDN-SECURITY-MIB DEFINITIONS ::= BEGIN

IMPORTS
    MODULE-IDENTITY, OBJECT-TYPE, NOTIFICATION-TYPE, Integer32, 
    Counter32, Unsigned32, IpAddress
        FROM SNMPv2-SMI
    OBJECT-GROUP, MODULE-COMPLIANCE, NOTIFICATION-GROUP
        FROM SNMPv2-CONF
    RowStatus, DateAndTime
        FROM SNMPv2-TC
    pdn-common
        FROM PDN-HEADER-MIB;

pdn-security MODULE-IDENTITY
    LAST-UPDATED "200507270000Z"  -- July 27, 2005
    ORGANIZATION "Paradyne Networks
                  MIB Working Group
                  Other information about group editing the MIB"
    CONTACT-INFO "Paradyne Networks, Inc.
                  8545 126th Avenue North
                  Largo, FL 33733
                  www.paradyne.com
        
                  General Comments to: mibwg_team@paradyne.com

                  Editor(s)
                      Bob      Steinberger
                      Rajesh   Gowda
                      Dragana  Gough
                      Jesus    Pinto
                      Clay     Sikes"

    DESCRIPTION
        "This module contains objects pertaining to managing security 
         aspects of the management domain.


          ===============================================================
          ==                                                           ==
          ==        Copyright (C) 2005 Paradyne Networks, Inc.         ==
          ==                                                           ==
          ==============================================================="



    REVISION    "200507270000Z"  -- July 27, 2005
    DESCRIPTION "Added the following objects to support control and
                 statistics for access to the Web and Telnet servers by
                 their respective clients:
                     1.  securityMgrWebAccess
                     2.  devSecurityWebSourceValidation
                     3.  devSecurityWebFailedValidationCount
                     4.  devSecurityTelnetServerAccess
                     5.  devSecurityTelnetFailedValidationCount
                     6.  devSecurityNotificationsEnable
                     7.  devSecurityAuthenFailedTable
                     8.  devSecurityFailedIpAddress
                     9.  devSecurityWebAuthenFailure
                     10. devSecurityTelnetAuthenFailure.

                 Noticed that the devSecuritySNMPTrapRateLimitPeriodGroup
                 was mistakenly associated with the deprecated
                 pdnSecurityComplianceDeprecated1 MODULE-COMPLIANCE, so
                 it was moved to be associated with the correct
                 MODULE-COMPLIANCE.

                 Modified the description for devSecurityMgrValidation 
                 and devSecurityMgrFailedValidationCount such that the
                 use is clearly explained in terms of the relationship
                 to IP address validation for SNMP managers, Web 
                 Clients, and Telnet Clients"

    REVISION    "200504180000Z"  -- April 18, 2005
    DESCRIPTION "1.  Update MIB module to SMIv2.
                 2.  Added devSecuritySNMPTrapRateLimitPeriod."

    REVISION    "200311060000Z"  -- November 6, 2003
    DESCRIPTION "Clay Sikes
                 Added a MIB object to allow the Web Server to be
                 enabled or disabled."

    REVISION    "200309290000Z" -- September 29,l 2003
    DESCRIPTION "Jesus Pinto
                 1.  Changed description for devSecurityMgrValidation.
                 2.  Added mib object to count the number of packets 
                     discarded due to IpSecurityValidations."

    REVISION    "200208220000Z"  -- August 22, 2002
    DESCRIPTION "Jesus Pinto
                 Deprecated securityMgrTrapAccess. Developers should
                 use pdn_TrapMgr.mib for trap manager configuration."

    REVISION    "200205210000Z"  -- May 21, 2002
    DESCRIPTION "Jesus Pinto
                 1.  Changed STATUS on newSecurityMgrTable to deprecated.
                 2.  Changed ACCESS on securityMgrIpAddress and 
                     securityMgrSubnetMask to be read-only."


    REVISION    "200201110000Z"  -- January 11, 2002
    DESCRIPTION "Dragana Gough
                 Removed devSecurityTrapMgrTable and added object in 
                 securityMgrTable to signal that traps are to be sent 
                 to specified ip address."

    REVISION    "200201070000Z"  -- January 7, 2002
    DESCRIPTION "Dragana Gough
                 Added devSecurityTrapMgrTable."


    REVISION    "200003030000Z"  -- March 3, 2000"
    DESCRIPTION "Rajesh Gowda
                 1. Added devSecurityFtpSourceValidation scalar object.
                 2. Added table object securityMgrTable which deprecates
                    newSecurityMgrTable for the following reasons
                    a. Index for the table is changed
                    b. Manager access object is broken down to 3 objects."


    REVISION    "199811180000Z"  -- November 18, 1998
    DESCRIPTION "Rob Steinberger
                 Reversed Rajesh's change from att-security to pdn-security
                 in that it breaks attDCE.mib."

    REVISION    "199811090000Z"  -- November 9, 1998
    DESCRIPTION "Rajesh Gowda
                 1.  Added devSecurityTelnetSourceValidation scalar object.
                 2.  Added newSecurityMgrSubnetMask objects into 
                     newSecurityMgrTable.
                     Changed the description of newSecurityMgrIpAddress.
                 3.  att-security group name has been changed to 
                     pdn-security.
                 4.  More enumerations added to object 
                     newSecurityMgrAccess."


    -- =====================================================================
    -- == Earlier revision history not captured and is unknown.
    -- == Seems like this module may have been created further back than
    -- == 1996 under another source code control system.
    -- =====================================================================


::=  { pdn-common 8 }


pdnSecurityNotifications  OBJECT IDENTIFIER ::= { pdn-security 0 }
pdnSecurityAFNs           OBJECT IDENTIFIER ::= { pdn-security 99 }

-- Gap the OID because this module was originally written in SMIv1
pdnSecurityConformance   OBJECT IDENTIFIER ::= { pdn-security 100 } 



-- =========================================================================
-- ==                  MIB Objects                                        ==
-- =========================================================================


devSecurityMgrValidation OBJECT-TYPE
    SYNTAX      INTEGER {
                    disable (1),
                    enable  (2)
                }
    MAX-ACCESS  read-write
    STATUS      current
    DESCRIPTION "This object is used to either enable or disable
                 IP validation.  When enabled, the first check on any
                 incoming PDU is based on the IP address of the packet.
                 If the IP address is configured in one of the manager 
                 tables, access is granted according to the level of 
                 access configured for that IpAddress.

                 If the implementation is such that there are separate
                 objects used for configuring the validation of IP 
                 addresses for Web Clients (via 
                 devSecurityWebSourceValidation) and Telnet Clients 
                 (via devSecurityTelnetSourceValidation), this object 
                 will be used to configure the validation of IP 
                 addresses for SNMP managers.  Otherwise the 
                 implementation is such that there is one object, 
                 namely this object, that configures the validation of
                 IP addresses for all clients and managers (SNMP, Web, 
                 and Telnet)."
    ::= { pdn-security 1 }


devSecurityMgrMaxNumber OBJECT-TYPE
    SYNTAX      Integer32
    MAX-ACCESS  read-only
    STATUS      current
    DESCRIPTION "Maximum number of managers allowed in the 
                 devSecurityMgrTable."
    ::= { pdn-security 2 }


devSecurityMgrCurrentNumber OBJECT-TYPE
    SYNTAX      Integer32
    MAX-ACCESS  read-only
    STATUS      current
    DESCRIPTION "Current number of managers in the devSecurityMgrTable."
    ::= { pdn-security 3 }


-- =========================================================================
-- == devSecurityMgrTable (Deprecated)
-- =========================================================================

devSecurityMgrTable OBJECT-TYPE
    SYNTAX      SEQUENCE OF DevSecurityMgrEntry
    MAX-ACCESS  not-accessible
    STATUS      deprecated
    DESCRIPTION "A list of the security manager entries.
                 In order to add a new Security Manager the 
                 devSecurityMgrIpAddress object must be created first by 
                 setting it to a valid IP Address."
    ::= { pdn-security 4 }

devSecurityMgrEntry OBJECT-TYPE
    SYNTAX      DevSecurityMgrEntry
    MAX-ACCESS  not-accessible
    STATUS      deprecated
    DESCRIPTION "The SNMP IP Address configuration items."
    INDEX       { devSecurityMgrIpAddress }
    ::= { devSecurityMgrTable 1 }

DevSecurityMgrEntry ::=
    SEQUENCE {
        devSecurityMgrIpAddress  IpAddress,
        devSecurityMgrAccess     INTEGER
    }

devSecurityMgrIpAddress OBJECT-TYPE
    SYNTAX      IpAddress
    MAX-ACCESS  read-write
    STATUS      deprecated
    DESCRIPTION "This is used to specify the IP address that identifies the
                 SNMP manager(s) that are authorized to send SNMP messages.

                 An existing Security Manager may be deleted by setting the 
                 devSecurityMgrIpAddress object to 0.0.0.0 or by setting the 
                 devSecurityMgrIpAddress object to a new IP Address.
                 A new Security Manager may be added by setting
                 the devSecurityMgrIpAddress object of 0.0.0.0 to the new 
                 address as long as there is still room for another Security 
                 Manager.

                 When ever a new Security Manager is added or an existing 
                 Security Manager's IP Address is modified, 
                 the devSecurityMgrAccess object is set to the default value 
                 of read (1)."
    ::= { devSecurityMgrEntry 1 }

devSecurityMgrAccess OBJECT-TYPE
                SYNTAX INTEGER {
                    read      (1),
                    readWrite (2)
                }
    MAX-ACCESS  read-write
    STATUS      deprecated
    DESCRIPTION "This field is used to specify the access allowed for an 
                 authorized NMS when Manager Validation is performed. 
                 If the IP address for the NMS sending an SNMP message is on 
                 the list of allowed managers, this option along with the 
                 Community Name access determine the type of access allowed 
                 for the that manager. 

                 When ever a new Security Manager is added or an existing 
                 Security Manager's IP Address is modified, the 
                 devSecurityMgrAccess object is set to the default value of 
                 read (1).  If the index for this object is not in the 
                 existing table and if there is room in the table then the 
                 index will be used to create a new Security Manager and 
                 will be given the requested access level."
    ::= { devSecurityMgrEntry 2 }


-- =========================================================================
-- == newSecurityMgrTable (Deprecated)                                    ==
-- =========================================================================

newSecurityMgrTable OBJECT-TYPE
    SYNTAX      SEQUENCE OF NewSecurityMgrEntry
    MAX-ACCESS  not-accessible
    STATUS      deprecated
    DESCRIPTION "A list of the security manager entries.  If an entry is not 
                 found in this table, it is added to the table."
    ::= { pdn-security 5 }

newSecurityMgrEntry OBJECT-TYPE
    SYNTAX      NewSecurityMgrEntry
    MAX-ACCESS  not-accessible
    STATUS      deprecated
    DESCRIPTION "The SNMP IP Address configuration items."
    INDEX       { newSecurityMgrIpAddress }
    ::= { newSecurityMgrTable 1 }

NewSecurityMgrEntry ::=
    SEQUENCE {
        newSecurityMgrIpAddress    IpAddress,
        newSecurityMgrAccess       INTEGER,
        newSecurityMgrSubnetMask   IpAddress
    }

newSecurityMgrIpAddress OBJECT-TYPE
    SYNTAX      IpAddress
    MAX-ACCESS  read-write
    STATUS      deprecated
    DESCRIPTION "This is used to specify the IP address that identifies the
                 SNMP manager(s) that are authorized to send SNMP messages.
                 This object is the binary AND of SNMP or telnet source IP
                 address and its subnet mask if the subnet mask is 
                 available.  Subnet mask is assumed to be 255.255.255.255 
                 when not available"
    ::= { newSecurityMgrEntry 1 }


newSecurityMgrAccess OBJECT-TYPE
    SYNTAX      INTEGER {
                    read      (1),
                    readWrite (2),
                    noAccess  (3),
                    telnetNoAccess  (4),
                    telnetRead      (5),
                    telnetReadWrite (6)
                }
    MAX-ACCESS  read-write
    STATUS      deprecated
    DESCRIPTION "This field is used to specify the access allowed for an 
                 authorized NMS when Manager Validation is performed.  If 
                 the IP address for the NMS sending an SNMP message is on 
                 the list of allowed managers, this option along with the 
                 Community Name access  determine the type of access allowed
                 for the  that manager. 

                 When ever a new Security Manager is added or an existing 
                 Security Manager's IP Address is modified, the 
                 newSecurityMgrAccess object is set to the default value of 
                 read (1).  If the index for this object is not in the 
                 existing table and if there is room in the table then the 
                 index will be used to create a new Security Manager and 
                 will be given the requested access level.  In addition 
                 changing an existing access permission to noAccess 
                 invalidates the corresponding row of this table.  It is up
                 to the implementation to decide whether to actually remove
                  this entry from the table or not.

                 read (1)            ==> no telnet access and snmp read only 
                                         access 
                 readWrite (2)       ==> no telnet access and snmp 
                                         read-write access
                 noAccess (3)        ==> no telnet access and no snmp 
                                         read-write access
                 telnetNoAccess (4)  ==> telnet access and no snmp access
                 telnetRead (5)      ==> telnet access and snmp read only 
                                         access
                 telnetReadWrite (6) ==> telnet access and snmp read-write 
                                         access."
    ::= { newSecurityMgrEntry 2 }

newSecurityMgrSubnetMask OBJECT-TYPE
    SYNTAX      IpAddress
    MAX-ACCESS  read-write
    STATUS      deprecated
    DESCRIPTION "This object is used to specify the subnet mask "
    ::= { newSecurityMgrEntry 3 }



devSecurityTelnetSourceValidation OBJECT-TYPE
    SYNTAX      INTEGER {
                    disable (1),
                    enable  (2)
                }
    MAX-ACCESS  read-write
    STATUS      current
    DESCRIPTION "This object is used to either enable or disable telnet 
                 source address screening "
    ::= { pdn-security 6 }

devSecurityFtpSourceValidation OBJECT-TYPE
    SYNTAX      INTEGER {
                    disable (1),
                    enable  (2)
                }
    MAX-ACCESS  read-write
    STATUS      current
    DESCRIPTION "This object is used to either enable or disable ftp 
                 source address screening "
    ::= { pdn-security 7 }


-- =========================================================================
-- == securityMgrTable                                                    ==
-- =========================================================================
securityMgrTable OBJECT-TYPE
    SYNTAX      SEQUENCE OF SecurityMgrEntry
    MAX-ACCESS  not-accessible
    STATUS      current
    DESCRIPTION "This table forms a Management Domain Access List.  
                 Each entry identifies an entity or range of entities 
                 from an IP address and a subnet mask pair.  In 
                 addition an entry defines subsections of the 
                 Management Domain that the entity or entities are
                 allowed to access.  In order for this table to be
                 used, the respective IP Validation object must be
                 enabled.  For example:

                 +---------------+-----------------------------------+
                 | Entity        | IP Validation Object              |
                 +---------------+-----------------------------------+
                 +---------------+-----------------------------------+
                 | FTP Client    | devSecurityFtpSourceValidation    |
                 +---------------+-----------------------------------+
                 | SNMP Manager  | devSecurityMgrValidation          |
                 +---------------+-----------------------------------+
                 | Web Client    | devSecurityWebSourceValidation    |
                 +---------------+-----------------------------------+
                 | Telnet Client | devSecurityTelnetSourceValidation |
                 +---------------+-----------------------------------+

                 This table is also used to specify SNMP 
                 Trap/Notification managers which traps/notifications
                 are to be set to if the entry has its 
                 securityMgrTrapAccess object set to trapAccess(1)."
    ::= { pdn-security 8 }

securityMgrEntry OBJECT-TYPE
    SYNTAX      SecurityMgrEntry
    MAX-ACCESS  not-accessible
    STATUS      current
    DESCRIPTION "An entry consists of both an IP address and subnet 
                 mask pair to uniquely identify an entity or range
                 of entities whose access to the Management Domain
                 are defined."
    INDEX       { securityMgrIpAddress, securityMgrSubnetMask}
    ::= { securityMgrTable 1 }

SecurityMgrEntry ::=
    SEQUENCE {
        securityMgrIpAddress      IpAddress,
        securityMgrSubnetMask     IpAddress,
        securityMgrSnmpAccess     INTEGER,
        securityMgrTelnetAccess   INTEGER,
        securityMgrFtpAccess      INTEGER,
        securityMgrTrapAccess     INTEGER,
        securityMgrRowStatus      RowStatus,
        securityMgrWebAccess      INTEGER
    }

securityMgrIpAddress OBJECT-TYPE
    SYNTAX      IpAddress
    MAX-ACCESS  read-only
    STATUS      current
    DESCRIPTION "Specifies the IP address portion of an entry."
    ::= { securityMgrEntry 1 }

securityMgrSubnetMask OBJECT-TYPE
    SYNTAX      IpAddress
    MAX-ACCESS  read-only
    STATUS      current
    DESCRIPTION "Specifies the subnet mask portion of an entry."
    ::= { securityMgrEntry 2 }

securityMgrSnmpAccess OBJECT-TYPE
    SYNTAX      INTEGER {
                    readOnly  (1),
                    readWrite (2),
                    noAccess (3)
                }
    MAX-ACCESS  read-write
    STATUS      current
    DESCRIPTION "This is used to specify the snmp access to the device."
    ::= { securityMgrEntry 3 }

securityMgrTelnetAccess OBJECT-TYPE
    SYNTAX      INTEGER {
                    disable (1),
                    enable  (2)
                }
    MAX-ACCESS  read-write
    STATUS      current
    DESCRIPTION "This is used to specify the telnet access to the device."
    ::= { securityMgrEntry 4 }

securityMgrFtpAccess OBJECT-TYPE
    SYNTAX      INTEGER {
                    disable (1),
                    enable  (2)
    }
    MAX-ACCESS  read-write
    STATUS      current
    DESCRIPTION "This is used to specify the ftp access to the device."
    ::= { securityMgrEntry 5 }

securityMgrTrapAccess OBJECT-TYPE
    SYNTAX      INTEGER {
                    trapAccess  (1),
                    noTrapAccess (2)
                }
    MAX-ACCESS  read-write
    STATUS      deprecated
    DESCRIPTION "This is used to specify the trap access to the device.
                 NOTE: the pdnDevTrapMgrTable should be used instead."
    ::= { securityMgrEntry 6 }

securityMgrRowStatus OBJECT-TYPE
    SYNTAX      RowStatus
    MAX-ACCESS  read-write
    STATUS      current
    DESCRIPTION "The status of this table entry."
    ::= { securityMgrEntry 7 }

securityMgrWebAccess OBJECT-TYPE
    SYNTAX      INTEGER {
                    disable (1),
                    enable  (2)
                }
    MAX-ACCESS  read-write
    STATUS      current
    DESCRIPTION "This is used to specify the Web Client access to the 
                 device."
    ::= { securityMgrEntry 8 }



devSecuritySNMPMgrAccess OBJECT-TYPE
    SYNTAX      INTEGER {
                    disable (1),
                    enable  (2)
                }
    MAX-ACCESS  read-write
    STATUS      current
    DESCRIPTION "This object is used to either enable or disable
                 SNMP access to the system.  When disabled the first check 
                 on any incoming PDU is based on the PDU type of the 
                 datagram.  If it is an SNMP manager trying to access SNMP 
                 agent on the system the access will be denied."
    ::= { pdn-security 9 }

devSecurityMgrFailedValidationCount OBJECT-TYPE
    SYNTAX      Counter32
    MAX-ACCESS  read-only
    STATUS      current
    DESCRIPTION "When IP Validation is enabled 
                 [devSecurityMgrValidation is set to enable(2)], this
                 object counts the number of IP packets that have failed
                 the IP Validation check.  Otherwise this object should
                 return 0.

                 If the implementation is such that there are separate
                 objects used for configuring the validation of IP 
                 addresses for Web Clients (via 
                 devSecurityWebSourceValidation) and Telnet Clients 
                 (via devSecurityTelnetSourceValidation), this object
                 will be used to count the number of IP packets that 
                 have failed the IP validation check for SNMP managers.
                 Otherwise the implementation is such that there is one
                 object, namely this object, that count the number of
                 IP packets that have failed the IP validation check 
                 for all clients and managers (SNMP, Web, and Telnet)."
    ::= {  pdn-security 10 }

devSecurityWebServerAccess OBJECT-TYPE
    SYNTAX      INTEGER {
                    disable (1),
                    enable  (2)
                }
    MAX-ACCESS  read-write
    STATUS      current
    DESCRIPTION "This object is used to either enable or disable access to 
                 the Web Server."
    ::= { pdn-security 11 }

devSecuritySNMPTrapRateLimitPeriod OBJECT-TYPE
    SYNTAX      Integer32(0..2147483647)
    UNITS       "seconds"
    MAX-ACCESS  read-write
    STATUS      current
    DESCRIPTION "The SNMP Trap Rate Limiting Period.  This period is the
                 gap, in seconds, that the agent enforces, between
                 consecutive traps/notifications for the same instance
                 of a particular event.  Events that occur before this 
                 period expires will not be sent to a manager.  Setting 
                 this object to 0, disables rate limiting.  

                 Care must be taken when assigning a value to this object.
                 Disabling rate limiting for traps/Notifications could
                 result in a large amount of traps/notifications being
                 sent to a manager.  Assigning a large value could prevent
                 the timely delivery of important diagnostic information."
    ::= { pdn-security 12 }

devSecurityWebSourceValidation OBJECT-TYPE
    SYNTAX      INTEGER {
                    disable (1),
                    enable  (2)
                }
    MAX-ACCESS  read-write
    STATUS      current
    DESCRIPTION "This object is used to enable or disable IP validation
                 for Web Client access to the device's Web Server.  

                 When enabled, IP validation for Web Clients is enabled.
                 A Web Client `access control list' consists of entries
                 in the securityMgrTable which are associated with Web 
                 access (securityMgrWebAccess is set to `enable').  The
                 IP validation occurs such that the source IP address 
                 in a HTTP PDU from a Web Client must exist in the Web 
                 Client `access control list' in order for the PDU to 
                 be processed by the device's Web Server.  If the IP
                 address is not in the `access control list', the PDU
                 is discarded.

                 When disabled, the source IP address in the HTTP PDU is
                 not validated."
    ::= { pdn-security 13 }

devSecurityWebFailedValidationCount OBJECT-TYPE
    SYNTAX      Counter32
    MAX-ACCESS  read-only
    STATUS      current
    DESCRIPTION "When devSecurityWebSourceValidation is enabled, this 
                 object counts the number of HTTP PDUs discarded because
                 their source IP address was not in the Web Client 
                 `access control list'.  When 
                 devSecurityWebSourceValidation is disabled, this 
                 object should return a 0."
    ::= {  pdn-security 14 }

devSecurityTelnetServerAccess OBJECT-TYPE
    SYNTAX      INTEGER {
                    disable (1),
                    enable  (2)
                }
    MAX-ACCESS  read-write
    STATUS      current
    DESCRIPTION "This object is used to enable or disable access to the
                 Telnet Server."
    ::= { pdn-security 15 }

devSecurityTelnetFailedValidationCount OBJECT-TYPE
    SYNTAX      Counter32
    MAX-ACCESS  read-only
    STATUS      current
    DESCRIPTION "When devSecurityTelnetSourceValidation is enabled, 
                 this object counts the number of Telnet PDUs discarded
                 because their source IP address was not in the Telnet 
                 Client `access control list'.  When 
                 devSecurityTelnetSourceValidataion is disabled, this 
                 object should return a 0."
    ::= {  pdn-security 16 }

devSecurityNotificationsEnable OBJECT-TYPE
    SYNTAX      BITS {
                    devSecurityWebNotification(0),
                    devSecurityTelnetNotification(1)
                }
    MAX-ACCESS  read-write
    STATUS      current
    DESCRIPTION "Provides the ability to enable or disable notifications
                 for this MIB module.  When the bit is set for a 
                 particular notification, the notification must be 
                 generated unless it is to be rate limited.  Reference 
                 `NOTES' for Traps/Notifications below.  When the bit is
                 reset for a particular notification, the notification 
                 must not be generated."
    ::= { pdn-security 17 }


-- =====================================================================
-- == devSecurityAuthenFailedTable                                    ==
-- =====================================================================
devSecurityAuthenFailedTable OBJECT-TYPE
    SYNTAX      SEQUENCE OF DevSecurityAuthenFailedEntry
    MAX-ACCESS  not-accessible
    STATUS      current
    DESCRIPTION "This table contains a list of IP addresses that have
                 attempted to access the SNMP Agent, Web Server, or the
                 Telnet Server and were not considered to be `invalid' 
                 because they were not in the respective `access control 
                 list'.  The maximum number of entries in the table is 
                 implementation dependent."
    ::= { pdn-security 18 }

devSecurityAuthenFailedEntry OBJECT-TYPE
    SYNTAX      DevSecurityAuthenFailedEntry
    MAX-ACCESS  not-accessible
    STATUS      current
    DESCRIPTION "An entry consists primarily of the IP address that was
                 considered `invalid' along with the time stamp of when
                 it was observed and which `access control list' 
                 considered it `invalid'."
    INDEX       { devSecurityAuthenFailedIndex }
    ::= { devSecurityAuthenFailedTable 1 }

DevSecurityAuthenFailedEntry ::=
    SEQUENCE {
        devSecurityAuthenFailedIndex                  Unsigned32,
        devSecurityAuthenFailedRowStatus              RowStatus,
        devSecurityAuthenFailedDateAndTime            DateAndTime,
        devSecurityAuthenFailedIpAddress              IpAddress,
        devSecurityAuthenFailedList                   INTEGER
    }

devSecurityAuthenFailedIndex OBJECT-TYPE
    SYNTAX      Unsigned32(1..4294967296)
    MAX-ACCESS  not-accessible
    STATUS      current
    DESCRIPTION "Identifies a unique entry in the table.  Lower 
                 numerical values indicate older entries in the table.
                 It is acceptable to reset the value of this object if
                 entries are aged out or manually removed and the table
                 becomes empty.  The maximum number of entries in the 
                 table is implementation specific."
    ::= { devSecurityAuthenFailedEntry 1 }

devSecurityAuthenFailedRowStatus OBJECT-TYPE
    SYNTAX      RowStatus
    MAX-ACCESS  read-write
    STATUS      current
    DESCRIPTION "This object exists only to allow a manager to
                 remove entries in the table.  As a result, only
                 active(1) and destroy(6) are supported."
    ::= { devSecurityAuthenFailedEntry 2 }

devSecurityAuthenFailedDateAndTime OBJECT-TYPE
    SYNTAX      DateAndTime
    MAX-ACCESS  read-only
    STATUS      current
    DESCRIPTION "Provides a date-time indication of when the
                 attempt to access the SNMP Agent with an
                 `invalid' IP address occurred."
    ::= { devSecurityAuthenFailedEntry 3 }

devSecurityAuthenFailedIpAddress OBJECT-TYPE
    SYNTAX      IpAddress
    MAX-ACCESS  read-only
    STATUS      current
    DESCRIPTION "The IP address that was considered `invalid'."
    ::= { devSecurityAuthenFailedEntry 4 }

devSecurityAuthenFailedList OBJECT-TYPE
    SYNTAX      INTEGER {
                    snmp(1),
                    web(2),
                    telnet(3)
                }
    MAX-ACCESS  read-only
    STATUS      current
    DESCRIPTION "Identifies the `access control list' the IP address
                 was not in which resulted in it being considered
                 `invalid'."
    ::= { devSecurityAuthenFailedEntry 5 }



devSecurityAuthenFailedAgeOutTime OBJECT-TYPE
    SYNTAX      Integer32(0..2147483647)
    UNITS       "seconds"
    MAX-ACCESS  read-write
    STATUS      current
    DESCRIPTION "The time, in seconds, to automatically age out entries
                 in the devSecurityAuthenFailedTable.  Setting this 
                 object to 0, disables the aging out of entries in the
                 table."
    ::= { pdn-security 19 }



-- =====================================================================
-- ==                                                                 ==
-- ==  { pdn-security 99 } is reserved for pdnSecurityAFNs            ==
-- ==  which is the Accessible for Notifications group                ==
-- ==                                                                 ==
-- =====================================================================



-- =========================================================================
-- ==       Notification objects (Accessible for Notifications)           ==
-- =========================================================================

devSecurityFailedIpAddress OBJECT-TYPE
    SYNTAX      IpAddress
    MAX-ACCESS  accessible-for-notify
    STATUS      current
    DESCRIPTION "The IP address of a client attempting to access the
                 device which has failed validation because it is not
                 in an entities `access control list'."
    ::= { pdnSecurityAFNs 1 }



-- =========================================================================
-- ==                    Traps/Notifications                              ==
-- =========================================================================

--
-- NOTES: 
--    1.  SNMP uses the authenticationFailure notification for an `IP 
--        Address Validation Event.'  Also Paradyne uses the 
--        devAuthenticationFailureIpAddress object to communicate the 
--        address that failed validation.
--    2.  Notifications should be rate limited (Throttled) such that there
--        is at least a one-minute gap between the generation of 
--        consecutive notifications of the same event.  When notifications
--        are rate limited, they are dropped and not queued for sending
--        at a future time.

devSecurityWebAuthenFailure NOTIFICATION-TYPE
    OBJECTS {
        devSecurityFailedIpAddress
    }
    STATUS      current
    DESCRIPTION "An IP address for a Web Client is not in the `access
                 control list'."
    ::= { pdnSecurityNotifications 1 } 

devSecurityTelnetAuthenFailure NOTIFICATION-TYPE
    OBJECTS {
        devSecurityFailedIpAddress    
    }
    STATUS      current
    DESCRIPTION "An IP address for a Telnet Client is not in the 
                 `access control list'."
    ::= { pdnSecurityNotifications 2 } 


-- =============================================================================
-- ==                  Conformance Information                                ==
-- =============================================================================
pdnSecurityCompliances  OBJECT IDENTIFIER ::= { pdnSecurityConformance 1 }
pdnSecurityGroups       OBJECT IDENTIFIER ::= { pdnSecurityConformance 2 }


-- ===========================
-- == Compliance Statements ==
-- ===========================


pdnSecurityCompliance MODULE-COMPLIANCE
    STATUS      current
    DESCRIPTION "The compliance statement for entities which
                 implement the pdnSecurity MIB module."
    MODULE      -- this module
    -- No mandatory groups are specified

    GROUP       devSecurityMgrValidationGroup
    DESCRIPTION "This group is only required for entities that need to 
                 enable or disable IP validation."

    GROUP       devSecurityMgrNumberGroup
    DESCRIPTION "This group is only required for entities that need to limit
                 and display the number of managers."

    GROUP       devSecurityTelnetSourceValidationGroup
    DESCRIPTION "This group is only required for entities that need to
                 be able to enable or disable Telnet IP address validation."

    GROUP       devSecurityFtpSourceValidationGroup
    DESCRIPTION "This group is only required for entities that need to
                 be able to enable or disable FTP IP address validation."

    GROUP       securityMgrTableGroup
    DESCRIPTION "This group is only required if any objects in the 
                 securityMgrTable are supported."

    GROUP       securityMgrSnmpAccessGroup
    DESCRIPTION "This group is only required if access lists are needed
                 for controlling SNMP access."

    GROUP       securityMgrTelnetAccessGroup
    DESCRIPTION "This group is only required if access lists are needed
                 for controlling Telnet access."

    GROUP       securityMgrFtpAccessGroup
    DESCRIPTION "This group is only required if access lists are needed
                 for controlling FTP access."

    GROUP       devSecuritySnmpAccessGroup
    DESCRIPTION "This group is only required for entities that need to
                 be able to enable or disable SNMP access."

    GROUP       devSecurityMgrFailedValidationGroup
    DESCRIPTION "This group is only required of IP packets that have failed
                 IP Validation need to be counted."

    GROUP       devSecurityWebServerAccessGroup
    DESCRIPTION "This group is only required for entities that need to
                 be able to enable or disable Web access."

    GROUP       devSecuritySNMPTrapRateLimitPeriodGroup
    DESCRIPTION "This group is only required if a rate limiting period
                 for SNMP Traps/Notifications is prescribed."

    GROUP       pdnSecuritySnmpAccessGroup
    DESCRIPTION "This group is only required for entities that need to
                 be able to enable or disable SNMP Agent access."

    GROUP       pdnSecuritySnmpIpValidationGroup
    DESCRIPTION "This group is only required for entities that need to 
                 be able to control IP address validation for SNMP 
                 managers attempting to access the SNMP Agent."

    GROUP       pdnSecurityWebIpValidationGroup
    DESCRIPTION "This group is only required for entities that need to 
                 be able to control IP address validation for Web
                 Clients attempting to access the Web Server."

    GROUP       pdnSecurityTelnetServerAccessGroup
    DESCRIPTION "This group is only required for entities that need to
                 be able to enable or disable Telnet Server access."

    GROUP       pdnSecurityTelnetIpValidationGroup
    DESCRIPTION "This group is only required for entities that need to 
                 be able to control IP address validation for Telnet
                 Clients attempting to access the Telnet Server."

    GROUP       pdnSecurityNotificationsEnableGroup
    DESCRIPTION "This group is only require for entities that need to
                 be able to enable or disable a notification."

    GROUP       pdnSecurityAuthenFailedGroup
    DESCRIPTION "This group is only required where there is a need to
                 display IP addresses which attempted to access the
                 SNMP Agent, Web Server, or Telnet Server but were 
                 considered `invalid'."

    GROUP       devSecurityAuthenFailedRowStatusGroup
    DESCRIPTION "This group is only required where there is a need to 
                 manually remove entries in the 
                 devSecurityAuthenFailedTable."

    GROUP       pdnSecurityAuthenFailedAgeOutTimeGroup
    DESCRIPTION "This group is only required where there is a need to
                 automatically remove (age out) entries in the 
                 devSecurityAuthenFailedTable."

    GROUP       pdnSecurityFailedIpAddressGroup
    DESCRIPTION "This group is only require if notifications containing
                 devSecurityFailedIpAddress are supported."

    GROUP       pdnSecurityWebAuthenFailedNtfyGroup
    DESCRIPTION "This group is only required if notifications for
                 Web Authentication Failures are supported."

    GROUP       pdnSecurityTelnetAuthenFailedNtfyGroup
    DESCRIPTION "This group is only required if notifications for
                 Telnet Authentication Failures are supported."

    
    OBJECT devSecurityAuthenFailedRowStatus
    SYNTAX      INTEGER {
                    active(1),
                    destroy(6)
                }
    DESCRIPTION "If the devSecurityAuthenFailedTable is supported 
                 and there will be support to remove rows manually,
                 an implementation must only support active(1) and
                 destroy(6) for the RowStatus."

    ::= { pdnSecurityCompliances 1 }


pdnSecurityComplianceDeprecated1 MODULE-COMPLIANCE
    STATUS      deprecated
    DESCRIPTION "The compliance statement for entities which
                 implement the pdnSecurity MIB module.

                 These groups are deprecated"
    MODULE      -- this module
    -- No mandatory groups are specified

    GROUP       devSecurityMgrGroup
    DESCRIPTION "This group is deprecated."

    GROUP       newSecurityMgrGroup
    DESCRIPTION "This group is deprecated."

    GROUP       securityMgrTrapAccessGroup
    DESCRIPTION "This group is only required if lists are needed for
                 SNMP Trap Managers.  When a trap/notification occurs,
                 this list identifies the managers who will need to 
                 receive the trap/notification."

    ::= { pdnSecurityCompliances 2 }





-- ==========================
-- == Units of Conformance ==
-- ==========================

pdnSecurityObjGroups   OBJECT IDENTIFIER ::= { pdnSecurityGroups 1 }
pdnSecurityAfnGroups   OBJECT IDENTIFIER ::= { pdnSecurityGroups 2 }
pdnSecurityNtfyGroups  OBJECT IDENTIFIER ::= { pdnSecurityGroups 3 }


-- ===================
-- == Object Groups ==
-- ===================

devSecurityMgrValidationGroup OBJECT-GROUP
    OBJECTS {
                devSecurityMgrValidation
    }
    STATUS      current
    DESCRIPTION "Object to enable or disable IP validation." 
    ::= { pdnSecurityObjGroups 1 }

devSecurityMgrNumberGroup OBJECT-GROUP
    OBJECTS {
                devSecurityMgrMaxNumber,
                devSecurityMgrCurrentNumber
    }
    STATUS      current
    DESCRIPTION "Objects to limit and display the number of managers."
    ::= { pdnSecurityObjGroups 2 }

devSecurityMgrGroup OBJECT-GROUP
    OBJECTS {
                devSecurityMgrIpAddress,
                devSecurityMgrAccess
    }
    STATUS      deprecated
    DESCRIPTION "Objects configuring security managers and their access."
    ::= { pdnSecurityObjGroups 3 }

newSecurityMgrGroup OBJECT-GROUP
    OBJECTS {
                newSecurityMgrIpAddress,
                newSecurityMgrAccess,
                newSecurityMgrSubnetMask
    }
    STATUS      deprecated
    DESCRIPTION "New group of objects configuring security managers and 
                 their access."
    ::= { pdnSecurityObjGroups 4 }


devSecurityTelnetSourceValidationGroup OBJECT-GROUP
    OBJECTS {
                devSecurityTelnetSourceValidation
    }
    STATUS      current
    DESCRIPTION "Object to enable or disable IP validation for Telnet."
    ::= { pdnSecurityObjGroups 5 }

devSecurityFtpSourceValidationGroup OBJECT-GROUP
    OBJECTS {
                devSecurityFtpSourceValidation
    }
    STATUS      current
    DESCRIPTION "Object to enable or disable IP validation for FTP."
    ::= { pdnSecurityObjGroups 6 }

securityMgrTableGroup OBJECT-GROUP
    OBJECTS {
                securityMgrIpAddress,
                securityMgrSubnetMask,
                securityMgrRowStatus
    }
    STATUS      current
    DESCRIPTION "Objects to support the securityMgrTable.  These are
                 indices and rowStatus to allow basic table access and
                 control."
    ::= { pdnSecurityObjGroups 7 }


securityMgrSnmpAccessGroup OBJECT-GROUP
    OBJECTS {
                securityMgrSnmpAccess
    }
    STATUS      current
    DESCRIPTION "Object to support access list for SNMP entities."
    ::= { pdnSecurityObjGroups 8 }

securityMgrTelnetAccessGroup OBJECT-GROUP
    OBJECTS {
                securityMgrTelnetAccess 
    }
    STATUS      current
    DESCRIPTION "Object to support access lists for Telnet entities."
    ::= { pdnSecurityObjGroups 9 }

securityMgrFtpAccessGroup OBJECT-GROUP
    OBJECTS {
                securityMgrFtpAccess
    }
    STATUS      current
    DESCRIPTION "Object to support access lists for FTP entities."
    ::= { pdnSecurityObjGroups 10 }

securityMgrTrapAccessGroup OBJECT-GROUP
    OBJECTS {
                securityMgrTrapAccess
    }
    STATUS      deprecated
    DESCRIPTION "Object to support managers to send trap/notifications 
                 to."
    ::= { pdnSecurityObjGroups 11 }

devSecuritySnmpAccessGroup OBJECT-GROUP
    OBJECTS {
                devSecuritySNMPMgrAccess
    }
    STATUS      current
    DESCRIPTION "Object to support enabling or disabling SNMP access."
    ::= { pdnSecurityObjGroups 12 }

devSecurityMgrFailedValidationGroup OBJECT-GROUP
    OBJECTS {
                devSecurityMgrFailedValidationCount    
    }
    STATUS      current
    DESCRIPTION "Object to count the number of IP packets that have failed
                 IP Validation."
    ::= { pdnSecurityObjGroups 13 }

devSecurityWebServerAccessGroup OBJECT-GROUP
    OBJECTS {
                devSecurityWebServerAccess
    }
    STATUS      current
    DESCRIPTION "Object to support enabling or disabling Web (HTTP) access."
    ::= { pdnSecurityObjGroups 14 }

devSecuritySNMPTrapRateLimitPeriodGroup OBJECT-GROUP
    OBJECTS {
                devSecuritySNMPTrapRateLimitPeriod
    }
    STATUS      current
    DESCRIPTION "Object to support a rate limiting period for SNMP
                 Traps/Notifications."
    ::= { pdnSecurityObjGroups 15 }

pdnSecuritySnmpAccessGroup OBJECT-GROUP
    OBJECTS {
        devSecuritySNMPMgrAccess
    }
    STATUS      current
    DESCRIPTION "Object to enable or disable access to the SNMP Agent."
    ::= { pdnSecurityObjGroups 16 }

pdnSecuritySnmpIpValidationGroup OBJECT-GROUP
    OBJECTS {
        securityMgrSnmpAccess,
        devSecurityMgrValidation,
        devSecurityMgrFailedValidationCount
    }
    STATUS      current
    DESCRIPTION "Objects to control IP address validation and statistics
                 relative to access to the SNMP Agent."
    ::= { pdnSecurityObjGroups 17 }

pdnSecurityWebIpValidationGroup OBJECT-GROUP
    OBJECTS {
        securityMgrWebAccess,
        devSecurityWebSourceValidation,
        devSecurityWebFailedValidationCount
    }
    STATUS      current
    DESCRIPTION "Objects to control IP address validation and statistics
                 relative to access to the Web Server."
    ::= { pdnSecurityObjGroups 18 }

pdnSecurityTelnetServerAccessGroup OBJECT-GROUP
    OBJECTS {
        devSecurityTelnetServerAccess
    }
    STATUS      current
    DESCRIPTION "Object to enable or disable access to the Telnet 
                 Server."
    ::= { pdnSecurityObjGroups 19 }

pdnSecurityTelnetIpValidationGroup OBJECT-GROUP
    OBJECTS {
        securityMgrTelnetAccess,
        devSecurityTelnetSourceValidation,
        devSecurityTelnetFailedValidationCount
    }
    STATUS      current
    DESCRIPTION "Objects to control IP address validation and statistics
                 relative to access to the Telnet Server."
    ::= { pdnSecurityObjGroups 20 }

pdnSecurityNotificationsEnableGroup OBJECT-GROUP
    OBJECTS {
        devSecurityNotificationsEnable
    }
    STATUS      current
    DESCRIPTION "Objects to control the enabling or disabling of
                 notifications."
    ::= { pdnSecurityObjGroups 21 }

pdnSecurityAuthenFailedGroup OBJECT-GROUP
    OBJECTS {
        devSecurityAuthenFailedDateAndTime,
        devSecurityAuthenFailedIpAddress,
        devSecurityAuthenFailedList
    }
    STATUS      current
    DESCRIPTION "Objects to display IP address which attempted to 
                 access the SNMP Agent, Web Server, or Telnet Server
                 but were considered `invalid'."
    ::= { pdnSecurityObjGroups 22 }

devSecurityAuthenFailedRowStatusGroup OBJECT-GROUP
    OBJECTS {        
        devSecurityAuthenFailedRowStatus
    }
    STATUS      current
    DESCRIPTION "Object to support the manual removal of entries in
                 the devSecurityAuthenFailedTable."
    ::= { pdnSecurityObjGroups 23 }

pdnSecurityAuthenFailedAgeOutTimeGroup OBJECT-GROUP
    OBJECTS {
        devSecurityAuthenFailedAgeOutTime
    }
    STATUS      current
    DESCRIPTION "Object to support configuration of an age out timer
                 for entries in the devSecurityAuthenFailedTable."
    ::= { pdnSecurityObjGroups 24 } 



-- ===================
-- == AFN Groups    ==
-- ===================

pdnSecurityFailedIpAddressGroup OBJECT-GROUP
    OBJECTS {
        devSecurityFailedIpAddress
    }
    STATUS      current
    DESCRIPTION "Object to hold the IP address which was considered
                 `invalid'."
    ::= { pdnSecurityAfnGroups 1 }



-- =========================
-- == Notification Groups ==
-- =========================

pdnSecurityWebAuthenFailedNtfyGroup NOTIFICATION-GROUP
    NOTIFICATIONS {
        devSecurityWebAuthenFailure
    }
    STATUS      current
    DESCRIPTION "Object to indicate a Web Authentication Failure
                 occurred."
    ::= { pdnSecurityNtfyGroups 1 }

pdnSecurityTelnetAuthenFailedNtfyGroup NOTIFICATION-GROUP
    NOTIFICATIONS {
        devSecurityTelnetAuthenFailure
    }
    STATUS      current
    DESCRIPTION "Object to indicate a Telnet Authentication Failure
                 occurred."
    ::= { pdnSecurityNtfyGroups 2 }



-- =========
-- == END ==
-- =========
END

PDN-DIAGNOSTICS-MIB DEFINITIONS ::= BEGIN

-- Version :  4.0 
-- Enterprise diagnostic mib
-- Copyright (C) 2000 Paradyne Corporation.

-- Created by : Prakash Easwar
-- Last Updated 05/02/2000
-- Last Updated 06/07/2000 Dragana Gough
-- Last Updated 10/05/2001 Jesus A. Pinto


IMPORTS
IpAddress
	FROM RFC1155-SMI
OBJECT-TYPE
	FROM RFC-1212
TRAP-TYPE
	FROM RFC-1215
ifIndex
	FROM RFC1213-MIB
RowStatus, DisplayString, AutonomousType
	FROM SNMPv2-TC
pdn-diagnostics
	FROM PDN-HEADER-MIB
ifTestId
	FROM IF-MIB
;

--
--    The  HotWire Diagnostics MIB
--
--    This MIB provides an NMS to trigger a diagnostic test 
--    The tests that can be performed are grouped into the following
--    categories :
--       1. Device Tests ( Self, Test Reset ...) 
--       2. interface related tests (bert test, packet loopback ...)
--       3. application based diagnostic tests (Ping, TraceRoute ...)
--
--    Interface related tests (2) are an exception. An NMS will use
--    the ifTestTable of RFC1573 to start these tests. However if any 
--    of the interface related tests need to have inputs. those tests
--    will use the objects defined under the ifTestInput group.
--    Hence in these cases implementation of the following groups
--    are mandatory.
--       ifDeviceInput
--       ifDeviceResults - This group is mandatory if more specific 
--                         information about the results is required
--                         (other than ifTestResult - RFC 1573,ifTestTable) 
--                         to be sent back to an NMS.
--                         Hence in these cases it is left to the 
--                         implementor of the device to put
--                         the OID of the object or results table
--                         containing such specifics to be put
--                         in ifTestCode (RFC 1573, ifTestTable).
--       Note  that the above mentioned groups compliment the ifTestTable
--       of RFC 1573
--
--    if the device supports device tests (1), the devControl.mib needs
--    to be implemented. In addition the following group needs to be 
--    implemented 
--       deviceTestInput
--       deviceTestResults
--
--    if the device supports application tests (1). implementation of the
--    following groups are mandatory.
--       applTests
--

-- History
--
-- 05/02/2000
--
-- Removed integer ranges as those should be designated in the
-- product documentation
--
-- 06/07/2000
--
-- Corrected spelling errors in Probe1,2,3, etc.
--
-- 10/04/2001
--
-- Added a new Interface test called BLERT (Block Error Rate Test)
-- which is intended for MVL.


diagTestMIBObjects    OBJECT IDENTIFIER ::= { pdn-diagnostics 1  }
diagTestMIBTraps      OBJECT IDENTIFIER ::= { pdn-diagnostics 2 }
diagIfTest            OBJECT IDENTIFIER ::= { diagTestMIBObjects 1 }
diagApplTest          OBJECT IDENTIFIER ::= { diagTestMIBObjects 2 }
diagTest              OBJECT IDENTIFIER ::= { diagTestMIBObjects 3 }

-- Table objects under diagIfTest
-- The Loopback Test Objects

ifLoopbackTestTable   OBJECT-TYPE
  SYNTAX       SEQUENCE OF IfLoopbackTestEntry
  ACCESS       not-accessible
  STATUS       mandatory
  DESCRIPTION
    "This table contains input and results of a packet loopback
     test. This table is indexed by ifIndex. This is a interface
     related test. There can be only one test running per 
     interface. This table should be used in conjunction with 
     ifTestTable(Rfc 1573) with all the semantics of ifTestTable."
::= { diagIfTest 1 }

ifLoopbackTestEntry OBJECT-TYPE
  SYNTAX       IfLoopbackTestEntry
  ACCESS       not-accessible
  STATUS       mandatory
  DESCRIPTION
    "An entry containing objects for test input and result
     for packet loopback test"
  INDEX { ifIndex }
::= { ifLoopbackTestTable 1 }

IfLoopbackTestEntry ::=
  SEQUENCE {
    loopbackTestInputNumCycles       INTEGER,
    loopbackTestResultsPktsSent      INTEGER,
    loopbackTestResultsPktsRcvdOK    INTEGER,
    loopbackTestResultsPktsRcvdErr   INTEGER,
    loopbackTestResultsPktsNotRcvd   INTEGER,
    loopbackTestResultsPktErrorRate  DisplayString,
    loopbackTestResultsErrSecs       INTEGER,
    loopbackTestResultsSvrErrSecs    INTEGER,
    loopbackTestResultsElpTime       INTEGER
  }

loopbackTestInputNumCycles OBJECT-TYPE
  SYNTAX       INTEGER
  ACCESS       read-write
  STATUS       mandatory
  DESCRIPTION
    "This object corresponds the number of cycles the test 
     to be run for. One cycle corresponds to a 15 second 
     interval. The default value for this object is 40."
::= { ifLoopbackTestEntry 1 }

loopbackTestResultsPktsSent OBJECT-TYPE
  SYNTAX        INTEGER
  ACCESS        read-only
  STATUS        mandatory
  DESCRIPTION
    "This object corresponds to the number of packets sent"
::= { ifLoopbackTestEntry 2 }

loopbackTestResultsPktsRcvdOK OBJECT-TYPE
  SYNTAX        INTEGER
  ACCESS        read-only
  STATUS        mandatory
  DESCRIPTION
    "This object corresponds to the number of packets which were received
     without any error"
::= { ifLoopbackTestEntry 3 }

loopbackTestResultsPktsRcvdErr OBJECT-TYPE
  SYNTAX        INTEGER
  ACCESS        read-only
  STATUS        mandatory
  DESCRIPTION
    "This object corresponds to the number of packets which were received
     with errors"
::= { ifLoopbackTestEntry 4 }

loopbackTestResultsPktsNotRcvd OBJECT-TYPE
  SYNTAX        INTEGER
  ACCESS        read-only
  STATUS        mandatory
  DESCRIPTION
    "This object corresponds to the number of packets which were sent
     but not received"
::= { ifLoopbackTestEntry 5 }

loopbackTestResultsPktErrorRate OBJECT-TYPE
  SYNTAX        DisplayString (SIZE (1..32))
  ACCESS        read-only
  STATUS        mandatory
  DESCRIPTION
     "Reflects the error rate of the loopback test. this string 
      will represent a floating point number of the form 
      [ErrRate][eE][+-][ErrRateBase] where ErrRate and ErrRateBase
      are integers. In Other Words 
      ErrRate * [10^ -ErrRateBase]
      shown below are example of the values returned.
            123456E-5 = 1.23456
            344567e-6 = 0.344567"
::= { ifLoopbackTestEntry 6 }

loopbackTestResultsErrSecs OBJECT-TYPE
  SYNTAX        INTEGER
  ACCESS        read-only
  STATUS        mandatory
  DESCRIPTION
    "This object corresponds to the number of errored seconds"
::= { ifLoopbackTestEntry 7 }

loopbackTestResultsSvrErrSecs OBJECT-TYPE
  SYNTAX        INTEGER
  ACCESS        read-only
  STATUS        mandatory
  DESCRIPTION
    "This object corresponds to the number of severely errored seconds"
::= { ifLoopbackTestEntry 8 }

loopbackTestResultsElpTime OBJECT-TYPE
  SYNTAX        INTEGER
  ACCESS        read-only
  STATUS        mandatory
  DESCRIPTION
    "This object corresponds to the number of seconds elapsed since the
     start of the test."
::= { ifLoopbackTestEntry 9 }

-- The BERT group

ifBERTObjectsTable OBJECT-TYPE
    SYNTAX  SEQUENCE OF IfBERTObjectsEntry
    ACCESS  not-accessible
    STATUS  mandatory
    DESCRIPTION
    "This table contains the objects for Bit Error Rate Test. This table
     is indexed by ifIndex."
::= { diagIfTest 2 }

ifBERTObjectsEntry  OBJECT-TYPE
    SYNTAX  IfBERTObjectsEntry
    ACCESS  not-accessible
    STATUS  mandatory
    DESCRIPTION
    "An Entry containing objects of BERT."
    INDEX   { ifIndex }
::= { ifBERTObjectsTable 1 }

IfBERTObjectsEntry ::=
    SEQUENCE {
        ifBERTTestDuration          INTEGER,
        ifBERTElapsedTime           INTEGER,
        ifBERTDownSyncUP            INTEGER,
        ifBERTUpSyncUP              INTEGER,
        ifBERTSegmentsSent          INTEGER,
        ifBERTDownMBitsRcvd         INTEGER,
        ifBERTUpMBitsRcvd           INTEGER,
        ifBERTDownBitErrDetected    INTEGER,
        ifBERTUpBitErrDetected      INTEGER,
        ifBERTDownBitErrRate        DisplayString,
        ifBERTUpBitErrRate          DisplayString,
        ifBERTDownErroredSecs       INTEGER,
        ifBERTUpErroredSecs         INTEGER,
        ifBERTDownLineRate          INTEGER,
        ifBERTUpLineRate            INTEGER,
        ifBERTDownMargin            INTEGER,
        ifBERTUpMargin              INTEGER
    }

ifBERTTestDuration  OBJECT-TYPE
SYNTAX              INTEGER
ACCESS              read-write
STATUS              mandatory
DESCRIPTION
   "This object represents the test duration in seconds."
::= {ifBERTObjectsEntry 1}

ifBERTElapsedTime       OBJECT-TYPE
SYNTAX              INTEGER
ACCESS              read-only
STATUS              mandatory
DESCRIPTION
   "This object represents the elapsed time in seconds."
::= {ifBERTObjectsEntry 2}

ifBERTDownSyncUP    OBJECT-TYPE
SYNTAX              INTEGER {
                        yes (1),
                        no (2)
                            }
ACCESS              read-only
STATUS              mandatory
DESCRIPTION
	"This object indicates whether Downstream sync is enabled ."
::= {ifBERTObjectsEntry 3}

ifBERTUpSyncUP      OBJECT-TYPE
SYNTAX              INTEGER {
                        yes (1),
                        no (2)
                            }
ACCESS              read-only
STATUS              mandatory
DESCRIPTION
	"This object indicates whether upstream sync is enabled."
::= {ifBERTObjectsEntry 4}

ifBERTSegmentsSent  OBJECT-TYPE
SYNTAX              INTEGER
ACCESS              read-only
STATUS              mandatory
DESCRIPTION
	"This object represents the number of segments sent during the test"
::= {ifBERTObjectsEntry 5}

ifBERTDownMBitsRcvd OBJECT-TYPE
SYNTAX              INTEGER
ACCESS              read-only
STATUS              mandatory
DESCRIPTION
	"This represents the number of million bits rcvd downstream."
::= {ifBERTObjectsEntry 6}

ifBERTUpMBitsRcvd   OBJECT-TYPE
SYNTAX              INTEGER
ACCESS              read-only
STATUS              mandatory
DESCRIPTION
	"This represents the number of million bits rcvd upstream."
::= {ifBERTObjectsEntry 7}

ifBERTDownBitErrDetected    OBJECT-TYPE
SYNTAX                      INTEGER
ACCESS                      read-only
STATUS                      mandatory
DESCRIPTION
	"This represents the number of bit errors detected downstream."
::= {ifBERTObjectsEntry 8}

ifBERTUpBitErrDetected      OBJECT-TYPE
SYNTAX                      INTEGER
ACCESS                      read-only
STATUS                      mandatory
DESCRIPTION
	"This represents the number of bit errors detected upstream."
::= {ifBERTObjectsEntry 9}

ifBERTDownBitErrRate    OBJECT-TYPE
SYNTAX                  DisplayString (SIZE (1..32))
ACCESS                  read-only
STATUS                  mandatory
DESCRIPTION
	  "This string will represent a floating point number of the 
               form [Er rRate] [eE] [+-] [ErrRatebase] where ErrTare and
               errRateBase are integers."
::= {ifBERTObjectsEntry 10}

ifBERTUpBitErrRate  OBJECT-TYPE
SYNTAX              DisplayString (SIZE (1..32))
ACCESS              read-only
STATUS              mandatory
DESCRIPTION
	  "This object reflects the error rate of BERT in Upstream direction. 
               This string will represent a floating point number of the form
               [ErrRate] [eE] [+-] [ErrRatebase]
               where ErrTare and errRateBase are integers."
::= {ifBERTObjectsEntry 11}

ifBERTDownErroredSecs   OBJECT-TYPE
SYNTAX                  INTEGER
ACCESS                  read-only
STATUS                  mandatory
DESCRIPTION
	"This represents number of errored seconds downstream. Errored second 
             is a second in which there is at least 1 block error."
::= {ifBERTObjectsEntry 12}


ifBERTUpErroredSecs OBJECT-TYPE
SYNTAX              INTEGER
ACCESS              read-only
STATUS              mandatory
DESCRIPTION
	"This represents number of errored seconds upstream. 
             Errored second is a second in which there is at least 1 block error."
::= {ifBERTObjectsEntry 13}

ifBERTDownLineRate  OBJECT-TYPE
SYNTAX              INTEGER
ACCESS              read-only
STATUS              mandatory
DESCRIPTION
	"This represents the downstream line rate in KBPS"
::= {ifBERTObjectsEntry 14}

ifBERTUpLineRate    OBJECT-TYPE
SYNTAX              INTEGER
ACCESS              read-only
STATUS              mandatory
DESCRIPTION
	"This represents the Upstream line rate in KBPS"
::= {ifBERTObjectsEntry 15}

ifBERTDownMargin    OBJECT-TYPE
SYNTAX              INTEGER
ACCESS              read-only
STATUS              mandatory
DESCRIPTION
	"This represents the Downstream margin in decibels (DB)."
::= {ifBERTObjectsEntry 16}

ifBERTUpMargin  OBJECT-TYPE
SYNTAX          INTEGER
ACCESS          read-only
STATUS          mandatory
DESCRIPTION
	"This represents the upstream margin in decibels (DB)."
::= {ifBERTObjectsEntry 17}

-- The BLERT group

ifBLERTObjectsTable OBJECT-TYPE
    SYNTAX  SEQUENCE OF IfBLERTObjectsEntry
    ACCESS  not-accessible
    STATUS  mandatory
    DESCRIPTION
    "This table contains the objects for Block Error Rate Test (BLERT).
     This table is indexed by ifIndex."
::= { diagIfTest 3 }

ifBLERTObjectsEntry  OBJECT-TYPE
    SYNTAX  IfBLERTObjectsEntry
    ACCESS  not-accessible
    STATUS  mandatory
    DESCRIPTION
    "An Entry containing objects of BLERT."
    INDEX   { ifIndex }
::= { ifBLERTObjectsTable 1 }

IfBLERTObjectsEntry ::=
    SEQUENCE {
        ifBLERTTestDuration          INTEGER,
        ifBLERTElapsedTime           INTEGER,
        ifBLERTTxSeqCount            INTEGER,
        ifBLERTRxSeqCount            INTEGER,
        ifBLERTRxGoodFrames          INTEGER,
        ifBLERTTxGoodFrames          INTEGER,
        ifBLERTRxBadFrames	     INTEGER,
        ifBLERTTxBadFrames           INTEGER,
        ifBLERTDnLineRate            INTEGER,
        ifBLERTUpLineRate            INTEGER
    }

ifBLERTTestDuration  OBJECT-TYPE
SYNTAX              INTEGER
ACCESS              read-write
STATUS              mandatory
DESCRIPTION
   "This object represents the test duration in seconds."
::= {ifBLERTObjectsEntry 1}

ifBLERTElapsedTime       OBJECT-TYPE
SYNTAX              INTEGER
ACCESS              read-only
STATUS              mandatory
DESCRIPTION
   "This object represents the elapsed time in seconds since the test started."
::= {ifBLERTObjectsEntry 2}

ifBLERTTxSeqCount    OBJECT-TYPE
SYNTAX              INTEGER
ACCESS              read-only
STATUS              mandatory
DESCRIPTION
   "This object indicates the next Tx sequence."
::= {ifBLERTObjectsEntry 3}

ifBLERTRxSeqCount    OBJECT-TYPE
SYNTAX              INTEGER
ACCESS              read-only
STATUS              mandatory
DESCRIPTION
   "This object indicates the next Rx sequence."
::= {ifBLERTObjectsEntry 4}

ifBLERTRxGoodFrames  OBJECT-TYPE
SYNTAX              INTEGER
ACCESS              read-only
STATUS              mandatory
DESCRIPTION
   "This object indicates the number of good frames received."
::= {ifBLERTObjectsEntry 5}

ifBLERTTxGoodFrames  OBJECT-TYPE
SYNTAX              INTEGER
ACCESS              read-only
STATUS              mandatory
DESCRIPTION
   "This object indicates the number of good frames transmitted."
::= {ifBLERTObjectsEntry 6}

ifBLERTRxBadFrames  OBJECT-TYPE
SYNTAX              INTEGER
ACCESS              read-only
STATUS              mandatory
DESCRIPTION
   "This object indicates the number of bad frames received."
::= {ifBLERTObjectsEntry 7}

ifBLERTTxBadFrames  OBJECT-TYPE
SYNTAX      	    INTEGER
ACCESS              read-only
STATUS              mandatory
DESCRIPTION
   "This object indicates the number of bad frames transmitted."
::= {ifBLERTObjectsEntry 8}

ifBLERTDnLineRate   OBJECT-TYPE
SYNTAX              INTEGER
ACCESS              read-only
STATUS              mandatory
DESCRIPTION
   "This object indicates the downstream line rate."
::= {ifBLERTObjectsEntry 9}

ifBLERTUpLineRate   OBJECT-TYPE
SYNTAX      	    INTEGER
ACCESS              read-only
STATUS              mandatory
DESCRIPTION
   "This object indicates the upstream line rate."
::= {ifBLERTObjectsEntry 10}

-- The applTests group. Implementation of all objects in this group is
-- is mandatory

applMaxNumberOfTests OBJECT-TYPE
  SYNTAX        INTEGER
  ACCESS        read-only
  STATUS        mandatory
  DESCRIPTION
    "This object identifies the maximum number of application based
     tests that can be simultaneously instantiated on the device."
::= { diagApplTest 1 }

applCurrentNumberOfTests OBJECT-TYPE
  SYNTAX        INTEGER
  ACCESS        read-only
  STATUS        mandatory
  DESCRIPTION
    "This object identifies the current number of application based
     tests that are running on the device."
::= { diagApplTest 2 }

applStopAllTests  OBJECT-TYPE
  SYNTAX INTEGER {
    noOp (1),
    stop (2),
    stopAndClear (3)
  }
  ACCESS       read-write
  STATUS       mandatory
  DESCRIPTION
    "The value of this object corresponds to stop all
     application based tests on the device.
     noOp -- no operation
     stop -- all the application tests will be stopped
             but current test results are still available
     stopAndClear -- all the application tests will be stoped
             and the results are cleared also"
::= { diagApplTest 3 }

applNewTestId OBJECT-TYPE
  SYNTAX        INTEGER
  ACCESS        read-only
  STATUS        mandatory
  DESCRIPTION
    "This value of this object corresponds to getting a
     magic number to start an application based test.
     The magic number is used as an index to create a
     row for the diagApplTestTable.  If no new rows
     can be created, this object will have a value of 0."
::= { diagApplTest 4 }

-- applTestStatusTable: This table controls all the application tests

applTestStatusTable OBJECT-TYPE
  SYNTAX       SEQUENCE OF ApplTestStatusEntry
  ACCESS       not-accessible
  STATUS       mandatory
  DESCRIPTION
    "This table controls all the application tests.  It defines a test type,
     starts a test, and clears a test."
::= { diagApplTest 5 }

applTestStatusEntry OBJECT-TYPE
  SYNTAX       ApplTestStatusEntry
  ACCESS       not-accessible
  STATUS       mandatory
  DESCRIPTION
    "An entry containing objects for invoking application based tests"
  INDEX { applTestId }
::= { applTestStatusTable 1 }

ApplTestStatusEntry ::=
  SEQUENCE {
    applTestId                 INTEGER,
    applTestType               AutonomousType,
    applTestStatus             INTEGER,
    applTestErrorCode          INTEGER,
    applTestOwner              DisplayString,
    applTestRowStatus          RowStatus
  }

applTestId OBJECT-TYPE
  SYNTAX        INTEGER
  ACCESS        read-only
  STATUS        mandatory
  DESCRIPTION
    "A unique ID to identify each application test."
::= { applTestStatusEntry 1 }

applTestType OBJECT-TYPE
  SYNTAX        AutonomousType
  ACCESS        read-write
  STATUS        mandatory
  DESCRIPTION
    "This object defines the application test type."
::= { applTestStatusEntry 2 }

applTestStatus OBJECT-TYPE
  SYNTAX        INTEGER {
    none (1),
    inProgress (2),
    success (3),
    failed (4),
	 abort (5)
    }
  ACCESS        read-only
  STATUS        mandatory
  DESCRIPTION
    "This object shows the current status of an application test.
       none        - indicates waiting for test parameters.
       inProgress  - indicates the test is in process.
       success     - indicates the test is completed.
       failed      - indicates the test is failed.
		 abort       - indicates the test was aborted"
::= { applTestStatusEntry 3 }

applTestErrorCode OBJECT-TYPE
  SYNTAX        INTEGER { none (1), timeout (2), icmpError (3), systemError (4) }
  ACCESS        read-only
  STATUS        mandatory
  DESCRIPTION
    "This object shows the reason for a test failure."
::= { applTestStatusEntry 4 }

applTestOwner OBJECT-TYPE
  SYNTAX        DisplayString (SIZE (1..40))
  ACCESS        read-write
  STATUS        mandatory
  DESCRIPTION
    "The network manager who has started the test"
::= { applTestStatusEntry 5 }

applTestRowStatus OBJECT-TYPE
  SYNTAX        RowStatus
  ACCESS        read-write
  STATUS        mandatory
  DESCRIPTION
    "This object is used to create a new row or delete an
     existing row for an application test."
::= { applTestStatusEntry 6 }

-- applPintTestTable: This table is for Ping test

applPingTestTable OBJECT-TYPE
  SYNTAX        SEQUENCE OF ApplPingTestEntry
  ACCESS        not-accessible
  STATUS        mandatory
  DESCRIPTION
    "This table contains objects which allow network manager to
     ping a destination."
::= { diagApplTest 6 }

applPingTestEntry OBJECT-TYPE
  SYNTAX        ApplPingTestEntry
  ACCESS        not-accessible
  STATUS        mandatory
  DESCRIPTION
    "This table contains the input parameters for a ping test
     and the results of the ping test."
  INDEX { applPingTestId }
::= { applPingTestTable 1}

ApplPingTestEntry ::=
  SEQUENCE {
    applPingTestId              INTEGER,
    applPingTestIpAddress       IpAddress,
    applPingTestSourceIpAddr    IpAddress,
    applPingTestPacketSize      INTEGER,
    applPingTestTimeout         INTEGER,
    applPingTestMaxPings        INTEGER,
    applPingTestPktsSent        INTEGER,
    applPingTestPktsRecv        INTEGER,
    applPingTestMinTime         INTEGER,
    applPingTestMaxTime         INTEGER,
    applPingTestAvgTime         INTEGER,
    applPingTestDomain          INTEGER,
    applPingTestIfIndex         INTEGER
}

applPingTestId OBJECT-TYPE
  SYNTAX    INTEGER
  ACCESS    read-only
  STATUS    mandatory
  DESCRIPTION
    "A unique ID to identify each application test."
::= { applPingTestEntry 1 }

applPingTestIpAddress OBJECT-TYPE
  SYNTAX        IpAddress
  ACCESS        read-write
  STATUS        mandatory
  DESCRIPTION
    "The IP address to be pinged."
::= { applPingTestEntry 2 }

applPingTestSourceIpAddr OBJECT-TYPE
  SYNTAX        IpAddress
  ACCESS        read-write
  STATUS        mandatory
  DESCRIPTION
    "The Source IP address where we are pinging from.
     This is an optional object for some devices.
     See operational specification for its use."
::= { applPingTestEntry 3 }

applPingTestPacketSize OBJECT-TYPE
  SYNTAX        INTEGER
  ACCESS        read-write
  STATUS        mandatory
  DESCRIPTION
    "This object corresponds to the size of the packet (in bytes)
     which will be sent during the Ping test.
     The default value for this object is 64 bytes"
::= { applPingTestEntry 4 }

applPingTestTimeout OBJECT-TYPE
  SYNTAX        INTEGER
  ACCESS        read-write
  STATUS        mandatory
  DESCRIPTION
    "This object corresponds to a timeout value (in seconds)
     between Pings.
     The default value for this object is 5 seconds"
::= { applPingTestEntry 5 }

applPingTestMaxPings OBJECT-TYPE
  SYNTAX        INTEGER
  ACCESS        read-write
  STATUS        mandatory
  DESCRIPTION
    "This object corresponds to  the maximum number of times the
     device should Ping for the destination.
     The default value for this object is 10"
::= { applPingTestEntry 6 }

applPingTestPktsSent OBJECT-TYPE
  SYNTAX        INTEGER
  ACCESS        read-only
  STATUS        mandatory
  DESCRIPTION
    "This object corresponds to  the total number of packets sent."
::= { applPingTestEntry 7 }

applPingTestPktsRecv OBJECT-TYPE
  SYNTAX        INTEGER
  ACCESS        read-only
  STATUS        mandatory
  DESCRIPTION
    "This object corresponds to  the total number of packets received
     without error"
::= { applPingTestEntry 8 }

applPingTestMinTime OBJECT-TYPE
  SYNTAX        INTEGER
  ACCESS        read-only
  STATUS        mandatory
  DESCRIPTION
    "The minimum round trip time."
::= { applPingTestEntry 9 }

applPingTestMaxTime OBJECT-TYPE
  SYNTAX        INTEGER
  ACCESS        read-only
  STATUS        mandatory
  DESCRIPTION
    "The maximum round trip time."
::= { applPingTestEntry 10 }

applPingTestAvgTime OBJECT-TYPE
  SYNTAX        INTEGER
  ACCESS        read-only
  STATUS        mandatory
  DESCRIPTION
    "The average round trip time."
::= { applPingTestEntry 11 }

applPingTestDomain    OBJECT-TYPE
  SYNTAX        INTEGER { 
	 noop (1),
    mgmt (2),
    service (3)
    }
  ACCESS        read-write
  STATUS        mandatory
  DESCRIPTION
    "This object specifies the destination ip address's domain.
     The Default is service domain. Not allowed if source ip address is entered.
     This is an optional object for some devices. See operational specification
     its use."
::= { applPingTestEntry 12 }

applPingTestIfIndex  OBJECT-TYPE
  SYNTAX        INTEGER
  ACCESS        read-write
  STATUS        mandatory
  DESCRIPTION
    "This object specifies the interface over which the ping test will
	  take place. "
::= { applPingTestEntry 13 }

-- applTracerouteConfigTable: to enter the parameters for a traceroute test

applTracerouteConfigTable OBJECT-TYPE
  SYNTAX        SEQUENCE OF ApplTracerouteConfigEntry
  ACCESS        not-accessible
  STATUS        mandatory
  DESCRIPTION
    "This table contains objects which allow network manager to
     enter the parameters of a traceroute test."
::= { diagApplTest 7 }

applTracerouteConfigEntry OBJECT-TYPE
  SYNTAX        ApplTracerouteConfigEntry
  ACCESS        not-accessible
  STATUS        mandatory
  DESCRIPTION
    "This table contains the input parameters for a traceroute test."
  INDEX { applTracerouteTestId }
::= { applTracerouteConfigTable 1}

ApplTracerouteConfigEntry ::=
  SEQUENCE {
    applTracerouteTestId        INTEGER,
    applTracerouteIpAddress     IpAddress,
    applTracerouteSourceIpAddr  IpAddress,
    applTraceroutePktsSize      INTEGER,
    applTracerouteTimeout       INTEGER,
    applTracerouteMaxHops       INTEGER,
    applTracerouteDomain        INTEGER,
    applTracerouteIfIndex       INTEGER
}

applTracerouteTestId OBJECT-TYPE
  SYNTAX        INTEGER
  ACCESS        read-only
  STATUS        mandatory
  DESCRIPTION
    "A unique ID to identify each application test."
::= { applTracerouteConfigEntry 1 }

applTracerouteIpAddress OBJECT-TYPE
  SYNTAX        IpAddress
  ACCESS        read-write
  STATUS        mandatory
  DESCRIPTION
    "The destination IP address of a traceroute test."
::= { applTracerouteConfigEntry 2 }

applTracerouteSourceIpAddr OBJECT-TYPE
  SYNTAX        IpAddress
  ACCESS        read-write
  STATUS        mandatory
  DESCRIPTION
    "The source IP address of where the traceroute test started.
     This is an optional object for some devices.
     See operational specification for its use."
::= { applTracerouteConfigEntry 3 }

applTraceroutePktsSize OBJECT-TYPE
  SYNTAX        INTEGER
  ACCESS        read-write
  STATUS        mandatory
  DESCRIPTION
    "This object corresponds to the size of the packet (in bytes)
     which will be sent during the traceroute test. 
     Please refer to product specific documentation for the 
     default values supported"
::= { applTracerouteConfigEntry 4 }

applTracerouteTimeout OBJECT-TYPE
  SYNTAX        INTEGER
  ACCESS        read-write
  STATUS        mandatory
  DESCRIPTION
    "This object corresponds to a timeout value (in seconds)
     of a traceroute test.
     The default value for this object is 5 seconds"
::= { applTracerouteConfigEntry 5 }

applTracerouteMaxHops OBJECT-TYPE
  SYNTAX        INTEGER
  ACCESS        read-write
  STATUS        mandatory
  DESCRIPTION
    "This object corresponds to the maximum number of hops
     to reach the destination.
     The default value for this object is device specific. See
	  Operational Specifications"
::= { applTracerouteConfigEntry 6 }

applTracerouteDomain    OBJECT-TYPE
  SYNTAX        INTEGER {
    noop (1),
    mgmt (2),
    service (3)
    }
  ACCESS        read-write
  STATUS        mandatory
  DESCRIPTION
    "This object specifies the destination ip address's domain.
     The Default is service domain. Not allowed if source ip address is entered.
     This is an optional object for some devices. See operational specification
     its use."
::= { applTracerouteConfigEntry 7 }

applTracerouteIfIndex  OBJECT-TYPE
  SYNTAX        INTEGER
  ACCESS        read-write
  STATUS        mandatory
  DESCRIPTION
    "This object specifies the interface over which the trace-route
	  test will take place. " 
::= { applTracerouteConfigEntry 8 }

-- Traceroute Results Table

applTracerouteResultTable OBJECT-TYPE
  SYNTAX        SEQUENCE OF ApplTracerouteResultEntry
  ACCESS        not-accessible
  STATUS        mandatory
  DESCRIPTION
    "This table contains results of traceroute test."
::= { diagApplTest 8 }

applTracerouteResultEntry OBJECT-TYPE
  SYNTAX        ApplTracerouteResultEntry
  ACCESS        not-accessible
  STATUS        mandatory
  DESCRIPTION
    "An entry contains the objects for the traceroute test."
  INDEX { applTracerouteResultTestId, applTracerouteHopCount }
::= { applTracerouteResultTable 1 }

ApplTracerouteResultEntry ::=
  SEQUENCE {
    applTracerouteResultTestId  INTEGER,
    applTracerouteHopCount      INTEGER,
    applTracerouteIpAddr        IpAddress,
    applTraceroutePktSize       INTEGER,
    applTracerouteProbe1RTT     INTEGER,
    applTracerouteProbe2RTT     INTEGER,
    applTracerouteProbe3RTT     INTEGER
  }

applTracerouteResultTestId OBJECT-TYPE
  SYNTAX        INTEGER
  ACCESS        read-only
  STATUS        mandatory
  DESCRIPTION
    "A unique ID to identify each application test."
::= { applTracerouteResultEntry 1 }

applTracerouteHopCount OBJECT-TYPE
  SYNTAX        INTEGER
  ACCESS        read-only
  STATUS        mandatory
  DESCRIPTION
    "This object contains the number of hops to reach the gateway."
::= { applTracerouteResultEntry 2 }

applTracerouteIpAddr OBJECT-TYPE
  SYNTAX        IpAddress
  ACCESS        read-only
  STATUS        mandatory
  DESCRIPTION
    "This object contains the IP address of the gateway."
::= { applTracerouteResultEntry 3 }

applTraceroutePktSize OBJECT-TYPE
  SYNTAX        INTEGER
  ACCESS        read-only
  STATUS        mandatory
  DESCRIPTION
    "This object corresponds to the size of the packet (in bytes)
     which will be sent during the traceroute test.
     Please refer to product specific documentation for the 
     default values supported"
::= { applTracerouteResultEntry 4 }

applTracerouteProbe1RTT OBJECT-TYPE
  SYNTAX        INTEGER
  ACCESS        read-only
  STATUS        mandatory
  DESCRIPTION
    "This object contains the round trip time (rtt) of the first
     probe sent to the gateway.
     If the probe has a timeout the rtt is set to -1."
::= { applTracerouteResultEntry 5 }

applTracerouteProbe2RTT OBJECT-TYPE
  SYNTAX        INTEGER
  ACCESS        read-only
  STATUS        mandatory
  DESCRIPTION
    "This object contains the round trip time (rtt) of the second
     probe sent to the gateway.
     If the probe has a timeout the rtt is set to -1."
::= { applTracerouteResultEntry 6 }

applTracerouteProbe3RTT OBJECT-TYPE
  SYNTAX        INTEGER
  ACCESS        read-only
  STATUS        mandatory
  DESCRIPTION
    "This object contains the round trip time (rtt) of the third
     probe sent to the gateway.
     If the probe has a timeout the rtt is set to -1."
::= { applTracerouteResultEntry 7 }

diagTestTrapEnable OBJECT-TYPE
  SYNTAX  INTEGER
  ACCESS  read-write
  STATUS  mandatory
  DESCRIPTION
    "This object is used to disable or enable TestOver
     and TestStart trap for all tests. It is bit sum and possible
     bit positions are 1 TestStart trap 2 TestOver trap"
::= { diagTest 1 }

-- Traps

diagApplTestStart TRAP-TYPE
  ENTERPRISE diagTestMIBTraps
  VARIABLES { ifIndex, applTestId, applTestType }
  DESCRIPTION
    "This trap signifies that an application test has been initiated."
::= 1

diagApplTestStop TRAP-TYPE
  ENTERPRISE diagTestMIBTraps
  VARIABLES { ifIndex, applTestId, applTestType, applTestStatus }
  DESCRIPTION
    "This trap signifies that an application test has completed.
     This trap compliments the diagApplTestStart trap."
::= 101 

diagIfTestStart TRAP-TYPE
  ENTERPRISE diagTestMIBTraps
  VARIABLES { ifTestId }
  DESCRIPTION
    "This trap signifies that a diagnostic test has been initiated."
::= 2

diagIfTestOver TRAP-TYPE
  ENTERPRISE diagTestMIBTraps
  VARIABLES { ifTestId }
  DESCRIPTION
    "This trap signifies that a diagnostic test has completed.
     This trap compliments the diagIfTestStart trap"
::= 102
 
END

PDN-DSLAM-SYSTEM-MIB DEFINITIONS ::= BEGIN

-- Version :  1.1 APPROVED
-- Enterprise pdn DSLAM mib
-- Copyright (C) 2002 Paradyne Corporation.

 
 IMPORTS
 TAddress,
 RowStatus,DisplayString
 FROM SNMPv2-TC
 IdslClockMode, SwitchState
 FROM PDN-TC
 Counter32,IpAddress,TimeTicks,
 Integer32, OBJECT-TYPE, NOTIFICATION-TYPE,
 MODULE-IDENTITY
 FROM SNMPv2-SMI
 OBJECT-GROUP, NOTIFICATION-GROUP
 FROM SNMPv2-CONF
 ifIndex, sysObjectID
 FROM RFC1213-MIB
 entPhysicalIndex
 FROM ENTITY-MIB
 pdn-common
 FROM PDN-HEADER-MIB 
 ;


pdn-dslam MODULE-IDENTITY

   LAST-UPDATED    "0206050000Z"
   ORGANIZATION    "Paradyne Corporation
		    MIB Working Group"

   CONTACT-INFO    "Paradyne Corporation
		    8545 126th Avenue North
		    Largo, FL 33733
		    www.paradyne.com

		    General Comments to: mibwg_team@paradyne.com

		    Editors
		    Prakash Easwar
		    Jesus Pinto
		    Dragana Gough"

   DESCRIPTION
    	"The DSLAM MIB. This MIB is specific to portcards and
 	DSLAM configuration/stats for MCC and the portcards.
 	The objects defined in this mib are specific to some
 	products and donot apply to all paradyne devices."

   REVISION "0206200000Z"
   DESCRIPTION "J. Pinto
    o Added IMPLIED modifier to the INDEX clause in:
	entCommunityTableEntry and sysDevUserAccountEntry.
   "

   REVISION "0206050000Z"
   DESCRIPTION "J. Pinto
    o Changed  sysDevUserAccountUserPassword to read-create
    o Expanded sysDevUserAccountPrivilege options
   "

   REVISION "0202220000Z"
   DESCRIPTION "Initial Release"


   ::= { pdn-common 24 }

sysDevDslamMIBObjects OBJECT IDENTIFIER ::= { pdn-dslam 1 }
sysDevDslamMIBTraps   OBJECT IDENTIFIER ::= { pdn-dslam 2 }


sysDevStats 				OBJECT IDENTIFIER ::= { sysDevDslamMIBObjects 1 }
sysDevConfig				OBJECT IDENTIFIER ::= { sysDevDslamMIBObjects 2 }

-- The statistics group. The implementation of this group
-- is mandatory.
 
 loginHistTable OBJECT-TYPE
   SYNTAX SEQUENCE OF LoginHistTableEntry
   MAX-ACCESS  not-accessible
   STATUS current
   DESCRIPTION
     "This table shows the most recent 10 logins and all active users 
	  currently accessing the device. It is indexed by userId
	  and loginTime."
 ::= { sysDevStats 1 }

 loginHistTableEntry OBJECT-TYPE
   SYNTAX  LoginHistTableEntry
   MAX-ACCESS  not-accessible
   STATUS  current
   DESCRIPTION
   		"This object corresponds to an entry in the login history table."
   INDEX { loginUserId, loginTime }
 ::= { loginHistTable 1 }

 LoginHistTableEntry ::=
   SEQUENCE {
   loginUserId 		DisplayString,
   loginTime 	TimeTicks,
   loginAccessApp 	INTEGER,
   loginAccessHost	IpAddress,
   loginUserPriv	 	INTEGER,
   loginStatus 	INTEGER
   }
 
 loginUserId OBJECT-TYPE
   SYNTAX DisplayString
   MAX-ACCESS read-only
   STATUS current
   DESCRIPTION
     "This object containes the user login id."
 ::= { loginHistTableEntry 1 }
 
 loginTime OBJECT-TYPE
   SYNTAX TimeTicks 
   MAX-ACCESS read-only
   STATUS current
   DESCRIPTION
     "This object containes the login time in seconds 
	 when the login session is established."
 ::= { loginHistTableEntry 2 }

 loginAccessApp OBJECT-TYPE
   SYNTAX INTEGER {
	console (1),
	telnet (2),
	ftp (3),
	web (4),
	modem (5)
   }
   MAX-ACCESS read-only
   STATUS current
   DESCRIPTION
     "This object describes the access application used 
	 by the end user to access the device. This can be 
	 done through console, using telnet, modem, web, or using ftp."
 ::= { loginHistTableEntry 3 }

 loginAccessHost OBJECT-TYPE
   SYNTAX IpAddress
   MAX-ACCESS read-only
   STATUS current
   DESCRIPTION
     "This object containes the ip address of the network
	 management station when the access application is
	 telnet or ftp. In case of console, this object contains
	 0.0.0.0."
 ::= { loginHistTableEntry 4 }

 loginUserPriv OBJECT-TYPE
   SYNTAX INTEGER {
	administrator (1),
	operator (2)
   }
   MAX-ACCESS read-only
   STATUS current
   DESCRIPTION
     "This object containes the access privileges of the user."
 ::= { loginHistTableEntry 5 }

 loginStatus OBJECT-TYPE
   SYNTAX INTEGER {
	active (1),
	inactive (2)
   }
   MAX-ACCESS read-only
   STATUS current
   DESCRIPTION
     "This object indicates whether the user is still accessing the
	 device."
 ::= { loginHistTableEntry 6 }

 loginFailureCountTable OBJECT-TYPE
   SYNTAX SEQUENCE OF LoginFailureCountTableEntry
   MAX-ACCESS  not-accessible
   STATUS current
   DESCRIPTION
     "This table containes the statistics for login failures. It
	  is indexed by access type i.e console, telnet or ftp."
 ::= { sysDevStats 2 }

 loginFailureCountTableEntry OBJECT-TYPE
   SYNTAX  LoginFailureCountTableEntry
   MAX-ACCESS  not-accessible
   STATUS  current
   DESCRIPTION
   "This object corresponds to an entry in the login failure count table."
   INDEX {loginFailureAccessApp}
 ::= { loginFailureCountTable 1 }

 LoginFailureCountTableEntry ::=
   SEQUENCE {
   loginFailureAccessApp INTEGER,
   loginFailureCount Counter32
   }

 loginFailureAccessApp OBJECT-TYPE
   SYNTAX INTEGER {
	console (1),
	telnet (2),
	ftp (3)
   }
   MAX-ACCESS read-only
   STATUS current
   DESCRIPTION
     "This object describes the access application used 
	 by the end user to access the device. This can be 
	 done through console, using telnet or using ftp."
 ::= { loginFailureCountTableEntry 1 }

 loginFailureCount OBJECT-TYPE
   SYNTAX Counter32
   MAX-ACCESS read-only
   STATUS current
   DESCRIPTION
     "This object containes the number of unsuccesful logins for console,
	 ftp or telnet."
 ::= { loginFailureCountTableEntry 2 }

 -- The configuration group. The implementation of this group
 -- is optional.

 enablePowerSourceFailureAlarm OBJECT-TYPE
   SYNTAX INTEGER {
     disable (1),
     enable (2)
   }
   MAX-ACCESS read-write
   STATUS current
   DESCRIPTION
     "This objects corresponds to enabling/disabling the 
      power source failure alarm - for both A and B power sources
      This object is for the MCC only.
      The default value of this object should be 1."
    ::= {sysDevConfig 1 }

 devIfTable OBJECT-TYPE
   SYNTAX SEQUENCE OF DevIfTableEntry
   MAX-ACCESS  not-accessible
   STATUS current
   DESCRIPTION
       "This table is used to configure information  for a
    particular interface"
    ::= {sysDevConfig 2 }

devIfTableEntry OBJECT-TYPE
    SYNTAX  DevIfTableEntry
    MAX-ACCESS  not-accessible
    STATUS  current
    DESCRIPTION
      "This object corresponds to an entry in the DevifTable "
    INDEX { ifIndex }
    ::= { devIfTable 1 }
 
DevIfTableEntry ::=
    SEQUENCE {
      devPacketDiscardPolicy INTEGER,
      devLinkIntegrity        INTEGER
      }
devPacketDiscardPolicy OBJECT-TYPE
    SYNTAX INTEGER {
	 noOp (1),
     mrrp (2),
     lrrp (3)
   }
   MAX-ACCESS read-create
   STATUS current
   DESCRIPTION
     "This object corresponds to the policy for packet discards
      during periods of congestion :
      mrrp - most recently received packets are discarded.
      lrrp - least recently received packets are discarded.
      The default value of this object should be 2"
    ::= { devIfTableEntry 1 }

devLinkIntegrity OBJECT-TYPE
     SYNTAX INTEGER {
     enable (1),
     disable (2),
     none (3)
       }
     MAX-ACCESS read-create
     STATUS current
     DESCRIPTION
         "This object corresponds to the enabling or disabling of
          the ethernet link integrity :
           enable - enable link integrity
           disable - disable link integrity
           none - for interfaces that do not support link integrity
           The default value of this object should be 1"
    ::= { devIfTableEntry 2 }

communityTrapAddressInfoTable OBJECT-TYPE
      SYNTAX SEQUENCE OF CommunityTrapAddressInfoTableEntry
      MAX-ACCESS  not-accessible
      STATUS current
      DESCRIPTION
        "This table is used to set the trap destination address
         for a particular community."
    ::= {sysDevConfig 3 }
 
communityTrapAddressInfoTableEntry OBJECT-TYPE
   SYNTAX  CommunityTrapAddressInfoTableEntry
   MAX-ACCESS  not-accessible
   STATUS current
   DESCRIPTION
     "This object corresponds to an entry in the community
      trap address info table."
   INDEX { trapCommunityName, trapDestAndPort}
 ::= { communityTrapAddressInfoTable 1 }
 
CommunityTrapAddressInfoTableEntry ::=
   SEQUENCE {
     trapCommunityName DisplayString,
     trapDestAndPort   TAddress,
     trapsEnable       INTEGER,
     trapRowStatus     RowStatus
 }
 
trapCommunityName OBJECT-TYPE
   SYNTAX  DisplayString (SIZE(1..32))
   MAX-ACCESS not-accessible
   STATUS current
   DESCRIPTION
     "This object corresponds to the name of the SNMP Community."
   ::= { communityTrapAddressInfoTableEntry 1 }
    
trapDestAndPort OBJECT-TYPE
   SYNTAX TAddress
   MAX-ACCESS not-accessible
   STATUS current
   DESCRIPTION
     "The IP Address and Port of the destination to which a trap
      must be sent."
   ::= { communityTrapAddressInfoTableEntry 2 }
 
trapsEnable OBJECT-TYPE
   SYNTAX INTEGER {
     enable (1),
     disable (2)
   }
   MAX-ACCESS read-create
   STATUS current
   DESCRIPTION
     "This object corresponds to turning traps on/off for a
      particular destination.
      enable (1) - traps will be sent to the specified destination.
      disable (2)- traps will not be sent to the specified 
      destination.
      The default value of this object should be 2."
 ::= { communityTrapAddressInfoTableEntry 3 }

trapRowStatus OBJECT-TYPE
   SYNTAX RowStatus 
   MAX-ACCESS read-only
   STATUS current
   DESCRIPTION
     "This object is used to add or delete a
       a row from the table."
   ::= { communityTrapAddressInfoTableEntry 4 }

entCommunityTable OBJECT-TYPE
   SYNTAX SEQUENCE OF EntCommunityTableEntry
   MAX-ACCESS  not-accessible
   STATUS current
   DESCRIPTION
     "This table is used to set the various configuration
      parameters for a particular community."
    ::= { sysDevConfig 4 }

entCommunityTableEntry OBJECT-TYPE
   SYNTAX  EntCommunityTableEntry
   MAX-ACCESS  not-accessible
   STATUS  current
   DESCRIPTION
     "This object corresponds to an entry in the community
      table."
   INDEX { IMPLIED entCommunityName }
   ::= { entCommunityTable 1 }

EntCommunityTableEntry ::=
   SEQUENCE {
     entCommunityName
       DisplayString,
     entCommunityType
       INTEGER,
     entCommunityRowStatus
	    RowStatus
 }
 
entCommunityName OBJECT-TYPE
   SYNTAX  DisplayString (SIZE(1..32))
   MAX-ACCESS not-accessible
   STATUS current
   DESCRIPTION
     "This object corresponds to the name of the SNMP Community"
 ::= { entCommunityTableEntry 1 }

entCommunityType OBJECT-TYPE
   SYNTAX INTEGER {
     readOnly (1),
     readWrite (2)
   }
   MAX-ACCESS read-create
   STATUS current
   DESCRIPTION
     "The type of the community
       readOnly - this community is only allowed to do get's
       readWrite - this community is allowed to do get's and 
                   set's
      The default value of this object should be 1"
 ::= { entCommunityTableEntry 2 }

entCommunityRowStatus OBJECT-TYPE
   SYNTAX RowStatus 
   MAX-ACCESS read-create
   STATUS current
   DESCRIPTION
     "This object is used to add or delete a
       a row from the table."
   ::= { entCommunityTableEntry 3 }


-- MCC-rq 200-210: A new user account group is added into the Hotwire System MIB
 
sysDevUserAccountTable OBJECT-TYPE
    SYNTAX  SEQUENCE OF SysDevUserAccountEntry
    MAX-ACCESS  not-accessible
    STATUS current
    DESCRIPTION
        "This table contains the user accounts."
    ::= { sysDevConfig 5}
 
sysDevUserAccountEntry OBJECT-TYPE
    SYNTAX  SysDevUserAccountEntry
    MAX-ACCESS  not-accessible
    STATUS  current
    DESCRIPTION
        "An entry containing user account information."
    INDEX { IMPLIED sysDevUserAccountUserId }
    ::= { sysDevUserAccountTable 1 }
 
SysDevUserAccountEntry  ::= SEQUENCE {
    sysDevUserAccountUserId   DisplayString,
    sysDevUserAccountPrivilege INTEGER,
    sysDevUserAccountUserPassword DisplayString,
    sysDevUserAccountAccessPartition DisplayString,
    sysDevUserAccountRowStatus RowStatus
	}
 
sysDevUserAccountUserId OBJECT-TYPE
    SYNTAX  DisplayString (SIZE(6..15))
    MAX-ACCESS  not-accessible
    STATUS  current
    DESCRIPTION
        "This object corresponds to the login ID of the
         user account."
    ::= { sysDevUserAccountEntry 1 }
 
sysDevUserAccountPrivilege OBJECT-TYPE
    SYNTAX  INTEGER {
        operator (1),
        administrator (2),
	maintenance (3),
	provisioning (4),
	manufacturing (5)
    }
    MAX-ACCESS  read-create
    STATUS  current
    DESCRIPTION
        "This object corresponds to the access privilege
         of the user account.  1 = Operator, 2 = Administrator,
	 3 = maintenance, 4 = provisioning, 5 = manufacturing."
    ::= { sysDevUserAccountEntry 2 }

sysDevUserAccountUserPassword OBJECT-TYPE
    SYNTAX  DisplayString (SIZE(6..15))
    MAX-ACCESS  read-create
    STATUS  current
    DESCRIPTION
        "This object corresponds to the password of the
         user account."
    ::= { sysDevUserAccountEntry 3 }
 
sysDevUserAccountAccessPartition  OBJECT-TYPE
    SYNTAX  DisplayString (SIZE(0..50))
    MAX-ACCESS  read-create
    STATUS current
    DESCRIPTION
    "This object corresponds to the access partition of the
     user account. The default value of this object is 'all'"
    ::= { sysDevUserAccountEntry 4 }

sysDevUserAccountRowStatus OBJECT-TYPE
	SYNTAX  RowStatus
	MAX-ACCESS  read-create
	STATUS current
	DESCRIPTION
	"This object corresponds to create or delete a row in
	sysDevUserAccountTable."
    ::= {sysDevUserAccountEntry 5 }

-- A new user account config group is added
 
sysDevConfigUserAccountTable OBJECT-TYPE
    SYNTAX  SEQUENCE OF SysDevConfigUserAccountEntry
    MAX-ACCESS  not-accessible
    STATUS current
    DESCRIPTION
        "This table contains the user accounts."
    ::= { sysDevConfig 8}
 
sysDevConfigUserAccountEntry OBJECT-TYPE
    SYNTAX  SysDevConfigUserAccountEntry
    MAX-ACCESS  not-accessible
    STATUS  current
    DESCRIPTION
        "An entry containing user account information."
    INDEX { sysDevConfigUserAccountIndex }
    ::= { sysDevConfigUserAccountTable 1 }
 
SysDevConfigUserAccountEntry  ::= SEQUENCE {
    sysDevConfigUserAccountIndex   Integer32,
    sysDevConfigUserAccountUserId   DisplayString,
    sysDevConfigUserAccountPrivilegedPassword DisplayString,
    sysDevConfigUserAccountUserPassword DisplayString,
    sysDevConfigUserAccountRowStatus RowStatus
	}
 

 sysDevConfigUserAccountIndex OBJECT-TYPE
   SYNTAX Integer32
   MAX-ACCESS not-accessible
   STATUS current
   DESCRIPTION
     "The value of this object is an index of the account config
      table. This object is used by sysDevConfigUserAccountTable
      to identify the row in the table. When creating new
      row of this table the value of this object may be
      obtained by retreiving the value of
      sysDevConfigUserAccountIndexNext."
 ::= { sysDevConfigUserAccountEntry 1 }

sysDevConfigUserAccountUserId OBJECT-TYPE
    SYNTAX  DisplayString (SIZE(1..15))
    MAX-ACCESS  read-create
    STATUS current
    DESCRIPTION
        "This object corresponds to the login ID of the
         user account."
    ::= { sysDevConfigUserAccountEntry 2 }
 
sysDevConfigUserAccountPrivilegedPassword OBJECT-TYPE
    SYNTAX  DisplayString (SIZE(0..15))
    MAX-ACCESS  read-create
    STATUS current
    DESCRIPTION
        "This object corresponds to the access privilege password
         of the user account.  If user is configured
	 with this password in addition to a UserPassword 
	 than the user is Administrator. In a case that user
	 is Operator and does not supply this password 
	 upon user configuration this value should be null string"
    ::= { sysDevConfigUserAccountEntry 3 }

sysDevConfigUserAccountUserPassword OBJECT-TYPE
    SYNTAX  DisplayString (SIZE(0..15))
    MAX-ACCESS  read-create
    STATUS  current
    DESCRIPTION
        "This object corresponds to the password of the
         user account."
    ::= { sysDevConfigUserAccountEntry 4 }
 
sysDevConfigUserAccountRowStatus OBJECT-TYPE
	SYNTAX  RowStatus
	MAX-ACCESS  read-create
	STATUS  current
	DESCRIPTION
	"This object corresponds to create or delete a row in
	sysDevConfigUserAccountTable."
    ::= {sysDevConfigUserAccountEntry 5 }

 sysDevConfigUserAccountIndexNext OBJECT-TYPE
   SYNTAX  Integer32
   MAX-ACCESS  read-only 
   STATUS current
   DESCRIPTION
	" This object contains an appropriate value to be
	  used for sysDevConfigUserAccountTable.
	  The value of 0 indicates that no unassigned 
	  entries are available.  To obtain 
	  sysDevConfigUserAccountIndex value for the new entry 
	  the manager issues a management protocol retrieval 
	  operation to obtain a current value of this object.
	  After each retrieval, the agent should modify the value
	  to the next unassigned index.  "
 ::= { sysDevConfig 9 }

-- the sysDevIDSLConfig group on the MCC

sysDevIDSLConfigTable OBJECT-TYPE
   SYNTAX  SEQUENCE OF SysDevIDSLConfigEntry
   MAX-ACCESS  not-accessible
   STATUS  current
    DESCRIPTION
         "A table that contains configuration information about
          IDSL Card."
    ::= { sysDevConfig 6 }

sysDevIDSLConfigEntry OBJECT-TYPE
   SYNTAX  SysDevIDSLConfigEntry
   MAX-ACCESS  not-accessible
   STATUS current
   DESCRIPTION
         "A list of information for IDSL device Configuration."
   INDEX  { entPhysicalIndex }
    ::= { sysDevIDSLConfigTable 1 }

SysDevIDSLConfigEntry ::=
    SEQUENCE {
            sysDevIDSLConfigPrimaryNetClockMode  IdslClockMode,
            sysDevIDSLConfigSecondaryNetClockMode  IdslClockMode
             }

sysDevIDSLConfigPrimaryNetClockMode  OBJECT-TYPE
    SYNTAX IdslClockMode
    MAX-ACCESS read-create
    STATUS current
    DESCRIPTION
        "This object indicates the network clock mode set
    for the primary network clock. IDSL portcards with a
    port configured as an NT will be set to
    portCardDriveClockOnboard(4), both driving the backplane
    and using the clock for the other Local Timing transceivers
    on the card. Port cards with only LT ports configured will
    receive a clock from the backplane using portCardSinkClock(2).
    portCardDriveClock(3) will drive the backplane alone. The 
    default value of this object is triState(1)."
    DEFVAL { triState }
::= { sysDevIDSLConfigEntry 1 }

sysDevIDSLConfigSecondaryNetClockMode  OBJECT-TYPE
    SYNTAX IdslClockMode
    MAX-ACCESS read-create
    STATUS current
    DESCRIPTION
        "This object indicates the network clock mode set
    for the secondary network clock. IDSL portcards with a
    port configured as an NT will be set to
    portCardDriveClockOnboard(4), both driving the backplane
    and using the clock for the other Local Timing transceivers
    on the card. Port cards with only LT ports configured will
    receive a clock from the backplane using portCardSinkClock(2).
    portCardDriveClock(3) will drive the backplane alone. The 
    default value of this object is triState(1)."
    DEFVAL { triState }
::= { sysDevIDSLConfigEntry 2 }

-- The syslog Group
sysDevDslamSyslog OBJECT IDENTIFIER ::= { sysDevConfig 7 }

sysDevSyslogFtpServerXferStatsEnable OBJECT-TYPE
  SYNTAX SwitchState
  MAX-ACCESS read-write
  STATUS current
  DESCRIPTION
    "This object allows the network manager to enable and disable 
     syslog messages for FTP server file transfer statistics"
  DEFVAL { disabled }
::= { sysDevDslamSyslog 1 }

sysDevSyslogTftpServerXferStatsEnable OBJECT-TYPE
  SYNTAX SwitchState
  MAX-ACCESS read-write
  STATUS current
  DESCRIPTION
    "This object allows the network manager to enable and disable 
     syslog messages for TFTP server file transfer statistics"
  DEFVAL { disabled }
::= { sysDevDslamSyslog 2 }




--Traps

cCN NOTIFICATION-TYPE
  OBJECTS { ifIndex }
  STATUS		current
  DESCRIPTION
    "This trap signifies a Configuration change  or 
     software upgrade in the xDSL card. This trap 
     is of 'warning' class"
 ::= { sysDevDslamMIBTraps 7}

authenticationFailureTrap NOTIFICATION-TYPE
 OBJECTS { loginFailureAccessApp, loginFailureCount }
 STATUS		current
 DESCRIPTION 
  "This trap signifies an authentication  failure. 
   Authentication failures can be telnet based or 
  terminal based. This trap is in addition to the
  SNMP based authentication failure trap, which
  is a generic trap."
  ::= { sysDevDslamMIBTraps 8}

-- the following traps are sent by the MCC *******

 fanModuleFailure NOTIFICATION-TYPE
  STATUS		current
   DESCRIPTION
   "This trap indicates the indicates the failure of 
    the fan module on the device." 
 ::= {sysDevDslamMIBTraps 9}

 fanModuleOperational NOTIFICATION-TYPE
  STATUS		current
   DESCRIPTION
   "This trap indicates the indicates the fan module on the 
    device is operational."  
 ::=  {sysDevDslamMIBTraps 109}



 powerSourceAFailure NOTIFICATION-TYPE
   STATUS		current
   DESCRIPTION
     "This trap indicates that power source A
      has failed. This is sent only by the MCC card. This 
      trap is of 'minor' class."
 ::= {sysDevDslamMIBTraps 10}

 powerSourceAOperational NOTIFICATION-TYPE
   STATUS		current
   DESCRIPTION
     "This trap indicates that the power source A
      is operational. This is sent only by the MCC card. 
      This trap is of 'minor' class. This trap compliments
      powerSourceAFailure trap."
 ::={ sysDevDslamMIBTraps 110}

slotPollFailure NOTIFICATION-TYPE
  OBJECTS { entPhysicalIndex }
  STATUS		current
  DESCRIPTION
   "This trap indicates a slot poll failure.
    This is sent only by the MCC card. this trap is
    of 'major' class."
 ::=  { sysDevDslamMIBTraps 11}

 newCardDetected NOTIFICATION-TYPE
   OBJECTS { entPhysicalIndex }
   STATUS		current
   DESCRIPTION
   "This trap indicates that a new card was detected 
    in a slot. This is sent only by the MCC card. this trap
    is of 'warning' class."
 ::=  {sysDevDslamMIBTraps 111}

-- ****************************

 ethernetJabber NOTIFICATION-TYPE
   OBJECTS { ifIndex }
   STATUS		current
   DESCRIPTION
     "This trap indicates that a jabber condition  has been 
      detected on the ethernet interface. This trap is of 
      'major' class."
 ::=  { sysDevDslamMIBTraps 12}

 ethernetJabberClear NOTIFICATION-TYPE
 
   OBJECTS { ifIndex }
   STATUS		current
   DESCRIPTION
     "This trap indicates that the jabber condition that was 
      detected no longer exists. This trap is of 'major' 
      class."
 ::= { sysDevDslamMIBTraps 112}

 ethernetJumbos NOTIFICATION-TYPE
   OBJECTS { ifIndex }
   STATUS		current
   DESCRIPTION
     "This trap indicates ethernet jumbos. this trap
      is of 'minor' class"
 ::=   { sysDevDslamMIBTraps 13}

 ethernetRunts NOTIFICATION-TYPE
   OBJECTS { ifIndex }
   STATUS		current
   DESCRIPTION
     "This trap indicates ethernet runts. this trap is of 'minor'"
 ::=  {sysDevDslamMIBTraps 14}

 powerSourceBFailure NOTIFICATION-TYPE
   STATUS		current
   DESCRIPTION
     "This trap indicates that power source B
      has failed. This is sent only by the MCC card. This 
      trap is of 'minor' class."
 ::= { sysDevDslamMIBTraps 17}

 powerSourceBOperational NOTIFICATION-TYPE
   STATUS		current
   DESCRIPTION
     "This trap indicates that the power source B
      is operational. This is sent only by the MCC card. 
      This trap is of 'minor' class. This trap compliments
      powerSourceBFailure trap."
 ::=  {sysDevDslamMIBTraps 117}

 nonIpConservativeCardDetected NOTIFICATION-TYPE
   OBJECTS { entPhysicalIndex }
   STATUS		current
   DESCRIPTION
     "This trap indicates that a non ip conservative DSL card
      exist in the chassis at the slot 'slotNumber'.This is
      sent only by the MCC card. This trap is of warning class."
 ::={ sysDevDslamMIBTraps 18}

nonSupportedMCC NOTIFICATION-TYPE
  OBJECTS { sysObjectID }
  STATUS		current
  DESCRIPTION
    "AN has detected MCC firmware release too low to support
     this device"
::={ sysDevDslamMIBTraps 20 }

nonSupportedChassis NOTIFICATION-TYPE
  OBJECTS { sysObjectID }
  STATUS		current
  DESCRIPTION
    "AN in slot xx has been installed in a chassis that cannot
     support one or more of its features. "
::=  {sysDevDslamMIBTraps 21}

 fanEntityModuleFailure NOTIFICATION-TYPE
   OBJECTS { entPhysicalIndex }
  STATUS		current
   DESCRIPTION
   "This trap indicates the indicates the failure of 
    the fan module on the device." 
 ::= {sysDevDslamMIBTraps 22}

 fanEntityModuleOperational NOTIFICATION-TYPE
   OBJECTS { entPhysicalIndex }
  STATUS		current
   DESCRIPTION
   "This trap indicates the indicates the fan module on the 
    device is operational."  
 ::=  {sysDevDslamMIBTraps 122}
END

--===========================================================================
-- Copyright (C) 2000 Paradyne Corporation
--

PDN-ETHER-MIB DEFINITIONS ::= BEGIN

IMPORTS
OBJECT-TYPE, MODULE-IDENTITY
FROM SNMPv2-SMI
OBJECT-GROUP
FROM SNMPv2-CONF
pdn-common
FROM PDN-HEADER-MIB
SwitchState, ManagementType,
ResetStates 
FROM PDN-TC
ifIndex
FROM RFC1213-MIB
ifMauEntry, ifMauIfIndex, ifMauIndex, ifJackIndex
FROM MAU-MIB
;

pdn-ether MODULE-IDENTITY
   LAST-UPDATED    "0205100000Z"
   ORGANIZATION    "Paradyne Corporation
		    MIB Working Group"

   CONTACT-INFO    "Paradyne Corporation
		    8545 126th Avenue North
		    Largo, FL 33733
		    www.paradyne.com

		    General Comments to: mibwg_team@paradyne.com

		    Editors
		    Wayne Jadoo
		    Prakash Easwar
		    Jesus A. Pinto
		    Dragana Gough
		    Clay Sikes"

  DESCRIPTION
     " This MIB contains objects that are used to configure
       ethernet interfaces."

   REVISION "0205100000Z"
   DESCRIPTION  "Added pdnIfJackTable. NOTE: please read the comments
                as to why the ifJackTable, in RFC 2668, was not augmented."

   REVISION "0201090000Z"
   DESCRIPTION  "Added pdnPortConfigMauExtTable to extend ipMauTable
		 from RFC 2668." 


   REVISION  "200108240000Z"
   DESCRIPTION "Add pdnPortConfigEthernetAutoNegotiateMode mib object.
                Add pdnPortCOnfigEthernetSpeed mib object."

   REVISION "200005020000Z"
   DESCRIPTION "Initial Release" 

   ::= { pdn-common 18 }




pdnPortConfigMIBObjects  OBJECT IDENTIFIER ::= { pdn-ether 1 }
pdnPortConfigMIBTraps    OBJECT IDENTIFIER ::= { pdn-ether 2 }
pdnPortConfigEthernet    OBJECT IDENTIFIER ::= { pdnPortConfigMIBObjects 1 }
pdnPortConfigGroups      OBJECT IDENTIFIER ::= { pdnPortConfigMIBObjects 2 }
pdnPortConfigMauExtMIBObject OBJECT IDENTIFIER ::= { pdnPortConfigMIBObjects 3 }
pdnPortConfigIfJackMIBObject OBJECT IDENTIFIER ::= { pdnPortConfigMIBObjects 4 }

-- Ethernet Type of Configuration
            
        pdnPortConfigEthernetTable OBJECT-TYPE
              SYNTAX  SEQUENCE OF PdnPortConfigEthernetEntry
              MAX-ACCESS  not-accessible
              STATUS current 
              DESCRIPTION
                "A Table that contains information about 
                 the Ethernet port configuration"
              ::= { pdnPortConfigEthernet 1 }

        pdnPortConfigEthernetEntry OBJECT-TYPE
              SYNTAX  PdnPortConfigEthernetEntry
              MAX-ACCESS  not-accessible
              STATUS current 
              DESCRIPTION
                  "An entry that contains configuration 
                   information about an ethernet Port "
              INDEX  { ifIndex }
              ::= { pdnPortConfigEthernetTable 1 }

        PdnPortConfigEthernetEntry ::=
                SEQUENCE
                {
                   pdnPortConfigEthernetDuplexMode     SwitchState,
                   pdnPortConfigEthernetManageType     ManagementType,
                   pdnPortConfigEthernetResetState     ResetStates,
                   pdnPortConfigEthernetAutoNegotiate  SwitchState,
                   pdnPortConfigEthernetSpeed          INTEGER
                }

          pdnPortConfigEthernetDuplexMode OBJECT-TYPE
              SYNTAX   SwitchState
              MAX-ACCESS   read-create
              STATUS   current
              DESCRIPTION
                      "This object is used to enable or Disable 
                       Duplex Mode on an ethernet Port. This object
		       can not be enabled if the auto-negotiate 
		       mode is enabled"
                      
              DEFVAL { disabled } -- Disabled
              ::= { pdnPortConfigEthernetEntry 1  }
        
          pdnPortConfigEthernetManageType OBJECT-TYPE
              SYNTAX   ManagementType
              MAX-ACCESS   read-create
              STATUS  current 
              DESCRIPTION
                      "This object is used to Enable or 
                       Disable Inband or Outband Management."
                      
              DEFVAL { outband } 
              ::= { pdnPortConfigEthernetEntry 2  }

          pdnPortConfigEthernetResetState OBJECT-TYPE
              SYNTAX   ResetStates
              MAX-ACCESS   read-create
              STATUS   current
              DESCRIPTION
                      "This object is used to reset the ethernet port." 

              DEFVAL { noOp } -- No
              ::= { pdnPortConfigEthernetEntry 3  }

          pdnPortConfigEthernetAutoNegotiate OBJECT-TYPE
              SYNTAX   SwitchState
              MAX-ACCESS   read-create
              STATUS  current 
              DESCRIPTION
                      "This object is used to enable or disable
                       the auto-negotiate mode. Enabling this
		       mode will disable selection of the speed
		       and/or full duplex mode."
                      
              DEFVAL { enabled } -- Enabled
              ::= { pdnPortConfigEthernetEntry 4  }
 
          pdnPortConfigEthernetSpeed OBJECT-TYPE
              SYNTAX   INTEGER {
		tenBaseT 	(1),
		hundredBaseT 	(2)
	      }
              MAX-ACCESS   read-create
              STATUS   current
              DESCRIPTION
                      "This object corresponds to the speed of
                       the ethernet port. This object can not be
		       set if the auto-negotiate mode is enabled."
	      DEFVAL { tenBaseT } -- 10BaseT
                      
              ::= { pdnPortConfigEthernetEntry 5  }
 
        
-- Extention talbe to ifMauTable
-- to add ConfigXover object
 
        pdnPortConfigMauExtTable OBJECT-TYPE
              SYNTAX  SEQUENCE OF PdnPortConfigMauExtEntry
              MAX-ACCESS  not-accessible
              STATUS current 
              DESCRIPTION
                "A Table that contains configuration information about 
                 the Ethernet port configuration and it extends standard
		 MAU table from RFC2668."
              ::= { pdnPortConfigMauExtMIBObject 1 }

        pdnPortConfigMauExtEntry OBJECT-TYPE
              SYNTAX  PdnPortConfigMauExtEntry
              MAX-ACCESS  not-accessible
              STATUS current 
              DESCRIPTION
                  "An entry that contains configuration 
                   information about an ethernet Port "
              AUGMENTS  { ifMauEntry }
              ::= { pdnPortConfigMauExtTable 1 }

        PdnPortConfigMauExtEntry ::=
                SEQUENCE
                {
                   pdnPortConfigXover    INTEGER 
		}

          pdnPortConfigXover OBJECT-TYPE
              SYNTAX  INTEGER  {
				mdi(1),
				mdix(2)
				}
              MAX-ACCESS   read-create
              STATUS  current 
              DESCRIPTION
                      "This object is used to configure 
		       if crossover or straightthrough cable is
		       used on ethernet interface if the interface
		       is not set for autonegotiontion."
              ::= { pdnPortConfigMauExtEntry 1  }

-- Augmentation of the ifJactTable in the 802.3 MAU MIB
-- RFC 2668
-- Originally I wanted to implement this table as an augmentation
-- of the ifJackTable in the 802.3 MAU MIB specified in RFC 2668 and 
-- call it pdnIfJackExtTable. However, the SNMP Research MIB Tools would
-- not successfully compile an augmentation of this table with an
-- object that is read-write because the ifJackTable only has
-- read-only objects. 
        pdnIfJackTable  OBJECT-TYPE
            SYNTAX      SEQUENCE OF PdnIfJackEntry
            MAX-ACCESS  not-accessible
            STATUS      current
            DESCRIPTION "This table conceptually extends the ifJackTable
                        but not as an augmentation. See the note above."
            ::= { pdnPortConfigIfJackMIBObject 1 }

        pdnIfJackEntry  OBJECT-TYPE
            SYNTAX      PdnIfJackEntry
            MAX-ACCESS  not-accessible
            STATUS      current
            DESCRIPTION "An entry that contains configuration information
                        about a jack."
            INDEX       { 
                            ifMauIfIndex,
                            ifMauIndex,
                            ifJackIndex
                        }
            ::= { pdnIfJackTable 1 }

        PdnIfJackEntry ::=
           SEQUENCE    {
                           pdnActiveJack        INTEGER
                       }

        pdnActiveJack   OBJECT-TYPE
            SYNTAX      INTEGER {
                            fiber(1),   -- Small Form-factor Pluggable (SFP)
                                        -- for fiber interfaces
                            rj45(2),    -- Copper wire interface
                            auto(3)     -- Automatically detects fiber(1) or
                                        -- rj45(2)
                        }
            MAX-ACCESS  read-write
            STATUS      current
            DESCRIPTION "This object allows the jack type to be configured or a 
                        priority to be set. This applies to Ethernet interfaces
                        that may support more than one type of jack on an inter-
                        face and only one jack is valid at a time. Consider two
                        cases:

                        1. A product supports two types of jacks, a RJ45 copper-
                           wire interface and a SFP fiber interface. The product is 
                           required to have the user set the active jack or allow it 
                           to be auto detected. The values for this object that 
                           allow the requirement to be satisfied and their interp-
                           retation are as follows:
                           a. fiber(1) - The fiber jack is active and the others, 
                                         e.g. rj45, are ignored.
                           b. rj45(2)  - The rj45 jack is actie and the others, 
                                         eg.fiber, are ignored.
                           c. auto(3)  - Either jack can be used and it is up
                                         to the implementation to determine which
                                         jack has presedence when both jacks are
                                         active. This determination must be clearly
                                         documented in the SNMP Operational Speci-
                                         fication.
                            No default is specified for this MIB object so the default
                            value for this object must be clearly documented in the
                            SNMP Operational Specification.

                         2. A product supports two types of jacks, a RJ45 copper-
                            wire interface and s SFP fiber interface. The product is
                            required to have the user select which jack has priority
                            when both jacks are active. The values for this object
                            that allow the requirement to be satisfied and their 
                            interpretation are as follos:
                            a. fiber(1) - The fiber jack has priority.
                            b. rj45(2)  - The rj45 jack has priority.
                            c. auto(3)  - Not used."                                              
            ::= { pdnIfJackEntry 1 }


--CONFORMANCE INFORMATION

pdnPortConfigEthernetGroup OBJECT-GROUP
	OBJECTS {
                   pdnPortConfigEthernetDuplexMode,
                   pdnPortConfigEthernetManageType,
                   pdnPortConfigEthernetResetState,
                   pdnPortConfigEthernetAutoNegotiate,
                   pdnPortConfigEthernetSpeed
       }
       STATUS	current
       DESCRIPTION
	"This collection of objects is used to set mode
	 and rate on any ethernet interface."

       ::= { pdnPortConfigGroups 1 }

pdnPortConfigExtMauGroup OBJECT-GROUP
	OBJECTS {
                   pdnPortConfigXover
        }
       STATUS	current
       DESCRIPTION
	"This object is used to set xover mode
	 on any ethernet interface."

       ::= { pdnPortConfigGroups 2 }

pdnPortConfigExtIfJackGroup OBJECT-GROUP
    OBJECTS     {
                    pdnActiveJack
                }
    STATUS      current
    DESCRIPTION "This object is used to set active jack
                on any ethernet interface supporting more
                than one jack."

    ::= { pdnPortConfigGroups 3 }


END


PDN-FILTER-MIB DEFINITIONS ::= BEGIN

-- Version :  1.1 PROPOSED 
-- Enterprise filter mib
-- Copyright (C) 2000 Paradyne Corporation.

-- Created by : Prakash Easwar

--  CHANGE HISTORY
--
--  04/27/00 Prakash Easwar
--  1) Top level oid changes
--  2) added support for filter injection traps (moved the ones that
--     were deprecated from hot_xdsl.mib to this mib
--
-- 11/13/01 Dragana Gough
--  1) Added common filter configuration table for ethernet and ip
--     filters (sysDevFilterConfigTable) that looks similar to
--     sysDevIpFilterConfigTable. Added object Type.
-- 
-- 11/15/01 Dragana Gough
--  1) Added layer 2 filter rule table. Added common binding
--     table and new scalar object for index next search.
--
-- 01/11/01 Dragana Gough
-- 1) updated tables (Filter, rules and binding tables)
--
-- 07/30/02 Dragana Gough
-- 1) Added new sysDevL3FilterRuleConfigTable
--
-- 08/14/02 Dragana Gough
-- 1) Updated CHANGE HISTORY
-- 2) Depricated sysDevIpFilterRuleConfigTable
-- 3) Added (3) 'none' to sysDevL3FilterRuleSrcAddrAction
--    and sysDevL3FilterRuleDestAddrAction
-- 4) Changed sysDevL3FilterRuleName display string limit
--    to 255 from 12
-- 5) Added description to RuleName (unique name recommended)
--    and SrcPortNum and DestPortNum (if out-range or in-range 
--    CompType than this is start of range)
-- 6) Added description to objects that provide Next RuleIndex and
--    next FilterIndex
--

IMPORTS
RowStatus,DisplayString
  FROM SNMPv2-TC
IpAddress, Counter
  FROM RFC1155-SMI
OBJECT-TYPE
  FROM RFC-1212
TRAP-TYPE
  FROM RFC-1215
ifIndex
  FROM RFC1213-MIB
VnidRange
	FROM PDN-TC
pdn-filter
  FROM PDN-HEADER-MIB
;

sysDevFilterMIBObjects OBJECT IDENTIFIER ::= { pdn-filter 1 }
sysDevFilterMIBTraps   OBJECT IDENTIFIER ::= { pdn-filter 2 }
sysDevFilter OBJECT IDENTIFIER ::= { sysDevFilterMIBObjects 1 }
sysDevIpFilter OBJECT IDENTIFIER ::= { sysDevFilterMIBObjects 2 }

-- The filter group.

-- IP Filter sub group.

 sysDevIpFilterConfigTable OBJECT-TYPE
   SYNTAX SEQUENCE OF SysDevIpFilterConfigTableEntry
   ACCESS not-accessible
   STATUS mandatory
   DESCRIPTION
     "This table allows the user to configure filtering information.
      Every filter is comprised of a number of rules(see SysDevRuleTable).
	  When a filter is bound to an interface, all the rules of that particular
      filter apply to that particular interface. Also the same filter
      maybe bound to several interfaces. This table only allows
      us to configure information about a particular filter.
      this table is indexed by sysDevIpFilterName." 
    ::= { sysDevIpFilter 1 }

sysDevIpFilterConfigTableEntry OBJECT-TYPE
   SYNTAX SysDevIpFilterConfigTableEntry
   ACCESS not-accessible
   STATUS mandatory
   DESCRIPTION
     "Describes a specific entry of the filter configuration table."
   INDEX { sysDevIpFilterName }
    ::= { sysDevIpFilterConfigTable 1 }

 SysDevIpFilterConfigTableEntry ::=
   SEQUENCE {
     sysDevIpFilterName       		   DisplayString,
     sysDevIpDefFilterAction   		   INTEGER,
     sysDevIpFilterNumOfDynamicRules       INTEGER,
     sysDevIpFilterNumOfStaticRules        INTEGER,
     sysDevIpFilterRefCount	           INTEGER,
	 sysDevIpFilterTcpAckFilterAction  INTEGER,
	 sysDevIpFilterDhcpFilterAction	   INTEGER,
     sysDevIpFilterRowStatus		   RowStatus
	}

 sysDevIpFilterName OBJECT-TYPE
   SYNTAX  DisplayString (SIZE(1..12))
   ACCESS read-only
   STATUS mandatory
   DESCRIPTION
     "The value of this object corresponds directly to the name
     of the filter."
 ::= { sysDevIpFilterConfigTableEntry 1 }

 sysDevIpDefFilterAction OBJECT-TYPE
   SYNTAX INTEGER {
     forward (1),
     discard (2),
     delete (3)
   }
   ACCESS read-write
   STATUS mandatory
   DESCRIPTION
     "The value of this object corresponds to the  default action
      taken on a particular IP packet based on the filter rule.
      forward - the packet is forwarded
        discard - the packet is discarded.
        delete - the rule of a particular filter or the 
        filter as a whole is deleted."
 ::= { sysDevIpFilterConfigTableEntry 2 }

 sysDevIpFilterNumOfDynamicRules OBJECT-TYPE
   SYNTAX INTEGER
   ACCESS read-only
   STATUS mandatory
   DESCRIPTION
     "This object corresponds to the number of dynamic rules 
      configured for this filter"
 ::= { sysDevIpFilterConfigTableEntry 3 }
 
 sysDevIpFilterNumOfStaticRules OBJECT-TYPE
   SYNTAX INTEGER
   ACCESS read-only
   STATUS mandatory
   DESCRIPTION
     "This object corresponds to the number of static rules 
      configured for this filter"
 ::= { sysDevIpFilterConfigTableEntry 4 }
 
 sysDevIpFilterRefCount OBJECT-TYPE
   SYNTAX INTEGER
   ACCESS read-only
   STATUS mandatory
   DESCRIPTION
     "This object corresponds to the number of 
      references for this filter by the various 
      interfaces of the system
      For Example if filter 'abc' is bound to
      two of the DSL interfaces as input filters. then
      the reference count for this filter is 2.
      if a filter 'def' is bound to the 10BaseT interface
      as both an input and an output filter. The reference count
      for this filter would be 2. Filters can be deleted from the
      system (by a user) only if the reference count equals 0"
 ::= { sysDevIpFilterConfigTableEntry 5 }

 sysDevIpFilterTcpAckFilterAction OBJECT-TYPE
 SYNTAX INTEGER {
	 forward (1),
	 discard (2),
	 noOp (3)
  }
 ACCESS read-write
 STATUS mandatory
 DESCRIPTION
	"The value of this object corresponds to the  default action
	taken on the first TCP ACK packet of the TCP connection. This
	object is not supported for MCC."
 ::= { sysDevIpFilterConfigTableEntry 6 }

 sysDevIpFilterDhcpFilterAction OBJECT-TYPE
 SYNTAX INTEGER {
	 forward (1),
	 discard (2),
	 noOp (3)
 }
 ACCESS read-write
 STATUS mandatory
 DESCRIPTION
	"The value of this object corresponds to the  default action
	taken on the DHCP transaction messages. This object is not supported
	for mcc."
 ::= { sysDevIpFilterConfigTableEntry 7 }

 sysDevIpFilterRowStatus OBJECT-TYPE
    SYNTAX RowStatus 
    ACCESS read-write
    STATUS mandatory
    DESCRIPTION
        "The object is used to add or delete a row from
         this table." 
 ::= { sysDevIpFilterConfigTableEntry 8 }

 sysDevIpFilterRuleConfigTable OBJECT-TYPE
   SYNTAX SEQUENCE OF SysDevIpFilterRuleConfigTableEntry
   ACCESS not-accessible
   STATUS deprecated
   DESCRIPTION
     "This table allows the user to configure the rules of each IP filter.
	 When a filter is bound to an interface, all the rules of that particular 
	 filter apply to that particular interface. Also, the same filter may be
	 found to several interfaces. This table is indexed by
	 sysDevIpFilterName and sysDevIpFilterRuleNumber."
    ::= { sysDevIpFilter 2 }

sysDevIpFilterRuleConfigTableEntry OBJECT-TYPE
   SYNTAX SysDevIpFilterRuleConfigTableEntry
   ACCESS not-accessible
   STATUS deprecated
   DESCRIPTION
     "Describes a specific entry of the filter rule configuration table."
   INDEX { sysDevIpRuleFilterName, sysDevIpFilterRuleNumber }
    ::= { sysDevIpFilterRuleConfigTable 1 }

 SysDevIpFilterRuleConfigTableEntry ::=
   SEQUENCE {
     sysDevIpRuleFilterName    		    DisplayString (SIZE(1..12)),
     sysDevIpFilterRuleNumber    		INTEGER,
     sysDevIpFilterRuleSrcAddress    	IpAddress,
     sysDevIpFilterRuleSrcAddrMask   	IpAddress,
	 sysDevIpFilterRuleSrcAddrCompEnable	INTEGER,
     sysDevIpFilterRuleSrcPortNum    	INTEGER,
     sysDevIpFilterRuleMaxSrcPortNum 	INTEGER,
     sysDevIpFilterRuleSrcCompType   	INTEGER,
     sysDevIpFilterRuleDestAddress   	IpAddress,
     sysDevIpFilterRuleDestAddrMask   	IpAddress,
	 sysDevIpFilterRuleDestAddrCompEnable	INTEGER,
     sysDevIpFilterRuleDestPortNum    	INTEGER,
     sysDevIpFilterRuleMaxDestPortNum 	INTEGER,
     sysDevIpFilterRuleDestCompType  	INTEGER,
     sysDevIpFilterRuleType            	INTEGER,
     sysDevIpFilterRuleProtocolTypeUdp  INTEGER,
     sysDevIpFilterRuleProtocolTypeTcp  INTEGER,
     sysDevIpFilterRuleProtocolTypeIcmp INTEGER,
     sysDevIpFilterRuleRowStatus 		RowStatus
   }

 sysDevIpRuleFilterName OBJECT-TYPE
   SYNTAX  DisplayString (SIZE(1..12))
   ACCESS read-only
   STATUS deprecated
   DESCRIPTION
     "The value of this object corresponds directly to the name
     of the filter."
 ::= { sysDevIpFilterRuleConfigTableEntry 1 }

 sysDevIpFilterRuleNumber OBJECT-TYPE
   SYNTAX INTEGER (1..33)
   ACCESS read-only
   STATUS deprecated
   DESCRIPTION
     "The value of this object corresponds directly to a rule 
      within a particular filter. If the value of this object
      is 0, then the sets apply to the filter as a whole. For
      example one may want to delete the whole filter. for
      a get only the name of the filter is returned."
   ::= { sysDevIpFilterRuleConfigTableEntry 2 }

 sysDevIpFilterRuleSrcAddress OBJECT-TYPE
   SYNTAX IpAddress
   ACCESS read-write
   STATUS deprecated
   DESCRIPTION
     "The value of this object corresponds directly to an source
      IP Address. This object could be set if IP packets need to be
      filtered based on where it is coming from. Setting this object
	  to 0.0.0.0 disables source IP address comparison."
   ::= { sysDevIpFilterRuleConfigTableEntry 3 }

 sysDevIpFilterRuleSrcAddrMask OBJECT-TYPE
   SYNTAX IpAddress
   ACCESS read-write
   STATUS deprecated
   DESCRIPTION
     "The value of this object corresponds directly to an source
      IP Address Mask. The value of this object is bitwise anded
      with the source address within the IP packet and then compared
      with the sysDevIPFilterSrcAddress."
   ::= { sysDevIpFilterRuleConfigTableEntry 4 }

 sysDevIpFilterRuleSrcAddrCompEnable OBJECT-TYPE
   SYNTAX INTEGER {
	enable (1),
	disable (2),
	noOp (3)
	}
   ACCESS read-write
   STATUS deprecated
   DESCRIPTION
      "This object enables or disables the source address comparison.
	  It is not supported for MCC."
   ::= { sysDevIpFilterRuleConfigTableEntry 5 }

 sysDevIpFilterRuleSrcPortNum OBJECT-TYPE
   SYNTAX INTEGER (0..65535)
   ACCESS read-write
   STATUS deprecated
   DESCRIPTION
     "The UDP or TCP port number of the source on which this filter 
      is applied."
   ::= { sysDevIpFilterRuleConfigTableEntry 6 }

 sysDevIpFilterRuleMaxSrcPortNum OBJECT-TYPE
   SYNTAX INTEGER (0..65535)
   ACCESS read-write
   STATUS deprecated
   DESCRIPTION
     "The maximum UDP or TCP port number of the source on which
      this filter is applied. This object is valid only if the source 
      comparison type is in-range or out-range"
   ::= { sysDevIpFilterRuleConfigTableEntry 7 }

 sysDevIpFilterRuleSrcCompType OBJECT-TYPE
   SYNTAX INTEGER {
     none (1),
     eq (2),
     neq (3),
     gt (4),
     lt (5),
     inRange (6),
     outRange (7)
   }
   ACCESS read-write
   STATUS deprecated
   DESCRIPTION
     "The value of this object corresponds to the type of
      comparison which is to be made for source based filtering 
      for the particular rule of the filter.
        none - no comparison is to be made.
        eq - equal to
        neq - not equal to
        gt - greater than
        lt - less than
        inRange - the source port number of the TCP or UDP packet
                  is within a specified range.
        outRange - the source port number of the TCP or UDP packet
                   lies outside a specified range."
   ::= { sysDevIpFilterRuleConfigTableEntry 8 }

 sysDevIpFilterRuleDestAddress OBJECT-TYPE
   SYNTAX IpAddress
   ACCESS read-write
   STATUS deprecated
   DESCRIPTION
     "The value of this object corresponds directly to an destination
      IP Address. This object could be set if IP packets need to be
      filtered based on where it is going to."
   ::= { sysDevIpFilterRuleConfigTableEntry 9 }

 sysDevIpFilterRuleDestAddrMask OBJECT-TYPE
   SYNTAX IpAddress
   ACCESS read-write
   STATUS deprecated
   DESCRIPTION
     "The value of this object corresponds directly to an destination
      IP Address Mask. The value of this object is bitwise anded
      with the destination address within the IP packet and then compared
      with the sysDevIPFilterRuleDestAddress"
   ::= { sysDevIpFilterRuleConfigTableEntry 10 }

 sysDevIpFilterRuleDestAddrCompEnable OBJECT-TYPE
   SYNTAX INTEGER {
	enable (1),
	disable (2),
	noOp (3)
	}
   ACCESS read-write
   STATUS deprecated
   DESCRIPTION
      "This object enables or disables the destination address comparison.
	  It is not supported for MCC."
   ::= { sysDevIpFilterRuleConfigTableEntry 11 }

 sysDevIpFilterRuleDestPortNum OBJECT-TYPE
   SYNTAX INTEGER (0..65535)
   ACCESS read-write
   STATUS deprecated
   DESCRIPTION
     "The UDP or TCP port number of the destination on which this filter 
      is applied"
   ::= { sysDevIpFilterRuleConfigTableEntry 12 }

 sysDevIpFilterRuleMaxDestPortNum OBJECT-TYPE
   SYNTAX INTEGER (0..65535)
   ACCESS read-write
   STATUS deprecated
   DESCRIPTION
     "The maximum UDP or TCP port number of the destination on which
      this filter is applied. This object is valid only if the destination
      comparison type is in-range or out-range"
   ::= { sysDevIpFilterRuleConfigTableEntry 13 }

 sysDevIpFilterRuleDestCompType OBJECT-TYPE
   SYNTAX INTEGER {
     none (1),
     eq (2),
     neq (3),
     gt (4),
     lt (5),
     inRange (6),
     outRange (7)
   }
   ACCESS read-write
   STATUS deprecated
  DESCRIPTION
    "The value of this object corresponds to the type of
     comparison which is to be made for destination based filtering 
     for the particular rule of the filter.
       none - no comparison is to be made.
       eq - equal to
       neq - not equal to
       gt - greater than
       lt - less than
       inRange - the source port number of the TCP or UDP packet
                 is within a specified range.
       outRange - the source port number of the TCP or UDP packet
                  lies outside a specified range."
   ::= { sysDevIpFilterRuleConfigTableEntry 14 }

 sysDevIpFilterRuleType OBJECT-TYPE
   SYNTAX INTEGER {
     static (1),
     dynamic (2)
   }
   ACCESS read-only
   STATUS deprecated
   DESCRIPTION
     "The value of this object corresponds to the type of
      type of rule configured
           static - This indicates that the rule was configured
                    by an NMS either by SNMP, console or using
                    telnet
           dynamic - this indicates that the rule was configured
                    by the the system for end-users who have obtaimed
                    an IP address using the DHCP protocol."
   ::= { sysDevIpFilterRuleConfigTableEntry 15 }
 
 sysDevIpFilterRuleProtocolTypeUdp OBJECT-TYPE
   SYNTAX INTEGER {
     forward (1),
     discard (2)
     }
    ACCESS read-write
    STATUS deprecated
    DESCRIPTION
      "The value of this object corresponds to the action
      taken on a particular UDP packet based on the source/
      destination port comparison rule."
   ::= { sysDevIpFilterRuleConfigTableEntry 16 }
 
 sysDevIpFilterRuleProtocolTypeTcp OBJECT-TYPE
    SYNTAX INTEGER {
        forward (1),
        discard (2)
    }
    ACCESS read-write
    STATUS deprecated
    DESCRIPTION
        "The value of this object corresponds to the action
         taken on a particular TCP packet bases on the source/
         destination port comparison rule."
   ::= { sysDevIpFilterRuleConfigTableEntry 17 }
 
 sysDevIpFilterRuleProtocolTypeIcmp OBJECT-TYPE
    SYNTAX INTEGER {
        forward (1),
        discard (2)
    }
    ACCESS read-write
    STATUS deprecated
    DESCRIPTION
        "The value of this object corresponds to the action
         taken on a particular ICMP packet bases on the protocol
         type comparison rule."
   ::= { sysDevIpFilterRuleConfigTableEntry 18 }

 sysDevIpFilterRuleRowStatus OBJECT-TYPE
    SYNTAX RowStatus 
    ACCESS read-write
    STATUS deprecated
    DESCRIPTION
        "The object is used to add or delete a row from
         this table." 
   ::= { sysDevIpFilterRuleConfigTableEntry 19 }

 sysDevMaxNumOfInputIpFilters OBJECT-TYPE
   SYNTAX INTEGER
   ACCESS read-only
   STATUS mandatory
   DESCRIPTION
     "The value of this object corresponds directly to the max
	 number of input IP filters supported by each device."
 ::= { sysDevIpFilter 3 }

 sysDevMaxNumOfOutputIpFilters OBJECT-TYPE
   SYNTAX INTEGER
   ACCESS read-only
   STATUS mandatory
   DESCRIPTION
     "The value of this object corresponds directly to the max
	 number of Output IP filters supported by each device."
 ::= { sysDevIpFilter 4 }

-- Filter Bindings

 sysDevIpFilterBindingTable OBJECT-TYPE
   SYNTAX SEQUENCE OF SysDevIpFilterBindingTableEntry
   ACCESS not-accessible
   STATUS mandatory
   DESCRIPTION
     "This table allows us to bind filters to a particular interface.
      As such this table is doubly indexed by ifIndex and
      sysDevIpBindingFilterName."
 ::= { sysDevIpFilter 5 }
 
 sysDevIpFilterBindingTableEntry OBJECT-TYPE
   SYNTAX SysDevIpFilterBindingTableEntry
   ACCESS not-accessible
   STATUS mandatory
   DESCRIPTION
     "Describes a specific entry of the filter binding table."
   INDEX { ifIndex, sysDevIpBindingFilterName }
 ::= { sysDevIpFilterBindingTable 1 }
 
 SysDevIpFilterBindingTableEntry ::=
   SEQUENCE {
	 sysDevIpBindingFilterName			DisplayString (SIZE(1..12)),
     sysDevIpBindingFilterType          INTEGER,
     sysDevIpBindingFilterRowStatus     RowStatus
   }
 
 sysDevIpBindingFilterName OBJECT-TYPE
   SYNTAX  DisplayString (SIZE(1..12))
   ACCESS read-only
   STATUS mandatory
   DESCRIPTION
     "The value of this object corresponds directly to the name
     of the filter."
 ::= { sysDevIpFilterBindingTableEntry 1 }

 sysDevIpBindingFilterType OBJECT-TYPE
   SYNTAX INTEGER {
     inputFilter (1),
     outputFilter (2),
     inputOutputFilter (3)
   }
   ACCESS read-write
   STATUS mandatory
   DESCRIPTION
     "The value of this object corresponds directly to the type
      of the filter which needs to be bound to a particular interface.
        inputFilter - This indicates that the filter is applied to the
                      packets coming in to the interface.
        outputFilter - this indicates that the filter is applied to
                       packets going out the interface.
        inputOutputFilter - this indicates that the filter is applied
                       packets going out the interface and to packets
                       coming in to the interface."
 ::= { sysDevIpFilterBindingTableEntry 2 }
 
 sysDevIpBindingFilterRowStatus OBJECT-TYPE
   SYNTAX RowStatus 
   ACCESS read-write
   STATUS mandatory
   DESCRIPTION
     "This object is used to add or delete a row from this table."
 ::= { sysDevIpFilterBindingTableEntry 3 }

 -- Service Node Filter bindings

 sysDevIpFilterSNBindingTable OBJECT-TYPE
 SYNTAX SEQUENCE OF SysDevIpFilterSNBindingTableEntry
 ACCESS not-accessible
 STATUS mandatory
 DESCRIPTION
  "This table allows us to bind filters to a particular interface on
   portcards.  This table is indexed by ifIndex, sysDevIpSNBindingVnidId
   and sysDevIpSNBindingFilterName."
 ::= { sysDevIpFilter 6 }

 sysDevIpFilterSNBindingTableEntry OBJECT-TYPE
 SYNTAX SysDevIpFilterSNBindingTableEntry
 ACCESS not-accessible
 STATUS mandatory
 DESCRIPTION
  "Describes a specific entry of the SNfilter binding table."
 INDEX { ifIndex, sysDevIpSNBindingVnidId, sysDevIpSNBindingFilterName }
 ::= { sysDevIpFilterSNBindingTable 1 }

 SysDevIpFilterSNBindingTableEntry ::=
 SEQUENCE {
    sysDevIpSNBindingVnidId			   VnidRange,
	sysDevIpSNBindingFilterName        DisplayString,
	sysDevIpSNBindingFilterType        INTEGER,
	sysDevIpSNBindingFilterRowStatus   RowStatus
  }

 sysDevIpSNBindingVnidId OBJECT-TYPE
 SYNTAX  VnidRange
 ACCESS  read-only
 STATUS  mandatory
 DESCRIPTION
   "The VNID Id number of the virtual network to which this filter
    is bound."
 ::= { sysDevIpFilterSNBindingTableEntry 1 }

 sysDevIpSNBindingFilterName OBJECT-TYPE
 SYNTAX  DisplayString (SIZE(1..12))
 ACCESS read-only
 STATUS mandatory
 DESCRIPTION
	 "The value of this object corresponds directly to the name of the filter."
 ::= { sysDevIpFilterSNBindingTableEntry 2 }

 sysDevIpSNBindingFilterType OBJECT-TYPE
 SYNTAX INTEGER {
	inputFilter (1),
    outputFilter (2),
	inputOutputFilter (3)
  }
 ACCESS read-write
 STATUS mandatory
 DESCRIPTION
   "The value of this object corresponds directly to the type
   of the filter which needs to be bound to a particular interface.
   inputFilter - This indicates that the filter is applied to the
   packets coming in to the interface.
   outputFilter - this indicates that the filter is applied to
   packets going out the interface.
   inputOutputFilter - this indicates that the filter is applied
   packets going out the interface and to packets coming in to the interface."
 ::= { sysDevIpFilterSNBindingTableEntry 3 }

 sysDevIpSNBindingFilterRowStatus OBJECT-TYPE
 SYNTAX RowStatus
 ACCESS read-write
 STATUS mandatory
 DESCRIPTION
   "This object is used to add or delete a row from this table."
 ::= { sysDevIpFilterSNBindingTableEntry 4 }

-- Filter Stats

 sysDevIpInputPacketsFiltered OBJECT-TYPE
   SYNTAX Counter
   ACCESS read-only
   STATUS mandatory
   DESCRIPTION
     "The number of IP packets that have been filtered on all the
      incoming interfaces due to not matching programmed filter 
      entries on interfaces that are activated for IP filtering.This
	  is supported on MCC only"
   ::= { sysDevIpFilter 7 }

 sysDevIpOutputPacketsFiltered OBJECT-TYPE
   SYNTAX Counter
   ACCESS read-only
   STATUS mandatory
   DESCRIPTION
     "The number of IP packets that have been filtered on all the
      outgoing interfaces due to not matching programmed filter 
      entries on interfaces that are activated for IP filtering.This
	  is supported on MCC only"
   ::= { sysDevIpFilter 8 }
 
 -- The SNInjection group.

sysDevSNInjectionType OBJECT-TYPE
    SYNTAX  INTEGER {
            ipFilter (1)
    }
    ACCESS  not-accessible
    STATUS  mandatory
    DESCRIPTION
       "The value of this object corresponds to the remote
        injection type"
    ::= { sysDevFilter 1 }

sysDevSNInjectionVnid OBJECT-TYPE
    SYNTAX  VnidRange
    ACCESS  not-accessible
    STATUS  mandatory
    DESCRIPTION
       "This object corresponds to the vnid id
        (bound to an interface) on which filter injection 
		  is not supported or has failed"
    ::= { sysDevFilter 2 }

--*******************************************************************
-- Common Filter sub group.
-- Configure filter table
-- Rule table
-- Binding table
--********************************************************************
-- The sysDevFilterConfigTable is used to create new filters.
-- To create new filter, filter index, filter name, type and 
-- and default action are neccessary to be specified. Next the 
-- user should create rules that will be attached to his filter. 
-- To create rule user should use L2 or L3, L4 FilterRuleTable)
-- depending on what type of rules user needs to create. To create
-- L2 (layer two) rule user needs to specify rule index, rule name, 
-- ether type (RFC 1700) and frame type that will be accepted. 
-- The user should also configure what action should be taken if  
-- the rule is matched to a frame. The ether type can be a range
-- of hex numbers (2bytes) so range objects should be used. 
-- Next the rule should be bound to one or more filters that are 
-- created. This binding is done by using FilterToRule binding 
-- table. This table is indexed by rule index and
-- filter index. Next the filter-rule binding (completed filter) 
-- should be bound to an interface by using FilterBindingTable. 
-- This table is indexed by ifIndex (interface we want filter 
-- bound to), filter index and direction that filter/rule 
-- combination is applied to (inboudn, outbound and inboundoutbound).
-- After this step the filter will take in effect and every 
-- packet on this interface will be examined for rule or set of  
-- rules that are bound to this filter. Filter should not be 
-- bound to an interface if the rule is not bound to a filter.
-- it can be done but the default action will take in effect 
-- and every packet will be checked. The rule cannot be deleted  
-- until all filter-rule bindings for this filter are deleted.
-- The rule cannot be deleted until all filter-interface 
-- bindings for this filter are disabled.
--***************************************************************************************

 sysDevFilterConfigTable OBJECT-TYPE
   SYNTAX SEQUENCE OF SysDevFilterConfigTableEntry
   ACCESS not-accessible
   STATUS mandatory
   DESCRIPTION
     "This table allows the user to configure filtering information.
      Every filter is comprised of a number of rules(see SysDevRuleTable).
      When a filter is bound to an interface, all the rules of that particular
      filter apply to that particular interface. Also the same filter
      maybe bound to several interfaces. This table only allows
      us to configure information about a particular filter.
      this table is indexed by sysDevFilterName." 
    ::= { sysDevFilter 3 }

sysDevFilterConfigTableEntry OBJECT-TYPE
   SYNTAX SysDevFilterConfigTableEntry
   ACCESS not-accessible
   STATUS mandatory
   DESCRIPTION
     "Describes a specific entry of the filter configuration table."
   INDEX { sysDevFilterIndex }
    ::= { sysDevFilterConfigTable 1 }

 SysDevFilterConfigTableEntry ::=
   SEQUENCE {
     sysDevFilterIndex       		   INTEGER,
     sysDevFilterName       		   DisplayString,
     sysDevFilterType       		   INTEGER,
     sysDevDefFilterAction   		   INTEGER,
     sysDevFilterNumOfDynamicRules         INTEGER,
     sysDevFilterNumOfStaticRules          INTEGER,
     sysDevFilterRefCount		   INTEGER,
     sysDevFilterRowStatus		   RowStatus
	}

 sysDevFilterIndex OBJECT-TYPE
   SYNTAX  INTEGER
   ACCESS read-only
   STATUS mandatory
   DESCRIPTION
     "The value of this object is an index of the filter.
      This object is used by sysDevFilterConfigTable to identify
      the row in the table. When creating new row of this table
      the value of this object may be obtained by retreiving the
      value of sysDevFilterIndexNext."
 ::= { sysDevFilterConfigTableEntry 1 }

 sysDevFilterName OBJECT-TYPE
   SYNTAX  DisplayString (SIZE(1..12))
   ACCESS read-write
   STATUS mandatory
   DESCRIPTION
     "The value of this object corresponds directly to the name
     of the filter."
 ::= { sysDevFilterConfigTableEntry 2 }


 sysDevFilterType OBJECT-TYPE
   SYNTAX  INTEGER { 
       layer1 (1),
       layer2       (2),
       layer3       (3),
       layer4       (4),
       layer5       (5),
       layer6       (6),
       layer7       (7),
       unknown  (8)
       }
   ACCESS read-write
   STATUS mandatory
   DESCRIPTION
     "The value of this object corresponds directly to the type 
     of the filter. Ethernet is layer 2 filter, Ip are layer 3 filters
     (include layer 4 protocol filtering)."
 ::= { sysDevFilterConfigTableEntry 3 }

 sysDevDefFilterAction OBJECT-TYPE
   SYNTAX INTEGER {
     forward (1),
     discard (2)
   }
   ACCESS read-write
   STATUS mandatory
   DESCRIPTION
     "The value of this object corresponds to the  default action
      taken on a particular IP packet based on the filter rule.
      forward - the packet is forwarded
        discard - the packet is discarded."
 ::= { sysDevFilterConfigTableEntry 4 }

 sysDevFilterNumOfDynamicRules OBJECT-TYPE
   SYNTAX INTEGER
   ACCESS read-only
   STATUS mandatory
   DESCRIPTION
     "This object corresponds to the number of dynamic rules 
      configured for this filter. Default is zero."
 ::= { sysDevFilterConfigTableEntry 5 }
 
 sysDevFilterNumOfStaticRules OBJECT-TYPE
   SYNTAX INTEGER
   ACCESS read-only
   STATUS mandatory
   DESCRIPTION
     "This object corresponds to the number of static rules 
      configured for this filter. Default is zero"
 ::= { sysDevFilterConfigTableEntry 6 }
 
 sysDevFilterRefCount OBJECT-TYPE
   SYNTAX INTEGER
   ACCESS read-only
   STATUS mandatory
   DESCRIPTION
     "This object corresponds to the number of 
      references for this filter by the various 
      interfaces of the system
      For Example if filter 'abc' is bound to
      two of the DSL interfaces as inbound filter then
      the reference count for this filter is 2.
      Filters can be deleted from the 
      system (by a user) only if the reference count equals 0.
      (the filter is not bound to any interfaces). The default is 0."
 ::= { sysDevFilterConfigTableEntry 7 }


 sysDevFilterRowStatus OBJECT-TYPE
    SYNTAX RowStatus 
    ACCESS read-write
    STATUS mandatory
    DESCRIPTION
        "The object is used to add or delete a row from
         this table." 
 ::= { sysDevFilterConfigTableEntry 8 }

--####################################
--#  Filter Layer2 rules 
--####################################

 sysDevL2FilterRuleConfigTable OBJECT-TYPE
   SYNTAX SEQUENCE OF SysDevL2FilterRuleConfigTableEntry
   ACCESS not-accessible
   STATUS mandatory
   DESCRIPTION
     "This table allows the user to configure the rules of each IP filter.
	 When a filter is bound to an interface, all the rules of that particular 
	 filter apply to that particular interface. Also, the same filter may be
	 found to several interfaces. This table is indexed by
	 sysDevL2FilterRuleIndex."
    ::= { sysDevFilter 4 }

sysDevL2FilterRuleConfigTableEntry OBJECT-TYPE
   SYNTAX SysDevL2FilterRuleConfigTableEntry
   ACCESS not-accessible
   STATUS mandatory
   DESCRIPTION
     "Describes a specific entry of the filter rule configuration table."
   INDEX { sysDevL2FilterRuleIndex }
    ::= { sysDevL2FilterRuleConfigTable 1 }

 SysDevL2FilterRuleConfigTableEntry ::=
   SEQUENCE {
     sysDevL2FilterRuleIndex    		  INTEGER, 
     sysDevL2FilterRuleName    		  DisplayString (SIZE(1..12)),
     sysDevL2FilterRuleEtherFrameType       INTEGER,
     sysDevL2FilterRuleEtherType            INTEGER,
     sysDevL2FilterRuleEtherTypeRangeStarts INTEGER,
     sysDevL2FilterRuleEtherTypeRangeEnds   INTEGER,
     sysDevL2FilterRuleAction     	  INTEGER,
     sysDevL2FilterRuleRowStatus            RowStatus
   }

 sysDevL2FilterRuleIndex OBJECT-TYPE
   SYNTAX INTEGER
   ACCESS read-only
   STATUS mandatory
   DESCRIPTION
     "The value of this object is an index of the filter
      rule table. This object is used by sysDevFilterConfigTable
      to identify the row in the table. When creating new
      row of this table the value of this object may be
      obtained by retreiving the value of
      sysDevL2FilterRuleIndexNext."
 ::= { sysDevL2FilterRuleConfigTableEntry 1 }

 sysDevL2FilterRuleName OBJECT-TYPE
   SYNTAX  DisplayString (SIZE(1..12))
   ACCESS read-write
   STATUS mandatory
   DESCRIPTION
     "The value of this object corresponds directly to the name
     of the rule."
 ::= { sysDevL2FilterRuleConfigTableEntry 2 }

 sysDevL2FilterRuleEtherFrameType OBJECT-TYPE 
   SYNTAX INTEGER {
		    dix(1),
		    snap(2)
		  }
   ACCESS read-write
   STATUS mandatory
   DESCRIPTION
      "This value descirbes if Ethernet frame types
       defined that can be transmitted." 
 ::= { sysDevL2FilterRuleConfigTableEntry 3 }
   
 sysDevL2FilterRuleEtherType OBJECT-TYPE 
   SYNTAX INTEGER {
		    range(1),
		    singleType(2)
		  }
   ACCESS read-write
   STATUS mandatory
   DESCRIPTION
      "This value descirbes if Ethernet types
       defined in RFC1700 are specified as range
       or one single type. It is possible to create
       rule using a range of types and therefore
       next object is added to create start of the range.This
       object is the first in range and the value 
       of it has to be smaller or equal to a hex 
       Ethernet type value entered in
       sysDevL2FilterRuleEtherTypeRangeEnds. 
       If this object specifies that the value used
       is a single type than
       sysDevL2FilterRuleEtherTypeRangeEnds will
       not be considered  valid."
 ::= { sysDevL2FilterRuleConfigTableEntry 4 }
   
 sysDevL2FilterRuleEtherTypeRangeStarts OBJECT-TYPE 
   SYNTAX INTEGER 
   ACCESS read-write
   STATUS mandatory
   DESCRIPTION
      "This value corresponds to Ethernet types
       defined in RFC1700. It is possible to create
       rule using a range of types and therefore
       next object is added to create range. This
       object is the first in range and the value 
       of it has to be smaller or equal to a hex 
       Ethernet type value entered next. If the
       value of sysDevL2FilterRuleEtherType is singleType(2)
       then only this value is considered."
 ::= { sysDevL2FilterRuleConfigTableEntry 5 }
   
 sysDevL2FilterRuleEtherTypeRangeEnds   OBJECT-TYPE 
   SYNTAX INTEGER
   ACCESS read-write
   STATUS mandatory
   DESCRIPTION
      "This value corresponds to Ethernet types
       defined in RFC1700. It is possible to create
       rule using a range of types and therefore
       this object is added to create range. This
       object is the second value in the range. The value 
       of it has to be larger or equal to a hex 
       Ethernet type value entered previously. This object
       is not considered valid if the value
       of sysDevL2FilterRuleEtherType is singleType(2)."
 ::= { sysDevL2FilterRuleConfigTableEntry 6 }

 sysDevL2FilterRuleAction   OBJECT-TYPE
     SYNTAX INTEGER {
	 forward (1),
	 discard (2)
	 }
     ACCESS read-write
     STATUS mandatory
     DESCRIPTION
	"The value of this object specify the action to
	 be done if the rule is matched to a packet."
 ::= { sysDevL2FilterRuleConfigTableEntry 7 }

 sysDevL2FilterRuleRowStatus OBJECT-TYPE
    SYNTAX RowStatus 
    ACCESS read-write
    STATUS mandatory
    DESCRIPTION
        "The object is used to add or delete a row from
         this table." 
 ::= { sysDevL2FilterRuleConfigTableEntry 8 }


--####################################
--#  Filter Layer3 rules 
--####################################

 sysDevL3FilterRuleConfigTable OBJECT-TYPE
   SYNTAX SEQUENCE OF SysDevL3FilterRuleConfigTableEntry
   ACCESS not-accessible
   STATUS mandatory
   DESCRIPTION
     "This table allows the user to configure the rules for layer three filter.
	 When a filter is bound to an interface, all the rules of that particular 
	 filter apply to the specified interface. Also, the same filter may be
	 bound to several interfaces. This table is indexed by
	 sysDevL3FilterRuleIndex."
    ::= { sysDevFilter 9 }

sysDevL3FilterRuleConfigTableEntry OBJECT-TYPE
   SYNTAX SysDevL3FilterRuleConfigTableEntry
   ACCESS not-accessible
   STATUS mandatory
   DESCRIPTION
     "Describes a specific entry of the filter rule configuration table."
   INDEX { sysDevL3FilterRuleIndex }
    ::= { sysDevL3FilterRuleConfigTable 1 }

 SysDevL3FilterRuleConfigTableEntry ::=
   SEQUENCE {
     sysDevL3FilterRuleIndex    	INTEGER,
     sysDevL3FilterRuleName    		DisplayString,
     sysDevL3FilterRuleSrcAddress    	IpAddress,
     sysDevL3FilterRuleSrcAddrMask   	IpAddress,
     sysDevL3FilterRuleSrcAddrAction	INTEGER,
     sysDevL3FilterRuleSrcPortNum    	INTEGER,
     sysDevL3FilterRuleMaxSrcPortNum 	INTEGER,
     sysDevL3FilterRuleSrcCompType   	INTEGER,
     sysDevL3FilterRuleDestAddress   	IpAddress,
     sysDevL3FilterRuleDestAddrMask   	IpAddress,
     sysDevL3FilterRuleDestAddrAction	INTEGER,
     sysDevL3FilterRuleDestPortNum    	INTEGER,
     sysDevL3FilterRuleMaxDestPortNum 	INTEGER,
     sysDevL3FilterRuleDestCompType  	INTEGER,
     sysDevL3FilterRuleProtocolTypeUdp  INTEGER,
     sysDevL3FilterRuleProtocolTypeTcp  INTEGER,
     sysDevL3FilterRuleProtocolTypeIcmp INTEGER,
     sysDevL3FilterRuleRowStatus 		RowStatus
   }

 sysDevL3FilterRuleIndex OBJECT-TYPE
   SYNTAX INTEGER 
   ACCESS read-only
   STATUS mandatory
   DESCRIPTION
     "The value of this object is an index of the filter
      rule table. This object is used by sysDevFilterConfigTable
      to identify the row in the table. When creating new
      row of this table the value of this object may be
      obtained by retreiving the value of
      sysDevL3FilterRuleIndexNext."
   ::= { sysDevL3FilterRuleConfigTableEntry 1 }

 sysDevL3FilterRuleName OBJECT-TYPE
   SYNTAX  DisplayString 
   ACCESS read-write
   STATUS mandatory
   DESCRIPTION
     "The value of this object corresponds directly to the name
     of the rule. It is highly recommended that the RuleName
     be unique user friendly name."
 ::= { sysDevL3FilterRuleConfigTableEntry 2 }


 sysDevL3FilterRuleSrcAddress OBJECT-TYPE
   SYNTAX IpAddress
   ACCESS read-write
   STATUS mandatory
   DESCRIPTION
     "The value of this object corresponds directly to a source
      IP Address. This object could be set if IP packets need to be
      filtered based on where it is coming from. Setting this object
	  to 0.0.0.0 disables source IP address comparison."
   ::= { sysDevL3FilterRuleConfigTableEntry 3 }

 sysDevL3FilterRuleSrcAddrMask OBJECT-TYPE
   SYNTAX IpAddress
   ACCESS read-write
   STATUS mandatory
   DESCRIPTION
     "The value of this object corresponds directly to an source
      IP Address Mask. The value of this object is bitwise anded
      with the source address within the IP packet." 
   ::= { sysDevL3FilterRuleConfigTableEntry 4 }

 sysDevL3FilterRuleSrcAddrAction OBJECT-TYPE
   SYNTAX INTEGER {
	forward (1),
	discard (2),
	none (3)
	}
   ACCESS read-write
   STATUS mandatory
   DESCRIPTION
      "This object specifies action taken with the source address
       filtering. If the selection allows any SrcAddr (effectively 
       ignoring this filed) than 'none' (3) is valid choice for this
       object."
    ::= { sysDevL3FilterRuleConfigTableEntry 5 }

 sysDevL3FilterRuleSrcPortNum OBJECT-TYPE
   SYNTAX INTEGER 
   ACCESS read-write
   STATUS mandatory
   DESCRIPTION
     "The UDP or TCP port number of the source on which this filter 
      is applied. This object is used as a start of range if
      the source comparison type is in-range or out-range."
   ::= { sysDevL3FilterRuleConfigTableEntry 6 }

 sysDevL3FilterRuleMaxSrcPortNum OBJECT-TYPE
   SYNTAX INTEGER
   ACCESS read-write
   STATUS mandatory
   DESCRIPTION
     "The maximum UDP or TCP port number of the source on which
      this filter is applied. This object is valid only if the source 
      comparison type is in-range or out-range"
   ::= { sysDevL3FilterRuleConfigTableEntry 7 }

 sysDevL3FilterRuleSrcCompType OBJECT-TYPE
   SYNTAX INTEGER {
     none (1),
     eq (2),
     neq (3),
     gt (4),
     lt (5),
     inRange (6),
     outRange (7)
   }
   ACCESS read-write
   STATUS mandatory
   DESCRIPTION
     "The value of this object corresponds to the type of
      comparison which is to be made for source based filtering 
      for the particular rule of the filter.
        none - no comparison is to be made.
        eq - equal to
        neq - not equal to
        gt - greater than
        lt - less than
        inRange - the source port number of the TCP or UDP packet
                  is within a specified range.
        outRange - the source port number of the TCP or UDP packet
                   lies outside a specified range."
   ::= { sysDevL3FilterRuleConfigTableEntry 8 }

 sysDevL3FilterRuleDestAddress OBJECT-TYPE
   SYNTAX IpAddress
   ACCESS read-write
   STATUS mandatory
   DESCRIPTION
     "The value of this object corresponds directly to an destination
      IP Address. This object could be set if IP packets need to be
      filtered based on where it is going to."
   ::= { sysDevL3FilterRuleConfigTableEntry 9 }

 sysDevL3FilterRuleDestAddrMask OBJECT-TYPE
   SYNTAX IpAddress
   ACCESS read-write
   STATUS mandatory
   DESCRIPTION
     "The value of this object corresponds directly to an destination
      IP Address Mask. The value of this object is bitwise anded
      with the destination address within the IP packet." 
   ::= { sysDevL3FilterRuleConfigTableEntry 10 }

 sysDevL3FilterRuleDestAddrAction OBJECT-TYPE
   SYNTAX INTEGER {
	forward (1),
	discard (2),
	none (3)
	}
   ACCESS read-write
   STATUS mandatory
   DESCRIPTION
      "This object specifies action taken for destination address 
       filtering. If the selection allows any DestAddr (effectively 
       ignoring this filed) than 'none' (3) is valid choice for this
       object."
   ::= { sysDevL3FilterRuleConfigTableEntry 11 }

 sysDevL3FilterRuleDestPortNum OBJECT-TYPE
   SYNTAX INTEGER 
   ACCESS read-write
   STATUS mandatory
   DESCRIPTION
     "The UDP or TCP port number of the destination on which this filter 
      is applied. This object is used as a start of range if
      the source comparison type is in-range or out-range."
   ::= { sysDevL3FilterRuleConfigTableEntry 12 }

 sysDevL3FilterRuleMaxDestPortNum OBJECT-TYPE
   SYNTAX INTEGER 
   ACCESS read-write
   STATUS mandatory
   DESCRIPTION
     "The maximum UDP or TCP port number of the destination on which
      this filter is applied. This object is valid only if the destination
      comparison type is in-range or out-range"
   ::= { sysDevL3FilterRuleConfigTableEntry 13 }

 sysDevL3FilterRuleDestCompType OBJECT-TYPE
   SYNTAX INTEGER {
     none (1),
     eq (2),
     neq (3),
     gt (4),
     lt (5),
     inRange (6),
     outRange (7)
   }
   ACCESS read-write
   STATUS mandatory
  DESCRIPTION
    "The value of this object corresponds to the type of
     comparison which is to be made for destination based filtering 
     for the particular rule of the filter.
       none - no comparison is to be made.
       eq - equal to
       neq - not equal to
       gt - greater than
       lt - less than
       inRange - the source port number of the TCP or UDP packet
                 is within a specified range.
       outRange - the source port number of the TCP or UDP packet
                  lies outside a specified range."
   ::= { sysDevL3FilterRuleConfigTableEntry 14 }

 
 sysDevL3FilterRuleProtocolTypeUdp OBJECT-TYPE
   SYNTAX INTEGER {
     forward (1),
     discard (2),
     none (3)
     }
    ACCESS read-write
    STATUS mandatory
    DESCRIPTION
      "The value of this object corresponds to the action
      taken on a particular UDP packet based on the source/
      destination port comparison rule.
      If the selection allows any Udp packet (effectively 
      ignoring this filed) than 'none' (3) is valid choice for this
      object."
   ::= { sysDevL3FilterRuleConfigTableEntry 15 }
 
 sysDevL3FilterRuleProtocolTypeTcp OBJECT-TYPE
    SYNTAX INTEGER {
        forward (1),
        discard (2),
	none (3)
    }
    ACCESS read-write
    STATUS mandatory
    DESCRIPTION
        "The value of this object corresponds to the action
         taken on a particular TCP packet bases on the source/
         destination port comparison rule.
         If the selection allows any Tcp packet (effectively 
         ignoring this filed) than 'none' (3) is valid choice for this
         object."
   ::= { sysDevL3FilterRuleConfigTableEntry 16 }
 
 sysDevL3FilterRuleProtocolTypeIcmp OBJECT-TYPE
    SYNTAX INTEGER {
        forward (1),
        discard (2),
	none (3)
    }
    ACCESS read-write
    STATUS mandatory
    DESCRIPTION
        "The value of this object corresponds to the action
         taken on a particular ICMP packet bases on the protocol
         type comparison rule.
         If the selection allows any Icmp packet (effectively 
         ignoring this filed) than 'none' (3) is valid choice for this
         object."
   ::= { sysDevL3FilterRuleConfigTableEntry 17 }

 sysDevL3FilterRuleRowStatus OBJECT-TYPE
    SYNTAX RowStatus 
    ACCESS read-write
    STATUS mandatory
    DESCRIPTION
        "The object is used to add or delete a row from
         this table." 
   ::= { sysDevL3FilterRuleConfigTableEntry 18 }

-- Filter Bindings

 sysDevFilterBindingTable OBJECT-TYPE
   SYNTAX SEQUENCE OF SysDevFilterBindingTableEntry
   ACCESS not-accessible
   STATUS mandatory
   DESCRIPTION
     "This table allows us to bind filters to a particular interface.
      As such this table is indexed by ifIndex,
      and by sysDevFilterBindingIndex."
 ::= { sysDevFilter 5 }
 
 sysDevFilterBindingTableEntry OBJECT-TYPE
   SYNTAX SysDevFilterBindingTableEntry
   ACCESS not-accessible
   STATUS mandatory
   DESCRIPTION
     "Describes a specific entry of the filter binding table."
   INDEX { ifIndex, sysDevFilterBindingIndex, sysDevFilterBindingDirection }
 ::= { sysDevFilterBindingTable 1 }
 
 SysDevFilterBindingTableEntry ::=
   SEQUENCE {
     sysDevFilterBindingIndex         INTEGER,  
     sysDevFilterBindingDirection     INTEGER,
     sysDevFilterBindingAdminStatus   INTEGER, 
     sysDevFilterBindingOperStatus    INTEGER, 
     sysDevFilterBindingRowStatus     RowStatus
   }

 sysDevFilterBindingIndex OBJECT-TYPE
   SYNTAX INTEGER 
   ACCESS read-only
   STATUS mandatory
   DESCRIPTION
     "The value of this object corresponds directly to the 
      filter index from sysDevFilterConfigTable."
  ::= { sysDevFilterBindingTableEntry 1 }

 sysDevFilterBindingDirection OBJECT-TYPE
   SYNTAX INTEGER {
     inboundFilter (1),
     outboundFilter (2),
     inboundOutboundFilter (3)
   }
   ACCESS read-only
   STATUS mandatory
   DESCRIPTION
     "The value of this object corresponds directly to the type
      of the filter which needs to be bound to a particular interface.
        inboundFilter - This indicates that the filter is applied to the
                      packets coming in to the interface.
        outboundFilter - this indicates that the filter is applied to
                       packets going out the interface.
        inboundOutboundFilter - this indicates that the filter is applied
                       packets going out the interface and to packets
                       coming in to the interface."
 ::= { sysDevFilterBindingTableEntry 2 }

 sysDevFilterBindingAdminStatus OBJECT-TYPE
   SYNTAX INTEGER { 
		up (1),
		down (2)
	        } 
   ACCESS read-write
   STATUS mandatory
   DESCRIPTION
     "The value of this is used to configure admin status 
      of filter binding. If admin status is up(1) that means
      that the binding is active. If the status is down(2)
      it means that this binding is inactive for specified
      interface. If the filter is bound to more than one
      interface the binings on the other interfaces will
      have to be configured separately. To read this object
      use sysDevFilterBindingOperStatus."
 ::= { sysDevFilterBindingTableEntry 3 }
 
 sysDevFilterBindingOperStatus OBJECT-TYPE
   SYNTAX INTEGER { 
		up (1),
		down (2)
	        } 
   ACCESS read-write
   STATUS mandatory
   DESCRIPTION
     "The value of this is used to read oper status 
      of filter binding. If oper status is up(1) that means
      that the binding is active. If the status is down(2)
      it means that this binding is inactive for specified
      interface. To configure this object
      use sysDevFilterBindingAdminStatus."
 ::= { sysDevFilterBindingTableEntry 4 }

 sysDevFilterBindingRowStatus OBJECT-TYPE
   SYNTAX RowStatus 
   ACCESS read-write
   STATUS mandatory
   DESCRIPTION
     "This object is used to add or delete a row from this table."
 ::= { sysDevFilterBindingTableEntry 5 }

-- Filter to Rule binding table

 sysDevFilterToRuleBindingTable OBJECT-TYPE
   SYNTAX SEQUENCE OF SysDevFilterToRuleBindingTableEntry
   ACCESS not-accessible
   STATUS mandatory
   DESCRIPTION
     "This table allows us to bind filters to a particular rules.
      As such this table is indexed by sysDevFilterToRuleBindingIndex,
      and by sysDevL2FilterIndex."
 ::= { sysDevFilter 8 }
 
 sysDevFilterToRuleBindingTableEntry OBJECT-TYPE
   SYNTAX SysDevFilterToRuleBindingTableEntry
   ACCESS not-accessible
   STATUS mandatory
   DESCRIPTION
     "Describes a specific entry of the filter binding table."
   INDEX { sysDevFilterIndex, sysDevFilterToRuleBindingIndex }
 ::= { sysDevFilterToRuleBindingTable 1 }
 
 SysDevFilterToRuleBindingTableEntry ::=
   SEQUENCE {
     sysDevFilterToRuleBindingIndex         INTEGER,  
     sysDevFilterToRulePriority		    INTEGER,
     sysDevFilterToRuleBindingRowStatus     RowStatus  
     }

 sysDevFilterToRuleBindingIndex OBJECT-TYPE
   SYNTAX INTEGER 
   ACCESS read-only
   STATUS mandatory
   DESCRIPTION
     "The value of this object corresponds directly to the 
      rule index from sysDevL2FilterRuleTable."
  ::= { sysDevFilterToRuleBindingTableEntry 1 }

sysDevFilterToRulePriority  OBJECT-TYPE
    SYNTAX INTEGER
    ACCESS read-write
    STATUS mandatory
    DESCRIPTION
        "Internally the table will be sorted based on this object-
	in the increasing order of priority. The highest priority being 1.
	The table cannot be created without rules being specified.
	The table lookups will be done on the sorted table."
::= { sysDevFilterToRuleBindingTableEntry 2 }


 sysDevFilterToRuleBindingRowStatus OBJECT-TYPE
   SYNTAX RowStatus 
   ACCESS read-write
   STATUS mandatory
   DESCRIPTION
     "This object is used to add or delete a row from this table."
 ::= { sysDevFilterToRuleBindingTableEntry 3 }

 sysDevFilterIndexNext OBJECT-TYPE
   SYNTAX  INTEGER
   ACCESS  read-only 
   STATUS mandatory
   DESCRIPTION
	" This object contains an appropriate value to be
	  used for sysDevFilterConfigTable.
	  The value of 0 indicates that no unassigned 
	  entries are available.  To obtain 
	  sysDevFilterIndex value for the new entry 
	  the manager issues a management protocol retrieval 
	  operation to obtain a current value of this object.
	  After each retrieval, the agent must modify the value
	  to the next unassigned index to prevent assignment
	  of the same value to multiple management systems. A
	  management systems should repeat the read to obtain a new
	  value should an attempt to create the new row using
	  previously returned index fail. As this is a scalar object
	  if the mib walk is done on this object it would
	  return the next unused value."
 ::= { sysDevFilter 6 }

 sysDevL2FilterRuleIndexNext OBJECT-TYPE
   SYNTAX  INTEGER
   ACCESS  read-only 
   STATUS mandatory
   DESCRIPTION
	" This object contains an appropriate value to be
	  used for sysDevL2FilterRuleConfigTable.
	  The value of 0 indicates that no unassigned 
	  entries are available.  To obtain 
	  sysDevL2FilterRuleIndex value for the new entry 
	  the manager issues a management protocol retrieval 
	  operation to obtain a current value of this object.
	  After each retrieval, the agent must modify the value
	  to the next unassigned index to prevent assignment
	  of the same value to multiple management systems. A
	  management systems should repeat the read to obtain a new
	  value should an attempt to create the new row using
	  previously returned index fail. As this is a scalar object
	  if the mib walk is done on this object it would
	  return the next unused value."
 ::= { sysDevFilter 7 }

 sysDevL3FilterRuleIndexNext OBJECT-TYPE
   SYNTAX  INTEGER
   ACCESS  read-only 
   STATUS mandatory
   DESCRIPTION
	" This object contains an appropriate value to be
	  used for sysDevL3FilterRuleConfigTable.
	  The value of 0 indicates that no unassigned 
	  entries are available.  To obtain 
	  sysDevL3FilterRuleIndex value for the new entry 
	  the manager issues a management protocol retrieval 
	  operation to obtain a current value of this object.
	  After each retrieval, the agent must modify the value
	  to the next unassigned index to prevent assignment
	  of the same value to multiple management systems. A
	  management systems should repeat the read to obtain a new
	  value should an attempt to create the new row using
	  previously returned index fail. As this is a scalar object
	  if the mib walk is done on this object it would
	  return the next unused value."
 ::= { sysDevFilter 10 }
--
-- Traps
--

 sysDevSNInjectionFailureTrap  TRAP-TYPE
  ENTERPRISE sysDevFilterMIBTraps
  VARIABLES {ifIndex, sysDevSNInjectionVnid, sysDevSNInjectionType }
  DESCRIPTION
   "This trap signifies that the injection of filters to SN failed
    It is of warning class"
  ::= 22

 sysDevSNInjectionIncompatibleTrap  TRAP-TYPE
  ENTERPRISE sysDevFilterMIBTraps
  VARIABLES {ifIndex, sysDevSNInjectionVnid, sysDevSNInjectionType }
  DESCRIPTION
   "This trap signifies that the injection of filters is not supported
    by the SN. It is of warning class"
  ::= 23

END

PDN-INET-MIB DEFINITIONS ::= BEGIN

-- Version :  1.1 APPROVED
-- Enterprise Inet mib
-- Copyright (C) 2000 Paradyne Corporation.

 
IMPORTS
Integer32,IpAddress,
OBJECT-TYPE, MODULE-IDENTITY
FROM SNMPv2-SMI
ifIndex
  FROM RFC1213-MIB
RowStatus
  FROM SNMPv2-TC
pdn-common
  FROM PDN-HEADER-MIB
;

pdn-inet MODULE-IDENTITY
   LAST-UPDATED    "0202210000Z"
   ORGANIZATION    "Paradyne Corporation
		    MIB Working Group"

   CONTACT-INFO    "Paradyne Corporation
		    8545 126th Avenue North
		    Largo, FL 33733
		    www.paradyne.com

		    General Comments to: mibwg_team@paradyne.com

		    Editors
		    Prakash Easwar
		    Dragana Gough"

  DESCRIPTION
     "This mib is used to configure ip address of some interface"

   REVISION "0202210000Z"
   DESCRIPTION "Changed to SMIv2" 

   REVISION "0005100000Z "
   DESCRIPTION "changed pdnInetIpSubnetMask to read-write"

   REVISION "0004270000Z"
   DESCRIPTION "removed pdnInetIpSubnetMask from the INDEX clause for
   		pdnInetIpAddressTable"

   ::= { pdn-common 26 }



pdnInetMIBObjects OBJECT IDENTIFIER ::= { pdn-inet 1 }
pdnInetMIBTraps   OBJECT IDENTIFIER ::= { pdn-inet 2 }

pdnInetTelnetServerPort OBJECT-TYPE
  SYNTAX INTEGER (1..65535)
  MAX-ACCESS read-write
  STATUS current
  DESCRIPTION
     "This object contains the telnet server (daemon) tcp
      port number."
  DEFVAL { 23 }
::= { pdnInetMIBObjects 1 }

pdnInetFtpServerControlPort OBJECT-TYPE
  SYNTAX INTEGER (1..65535)
  MAX-ACCESS read-write
  STATUS current
  DESCRIPTION
     "This object contains the ftp server control (daemon) tcp
      port number."
  DEFVAL { 21 }
::= { pdnInetMIBObjects 2 }

pdnInetFtpServerDataPort OBJECT-TYPE
  SYNTAX INTEGER (1..65535)
  MAX-ACCESS read-write
  STATUS current
  DESCRIPTION
     "This object contains the ftp server data connection tcp
      port number."
  DEFVAL { 20 }
::= { pdnInetMIBObjects 3 }
 
pdnInetIpAddressTableMaxIpSubnets OBJECT-TYPE
  SYNTAX Integer32
  MAX-ACCESS read-only
  STATUS current
  DESCRIPTION
    "This object  indicates the maximum number of entries in
     the pdnInetAddressTable"
::= { pdnInetMIBObjects 4 }

pdnInetIpAddressTableCurrentIpSubnets OBJECT-TYPE
  SYNTAX Integer32
  MAX-ACCESS read-only
  STATUS current
  DESCRIPTION
    "This object  indicates the number of entries configured in
     the pdnInetAddressTable"
::= { pdnInetMIBObjects 5 }
 
pdnInetIpAddressTable OBJECT-TYPE
  SYNTAX SEQUENCE OF PdnInetIpAddressTableEntry
  MAX-ACCESS  not-accessible
  STATUS  current
  DESCRIPTION
    "This table used to configure ipaddresses for an interface
     which support the internet (IP) protocol"
::= { pdnInetMIBObjects 6 }
 
pdnInetIpAddressTableEntry OBJECT-TYPE
  SYNTAX  PdnInetIpAddressTableEntry
  MAX-ACCESS  not-accessible
  STATUS  current
  DESCRIPTION
    "This object corresponds to an entry in the IP address table."
  INDEX { ifIndex, pdnInetIpAddress }
::= { pdnInetIpAddressTable 1 }

PdnInetIpAddressTableEntry ::=
  SEQUENCE
  {
    pdnInetIpAddress IpAddress,
    pdnInetIpSubnetMask IpAddress,
    pdnInetIpAddressType INTEGER,
    pdnInetIpRowStatus RowStatus,
    pdnInetIpGateway IpAddress
  }
 
pdnInetIpAddress OBJECT-TYPE
  SYNTAX IpAddress
  MAX-ACCESS not-accessible
  STATUS current
  DESCRIPTION
    "This object is used to configure an IP address for an interface"
::= { pdnInetIpAddressTableEntry 1 }

pdnInetIpSubnetMask OBJECT-TYPE
  SYNTAX IpAddress
  MAX-ACCESS read-create
  STATUS current
  DESCRIPTION
    "This object is used to configure an IP subnet mask for an interface.
	  subnet mask should result in contiguous subnets"
::= { pdnInetIpAddressTableEntry 2 }

pdnInetIpAddressType OBJECT-TYPE
  SYNTAX INTEGER { primary (1),
		  secondary(2),
		  primaryBootp(3),
		  secondaryBootp(4)
		  }
	
  MAX-ACCESS read-create
  STATUS current
  DESCRIPTION
    "This object is used to configure the address type for an interface
	  an interface can have only one primary ip address and more than one
	  secondary ip address. the primary ip address is essentially the
	  router ID. The secondary ip address would result in the interface
	  being multi-homed. The default value is primary type."
::= { pdnInetIpAddressTableEntry 3 }

pdnInetIpRowStatus OBJECT-TYPE
  SYNTAX RowStatus
  MAX-ACCESS read-create
  STATUS current
  DESCRIPTION
    "This object is used to manage rows (add/delete/modify) in this table"
::= { pdnInetIpAddressTableEntry 4 }

pdnInetIpGateway  OBJECT-TYPE
  SYNTAX IpAddress
  MAX-ACCESS read-create
  STATUS current
  DESCRIPTION
    "This object is used to configure an gateway for an interface."
::= { pdnInetIpAddressTableEntry 5 }
END

--
-- Copyright (C) 2003 Paradyne Corporation.
--
PDN-SYSLOG-MIB DEFINITIONS ::= BEGIN 

IMPORTS 
	MODULE-IDENTITY, OBJECT-TYPE, Integer32, IpAddress
	 FROM SNMPv2-SMI
	entPhysicalIndex
	FROM ENTITY-MIB
	MODULE-COMPLIANCE, OBJECT-GROUP
        FROM SNMPv2-CONF
	pdn-syslog
          FROM PDN-HEADER-MIB; 

    pdnSyslog MODULE-IDENTITY 
        LAST-UPDATED "200302130000Z" -- February 13, 2003
        ORGANIZATION "Paradyne Networks
                      MIB Working Group"
                     
        CONTACT-INFO "Paradyne Networks, Inc. 
                      8545 126th Avenue North 
                      Largo, FL 33733 
                      www.paradyne.com 
		      
                      General Comments to: mibwg_team@eng.paradyne.com 
                      Editor: Dragana Gough 	- Original Author
		      Editor: Mike Himelstein 	- Updated Mib
		      Editor: Jesus Pinto 	- Updated Mib
                      " 
	DESCRIPTION "1)Added pdnEntitySyslogTable to be used for entities
	             2)Added conformance statements."
        REVISION "200302130000Z" -- February 13, 2003

	DESCRIPTION "4 changes:
	             1)Add to the description of pdnSyslogIpAddr
	             2)Rewording the description of pdnSyslogNumber.
	             3)Expanding the pdnSyslogMessage size from 255 to
			       1024
		     4)Adding a new object: pdnSyslogRateLimiting"
		     
        REVISION "200111150000Z" -- November 15, 2001
	DESCRIPTION "Changing pdn-common 31 to pdn-syslog 1"
        REVISION "200104100000Z" -- October 4, 2001
        DESCRIPTION 
	     "Added new object pdnSyslogMsgToConsole, and
	      changed comments to reflects the change status of a referenced
	      ietf draft. This draft ( draft-ietf-syslog-syslog-12)
	      is now RFC 3164."

        REVISION "200108090000Z" -- August 9, 2001
        DESCRIPTION 
	    "This mib defines a collection of objects  for managing 
	     syslog messages.  The objects are used to configure both syslog 
	     functions and syslog daemons.
	     This mib also allows one to retrieve syslog message
	     from a device. 
             The modifications to this mib include
	     * making mib snmp v2
	     * deprecated pdnSyslogLevel
             * adding pdnSyslogSeverityThreshold
             * adding pdnSyslogRemoteDaemon
             * adding pdnSyslogTable
             * adding pdnSyslogNumOfMsgInTable 
             * adding pdnSyslogMaxTableSize
             * adding pdnSyslogClearTable"

        REVISION "200004240000Z" -- April 24, 2000
        DESCRIPTION "Editor: Dragana Gough
                     Initial Version" 
        REVISION "200002050000Z"   -- May 02, 2000
        DESCRIPTION "Editor: Dragana Gough
                     Updated OBJECT IDENTIFIER to pdn-syslog" 
	::= { pdn-syslog 1 }

pdnSyslogConformance OBJECT IDENTIFIER ::= 
	{ pdn-syslog 14 }

--+++++++++++++++++++++++++++++++++++++++++++++++++++++++++++++++++++++++++++++

-- Syslog Configuration Group
pdnSyslogStatus  OBJECT-TYPE
    SYNTAX       INTEGER { disable (1), enable (2) }
    MAX-ACCESS   read-write
    STATUS       current
    DESCRIPTION
		 " This value allows user to
		 disable or enable syslog event generation. "
    ::= { pdnSyslog 1 }

pdnSyslogIPAddr  OBJECT-TYPE
    SYNTAX       IpAddress
    MAX-ACCESS   read-write
    STATUS       current
    DESCRIPTION
		 " This value is the IP address of a syslog server.
		 If the ip address is known then this can be used for
		 the remote syslog daemon" 
    ::= { pdnSyslog 2 }

-- The following object has been deprecated
-- It is still valid on older products that use this mib, 
--     i.e. DSL Router endpoints
-- All new products should use pdnSyslogSeverityThreshold which uses 
-- the severity values in the RFC 3164

pdnSyslogLevel   OBJECT-TYPE
    SYNTAX       INTEGER 
                 {  emerg (1), err   (2), norm  (3), info  (4) }
    MAX-ACCESS   read-write
    STATUS       deprecated
    DESCRIPTION
		" This value corresponds to a minimum severity level
		of events that will be logged.  "
    DEFVAL { norm }
    ::= { pdnSyslog 3 }

    
pdnSyslogPort    OBJECT-TYPE
    SYNTAX       Integer32 
    MAX-ACCESS   read-write
    STATUS       current
    DESCRIPTION
		 "This value corresponds to a UDP port number to which
		  system events are sent. The default is 514. "
    DEFVAL { 514 }
    ::= { pdnSyslog 4 }

-- The extension to this mib are below, they include the 
-- * pdnSyslogSeverityThreshold
-- * pdnSyslogRemoteDaemon
-- * pdnSyslogTable
-- * pdnSyslogNumOfMsgInTable 
-- * pdnSyslogMaxTableSize
-- * pdnSyslogClearTable
-- * pdnSyslogMsgToConsole 
	
pdnSyslogSeverityThreshold OBJECT-TYPE
    SYNTAX       INTEGER 
                 { 
                    emerg     (0),
                    alert     (1),
                    critical  (2),
                    error     (3),
                    warning   (4),
                    notice    (5),
                    info      (6),
                    debug     (7)
		 }
    MAX-ACCESS   read-write
    STATUS       current
    DESCRIPTION
		"This value corresponds to a minimum severity level
		 that a syslog messages can be set.  All syslog message
		 with an enum value greater than the threshold will not be
		 sent.  The values are obtain from the 
		 RFC 3164 The BSD Syslog Protocol:
		 
		 emerg    (0) - Emergency: system is unusable
		 alert    (1) - Alert: action must be taken immediately
		 critical (2) - Critical: critical conditions
		 error    (3) - Error: error conditions 
		 warning  (4) - Warning: warning conditions
		 notice   (5) - Notice: normal but significant condition
		 info     (6) - Informational: informational messages
		 debug    (7) - Debug: debug-level messages

		 For a more complete description of the severity levels, 
		 please reference your Operation Specification Manual
		 for details pertaining to that product."
    ::= { pdnSyslog 5 }

pdnSyslogRemoteDaemon OBJECT-TYPE
    SYNTAX       INTEGER { disable (1), enable (2) }
    MAX-ACCESS   read-write
    STATUS       current
    DESCRIPTION
		 "This value allows user to
		  disable or enable syslog messages going to a remote daemon."
    ::= { pdnSyslog 6 }
 
--
-- Syslog Table and supporting objects.
--

pdnSyslogTable   OBJECT-TYPE
    SYNTAX       SEQUENCE OF PdnSyslogEntry
    MAX-ACCESS   not-accessible
    STATUS       current
    DESCRIPTION
                 "This table supports retrieval of the syslog messages."
    ::= { pdnSyslog 7 }

pdnSyslogEntry   OBJECT-TYPE 
    SYNTAX       PdnSyslogEntry
    MAX-ACCESS   not-accessible
    STATUS       current
    DESCRIPTION
	        "An entry in the pdnSyslogTable."
    INDEX { pdnSyslogNumber }
    ::= { pdnSyslogTable 1 }

PdnSyslogEntry ::=
    SEQUENCE
    {
	pdnSyslogNumber        Integer32,
	pdnSyslogMessage       OCTET STRING
    }

pdnSyslogNumber  OBJECT-TYPE
    SYNTAX       Integer32
    MAX-ACCESS   not-accessible
    STATUS       current
    DESCRIPTION
	         "This is a sequentially increasing index of syslog messages
                  starting at 1.  When the table reaches its maximum size
		  (as defined by pdnSyslogMaxTableSize) then the oldest 
		  message will be dropped without renumbering any messages 
		  that remain.  The index is reset to 1 on a device reset or 
		  when the table is cleared (using pdnSyslogClearTable)."	
    ::= { pdnSyslogEntry 1}

pdnSyslogMessage OBJECT-TYPE
    SYNTAX       OCTET STRING(SIZE(1024))
    MAX-ACCESS   read-only
    STATUS       current
    DESCRIPTION
		 "The text of the syslog message."
    ::= { pdnSyslogEntry 2 }

--
-- Entity syslog table and supporting objects.
--
-- This table should be used in a system that
-- needs to clasify syslog messages per entities.
--

pdnEntitySyslogTable   OBJECT-TYPE
    SYNTAX       SEQUENCE OF PdnEntitySyslogEntry
    MAX-ACCESS   not-accessible
    STATUS       current
    DESCRIPTION
        "This table supports retrieval of the syslog messages.
	Each entry corresponds to a message being generated by
	(or on behalf of) an entity (e.g. port card)."

    ::= { pdnSyslog 13 }

pdnEntitySyslogEntry   OBJECT-TYPE 
    SYNTAX       PdnEntitySyslogEntry
    MAX-ACCESS   not-accessible
    STATUS       current
    DESCRIPTION
	        "An entry in the pdnEntitySyslogTable "
    INDEX { entPhysicalIndex, pdnEntitySyslogNumber }
    ::= { pdnEntitySyslogTable 1 }

PdnEntitySyslogEntry ::=
    SEQUENCE
    {
	pdnEntitySyslogNumber        Integer32,
	pdnEntitySyslogMessage       OCTET STRING
    }

pdnEntitySyslogNumber  OBJECT-TYPE
    SYNTAX       Integer32
    MAX-ACCESS   not-accessible
    STATUS       current
    DESCRIPTION
	         "This is a sequentially increasing index of syslog messages
                  starting at 1.  When the table reaches its maximum size
		  (as defined by pdnSyslogMaxTableSize) then the oldest 
		  message will be dropped without renumbering any messages 
		  that remain.  The index is reset to 1 on a device reset or 
		  when the table is cleared (using pdnSyslogClearTable)."	
    ::= { pdnEntitySyslogEntry 1}

pdnEntitySyslogMessage OBJECT-TYPE
    SYNTAX       OCTET STRING(SIZE(1024))
    MAX-ACCESS   read-only
    STATUS       current
    DESCRIPTION
		 "The text of the syslog message."
    ::= { pdnEntitySyslogEntry 2 }



pdnSyslogNumOfMsgInTable OBJECT-TYPE 
    SYNTAX       Integer32 
    MAX-ACCESS   read-only
    STATUS       current 
    DESCRIPTION
                 "This value let the users know how many syslog messages are
		  currently in the syslog table."
    ::= { pdnSyslog 8 }

pdnSyslogMaxTableSize OBJECT-TYPE 
    SYNTAX       Integer32 
    MAX-ACCESS   read-only
    STATUS       current 
    DESCRIPTION
                 "The maximum number of syslog message the syslog table
		 can hold."
    ::= { pdnSyslog 9 }

pdnSyslogClearTable OBJECT-TYPE 
    SYNTAX       INTEGER { noOp(1), clear(2) }
    MAX-ACCESS   read-write
    STATUS       current 
    DESCRIPTION
                 "Clears all the entries in the syslog message table."
    ::= { pdnSyslog 10 }

pdnSyslogMsgToConsole OBJECT-TYPE 
    SYNTAX       INTEGER { disable (1), enable (2) }
    MAX-ACCESS   read-write
    STATUS       current 
    DESCRIPTION
                 "This allows messages to be sent to the device's console port.
		  Note this is intended for debug use only!
		  It is not recommended to be used to monitor syslog message
		  on a regular bases.  If one needs to constantly monitor 
		  the syslog messages, then they should use the remote syslog 
		  daemon, or other user interfaces."
    ::= { pdnSyslog 11 }

pdnSyslogRateLimiting OBJECT-TYPE 
    SYNTAX       INTEGER { disable (1), enable (2) }
    MAX-ACCESS   read-write
    STATUS       current 
    DESCRIPTION
                 "This allows one to enable or disable rate limitiming. When
		  rate limiting is enabled, it prevents the exact same message 
		  from being resent within a fixed amount of time.  "
    ::= { pdnSyslog 12 }

--
-- Conformance Information
--

pdnSyslogCompliances OBJECT IDENTIFIER
     ::= { pdnSyslogConformance 1 }

pdnSyslogGroups OBJECT IDENTIFIER
     ::= { pdnSyslogConformance 2 }

pdnSyslogCompliance MODULE-COMPLIANCE
     STATUS  current
     DESCRIPTION
             "The compliance statement for configurable
	      attributes for syslog manager."
     MODULE
     MANDATORY-GROUPS {	pdnSyslogGroup }

     OBJECT pdnSyslogStatus
     MIN-ACCESS read-only
     DESCRIPTION
	     "Write access is not required."

     OBJECT pdnSyslogIPAddr
     MIN-ACCESS read-only
     DESCRIPTION
	     "Write access is not required."

     OBJECT pdnSyslogPort
     MIN-ACCESS read-only
     DESCRIPTION
	     "Write access is not required."

     OBJECT pdnSyslogSeverityThreshold
     MIN-ACCESS read-only
     DESCRIPTION
	     "Write access is not required."

     OBJECT pdnSyslogRemoteDaemon
     MIN-ACCESS read-only
     DESCRIPTION
	     "Write access is not required."

     OBJECT pdnSyslogClearTable
     MIN-ACCESS read-only
     DESCRIPTION
	     "Write access is not required."

     OBJECT pdnSyslogMsgToConsole
     MIN-ACCESS read-only
     DESCRIPTION
	     "Write access is not required."

     OBJECT pdnSyslogRateLimiting
     MIN-ACCESS read-only
     DESCRIPTION
	     "Write access is not required."

-- Optional groups

     GROUP pdnSyslogOptionalGroup
     DESCRIPTION
	     "Implementation of this group is optional for the
	      syslog manager implementation."

     ::= { pdnSyslogCompliances 1 }

-- units of conformance

pdnSyslogGroup	OBJECT-GROUP
     OBJECTS
     {
	pdnSyslogStatus,
	pdnSyslogIPAddr,
	pdnSyslogPort,
	pdnSyslogSeverityThreshold,
	pdnSyslogRemoteDaemon,
	pdnSyslogMessage,
	pdnSyslogNumOfMsgInTable,
	pdnSyslogMaxTableSize,
	pdnSyslogClearTable,
	pdnSyslogMsgToConsole,
	pdnSyslogRateLimiting
     }
     STATUS current
     DESCRIPTION
             "A collection of objects that permits configuration
              and display of syslog messages generated."
     ::= { pdnSyslogGroups 1 }

pdnSyslogOptionalGroup	OBJECT-GROUP
     OBJECTS
     {
	pdnEntitySyslogMessage
     }	
     STATUS current
     DESCRIPTION
             " A collection of syslog messages classified 
	      per entities."
     ::= { pdnSyslogGroups 2 }

pdnSyslogDeprecatedGroup OBJECT-GROUP
	OBJECTS
	{
	  pdnSyslogLevel
	}
	STATUS deprecated
	DESCRIPTION
		"Objects being deprecated should be added to this group"
       ::= {pdnSyslogGroups 3 }

END 

-- ===============================================================
-- Copyright (C) 2003 Paradyne Corporation.
-- ===============================================================

PDN-UPLINK-TAGGING-MIB DEFINITIONS ::= BEGIN

IMPORTS
    MODULE-IDENTITY, OBJECT-TYPE, Unsigned32
        FROM SNMPv2-SMI
    OBJECT-GROUP
        FROM SNMPv2-CONF
    VlanId
        FROM Q-BRIDGE-MIB
    pdn-common
        FROM PDN-HEADER-MIB;
        
pdnUplinkTagging MODULE-IDENTITY
    LAST-UPDATED "200303120000Z"  -- March 12, 2003
    ORGANIZATION "Paradyne Networks
                  MIB Working Group
                  Other information about group editing the MIB"
    CONTACT-INFO "Paradyne Networks, Inc.
                  8545 126th Avenue North
                  Largo, FL 33733
                  www.paradyne.com
        
                  General Comments to: mibwg_team@paradyne.com

                  Editors
                        Clay Sikes"

    DESCRIPTION
        "This MIB contains objects that are used to configure Uplink Tagging (ULT). 
        Uplink Tagging is a term used to describe a feature that simplifies the
        setup and administration of networks where a service provider wants to
        use a unique VLAN per subscriber port. Ingress frames will get tagged
        with a VLAN and these tagged frame will be transmitted on the uplink port
        towards the WAN.

        In cases where the hardware implementation permits, multiple units can be
        interconnected together to form a 'Uplink Tagging Domain (ULT Domain)'. A ULT
        domain is defined as the set of interconnected Paradyne DSLAMs that share a 
        common block of VLAN IDs. The maximum number of Paradyne DSLAMs that can be 
        interconnected is implementation dependent. Generally, all DSLAMs in a ULT
        Domain will be configured with the same block of VLAN IDs. Each chassis/unit
        will be assigned a unique ULT Index within the ULT Domain.

        There are two parts of configuring Uplink Tagging:
        1. Uplink Base VLAN Tag - This object specifies the beginning VLAN ID for a
                                  particular common block of VLAN IDs. This object 
                                  will be defined as an enumeration whose values will
                                  depend on the number of port in a chassis/unit.
        2. Uplink Tag Index     - This object specifies the index within some block
                                  of VLAN IDs. Generally, this index can thought of a
                                  chassis/unit number as can be seen with the examples
                                  below."

        
    REVISION "200303120000Z"  -- March 12, 2003
    DESCRIPTION "Deprecated the origional objects, ultBaseVlanTag and
                ultIndex. Added new objects as follows:
                1. pdnUltIndex         - This new object is basically an Unsigned32
                                         that excludes '0'. It idea is that different
                                         implementations will support different maximum
                                         values of the index. As such, the syntax for
                                         this object will cover any implementation and
                                         actual implementation specific maximum values 
                                         should be documented in something like the 
                                         implementation's SNMP Op Spec.
               2. pdnGenUltBaseVlanTag - This object allows a any base VLAN Tag to
                                         be defined.
               3. pdn48UltBaseVlanTag  - This object defines a set of enumerations
                                         for base VLAN Tags for chassis/units that
                                         contain 48 ports. 
               4. pdn24UltBaseVlanTag  - This object defines a set of enumerations
                                         for base VLAN Tags for chassis/units that
                                         contain 24 ports."

    REVISION "200205150000Z"  -- May 15, 2002
    DESCRIPTION "Initial Release."

::=  { pdn-common 37 }

-- Base in the MIB Module for all objects.
pdnUplinkTaggingObjects OBJECT IDENTIFIER ::= { pdnUplinkTagging 1 }

-- Objects for Rev 2 of this MIB
pdnUplinkTaggingObjectsR2 OBJECT IDENTIFIER ::= { pdnUplinkTagging 3 }




-- Uplink Tagging (ULT) Index
pdnUltIndex     OBJECT-TYPE
    SYNTAX      Unsigned32(1..4294967295)
    MAX-ACCESS  read-write
    STATUS      current
    DESCRIPTION "This object represents VLAN tag index which is an
                index into a block of VLAN Tags the unit will use. Generally,
                this can be also thought of as the chassis/unit number in the
                case where multiple units are interconnected and form a 
                ULT Domain described above.

                It is strongly encouraged that the upper limit for
                a particular implementation be clearly documented in the
                product's SNMP Op Spec."
    DEFVAL      { 1 }
    ::= { pdnUplinkTaggingObjectsR2 1 }

-- Generic Uplink Tagging Base (ULT) VLAN Tag not related to the
-- number of ports that exist in a chassis/unit.
pdnGenUltBaseVlanTag     OBJECT-TYPE
    SYNTAX      VlanId
    MAX-ACCESS  read-write
    STATUS      current
    DESCRIPTION "This object can be used to allow any Uplink
                Tagging Base Index to be entered when they
                don't like the 'canned' list defined in the
                objects below."
    DEFVAL      { 16 }
    ::= { pdnUplinkTaggingObjectsR2 2 }

-- Uplink Tagging Base (ULT) VLAN Tag for 48 Port Units
pdn48UltBaseVlanTag  OBJECT-TYPE
    SYNTAX      INTEGER {
                                      -- Base VLAN Tag
                    ultBase16(1),     -- 16    (0x0010)
                    ultBase512(2),    -- 512   (0x0200)
                    ultBase1024(3),   -- 1024  (0x0400)
                    ultBase1536(4),   -- 1536  (0x0600)
                    ultBase2048(5),   -- 2048  (0x0800)
                    ultBase2560(6),   -- 2560  (0x0A00)
                    ultBase3072(7),   -- 3072  (0x0C00)
                    ultBase3584(8)    -- 3584  (0x0E00)
                }
    MAX-ACCESS  read-write
    STATUS      current
    DESCRIPTION "This object represents Uplink Tagging base index which
                is the starting VLAN ID for a particular common block
                of VLAN IDs for chassis/units that contain 48 DSL 
                subscriber ports."
    DEFVAL      { ultBase16 }
    ::= { pdnUplinkTaggingObjectsR2 3 }

-- *********************************************************************************
-- The following table summarizes the range of VLAN tags in a stack where
-- each unit supports 48 ports and up to 5 stacked units are supported:
--     ULT Base VLAN Tag       Subscriber VLAN Port Tags (units 1 through 5)
--
--     16      (0x0010)        16    -   255
--     512     (0x0200)        512   -   751
--     1024    (0x0400)        1024  -  1263
--     1536    (0x0600)        1536  -  1775
--     2048    (0x0800)        2048  -  2287
--     2560    (0x0A00)        2560  -  2799
--     3072    (0x0C00)        3072  -  3311
--     3584    (0x0E00)        3584  -  3823
--
--
-- The following table shows the tags for each unit in a stack:
--    Note that the unit number equates to the ULT Index.
--
--    Base             Unit 1      Unit 2       Unit 3       Unit 4       Unit 5
--    Vlan Tag         ULT Tags    ULT Tags     ULT Tags     ULT Tags     ULT Tags
--
--      16  (0x0010)     16-63       64-111      112-159      160-207      208-255      
--     512  (0x0200)    512-559     560-607      608-655      656-703      704-751
--    1024  (0x0400)   1024-1071   1072-1119    1120-1167    1168-1215    1216-1263
--    1536  (0x0600)   1536-1583   1584-1631    1632-1679    1680-1727    1728-1775
--    2048  (0x0800)   2048-2095   2096-2143    2144-2191    2192-2239    2240-2287
--    2560  (0x0A00)   2560-2607   2608-2655    2656-2703    2704-2751    2752-2799
--    3072  (0x0C00)   3072-3119   3120-3167    3168-3215    3216-3263    3264-3311
--    3584  (0x0E00)   3584-3631   3632-3679    3680-3727    3728-3775    3776-3823
-- **********************************************************************************


-- Uplink Tagging Base (ULT) VLAN Tag for 24 Port Units
pdn24UltBaseVlanTag  OBJECT-TYPE
    SYNTAX      INTEGER {
                                      -- Base VLAN Tag
                    ultBase16(1),     -- 16    (0x0010)
                    ultBase256(2),    -- 126   (0x0100)
                    ultBase512(3),    -- 512   (0x0200)
                    ultBase768(4),    -- 768   (0x0300)
                    ultBase1024(5),   -- 1024  (0x0400)
                    ultBase1280(6),   -- 1280  (0x0500)
                    ultBase1536(7),   -- 1536  (0x0600)
                    ultBase1792(8),   -- 1792  (0x0700)
                    ultBase2048(9),   -- 2048  (0x0800)
                    ultBase2304(10),  -- 2304  (0x0900)
                    ultBase2560(11),  -- 2560  (0x0A00)
                    ultBase2816(12),  -- 2816  (0x0B00)
                    ultBase3072(13),  -- 3072  (0x0C00)
                    ultBase3328(14),  -- 3328  (0x0D00)
                    ultBase3584(15),  -- 3584  (0x0E00)
                    ultBase3840(16)   -- 3840  (0x0F00)
                }
    MAX-ACCESS  read-write
    STATUS      current
    DESCRIPTION "This object represents Uplink Tagging base index which
                is the starting VLAN ID for a particular common block
                of VLAN IDs for chassis/units that contain 24 DSL 
                subscriber ports."
    DEFVAL      { ultBase16 }
    ::= { pdnUplinkTaggingObjectsR2 4 }

-- **********************************************************************************
-- The following table summarizes the range of VLAN tags in a stack where
-- each unit supports 24 ports and up to 10 stacked units are supported:
--
--     ULT Base VLAN Tag       Subscriber VLAN Port Tags (units 1 through 10)
--
--     16      (0x0010)        16    -   255
--     256     (0x0100)        256   -   495
--     512     (0x0200)        512   -   751
--     768     (0x0300)        768   -  1007 
--     1024    (0x0400)        1024  -  1263
--     1280    (0x0500)        1280  -  1519
--     1536    (0x0600)        1536  -  1775
--     1792    (0x0700)        1792  -  2031
--     2048    (0x0800)        2048  -  2287
--     2304    (0x0900)        2304  -  2543
--     2560    (0x0A00)        2560  -  2799
--     2816    (0x0B00)        2816  -  3057
--     3072    (0x0C00)        3072  -  3311
--     3328    (0x0D00)        3328  -  3567
--     3584    (0x0E00)        3584  -  3823
--     3840    (0x0F00)        3840  -  4079
--
--
-- The following table shows the tags for each unit in a stack:
--
--    Note that the unit number equates to the ULT Index.
--
--    Base             Unit 1      Unit 2       Unit 3       Unit 4       Unit 5
--    Vlan Tag         ULT Tags    ULT Tags     ULT Tags     ULT Tags     ULT Tags
--
--      16  (0x0010)     16-39       40-63        64-87        88-111      112-135
--     256  (0x0100)    256-279     280-303      304-327      328-351      352-375
--     512  (0x0200)    512-535     536-559      560-583      584-607      608-631
--     768  (0x0300)    768-791     792-815      816-839      840-863      864-887
--    1024  (0x0400)   1024-1047   1048-1071    1072-1095    1096-1119    1120-1143
--    1280  (0x0500)   1280-1303   1304-1327    1328-1351    1352-1375    1376-1399
--    1536  (0x0600)   1536-1559   1560-1583    1584-1607    1608-1631    1632-1655
--    1792  (0x0700)   1792-1815   1816-1839    1840-1863    1864-1887    1888-1911
--    2048  (0x0800)   2048-2071   2072-2095    2096-2119    2120-2143    2144-2167
--    2304  (0x0900)   2304-2327   2328-2351    2352-2375    2376-2399    2400-2423
--    2560  (0x0A00)   2560-2583   2584-2607    2608-2631    2632-2655    2656-2679
--    2816  (0x0B00)   2816-2839   2840-2863    2864-2887    2888-2911    2912-2935
--    3072  (0x0C00)   3072-3095   3096-3119    3120-3143    3144-3167    3168-3191
--    3328  (0x0D00)   3328-3351   3352-3375    3376-3399    3400-3423    3424-3447
--    3584  (0x0E00)   3584-3607   3608-3631    3632-3655    3656-3679    3680-3703
--    3840  (0x0F00)   3840-3863   3864-3887    3888-3911    3912-3935    3936-3959
--
--    Base             Unit 6      Unit 7       Unit 8       Unit 9       Unit 10
--    Vlan Tag         ULT Tags    ULT Tags     ULT Tags     ULT Tags     ULT Tags
--
--      16  (0x0010)    136-159     160-183      184-207      208-231      232-255
--     256  (0x0100)    376-399     400-423      424-447      448-471      472-495
--     512  (0x0200)    632-655     656-679      680-703      704-727      728-751
--     768  (0x0300)    888-911     912-935      936-959      960-983      984-1007
--    1024  (0x0400)   1144-1167   1168-1191    1192-1215    1216-1239    1240-1263
--    1280  (0x0500)   1400-1423   1424-1447    1448-1471    1472-1495    1496-1519
--    1536  (0x0600)   1656-1679   1680-1703    1704-1727    1728-1751    1752-1775
--    1792  (0x0700)   1912-1935   1936-1959    1960-1983    1984-2007    2008-2031
--    2048  (0x0800)   2168-2191   2192-2215    2216-2239    2240-2263    2264-2287
--    2304  (0x0900)   2424-2447   2448-2471    2472-2495    2496-2519    2520-2543
--    2560  (0x0A00)   2680-2703   2704-2727    2728-2751    2752-2775    2776-2799
--    2816  (0x0B00)   2936-2959   2960-2983    2984-3007    3008-3033    3034-3057
--    3072  (0x0C00)   3192-3215   3216-3239    3240-3263    3264-3287    3288-3311
--    3328  (0x0D00)   3448-3471   3472-3495    3496-3519    3520-3543    3544-3567
--    3584  (0x0E00)   3704-3727   3728-3751    3752-3775    3776-3799    3800-3823
--    3840  (0x0F00)   3960-3983   3984-4007    4008-4031    4032-4055    4056-4079
-- **********************************************************************************



-- **********************************************************************************
-- **********************************************************************************
-- **             The objects below have been deprecated                           **
-- **********************************************************************************
-- **********************************************************************************

-- Uplink Tagging Base (ULT) VLAN Tag
ultBaseVlanTag  OBJECT-TYPE
    SYNTAX      INTEGER {
                                      -- Base VLAN Tag
                    ultBase16(1),     -- 16    (0x0010)
                    ultBase512(2),    -- 512   (0x0200)
                    ultBase1024(3),   -- 1024  (0x0400)
                    ultBase1536(4),   -- 1536  (0x0600)
                    ultBase2048(5),   -- 2048  (0x0800)
                    ultBase2560(6),   -- 2560  (0x0A00)
                    ultBase3072(7),   -- 3072  (0x0C00)
                    ultBase3584(8)    -- 3584  (0x0E00)
                }
    MAX-ACCESS  read-write
    STATUS      deprecated
    DESCRIPTION "This object represents Uplink Tagging base index.

                 This object has been deprecated. Please use an object defined
                 in pdnUplinkTaggingObjectsR2."
    DEFVAL      { ultBase16 }
    ::= { pdnUplinkTaggingObjects 1 }


-- Uplink Tagging (ULT) Index
ultIndex        OBJECT-TYPE
    SYNTAX      INTEGER(1..5)
    MAX-ACCESS  read-write
    STATUS      deprecated
    DESCRIPTION "This object represents VLAN tag index which represents an
                index into a block of VLAN Tags the unit will use.

                This object has been deprecated. Please use pdnUltIndex, which
                is more general below."
    DEFVAL      { 1 }
    ::= { pdnUplinkTaggingObjects 2 }



--+++++++++++++++++++++++++++++++++++++++++++++++++++++++++++++++++++++++++++++
--
-- Conformance Information
--

pdnUplinkTaggingConformance  OBJECT IDENTIFIER ::= { pdnUplinkTagging 2 }
pdnUplinkTaggingGroups       OBJECT IDENTIFIER ::= { pdnUplinkTaggingConformance 1 }
pdnUplinkTaggingCompliances  OBJECT IDENTIFIER ::= { pdnUplinkTaggingConformance 2 }
pdnUplinkTaggingDeprecatedGroup OBJECT IDENTIFIER ::= { pdnUplinkTaggingConformance 3 } 

--
-- Units of Conformance for Current Objects
--
pdn48PortUpLinkTaggingGroup OBJECT-GROUP
    OBJECTS     {
                     pdnUltIndex, 
                     pdnGenUltBaseVlanTag,
                     pdn48UltBaseVlanTag                    
    }
    STATUS      current
    DESCRIPTION "Uplink Tagging Objects for 48-Port chassis/units."
    ::= { pdnUplinkTaggingGroups  1 }

pdn24PortUpLinkTaggingGroup OBJECT-GROUP
    OBJECTS     {
                     pdnUltIndex, 
                     pdnGenUltBaseVlanTag,
                     pdn24UltBaseVlanTag                    
    }
    STATUS      current
    DESCRIPTION "Uplink Tagging Objects for 24-Port chassis/units."
    ::= { pdnUplinkTaggingGroups  2 }

--
-- Units of Conformance for Deprecated Objects
--
upLinkTaggingDeprecatedGroup OBJECT-GROUP
    OBJECTS     {
                     ultBaseVlanTag,
                     ultIndex
    }
    STATUS      deprecated
    DESCRIPTION "Objects not to use."
    ::= { pdnUplinkTaggingDeprecatedGroup 1 }


END

-- ====================================================================
-- ==  Copyright (C) 2004 Paradyne Corporation.                      ==
-- ====================================================================

PDN-STACKABLE-MIB DEFINITIONS ::= BEGIN

IMPORTS
    MODULE-IDENTITY, OBJECT-TYPE, Unsigned32, NOTIFICATION-TYPE, 
    Integer32
        FROM SNMPv2-SMI
    OBJECT-GROUP, NOTIFICATION-GROUP, MODULE-COMPLIANCE
        FROM SNMPv2-CONF
    DisplayString, TruthValue
        FROM SNMPv2-TC
    pdn-common
        FROM PDN-HEADER-MIB
    SwitchState
        FROM PDN-TC;
    
        
pdnStackable MODULE-IDENTITY
    LAST-UPDATED "200409140000Z"  -- September 14, 2003
    ORGANIZATION "Paradyne Networks
                  MIB Working Group
                  Other information about group editing the MIB"
    CONTACT-INFO "Paradyne Networks, Inc.
                  8545 126th Avenue North
                  Largo, FL 33733
                  www.paradyne.com
        
                  General Comments to: mibwg_team@paradyne.com

                  Editors
                        Clay Sikes"

    DESCRIPTION
        "This MIB contains objects that are used for configuration and
         statistics reporting things that are unique to a stackable product."

    REVISION "200409140000Z"  -- September 14, 2004
    DESCRIPTION "Added stack links for the Verdun ML PPP project.  Also,
                 cleaned up errors flaged by libsmi.  These changes were
                 radical, but only effected stuff that has not been
                 implemented in any agents."

    REVISION "200303120000Z"  -- March 12, 2003
    DESCRIPTION "Added third stack link for the Verdun product."

    REVISION "200207310000Z"  -- June 31, 2002
    DESCRIPTION "Added Single Management Entity objects"

    REVISION "200205150000Z"  -- May 15, 2002
    DESCRIPTION "Initial Release."

::=  { pdn-common 36 }



-- ====================================================================
-- == Define groups for Notifications, MIB Objects, Accessible for   ==
-- == Notifications (AFNs), and Conformance.                         ==
-- == These may just be place holders.                               ==
-- ====================================================================

pdnStackableNotifications  OBJECT IDENTIFIER ::= { pdnStackable 0 }
pdnStackableObjects        OBJECT IDENTIFIER ::= { pdnStackable 1 }
pdnStackableAFNs           OBJECT IDENTIFIER ::= { pdnStackable 2 }
pdnStackableConformance    OBJECT IDENTIFIER ::= { pdnStackable 3 }



-- ====================================================================
-- == Textual Conventions                                            ==
-- ====================================================================
-- None defined



-- ====================================================================
-- == MIB Objects                                                    ==
-- ====================================================================


-- The WAN Interface Group
wanInterface OBJECT-TYPE
    SYNTAX      BITS {
                    stackLink1(0),
                    stackLink2(1),
                    plugInModule(2),
                    stackLink3(3),
                    stackLink4(4),
                    stackLink5(5),
                    stackLink6(6),
                    stackLink7(7),
                    stackLink8(8),
                    stackLink9(9),
                    stackLink10(10),
                    stackLink11(11),
                    stackLink12(12),
                    stackLink13(13),
                    stackLink14(14),
                    stackLink15(15),
                    stackLink16(16),
                    stackLink17(17),
                    stackLink18(18)
                }
    MAX-ACCESS  read-write
    STATUS      current
    DESCRIPTION "This object allows the WAN interface to be selected. Given 
                that the syntax for this object is BITS, it is intented that 
                the implementation could support multiple-simulatneous 
                uplinks.

                There is no default value suggested or specified with a 
                DEFVAL directive. The intent is that the particular 
                project using this MIB object will specify its own
                default value. It seems like projects using this MIB object
                may be different enough that it would not be a good idea to
                specify a default here."
    ::= { pdnStackableObjects 1 }


pdnStackMethod  OBJECT-TYPE
    SYNTAX      INTEGER {
                    daisyChain(1),
                    star(2)
                }
    MAX-ACCESS  read-only
    STATUS      current
    DESCRIPTION "This object identifies the method by which units are
                interconnected."
    ::= { pdnStackableObjects 2 }

pdnStackConfigurationTable OBJECT-TYPE
    SYNTAX      SEQUENCE OF PdnStackConfigurationEntry
    MAX-ACCESS  not-accessible
    STATUS      current
    DESCRIPTION "This table is used to display the stack configuration.

                Implementation details regarding units becoming attached to 
                or removed from the Stack should be covered in the 
                implementation's Operational Specification."
    ::= { pdnStackableObjects 3 }

pdnStackConfigurationEntry OBJECT-TYPE
    SYNTAX      PdnStackConfigurationEntry
    MAX-ACCESS  not-accessible
    STATUS      current
    DESCRIPTION "Each entry represents a unit in the stack."
    INDEX       { pdnUnitExternalID }
    ::= { pdnStackConfigurationTable 1 }

PdnStackConfigurationEntry ::=
    SEQUENCE {
        pdnUnitExternalID           Unsigned32,
        pdnUnitEntPhysicalIndex     INTEGER,
        pdnUnitAssigned             TruthValue,
        pdnUnitGUID                 DisplayString,
        pdnUnitPresent              TruthValue
    }

pdnUnitExternalID OBJECT-TYPE
    SYNTAX      Unsigned32
    MAX-ACCESS  not-accessible
    STATUS      current
    DESCRIPTION "This object is the External ID used to refer
                to a particular unit. The value of this
                External ID will typically be indicated on
                the unit by some means such as a LED."
    ::= { pdnStackConfigurationEntry 1 }

pdnUnitEntPhysicalIndex OBJECT-TYPE
    SYNTAX      Integer32 (1..2147483647)
    MAX-ACCESS  read-only
    STATUS      current
    DESCRIPTION "This object serves to map the table row to
                 an entry into the entPhysicalTable. This object
                 will contain the entPhysicalIndex associated with
                 the unit."
    ::= { pdnStackConfigurationEntry 2 }

pdnUnitAssigned OBJECT-TYPE
    SYNTAX      TruthValue
    MAX-ACCESS  read-write
    STATUS      current
    DESCRIPTION "This object indicates if the External ID has been
                assigned to a particular Globally Unique Identifier (GUID). 

                Writing a false(2) is a mechanism to
                delete a unit from a stack. When a unit is deleted from
                a stack, all data that the Stack knows about the unit
                is purged.

                On read operations:
                    true(1)  - indicates that the External ID has been
                               assigned to a unit
                    false(2) - indicates that the External ID has not
                               been assigned to a unit"
    ::= { pdnStackConfigurationEntry 3 }

pdnUnitGUID OBJECT-TYPE
    SYNTAX      DisplayString  
    MAX-ACCESS  read-only
    STATUS      current
    DESCRIPTION "This object is the representation of the units' 
                Globally Unique Identifier (GUID). The requirement
                for this identifier is that is something that makes
                the unit uniquely identifiable. A MAC addresses is
                an example of something that could be used as a GUID.
                The particular implementation's Operational Specification
                should clarify what is used as the implementation's 
                GUID."
    ::= { pdnStackConfigurationEntry 4 }

pdnUnitPresent OBJECT-TYPE
    SYNTAX      TruthValue
    MAX-ACCESS  read-only
    STATUS      current
    DESCRIPTION "This object identifies if the unit is present in the
                stack. Note that when a unit is removed from a stack, 
                its stack and configuration information is retained.
                    true(1)  - indicates that the unit is present
                    false(2) - indicates that the unit is no present" 
    ::= { pdnStackConfigurationEntry 5 }


pdnMoveUnitCmdTable OBJECT-TYPE
    SYNTAX      SEQUENCE OF PdnMoveUnitCmdEntry
    MAX-ACCESS  not-accessible
    STATUS      current
    DESCRIPTION "This table contains the objects necessary to support a command
                to move a unit in a stack. This command only applies when
                singleManagementEntity is enabled." 
    ::= { pdnStackableObjects 4 }

pdnMoveUnitCmdEntry OBJECT-TYPE
    SYNTAX      PdnMoveUnitCmdEntry
    MAX-ACCESS  not-accessible
    STATUS      current
    DESCRIPTION "The table has a single row supporting a command to move a
                unit in a stack."
    INDEX       { pdnMoveUnitSrcNumber, pdnMoveUnitDestNumber }
    ::= { pdnMoveUnitCmdTable 1 }

PdnMoveUnitCmdEntry ::=
    SEQUENCE {
        pdnMoveUnitSrcNumber     Unsigned32,
        pdnMoveUnitDestNumber    Unsigned32,
        pdnMoveUnitCmd           INTEGER
    }

pdnMoveUnitSrcNumber OBJECT-TYPE
    SYNTAX      Unsigned32
    MAX-ACCESS  not-accessible
    STATUS      current
    DESCRIPTION "This object is used as a table index and serves as the identifier for
                the source unit in the move command. The implementation's Operational
                Specification should clearly specify what this object represents.
                For example, this object could be what is refered to as the
                unit's External ID."
    ::= { pdnMoveUnitCmdEntry 1 }

pdnMoveUnitDestNumber OBJECT-TYPE
    SYNTAX      Unsigned32
    MAX-ACCESS  not-accessible
    STATUS      current
    DESCRIPTION "This object is used as a table index and serves as the identifier for
                the destination unit in the move command.The implementation's Operational
                Specification should clearly specify what this object represents.
                For example, this object could be what is refered to as the
                unit's External ID."
    ::= { pdnMoveUnitCmdEntry 2 }

pdnMoveUnitCmd OBJECT-TYPE
    SYNTAX      INTEGER {
                    noOp(1),
                    move(2)
                }
    MAX-ACCESS  read-write
    STATUS      current
    DESCRIPTION "Writing the value move(2) will cause the stack and configuration 
                related information for the source unit to be moved to the
                destination unit. This object always returns a noOp(1) on a 
                read operation."
    ::= { pdnMoveUnitCmdEntry 3 }

pdnStackUnitAddedTrapEnable OBJECT-TYPE
    SYNTAX      SwitchState
    MAX-ACCESS  read-write
    STATUS      current
    DESCRIPTION "Indicates whether the pdnStackUnitAdded trap should be 
                generated. The following values are defined for this object:
                    enabled(1)   - Generates the trap
                    disabled(2)  - Does not generate the trap"
    ::= { pdnStackableObjects 5 }

pdnStackUnitComFailureTrapEnable OBJECT-TYPE
    SYNTAX      SwitchState
    MAX-ACCESS  read-write
    STATUS      current
    DESCRIPTION "Indicates whether the pdnStackUnitComFailure trap should be 
                generated. The following values are defined for this object:
                    enabled(1)   - Generates the trap
                    disabled(2)  - Does not generate the trap"
    ::= { pdnStackableObjects 6 }

pdnStackUnitComRestoredTrapEnable OBJECT-TYPE
    SYNTAX      SwitchState
    MAX-ACCESS  read-write
    STATUS      current
    DESCRIPTION "Indicates whether the pdnStackUnitComRestored trap should be 
                generated. The following values are defined for this object:
                    enabled(1)   - Generates the trap
                    disabled(2)  - Does not generate the trap"
    ::= { pdnStackableObjects 7 }


-- ====================================================================
-- == Traps                                                          ==
-- ====================================================================

pdnStackUnitAdded NOTIFICATION-TYPE
    OBJECTS     { pdnUnitGUID }
    STATUS      current
    DESCRIPTION "This trap signifies that a new unit has been added to a
                stack."
    ::= { pdnStackableNotifications 1 } 

pdnStackUnitComFailure NOTIFICATION-TYPE
    OBJECTS     { pdnUnitGUID }
    STATUS      current
    DESCRIPTION "This trap signifies that a loss of communication has occured
                with a unit that was part of a stack."
    ::= { pdnStackableNotifications 2 } 

pdnStackUnitComRestored NOTIFICATION-TYPE
    OBJECTS     { pdnUnitGUID }
    STATUS      current
    DESCRIPTION "This trap signifies that communication to a unit that was
                part of the stack has occured."
    ::= { pdnStackableNotifications 3 } 

            

-- ====================================================================
-- == Conformance Information                                        ==
-- ====================================================================


pdnStackableCompliances  OBJECT IDENTIFIER ::= { pdnStackableConformance 1 }
pdnStackableGroups       OBJECT IDENTIFIER ::= { pdnStackableConformance 2 }


-- ===========================
-- == Compliance Statements ==
-- ===========================
pdnStackableConmpliance  MODULE-COMPLIANCE
    STATUS      current
    DESCRIPTION "The compliance statement for elements implementing 
                 stackable units."
    MODULE      -- this module
    -- No mandatory groups are specified.

    GROUP       wanInterfaceGroup
    DESCRIPTION "This group is only required for implementations that 
                 need to select the WAN interface(s)."

    GROUP       singleManagementEntityGroup
    DESCRIPTION "This group is only required for implementations that
                 implement a `single logical management entity'. "

    GROUP       singleManagementEntityNotificationGroup
    DESCRIPTION "This group is only required for implementations that
                 generate notification related to the `single logical
                 management entity`."
    ::= { pdnStackableCompliances 1 }


-- ==========================
-- == Units of Conformance ==
-- ==========================

pdnStackableObjGroups       OBJECT IDENTIFIER ::= { pdnStackableGroups 1 }
pdnStackableAfnGroups       OBJECT IDENTIFIER ::= { pdnStackableGroups 2 }
pdnStackableNtfyGroups      OBJECT IDENTIFIER ::= { pdnStackableGroups 3 }


-- ============================
-- == pdnStackableObjGroups  ==
-- ============================

wanInterfaceGroup OBJECT-GROUP
    OBJECTS {
                wanInterface
    }
    STATUS      current
    DESCRIPTION "Objects related to the WAN."
    ::= { pdnStackableObjGroups  1 }

singleManagementEntityGroup OBJECT-GROUP
    OBJECTS {
                pdnStackMethod,
                pdnUnitEntPhysicalIndex,
                pdnUnitAssigned,
                pdnUnitGUID,
                pdnUnitPresent,
                pdnMoveUnitCmd,
                pdnStackUnitAddedTrapEnable,
                pdnStackUnitComFailureTrapEnable,
                pdnStackUnitComRestoredTrapEnable
    }
    STATUS      current
    DESCRIPTION "Objects related to the Single Management Entity."
    ::= { pdnStackableObjGroups 2 }


-- ============================
-- == pdnStackableAfnGroups  ==
-- ============================
-- None.

-- =============================
-- == pdnStackableNtfyGroups  ==
-- =============================

singleManagementEntityNotificationGroup NOTIFICATION-GROUP
    NOTIFICATIONS {
                pdnStackUnitAdded,
                pdnStackUnitComFailure,
                pdnStackUnitComRestored
    }
    STATUS      current
    DESCRIPTION "Notifications that must be implemented for Single
                Management Entity implementations." 
    ::= { pdnStackableNtfyGroups 1 }

END

PDN-DEVICE-TIME-MIB DEFINITIONS ::= BEGIN

-- Last Updated: 6/3/02

-- Enterprise Time MIB
-- Copyright (C) 1999-2002 Paradyne Corporation.

-- Created by : Prakash Easwar

-- REVISION HISTORY:
-- Date of Chg  Revision (Most Recent First)                            By
--
-- 06/03/02     Removed unneeded devNTPIf object.                       alfano
-- 05/07/02     Added new objects for SNTP support.  Changed/corrected  alfano
--              existing object descriptions to reflect SNTP support.
--

IMPORTS
IpAddress
FROM RFC1155-SMI
OBJECT-TYPE
FROM RFC-1212
DateAndTime
FROM SNMPv2-TC
NTPMode
FROM PDN-TC
pdn-time
FROM PDN-HEADER-MIB

;
devTimeMIBObjects       OBJECT IDENTIFIER ::= { pdn-time 1 }
devTimeMIBTraps         OBJECT IDENTIFIER ::= { pdn-time 2 }
devTimeAndDate          OBJECT IDENTIFIER ::= { devTimeMIBObjects 1 }
devNTP                  OBJECT IDENTIFIER ::= { devTimeMIBObjects 2 }


-- Time And Date Group

devDateAndTime OBJECT-TYPE
    SYNTAX  DateAndTime
    ACCESS  read-write
    STATUS  mandatory
    DESCRIPTION
       "This object displays the date and time on the entity.
       It allows an NMS to set the date and time in the appropriate
       timezone."
    ::= { devTimeAndDate 1 }

-- [S]NTP ([Simple] Network Time Protocol) group

devNTPServerIP OBJECT-TYPE
    SYNTAX  IpAddress
    ACCESS  read-write
    STATUS  mandatory
    DESCRIPTION
        "The IP address of the NTP/SNTP server."
    ::= { devNTP 1 }

devNTPMode OBJECT-TYPE
    SYNTAX  NTPMode
    ACCESS  read-write
    STATUS  mandatory
    DESCRIPTION
        "This object allows an NMS to configure the mode in which NTP/SNTP
        will operate.  In unicast(1) mode, NTP/SNTP polls the server
        specified via the devNTPServerIP object.  In broadcast(2) mode,
        NTP/SNTP polls by broadcasting a request so that any NTP/SNTP
        server could respond.  Alternatively, in broadcast(2) mode, the
        client only listens for messages broadcasted by any server.  In
        multicast(3) mode, the client listens for messages from any server
        sent to the multicast group defined for NTP/SNTP (224.0.1.1).
        Default value is broadcast(2)."
    ::= { devNTP 2 }

devNTPSynchronised OBJECT-TYPE
    SYNTAX  INTEGER (1 .. 24)
    ACCESS  read-write
    STATUS  mandatory
    DESCRIPTION
        "This object allows an NMS to configure the poll interval (hours)    
        for the NTP/SNTP client to use to send requests to an NTP/SNTP
        server to synchronize the local clock for the device.
        Default value is 1 hour."
    ::= { devNTP 3 }

devNTPEnable OBJECT-TYPE
    SYNTAX  INTEGER { enabled(1), disabled(2) }
    ACCESS  read-write
    STATUS  mandatory
    DESCRIPTION
        "Indicates whether or not the local clock is synchronized
        via NTP/SNTP.  When set to enabled(1), NTP/SNTP is operational
        and will attempt to synchronize the local clock based on the
        message(s) received from an NTP/SNTP server.
        Default value is enabled(1)."
    ::= { devNTP 4 }

devNTPOffsetFromUTC OBJECT-TYPE
    SYNTAX  INTEGER
    ACCESS  read-write
    STATUS  mandatory
    DESCRIPTION
        "Offset (minutes) from the coordinated universal time (UTC), also
        known as Greenwich mean time (GMT), to local time represented as a
        signed integer.  The sign of the integer denotes the direction of local
        time from UTC (e.g., offsets for local times west of the zero meridian
        to the international date line are negative).
        Default value is 0 (i.e., at UTC)."
    ::= { devNTP 5 }

END

-- ===============================================================
-- Copyright (C) 2003 Paradyne Corporation.
-- ===============================================================

PDN-ATM-BRIDGE-IWF-MIB DEFINITIONS ::= BEGIN

IMPORTS
    MODULE-IDENTITY, OBJECT-TYPE, Unsigned32
        FROM SNMPv2-SMI
    OBJECT-GROUP, MODULE-COMPLIANCE
        FROM SNMPv2-CONF
    RowStatus
        FROM SNMPv2-TC
    ifIndex
        FROM IF-MIB
    pdn-common
        FROM PDN-HEADER-MIB;
        
pdnAtmBridgeIwfMIB MODULE-IDENTITY
    LAST-UPDATED "200303240000Z"  -- April 24, 2003
    ORGANIZATION "Paradyne Networks
                  MIB Working Group
                  Other information about group editing the MIB"
    CONTACT-INFO "Paradyne Networks, Inc.
                  8545 126th Avenue North
                  Largo, FL 33733
                  www.paradyne.com
        
                  General Comments to: mibwg_team@paradyne.com

                  Editors
                        Clay Sikes"

    DESCRIPTION
        "This MIB contains objects that are used for monitoring and 
        controlling the ATM/Bridge Interworking Function."

    REVISION "200304240000Z"  -- April 24, 2003
    DESCRIPTION "Added stronger Conformance/Compliance statements."

    REVISION "200303240000Z"  -- March 24, 2003
    DESCRIPTION "Corrected typo in that the pdnAtmBridgeIwfVplVpi
                 should have been pdnAtmBridgeIwfVclVpi."
        
    REVISION "200303170000Z"  -- March 17, 2003
    DESCRIPTION "Initial release."


::=  { pdn-common 43 }

pdnAtmBridgeIwfNotifications OBJECT IDENTIFIER ::= { pdnAtmBridgeIwfMIB 0 }
pdnAtmBridgeIwfObjects       OBJECT IDENTIFIER ::= { pdnAtmBridgeIwfMIB 1 }
pdnAtmBridgeIwfConformance   OBJECT IDENTIFIER ::= { pdnAtmBridgeIwfMIB 2 }



pdnAtmBridgeIwfTable     OBJECT-TYPE
    SYNTAX      SEQUENCE OF PdnAtmBridgeIwfEntry
    MAX-ACCESS  not-accessible
    STATUS      current
    DESCRIPTION "This table allows mapping of ATM VCs to Bridge Ports."
    ::= { pdnAtmBridgeIwfObjects 1 }

pdnAtmBridgeIwfEntry     OBJECT-TYPE
    SYNTAX      PdnAtmBridgeIwfEntry
    MAX-ACCESS  not-accessible
    STATUS      current
    DESCRIPTION "An entry in the pdnAtmBridgeIwfTable."
    INDEX       { ifIndex,
                  pdnAtmBridgeIwfVclVpi,
                  pdnAtmBridgeIwfVclVci  }
    ::= { pdnAtmBridgeIwfTable 1 }

PdnAtmBridgeIwfEntry ::=
    SEQUENCE {
        pdnAtmBridgeIwfVclVpi          Unsigned32,
        pdnAtmBridgeIwfVclVci          Unsigned32,
        pdnAtmBridgeIwfRowStatus       RowStatus,
        pdnAtmBridgeIwfDot1dBasePort   Unsigned32
    }

pdnAtmBridgeIwfVclVpi OBJECT-TYPE
    SYNTAX      Unsigned32(0..4095)
    MAX-ACCESS  not-accessible
    STATUS      current
    DESCRIPTION "The VPI value of the VPL."
    ::= { pdnAtmBridgeIwfEntry 1 }

pdnAtmBridgeIwfVclVci OBJECT-TYPE
    SYNTAX      Unsigned32(0..65535)
    MAX-ACCESS  not-accessible
    STATUS      current
    DESCRIPTION "The VCI value of the VCL."
    ::= { pdnAtmBridgeIwfEntry 2 }

pdnAtmBridgeIwfRowStatus OBJECT-TYPE
    SYNTAX      RowStatus
    MAX-ACCESS  read-create
    STATUS      current
    DESCRIPTION "The SNMP RowStatus of the current row."
    ::= { pdnAtmBridgeIwfEntry 3 }

pdnAtmBridgeIwfDot1dBasePort OBJECT-TYPE
    SYNTAX      Unsigned32(1..65535)
    MAX-ACCESS  read-create
    STATUS      current
    DESCRIPTION "This object specifies the bridge port the 
                VPI/VCI maps to."
    ::= { pdnAtmBridgeIwfEntry 4 }


-- =============================================================================
-- ==                  Conformance Information                                ==
-- =============================================================================

pdnAtmBridgeIwfCompliances  OBJECT IDENTIFIER ::= { pdnAtmBridgeIwfConformance 1 }
pdnAtmBridgeIwfGroups       OBJECT IDENTIFIER ::= { pdnAtmBridgeIwfConformance 2 }


-- ===========================
-- == Compliance Statements ==
-- ===========================

pdnAtmBridgeIwfMIBCompliance MODULE-COMPLIANCE
    STATUS      current
    DESCRIPTION "The compliance statement for pdnAtmBridgeIwf entities which
                implement the pdnAtmBridgeIwfMIB."
    MODULE      -- this module
    MANDATORY-GROUPS { pdnAtmBridgeIwfGroup }
    ::= { pdnAtmBridgeIwfCompliances 1 }


-- ==========================
-- == Units of Conformance ==
-- ==========================

pdnAtmBridgeIwfGroup OBJECT-GROUP
    OBJECTS     {
                     pdnAtmBridgeIwfRowStatus, 
                     pdnAtmBridgeIwfDot1dBasePort           
    }
    STATUS      current
    DESCRIPTION "Objects grouped for ATM to Bridge Port Mapping."
    ::= { pdnAtmBridgeIwfGroups  1 }


END

PDN-REACHDSL-MIB DEFINITIONS ::= BEGIN

--
-- Copyright (C) 2002, Paradyne. All rights reserved.
--

IMPORTS
    MODULE-IDENTITY, OBJECT-TYPE, Unsigned32
        FROM SNMPv2-SMI
    ifIndex
        FROM IF-MIB
    MODULE-COMPLIANCE, OBJECT-GROUP
        FROM SNMPv2-CONF
    DisplayString  
        FROM SNMPv2-TC
    pdn-interfaces
        FROM PDN-HEADER-MIB;
 
pdnReachDSL  MODULE-IDENTITY
        LAST-UPDATED "200404021430Z"
        ORGANIZATION "Paradyne Corp MIB Working Group"
        CONTACT-INFO "Paradyne Networks, Inc.
              8545, 126th Ave. N.,
              Largo, FL 33779
              www.paradyne.com

           General Comments to:
              mibwg_team@eng.paradyne.com

           Editors: A.Z.Shaikh
                    Daniel Varagunasingh
		    Jesus Pinto
		    Dulce Martinez"

        DESCRIPTION 
           "The Paradyne enterprise ReachDSL MIB.
            This MIB is written specifically to facilitate 
            in the management of ReachDSL devices as well as
            help in configuration of Spectrum Management 
            specific objects for ReachDSL products."

        REVISION "200404021430Z"
        DESCRIPTION
           "Dulce Martinez
            Added Line Mode configuration and status
	    items for ADSLR."

        REVISION "200310161500Z"
        DESCRIPTION
           "Clay Sikes
            Added Extra Short enumeration to 
            reachDSLSpectrumMgmtConfLoopLength."

        REVISION "200301151200Z"
        DESCRIPTION
           "1. This mib SHOULD only be used for reachDSL
	       specific technology and not for spectrum
	       management."

        REVISION "200301121200Z"
        DESCRIPTION
           "1. The pdn_spectrummgmt.mib is a new common
	       mib that should be used for all DSL interfaces
	       that require configuration spectrum management
	       parameters."

        REVISION "200210151700Z"
        DESCRIPTION
           "1. Deprecated the reach DSL Circuit Identifier Object.
            2. Added 'Quad Mode' as a loop measurement method.
            3. Added Configuration object for Quad Mode.
            4. Deprecated the old conformance statement & units
               of conformance.
            5. Added new conformance statement & units of
               conformance to clearly reflect the objects' roles."

        REVISION "200207120315Z"
        DESCRIPTION
           "1. Deprecated the Spectrum Management Zone Object.
            2. Added Loop Measurement Method object.
            3. Added EWL Units object.
            4. Added Spectrum Management Mode object.
            5. Added objects for Min & Max EWL values.
            These changes are required for dynamic updation of
            spectrum management configuration."

        ::= { pdn-interfaces 20 }

pdnReachDSLObjects  OBJECT IDENTIFIER ::= { pdnReachDSL 1 }

--
-- START OF PdnReachDSL mib definitions
--

reachDSLSpectrumMgmtSelection OBJECT-TYPE
    SYNTAX      INTEGER {
                    enabled(1),
                    disabled(2)
                }
    MAX-ACCESS  read-write
    STATUS      current
    DESCRIPTION
       "This object has been deprecated. The corresponding
        object in the new pdn_spectrumMgmt.mib should be used
	instead.
	
	This object is used to Enable or Disable 
        Spectrum Management on this device. Enabling
        this object limits the DSL speeds and the maximum
        transmit power on each port based on line length in order
        to meet local Spectrum Management guidelines.

        The values that this object can accept are controlled
        by the 'Mode' object."

    ::= { pdnReachDSLObjects 1 }

reachDSLSpectrumMgmtZone OBJECT-TYPE
    SYNTAX      INTEGER {
                    usa1(1),
                    uk1(2),
                    canada1(3),
                    japan1(4),
                    emea1(5)
                }
    MAX-ACCESS  read-only
    STATUS      deprecated
    DESCRIPTION
       "This object shows the geographic location or the spectrum
        zone used for spectrum management.  It also represents
        which Spectrum Management standard will be used on this
        device to calculate the effective maximum 'Tx Rates' and
        the maximum allowed 'Tx Power' to comply with Spectrum
        Management regulations for that specific region.

        Note: Spectrum Management must be Enabled for
              'SpectrumMgmtZone' to take effect."

    DEFVAL { usa1 }

    ::= { pdnReachDSLObjects 2 }

reachDSLSpectrumMgmtConfTable OBJECT-TYPE
    SYNTAX      SEQUENCE OF ReachDSLSpectrumMgmtConfEntry
    MAX-ACCESS  not-accessible
    STATUS      current
    DESCRIPTION
	"The ReachDSL Spectrum Management Configuration Table
        This table is used for configuring spectrum management
        objects." 

    ::= { pdnReachDSLObjects 3 }

reachDSLSpectrumMgmtConfEntry OBJECT-TYPE
    SYNTAX      ReachDSLSpectrumMgmtConfEntry
    MAX-ACCESS  not-accessible
    STATUS      current
    DESCRIPTION
       	"An entry in the ReachDSL Spectrum Management 
        Configuration table.

        Note: This entry can be accessed only for ifIndex 
              values that belong to a physical interface. 
              e.g. for ifType = 'adsl'."

    INDEX   { ifIndex }

    ::= { reachDSLSpectrumMgmtConfTable 1 }

ReachDSLSpectrumMgmtConfEntry ::= 
    SEQUENCE {
        reachDSLSpectrumMgmtConfEWL            Unsigned32,
        reachDSLSpectrumMgmtConfLoopLength     INTEGER,
        reachDSLSpectrumMgmtConfAtucMaxTxPower INTEGER,
        reachDSLSpectrumMgmtConfAturMaxTxPower INTEGER,
        reachDSLSpectrumMgmtConfQuadMode       INTEGER
    }

reachDSLSpectrumMgmtConfEWL OBJECT-TYPE
    SYNTAX      Unsigned32
    MAX-ACCESS  read-write
    STATUS      current
    DESCRIPTION
       "This object has been deprecated. The corresponding
        object in the new pdn_spectrumMgmt.mib should be used
	instead.

        The Equivalent Working Length (EWL).  The value selected
        corresponds to the estimated length of the line in

            feet   - if 'EWLUnits' object is 'feet'.
            meters - if 'EWLUnits' object is 'meters'. 

        This value is usually specified by the carrier and MUST
        be in integral multiples of 

            500 feet, if 'EWLUnits' is 'feet'.
            200 meters, if 'EWLUnits' is 'meters'.

        The range of values that this object can take is determined
        by the 'MinEWL' and 'MaxEWL' objects.
        Changing this object may limit the maximum transmit power
        and the effective DSL speeds at which the ports train up.

        Note: This object will be used only if Spectrum Management
              is enabled and 'LoopMeasurementMethod' is 'ewl'.
              This object shares a mutual exclusion relationship
              with 'ConfLoopLength' & 'ConfQuadMode' objects, as
              only one of the three will be used for configuration
              at any given instant of time."

    ::= { reachDSLSpectrumMgmtConfEntry 1 }

reachDSLSpectrumMgmtConfLoopLength OBJECT-TYPE
    SYNTAX      INTEGER {
                    short(1),
                    medium(2),
                    long(3),
                    extraShort(4)
                }
    MAX-ACCESS  read-write
    STATUS      current
    DESCRIPTION
       "This object has been deprecated. The corresponding
        object in the new pdn_spectrumMgmt.mib should be used
	instead.


        This entry specifies the loop length for the line. The
        configurable values are short(1), medium(2) long(3), and 
        extraShort(4). The 'Loop Length' feature can be used only 
        if the 'reachDSLSpectrumMgmtSelection' object is Enabled and
        the 'LoopMeasurementMethod' is 'loopLength'. Changing this
        object may limit the maximum transmit power and the
        effective DSL speeds at which ports train up.

        Note: This object shares a mutual exclusion relationship 
              with the 'ConfEWL' & 'ConfQuadMode' objects.
              i.e. only one of the three can be used for
              configuration at one time."

    ::= { reachDSLSpectrumMgmtConfEntry 2 }

reachDSLSpectrumMgmtConfAtucMaxTxPower OBJECT-TYPE
    SYNTAX      INTEGER (-140..120)
    UNITS       "tenth dB"
    MAX-ACCESS  read-write
    STATUS      current
    DESCRIPTION
        "The maximum transmit power at the ATUC (in tenth dB).  
        This value will be based on the spectrum management 
        selection.  It ranges from -140 to 120 in increments
        of 10."

    ::= { reachDSLSpectrumMgmtConfEntry 3 }

reachDSLSpectrumMgmtConfAturMaxTxPower OBJECT-TYPE
    SYNTAX      INTEGER (-140..120)
    UNITS       "tenth dB"
    MAX-ACCESS  read-write
    STATUS      current
    DESCRIPTION
        "The maximum transmit power at the ATUR (in tenth dB).
        This value will be based on the spectrum management
        selection. It ranges from -140 to 120 in increments
        of 10."

    ::= { reachDSLSpectrumMgmtConfEntry 4 }

reachDSLSpectrumMgmtConfQuadMode OBJECT-TYPE
    SYNTAX      INTEGER {
                    sameQuad(1),
                    segregatedQuadUpto3km(2),
                    segregatedQuadAbove3km(3)
                }
    MAX-ACCESS  read-write
    STATUS      current
    DESCRIPTION
       "This object has been deprecated. The corresponding
        object in the new pdn_spectrumMgmt.mib should be used
	instead.

        This entry specifies the quad cable configuration &
        length for the line. The configurable values are
        sameQuad(1), segregatedQuadUpto3km(2) and
        segregatedQuadAbove3km(3). The 'Quad Mode' feature can be
        used only if the 'reachDSLSpectrumMgmtSelection' object
        is Enabled and the 'LoopMeasurementMethod' is 'quadMode'.
        Changing this object may limit the maximum transmit power
        and the effective DSL speeds at which ports train up.

        Note: This object shares a mutual exclusion relationship 
              with the 'ConfEWL' & 'ConfLoopLength' objects.
              i.e. only one of the three can be used for
              configuration at one time."

    ::= { reachDSLSpectrumMgmtConfEntry 5 }

reachDSLSpectrumMgmtLineInfoTable OBJECT-TYPE
    SYNTAX      SEQUENCE OF ReachDSLSpectrumMgmtLineInfoEntry
    MAX-ACCESS  not-accessible
    STATUS      current
    DESCRIPTION
       "This object has been deprecated. The corresponding
        object in the new pdn_spectrumMgmt.mib should be used
	instead.

        The ReachDSL Spectrum Management Line Info Table.
        This table gives information about the spectrum 
        management ranges that are applicable for each port,
        based on the spectral requirements for the device."

    ::= { pdnReachDSLObjects 4 }

reachDSLSpectrumMgmtLineInfoEntry OBJECT-TYPE
    SYNTAX      ReachDSLSpectrumMgmtLineInfoEntry
    MAX-ACCESS  not-accessible
    STATUS      current
    DESCRIPTION
       "This object has been deprecated. The corresponding
        object in the new pdn_spectrumMgmt.mib should be used
	instead.


        An entry in the reachDSLSpectrumMgmtLineInfoTable table.

        Note: This entry can be accessed only for ifIndex values
              that belong to a physical interface. 
              e.g. for ifType = 'adsl'."

    INDEX   { ifIndex }

    ::= { reachDSLSpectrumMgmtLineInfoTable 1 }

ReachDSLSpectrumMgmtLineInfoEntry ::= 
    SEQUENCE {
        reachDSLSpectrumMgmtAtucMaxTxRate  Unsigned32,
        reachDSLSpectrumMgmtAtucMinTxRate  Unsigned32,
        reachDSLSpectrumMgmtAtucMaxTxPower INTEGER, 
        reachDSLSpectrumMgmtAturMaxTxRate  Unsigned32,
        reachDSLSpectrumMgmtAturMinTxRate  Unsigned32,
        reachDSLSpectrumMgmtAturMaxTxPower INTEGER,
        reachDSLSpectrumMgmtMinEWL         Unsigned32,
        reachDSLSpectrumMgmtMaxEWL         Unsigned32
    }

reachDSLSpectrumMgmtAtucMaxTxRate OBJECT-TYPE
    SYNTAX      Unsigned32
    UNITS       "bps"
    MAX-ACCESS  read-only
    STATUS      current
    DESCRIPTION
       "This object has been deprecated. The corresponding
        object in the new pdn_spectrumMgmt.mib should be used
	instead.


        This rate will be the max allowed Tx Rate(in bps) for 
        the port based on the Spectrum Management requirements for
        ATUC in a particular spectral compliance configuration."
 
    ::= { reachDSLSpectrumMgmtLineInfoEntry 1 }

reachDSLSpectrumMgmtAtucMinTxRate OBJECT-TYPE
    SYNTAX      Unsigned32
    UNITS       "bps"
    MAX-ACCESS  read-only
    STATUS      current
    DESCRIPTION
       "This object has been deprecated. The corresponding
        object in the new pdn_spectrumMgmt.mib should be used
	instead.


        This rate will be the min allowed Tx Rate based on the
        spectrum management requirements for the ATUC. The
        MinTxRate will be upper bounded by
        'reachDSLSpectrumMgmtAtucMaxTxRate' object."

    ::= { reachDSLSpectrumMgmtLineInfoEntry 2 }

reachDSLSpectrumMgmtAtucMaxTxPower OBJECT-TYPE
    SYNTAX      INTEGER(-140..120)
    UNITS       "tenth dB"
    MAX-ACCESS  read-only
    STATUS      current
    DESCRIPTION
       "This object has been deprecated. The corresponding
        object in the new pdn_spectrumMgmt.mib should be used
	instead.


        The maximum transmit power at the ATUC (in tenth dB).  
        This value will be based on the spectrum management
        selection."

    ::= { reachDSLSpectrumMgmtLineInfoEntry 3 }

reachDSLSpectrumMgmtAturMaxTxRate OBJECT-TYPE
    SYNTAX      Unsigned32
    UNITS       "bps"
    MAX-ACCESS  read-only
    STATUS      current
    DESCRIPTION
       "This object has been deprecated. The corresponding
        object in the new pdn_spectrumMgmt.mib should be used
	instead.


        This rate will be the max allowed Tx Rate(in bps) for 
        the port based on the Spectrum Management requirements for
        ATUC in a particular spectral compliance configuration."

    ::= { reachDSLSpectrumMgmtLineInfoEntry 4 }

reachDSLSpectrumMgmtAturMinTxRate OBJECT-TYPE
    SYNTAX      Unsigned32
    UNITS       "bps"
    MAX-ACCESS  read-only
    STATUS      current
    DESCRIPTION
       "This object has been deprecated. The corresponding
        object in the new pdn_spectrumMgmt.mib should be used
	instead.


        This rate will be the min allowed Tx Rate based on the
        spectrum management requirements for the ATUR. The 
        MinTxRate will be upper bounded by
        'reachDSLSpectrumMgmtAturMaxTxRate' object."

    ::= { reachDSLSpectrumMgmtLineInfoEntry 5 }

reachDSLSpectrumMgmtAturMaxTxPower OBJECT-TYPE
    SYNTAX      INTEGER(-140..120)
    UNITS       "tenth dB"
    MAX-ACCESS  read-only
    STATUS      current
    DESCRIPTION
       "This object has been deprecated. The corresponding
        object in the new pdn_spectrumMgmt.mib should be used
	instead.


        The maximum transmit power at the ATUR (in tenth dB).  This
        value will be based on the spectrum management selection."

    ::= { reachDSLSpectrumMgmtLineInfoEntry 6 }

reachDSLSpectrumMgmtMinEWL OBJECT-TYPE
    SYNTAX      Unsigned32
    MAX-ACCESS  read-only
    STATUS      current
    DESCRIPTION
       "This object has been deprecated. The corresponding
        object in the new pdn_spectrumMgmt.mib should be used
	instead.

	
        The minimum value (in feet, if 'EWLUnits' is 'feet, or in
        meters, if 'EWLUnits' is 'meters') that the 'ConfEWL'
        object can accept. Together with the 'MaxEWL' object,
        this object indicates the range of EWL when 'EWLUnits' is
        either 'feet' or 'meters'.

        Note : This object is valid only if the
               'LoopMeasurementMethod' object is 'ewl'."

    ::= { reachDSLSpectrumMgmtLineInfoEntry 7 }

reachDSLSpectrumMgmtMaxEWL OBJECT-TYPE
    SYNTAX      Unsigned32
    MAX-ACCESS  read-only
    STATUS      current
    DESCRIPTION
       "This object has been deprecated. The corresponding
        object in the new pdn_spectrumMgmt.mib should be used
	instead.

	
        The maximum value (in feet, if 'EWLUnits' is 'feet, or in
        meters, if 'EWLUnits' is 'meters') that the 'ConfEWL'
        object can accept. Together with the 'MinEWL' object,
        this object indicates the range of EWL when 'EWLUnits' is
        either 'feet' or 'meters'.

        Note : This object is valid only if the
               'LoopMeasurementMethod' object is 'ewl'."

    ::= { reachDSLSpectrumMgmtLineInfoEntry 8 }

reachDSLLineTable OBJECT-TYPE
    SYNTAX      SEQUENCE OF ReachDSLLineEntry
    MAX-ACCESS  not-accessible
    STATUS      current
    DESCRIPTION
       "The ReachDSL Line Table."

    ::= { pdnReachDSLObjects 5 }

reachDSLLineEntry OBJECT-TYPE
    SYNTAX      ReachDSLLineEntry
    MAX-ACCESS  not-accessible
    STATUS      current
    DESCRIPTION
       "An entry in the reachDSLLineTable.

        Note: This entry can be accessed only for ifIndex values
              that belong to a physical interface. 
              e.g. for ifType = 'adsl'."

    INDEX   { ifIndex }

    ::= { reachDSLLineTable 1 }

ReachDSLLineEntry ::= 
    SEQUENCE {
        reachDSLPotsDetectionVoltage  INTEGER,
        reachDSLCircuitIdentifier     DisplayString,
        reachDSLLineModeConfig	      INTEGER,
        reachDSLLineModeStatus	      INTEGER
    }

reachDSLPotsDetectionVoltage OBJECT-TYPE
    SYNTAX      INTEGER (0..74)
    UNITS       "volts"
    MAX-ACCESS  read-write
    STATUS      current
    DESCRIPTION
        "This object defines the configurable voltage used to 
        detect the presence of POTS on the DSL line. The range
        is 0-74 volts. The default value is 3 volts.

        Note: This object can be accessed only for ifIndex  
              values that belong to a physical interface.
              i.e. ifType = adsl/reachDSL."

    DEFVAL { 3 }

    ::= { reachDSLLineEntry 1 }

reachDSLCircuitIdentifier OBJECT-TYPE
    SYNTAX      DisplayString (SIZE(1..32))
    MAX-ACCESS  read-write
    STATUS      deprecated
    DESCRIPTION
       "The value of this object reflects the transmission
        vendor's circuit identifier to facilitate troubleshooting.

        Note: This object can be accessed only for ifIndex  
              values that belong to a physical interface.
              e.g. for ifType = 'adsl'.

        This object is deprecated in favor of ifAlias. It is
        highly recommended that future implementations use
        ifAlias to store the Circuit Identifier associated with
        reach DSL interfaces." 

    ::= { reachDSLLineEntry 2 }

reachDSLLineModeConfig OBJECT-TYPE
    SYNTAX      INTEGER {
			adsl(1),
			reach(2),
			dualmode(3)
		}
    MAX-ACCESS  read-write
    STATUS      current
    DESCRIPTION
	"This object specifies the line mode configuration.
	The configurable values are adsl(1), reach(2), and
	dualmode(3).  A value of 'dualmode' indicates that the 
	interface will initially train up using ADSL or
	ReachDSL based on the type of initiation signaling
	being sent by the CPE at the start of aquisition.

        Note: This object can be accessed only for ifIndex  
              values that belong to a physical interface.
              e.g. for ifType = 'adsl'."

    ::= { reachDSLLineEntry 3 }

reachDSLLineModeStatus OBJECT-TYPE
    SYNTAX      INTEGER {
			adsl(1),
			reach(2)
		}
    MAX-ACCESS  read-only
    STATUS      current
    DESCRIPTION
	"This object reports the current line mode being used.
	If the line is configured for dual mode, then the
	port can train up in either ADSL or ReachDSL mode.
	A value of 'adsl' indicates that the interface has
	trained up using ADSL.  A value of 'reach' indicates
	that the interface has trained up using ReachDSL.

        Note: This object can be accessed only for ifIndex  
              values that belong to a physical interface.
              e.g. for ifType = 'adsl'."

    ::= { reachDSLLineEntry 4 }

reachDSLSpectrumMgmtLoopMeasurementMethod OBJECT-TYPE
    SYNTAX      INTEGER {
                    none(1),
                    loopLength(2),
                    ewl(3),
                    quadMode(4)
                }
    MAX-ACCESS  read-only
    STATUS      current
    DESCRIPTION
       "This object has been deprecated. The corresponding
        object in the new pdn_spectrumMgmt.mib should be used
	instead.


        This object indicates the measurement method used in
        describing the Loop Length of a circuit. Following are the
        details of each of the options:

            none(1)       - Indicates that the Spectral Compliance
                            is NOT dependant on any Loop Length
                            measurements or configurations.
            loopLength(2) - The 'ConfLoopLength' object is used to
                            determine spectral compliance. The
                            'ConfEWL' & 'ConfQuadMode' objects are
                            not used in this mode.
            ewl(3)        - The 'ConfEWL' object is used to
                            configure the estimated loop length,
                            which is used to determine spectral
                            compliance. In this mode the
                            'ConfLoopLength' & 'ConfQuadMode'
                            objects are not used. 
            quadMode(4)   - The 'ConfQuadMode' object is used to
                            determine spectral compliance. The
                            'ConfEWL' & 'ConfLoopLength' objects
                            are not used in this mode.

        This object determines which of the three objects :
        'ConfEWL', 'ConfLoopLength' or 'ConfQuadMode' is used
        (if any) to enforce spectrally compliant maximum
        'Tx Rates' and the maximum allowed 'Tx Power' on a given
        circuit."

    ::= { pdnReachDSLObjects 6 }

reachDSLSpectrumMgmtEWLUnits OBJECT-TYPE
    SYNTAX      INTEGER {
                    none(1),
                    feet(2),
                    meters(3)
                }
    MAX-ACCESS  read-only
    STATUS      current
    DESCRIPTION
       "This object has been deprecated. The corresponding
        object in the new pdn_spectrumMgmt.mib should be used
	instead.


        This object indicates the units of measurement used in
        describing the Estimated Working Length of a circuit.
        Following are the details of each of the units:

            none(1)     - Indicates that the Spectral Compliance is
                          NOT dependant on the 'ConfEWL' object.
            feet(2)     - The 'ConfEWL' is measured and configured
                          in feet.
            meters(3)   - The 'ConfEWL' is measured and configured
                          in meters."

    ::= { pdnReachDSLObjects 7 }

reachDSLSpectrumMgmtMode OBJECT-TYPE
    SYNTAX      INTEGER {
                    enableOnly(1),
                    disableOnly(2),
                    both(3)
                }
    MAX-ACCESS  read-only
    STATUS      current
    DESCRIPTION
       "This object has been deprecated. The corresponding
        object in the new pdn_spectrumMgmt.mib should be used
	instead.


        This object restricts the MAX-ACCESS of the 'Selection'
        object.
        Following are the details of each of the values:

            enableOnly(1)  - Indicates that the 'Selection' object
                             IS always 'enabled' and cannot be set
                             to 'disabled'.
            disableOnly(2) - Indicates that the 'Selection' object
                             IS always 'disabled' and cannot be set
                             to 'enabled'.
            both(3)        - Indicates that the 'Selection' object
                             will accept both the 'enabled' and
                             'disabled' values."

    ::= { pdnReachDSLObjects 8 }

--
-- Conformance information
--

pdnReachDSLConformance  OBJECT IDENTIFIER
    ::= { pdnReachDSL 2 }

pdnReachDSLGroups       OBJECT IDENTIFIER
    ::= { pdnReachDSLConformance 1 }

pdnReachDSLCompliances  OBJECT IDENTIFIER
    ::= { pdnReachDSLConformance 2 }

-- Compliance statements

pdnReachDSLCompliance1 MODULE-COMPLIANCE 
    STATUS      current
    DESCRIPTION
       "The compliance statement for SNMP entities which manage
        ReachDSL interfaces."

    MODULE   -- this module
        MANDATORY-GROUPS { 
            pdnReachDSLGeneralConfigGroup,
            pdnReachDSLGeneralInformationGroup
        }

-- The groups :
--      pdnReachDSLEWLModeGroup
--      pdnReachDSLLoopLengthModeGroup
--      pdnReachDSLQuadModeGroup
-- are mutually exclusive; at most one of these groups is
-- implemented for a particular reachDSL interface. If the
-- Loop Measurement Method is 'none', then none of these
-- groups should be implemented.

    GROUP   pdnReachDSLEWLModeGroup
    DESCRIPTION
       "This group is mandatory for reachDSL interfaces whose
        loop/line length measurement method is EWL.
        i.e.the reachDSLSpectrumMgmtLoopMeasurementMethod object
        is 'ewl'."

    GROUP   pdnReachDSLLoopLengthModeGroup
    DESCRIPTION
       "This group is mandatory for reachDSL interfaces whose
        loop/line length measurement method is LoopLength (short
        /medium/long).
        i.e.the reachDSLSpectrumMgmtLoopMeasurementMethod object
        is 'loopLength'."

    GROUP   pdnReachDSLQuadModeGroup
    DESCRIPTION
       "This group is mandatory for reachDSL interfaces whose
        loop/line length measurement method is based on Quads.
        i.e.the reachDSLSpectrumMgmtLoopMeasurementMethod object
        is 'quadMode'."

    OBJECT      reachDSLSpectrumMgmtSelection
    MIN-ACCESS  read-only
    DESCRIPTION 
       "Write access is not required."

    OBJECT      reachDSLSpectrumMgmtConfAtucMaxTxPower
    MIN-ACCESS  read-only
    DESCRIPTION 
       "Write access is not required."

    OBJECT      reachDSLSpectrumMgmtConfAturMaxTxPower
    MIN-ACCESS  read-only
    DESCRIPTION 
       "Write access is not required."

    OBJECT      reachDSLPotsDetectionVoltage
    MIN-ACCESS  read-only
    DESCRIPTION 
       "Write access is not required."

    OBJECT      reachDSLLineModeConfig
    MIN-ACCESS  read-only
    DESCRIPTION 
       "Write access is not required."

    ::= { pdnReachDSLCompliances 2 }

-- Units of conformance

pdnReachDSLGeneralConfigGroup OBJECT-GROUP
    OBJECTS {
        reachDSLSpectrumMgmtSelection,
        reachDSLSpectrumMgmtConfAtucMaxTxPower,
        reachDSLSpectrumMgmtConfAturMaxTxPower,
        reachDSLPotsDetectionVoltage,
        reachDSLLineModeConfig
    }
    STATUS      current
    DESCRIPTION 
       "A collection of configuration objects required for
        providing access to configure all reachDSL interfaces."

    ::= { pdnReachDSLGroups 4 }

pdnReachDSLGeneralInformationGroup OBJECT-GROUP
    OBJECTS {
        reachDSLSpectrumMgmtAtucMaxTxRate,
        reachDSLSpectrumMgmtAtucMinTxRate,
        reachDSLSpectrumMgmtAtucMaxTxPower,
        reachDSLSpectrumMgmtAturMaxTxRate,
        reachDSLSpectrumMgmtAturMinTxRate,
        reachDSLSpectrumMgmtAturMaxTxPower,
        reachDSLSpectrumMgmtLoopMeasurementMethod,
        reachDSLSpectrumMgmtEWLUnits,
        reachDSLSpectrumMgmtMode,
        reachDSLLineModeStatus
    }
    STATUS      current
    DESCRIPTION 
       "A collection of objects providing information applicable
        to all reachDSL interfaces."

    ::= { pdnReachDSLGroups 5 }

-- The following three groups are mutually exclusive; at most one
-- of these groups is implemented for any interface

pdnReachDSLEWLModeGroup OBJECT-GROUP
    OBJECTS {
        reachDSLSpectrumMgmtConfEWL,
        reachDSLSpectrumMgmtMinEWL,
        reachDSLSpectrumMgmtMaxEWL
    }
    STATUS      current
    DESCRIPTION 
       "A collection of objects providing configuration
        access and information specific to reachDSL interfaces
        whose loop/line length measurement method is EWL.
        i.e.the reachDSLSpectrumMgmtLoopMeasurementMethod object
        is 'ewl'."

    ::= { pdnReachDSLGroups 6 }

pdnReachDSLLoopLengthModeGroup OBJECT-GROUP
    OBJECTS {
        reachDSLSpectrumMgmtConfLoopLength
    }
    STATUS      current
    DESCRIPTION 
       "A collection of object(s) providing configuration
        access and information specific to reachDSL interfaces
        whose loop/line length measurement method is Loop Length
        (short/medium/long).
        i.e.the reachDSLSpectrumMgmtLoopMeasurementMethod object
        is 'loopLength'."

    ::= { pdnReachDSLGroups 7 }

pdnReachDSLQuadModeGroup OBJECT-GROUP
    OBJECTS {
        reachDSLSpectrumMgmtConfQuadMode
    }
    STATUS      current
    DESCRIPTION 
       "A collection of object(s) providing configuration
        access and information specific to reachDSL interfaces
        whose loop/line length measurement method is based on the
        Quad configuration.
        i.e.the reachDSLSpectrumMgmtLoopMeasurementMethod object
        is 'quadMode'."

    ::= { pdnReachDSLGroups 8 }

--
-- Deprecated definitions - Compliance
--

pdnReachDSLCompliance MODULE-COMPLIANCE 
    STATUS      deprecated
    DESCRIPTION
       "The compliance statement for SNMP entities which manage
        ReachDSL interfaces."

MODULE   -- this module
    MANDATORY-GROUPS { 
       pdnReachDSLConfigurationGroup, pdnReachDSLInformationGroup
    }
 
    OBJECT      reachDSLSpectrumMgmtSelection
    MIN-ACCESS  read-only
    DESCRIPTION 
       "Write access is not required."

    OBJECT      reachDSLSpectrumMgmtConfEWL
    MIN-ACCESS  read-only
    DESCRIPTION 
       "Write access is not required."

    OBJECT      reachDSLSpectrumMgmtConfLoopLength
    MIN-ACCESS  read-only
    DESCRIPTION 
       "Write access is not required."

    OBJECT      reachDSLSpectrumMgmtConfAtucMaxTxPower
    MIN-ACCESS  read-only
    DESCRIPTION 
       "Write access is not required."

    OBJECT      reachDSLSpectrumMgmtConfAturMaxTxPower
    MIN-ACCESS  read-only
    DESCRIPTION 
       "Write access is not required."

    OBJECT      reachDSLPotsDetectionVoltage
    MIN-ACCESS  read-only
    DESCRIPTION 
       "Write access is not required."

    OBJECT      reachDSLCircuitIdentifier
    MIN-ACCESS  read-only
    DESCRIPTION 
       "Write access is not required."

    ::= { pdnReachDSLCompliances 1 }

--
-- Deprecated definitions - Groups
--

pdnReachDSLConfigurationGroup OBJECT-GROUP
    OBJECTS {
        reachDSLSpectrumMgmtSelection,
        reachDSLSpectrumMgmtConfEWL,
        reachDSLSpectrumMgmtConfLoopLength,
        reachDSLSpectrumMgmtConfAtucMaxTxPower,
        reachDSLSpectrumMgmtConfAturMaxTxPower,
        reachDSLPotsDetectionVoltage,
        reachDSLCircuitIdentifier
    }
    STATUS      deprecated -- Set as required for the group
    DESCRIPTION 
       "A collection of configuration objects required 
        for providing access to configuration as well 
        as status information for reachDSL products."

    ::= { pdnReachDSLGroups 1 }

pdnReachDSLInformationGroup OBJECT-GROUP
    OBJECTS {
        reachDSLSpectrumMgmtAtucMaxTxRate,
        reachDSLSpectrumMgmtAtucMinTxRate,
        reachDSLSpectrumMgmtAtucMaxTxPower,
        reachDSLSpectrumMgmtAturMaxTxRate,
        reachDSLSpectrumMgmtAturMinTxRate,
        reachDSLSpectrumMgmtAturMaxTxPower,
        reachDSLSpectrumMgmtMinEWL,
        reachDSLSpectrumMgmtMaxEWL,
        reachDSLSpectrumMgmtLoopMeasurementMethod,
        reachDSLSpectrumMgmtEWLUnits,
        reachDSLSpectrumMgmtMode
    }
    STATUS      deprecated -- Set as required for the group
    DESCRIPTION 
        "A collection of objects providing access meant
         specifically for accessing information for 
         for reachDSL products."

    ::= { pdnReachDSLGroups 2 }

pdnReachDSLDeprecatedGroup OBJECT-GROUP
    OBJECTS {
        reachDSLSpectrumMgmtZone,
        reachDSLCircuitIdentifier
    }
    STATUS      deprecated -- Set as required for the group
    DESCRIPTION 
        "A collection of objects that have been deprecated."

    ::= { pdnReachDSLGroups 3 }

END

-- ===============================================================
-- ==                                                           ==
-- ==         Copyright (C) 2005 Paradyne Corporation.          ==
-- ==                                                           ==
-- ===============================================================


PDN-SPECTRUMMGMT-MIB DEFINITIONS ::= BEGIN

IMPORTS
	Integer32, Unsigned32,
	OBJECT-TYPE, MODULE-IDENTITY 
	    FROM SNMPv2-SMI
	MODULE-COMPLIANCE, OBJECT-GROUP
            FROM SNMPv2-CONF
	entPhysicalIndex
            FROM ENTITY-MIB
	ifIndex, ifType
	    FROM IF-MIB
	pdn-interfaces
	    FROM PDN-HEADER-MIB;
	
pdnSpectrumMgmt	MODULE-IDENTITY
	    LAST-UPDATED "200501190000Z"   -- January 19, 2005
	    ORGANIZATION "Paradyne Corp MIB Working Group"
	    CONTACT-INFO "Paradyne Networks, Inc.
			  8545 126th Ave North
			  Largo, FL 33733
			  www.paradyne.com

			  General Comments to:
			    mibwg_team@eng.paradyne.com

			  Editors: R.A.Bowhall,
				   Jesus Pinto,
                                   Clay Sikes"

	    DESCRIPTION "R.A.Bowhall
	    	The Paradyne enterprise SPECTRUM MIB.
	    	This MIB is written to facilitate spectrum
		management of any xDSL interfaces. This mib
	 	replaces older versions of the spectrum 
		management including the reachDSL.mib.

                =============================================================
                ==                                                         ==
                ==       Copyright (C) 2005 Paradyne Corporation.          ==
                ==                                                         ==
                ============================================================="

            REVISION "200501190000Z"  -- January 19, 2005
            DESCRIPTION "Clay Sikes
                Added enum to the newSpectrumMgmtStd object to support the
                JJ-100.01 spectrum management standard."

            REVISION "200310131500Z"  -- October 13, 2003
            DESCRIPTION "Clay Sikes
                Added spectrumMgmtSelection back in as a deprecated
                object so that code instrumented for the 'older' version
                of this MIB would not have to be rewritten to support
                the newSpectrumMgmtSelection. Also, don't want to burden
                NMS applications that could support the spectrumMgmtSelection
                Object. Most likely, the loss of spectrumMgmtSelection was a 
                cut and paste error."

            REVISION "200310081500Z"  -- October 8, 2003
            DESCRIPTION "Clay Sikes
                Changes for G.991.2 compliance.
                1. Added Extra Short Loop Length parameter 
                   to newSpectrumMgmtConfLoopLength in order
                   to  comply with Access Network Frequency
                   Plan for the BT Access Network.
                2. Added Extra Short Loop Length parameter 
                   to spectrumMgmtLineLength in order
                   to  comply with Access Network Frequency
                   Plan for the BT Access Network. This change
                   was for older products that still used the
                   the deprecated object.
                4. Removed the DEFVAL clause since the value
                   is technology dependent.
                3. Added ability to select a particular
                   spectrum management plan or standard by
                   adding newSpectrumMgmtStd to the
                   newSpectrumMgmtGeneralConfigTable."

	    REVISION "200301151300Z"
	    DESCRIPTION "Jesus Pinto
		1. Changed indexes on GeneralConfigTable.
		2. Removed DSL Line Table.
		3. Renamed newSpectrumMgmtAturMaxTxRate
		4. Renamed newSpectrumMgmtAturMinTxRate
		5. Renamed newSpectrumMgmtAturTxPower
		6. Renamed newSpectrumMgmtAtucMinTxRate
		7. Renamed newSpectrumMgmtAtucMaxTxRate
		8. Renamed newSpectrumMgmtAtucTxPower
		9. Added   newSpectrumMgmtXturMax2TxRate
		10.Added   newSpectrumMgmtXturMin2TxRate
		11.Added   newSpectrumMgmtXtucMax2TxRate
		12.Added   newSpectrumMgmtXtucMax2TxRate"

	    REVISION "200301091500Z"
	    DESCRIPTION "Jesus Pinto
		1. Deprecated spectrumMgmtTable and all its objects.
		2. Added newSpectrumMgmtTable.
		3. Added newSpectrumMgmtMode.
		4. Added newSpectrumMgmtEWLUnits.
		5. Added newSpectrumMgmtLoopMeasurementMethod.
		6. Added newSpectrumMgmtLineInfoTable.
		7. Added newSpectrumMgmtGeneralConfigTable."

	    REVISION "200105161530Z"
	    DESCRIPTION "R.A.Bowhall
	    	Added DEFVAL caluse,  Added the pdnSpecMgmtTraps,
	    	and pdnSpecMgmtMIBConformance info.
		Added an Informational Note at the Beginning of
		this MIB."

	    REVISION "200105080550Z"
	    DESCRIPTION "R.A.Bowhall
	    	Added the EWL Deployment Guidelines Table
	    	and Changed spectrumMgmtAllowedSpeeds to
		spectrumMgmtAllowedSpeedsMin1, spectrumMgmtAllowedSpeedsMax1,
		spectrumMgmtAllowedSpeedsMin2, spectrumMgmtAllowedSpeedsMax2"

	    ::= { pdn-interfaces 19 }

pdnSpecMgmtObjects		OBJECT IDENTIFIER ::= { pdnSpectrumMgmt 1 }
pdnNewSpecMgmtObjects		OBJECT IDENTIFIER ::= { pdnSpectrumMgmt 2 }

--
-- START OF Spectrum Management definitions
--

--
-- General options for spectrum management
--
newSpectrumMgmtGeneralConfigTable OBJECT-TYPE
     SYNTAX  SEQUENCE OF NewSpectrumMgmtGeneralConfigEntry
     MAX-ACCESS  not-accessible
     STATUS  current
     DESCRIPTION
	"General Configuration of the spectrum management.
	This table contains an entry for each technology
	managed by this device."
     ::= { pdnNewSpecMgmtObjects 1 }

newSpectrumMgmtGeneralConfigEntry OBJECT-TYPE
     SYNTAX  NewSpectrumMgmtGeneralConfigEntry
     MAX-ACCESS  not-accessible
     STATUS  current
     DESCRIPTION
	"An entry with the general spectrum mgmt configuration
	 parameters for a specific DSL technology."
    INDEX   { entPhysicalIndex, ifType }
    ::= { newSpectrumMgmtGeneralConfigTable 1 }

NewSpectrumMgmtGeneralConfigEntry ::= SEQUENCE {
     newSpectrumMgmtSelection		  INTEGER,
     newSpectrumMgmtMode		  INTEGER,
     newSpectrumMgmtLoopMeasurementMethod INTEGER,
     newSpectrumMgmtEWLUnits		  INTEGER,
     newSpectrumMgmtStd 		  INTEGER
}

newSpectrumMgmtSelection OBJECT-TYPE
     SYNTAX  INTEGER {
		enabled(1),
		disabled(2)
	 }
     MAX-ACCESS read-write
     STATUS  	current
     DESCRIPTION
	"This object is used to Enable or Disable 
	 Spectrum Management on DSL interfaces 
	 managed by this device. Enabling this object
	 limits the DSL speeds on each port based on
	 line length in order to meet ANSI T1.417
	 Spectrum Management requirements or BT Access
	 Network Spectrum requirements.

	The values that this object can accept are
        controlled by the -Mode- object.

        In cases where a particular spectrum management plan or
        standard needs to be selected, the ewSpectrumMgmtStd can
        be used to make that selection."

     ::= { newSpectrumMgmtGeneralConfigEntry 1 }

newSpectrumMgmtMode OBJECT-TYPE
    SYNTAX      INTEGER {
                    enableOnly(1),
                    disableOnly(2),
                    both(3)
                }
    MAX-ACCESS  read-only
    STATUS      current
    DESCRIPTION
       "This object restricts the MAX-ACCESS of the 'Selection'
        object.
        Following are the details of each of the values:

            enableOnly(1)  - Indicates that the 'Selection' object
                             IS always 'enabled' and cannot be set
                             to 'disabled'.
            disableOnly(2) - Indicates that the 'Selection' object
                             IS always 'disabled' and cannot be set
                             to 'enabled'.
            both(3)        - Indicates that the 'Selection' object
                             will accept both the 'enabled' and
                             'disabled' values."

    ::= { newSpectrumMgmtGeneralConfigEntry 2 }

newSpectrumMgmtLoopMeasurementMethod OBJECT-TYPE
    SYNTAX      INTEGER {
                    none(1),
                    loopLength(2),
                    ewl(3),
                    quadMode(4)
                }
    MAX-ACCESS  read-only
    STATUS      current
    DESCRIPTION
       "This object indicates the measurement method used in
        describing the Loop Length of a circuit. Following are the
        details of each of the options:

            none(1)       - Indicates that the Spectral Compliance
                            is NOT dependant on any Loop Length
                            measurements or configurations.
            loopLength(2) - The 'ConfLoopLength' object is used to
                            determine spectral compliance. The
                            'ConfEWL' & 'ConfQuadMode' objects are
                            not used in this mode.
            ewl(3)        - The 'ConfEWL' object is used to
                            configure the estimated loop length,
                            which is used to determine spectral
                            compliance. In this mode the
                            'ConfLoopLength' & 'ConfQuadMode'
                            objects are not used.
            quadMode(4)   - The 'ConfQuadMode' object is used to
                            determine spectral compliance. The
                            'ConfEWL' & 'ConfLoopLength' objects
                            are not used in this mode.

        This object determines which of the three objects :
        'ConfEWL', 'ConfLoopLength' or 'ConfQuadMode' is used
        (if any) to enforce spectrally compliant maximum
        'Tx Rates' and the maximum allowed 'Tx Power' on a given
        circuit."

    ::= { newSpectrumMgmtGeneralConfigEntry 3 }

newSpectrumMgmtEWLUnits OBJECT-TYPE
    SYNTAX      INTEGER {
                    none(1),
                    feet(2),
                    meters(3)
                }
    MAX-ACCESS  read-only
    STATUS      current
    DESCRIPTION
       "This object indicates the units of measurement used in
        describing the Estimated Working Length of a circuit.
        Following are the details of each of the units:

            none(1)     - Indicates that the Spectral Compliance is
                          NOT dependant on the 'ConfEWL' object.
            feet(2)     - The 'ConfEWL' is measured and configured
                          in feet.
            meters(3)   - The 'ConfEWL' is measured and configured
                          in meters."

    ::= { newSpectrumMgmtGeneralConfigEntry 4 }

newSpectrumMgmtStd OBJECT-TYPE
    SYNTAX      INTEGER {
                    none(1),
                    other(2),
                    ansiT1417(3),
                    anfpND1602(4),
                    jj10001(5)
                }
    MAX-ACCESS  read-write
    STATUS      current
    DESCRIPTION
       "This object indicates the spectrum management plan or standard 
        to which the entry is complying with.

            none(1)         - No special compliance scheme is specified.
            other(2)        - None of the selections listed next.
                              An example of other(2) could be the case
                              where initialization configuration files
                              are used to specify spectrum managment
                              compliance parameters.
            ansiT1417(3)    - Alliance for Telecommunications Industry
                              Solutions' T1.417 Spectrum Management for Loop
                              Transmission Systems.
            anfpND1602(4)   - Access Network Frequency Plan as specified
                              in the Network Interoperability Consultative
                              Committee's ND1602 document.
            jj10001(5)      - Telecommunications Technology Committee (TTC)
                              standard, `Spectrum Management for Metallic 
                              Transmission Systems Version 1'."

    ::= { newSpectrumMgmtGeneralConfigEntry 5 }

--
-- Spectrum Mgmt Configuration Table
--
newSpectrumMgmtConfTable OBJECT-TYPE
    SYNTAX      SEQUENCE OF NewSpectrumMgmtConfEntry
    MAX-ACCESS  not-accessible
    STATUS      current
    DESCRIPTION
       "The new Spectrum Management Configuration Table
        This table is used for configuring spectrum management
        objects on any DSL interface." 

    ::= { pdnNewSpecMgmtObjects 2 }

newSpectrumMgmtConfEntry OBJECT-TYPE
    SYNTAX      NewSpectrumMgmtConfEntry
    MAX-ACCESS  not-accessible
    STATUS      current
    DESCRIPTION
       "An entry in the xDSL Spectrum Management 
        Configuration table.

        Note: This entry can be accessed only for ifIndex 
              values that belong to a physical interface. 
              e.g. for ifType = 'shdsl' (IANAifType=169)."

    INDEX   { ifIndex }

    ::= { newSpectrumMgmtConfTable 1 }

NewSpectrumMgmtConfEntry ::= 
    SEQUENCE {
        newSpectrumMgmtConfEWL            	Unsigned32,
        newSpectrumMgmtConfLoopLength     	INTEGER,
        newSpectrumMgmtConfQuadMode       	INTEGER
    }

newSpectrumMgmtConfEWL OBJECT-TYPE
    SYNTAX      Unsigned32
    MAX-ACCESS  read-write
    STATUS      current
    DESCRIPTION
       "The Equivalent Working Length (EWL).  The value selected
        corresponds to the estimated length of the line in

            feet   - if 'EWLUnits' object is 'feet'.
            meters - if 'EWLUnits' object is 'meters'. 

        This value is usually specified by the carrier and MUST
        be in integral multiples of 

            500 feet, if 'EWLUnits' is 'feet'.
            200 meters, if 'EWLUnits' is 'meters'.

        The range of values that this object can take is determined
        by the 'MinEWL' and 'MaxEWL' objects.
        Changing this object may limit the maximum transmit power
        and the effective DSL speeds at which the ports train up.

        Note: This object will be used only if Spectrum Management
              is enabled and 'LoopMeasurementMethod' is 'ewl'.
              This object shares a mutual exclusion relationship
              with the 'ConfLoopLength' & 'ConfQuadMode' objects, 
	      as only one of the two will be used for configuration
	      at any time."

    ::= { newSpectrumMgmtConfEntry 1 }

newSpectrumMgmtConfLoopLength OBJECT-TYPE
    SYNTAX      INTEGER {
                    short(1),
                    medium(2),
                    long(3),
                    extraShort(4)
                }
    MAX-ACCESS  read-write
    STATUS      current
    DESCRIPTION
       "This entry specifies the loop length for the line. The
        configurable values are short(1), medium(2), long(3), and
        extraShort(4).

        The 'Loop Length' feature can be used only if the 
        'shdslSpectrumMgmtSelection' object is Enabled and
        the 'LoopMeasurementMethod' is 'loopLength'. Changing this
        object may limit the maximum transmit power and the
        effective DSL speeds at which ports train up.

        Note: This object shares a mutual exclusion relationship 
              with the 'ConfEWL'  objects. i.e. only one of the
	      three can be used for configuration at one time."

    ::= { newSpectrumMgmtConfEntry 2 }

newSpectrumMgmtConfQuadMode OBJECT-TYPE
    SYNTAX      INTEGER {
                    sameQuad(1),
                    segregatedQuadUpto3km(2),
                    segregatedQuadAbove3km(3)
                }
    MAX-ACCESS  read-write
    STATUS      current
    DESCRIPTION
       "This entry specifies the quad cable configuration &
        length for the line. The configurable values are
        sameQuad(1), segregatedQuadUpto3km(2) and
        segregatedQuadAbove3km(3). The 'Quad Mode' feature can be
        used only if the 'reachDSLSpectrumMgmtSelection' object
        is Enabled and the 'LoopMeasurementMethod' is 'quadMode'.
        Changing this object may limit the maximum transmit power
        and the effective DSL speeds at which ports train up.

        Note: This object shares a mutual exclusion relationship 
              with the 'ConfEWL' & 'ConfLoopLength' objects.
              i.e. only one of the three can be used for
              configuration at one time."

    ::= { newSpectrumMgmtConfEntry 3 }

--
-- Spectrum Management Line Info Table
--
newSpectrumMgmtLineInfoTable OBJECT-TYPE
    SYNTAX      SEQUENCE OF NewSpectrumMgmtLineInfoEntry
    MAX-ACCESS  not-accessible
    STATUS      current
    DESCRIPTION
       "The Spectrum Management Line Info Table.
        This table gives information about the spectrum 
        management ranges that are applicable for each port,
        based on the spectral requirements for the device."

    ::= { pdnNewSpecMgmtObjects 3 }

newSpectrumMgmtLineInfoEntry OBJECT-TYPE
    SYNTAX      NewSpectrumMgmtLineInfoEntry
    MAX-ACCESS  not-accessible
    STATUS      current
    DESCRIPTION
       "An entry in the newSpectrumMgmtLineInfoTable table.

        Note: This entry can be accessed only for ifIndex values
              that belong to a physical interface. 
              e.g. for ifType = 'adsl'."

    INDEX   { ifIndex }

    ::= { newSpectrumMgmtLineInfoTable 1 }

NewSpectrumMgmtLineInfoEntry ::= 
    SEQUENCE {
        newSpectrumMgmtXtucMax1TxRate  Unsigned32,
        newSpectrumMgmtXtucMin1TxRate  Unsigned32,
        newSpectrumMgmtXtucMax2TxRate  Unsigned32,
        newSpectrumMgmtXtucMin2TxRate  Unsigned32,
        newSpectrumMgmtXtucMaxTxPower  Integer32,
        newSpectrumMgmtXturMax1TxRate  Unsigned32,
        newSpectrumMgmtXturMin1TxRate  Unsigned32,
        newSpectrumMgmtXturMax2TxRate  Unsigned32,
        newSpectrumMgmtXturMin2TxRate  Unsigned32,
        newSpectrumMgmtXturMaxTxPower  Integer32,
        newSpectrumMgmtMinEWL          Unsigned32,
        newSpectrumMgmtMaxEWL          Unsigned32
    }

newSpectrumMgmtXtucMax1TxRate OBJECT-TYPE
    SYNTAX      Unsigned32
    UNITS       "bps"
    MAX-ACCESS  read-only
    STATUS      current
    DESCRIPTION
       "This rate will be the max allowed Tx Rate(in bps) for 
        the port based on the Spectrum Management requirements for
        XTUC in a particular spectral compliance configuration.
	
	Some measurement methods may have more than one range for
	the TxRate. Min1TxRate and Max1TxRate will always have
	the first range of values and the Min2TxRate and Max2TxRate
	will have the second range if the method demands it."
 
    ::= { newSpectrumMgmtLineInfoEntry 1 }

newSpectrumMgmtXtucMin1TxRate OBJECT-TYPE
    SYNTAX      Unsigned32
    UNITS       "bps"
    MAX-ACCESS  read-only
    STATUS      current
    DESCRIPTION
       "This rate will be the min allowed Tx Rate based on the
        spectrum management requirements for the XTUC. The
        MinTxRate will be upper bounded by 
	'newSpectrumMgmtXtucMax1TxRate' object.

	Some measurement methods may have more than one range for
	the TxRate. Min1TxRate and Max1TxRate will always have
	the first range of values and the Min2TxRate and Max2TxRate
	will have the second range if the method demands it."

    ::= { newSpectrumMgmtLineInfoEntry 2 }


newSpectrumMgmtXtucMax2TxRate OBJECT-TYPE
    SYNTAX      Unsigned32
    UNITS       "bps"
    MAX-ACCESS  read-only
    STATUS      current
    DESCRIPTION
       "This rate will be the max allowed Tx Rate(in bps) for 
        the port based on the Spectrum Management requirements for
        XTUC in a particular spectral compliance configuration.
	This object is the 
	
	Some measurement methods may have more than one range for
	the TxRate. Min1TxRate and Max1TxRate will always have
	the first range of values and the Min2TxRate and Max2TxRate
	will have the second range if the method demands it."
 
    ::= { newSpectrumMgmtLineInfoEntry 3 }

newSpectrumMgmtXtucMin2TxRate OBJECT-TYPE
    SYNTAX      Unsigned32
    UNITS       "bps"
    MAX-ACCESS  read-only
    STATUS      current
    DESCRIPTION
       "This rate will be the min allowed Tx Rate based on the
        spectrum management requirements for the XTUC. The
        MinTxRate will be upper bounded by 
	'newSpectrumMgmtXtucMax1TxRate' object.

	Some measurement methods may have more than one range for
	the TxRate. Min1TxRate and Max1TxRate will always have
	the first range of values and the Min2TxRate and Max2TxRate
	will have the second range if the method demands it."

    ::= { newSpectrumMgmtLineInfoEntry 4 }


newSpectrumMgmtXtucMaxTxPower OBJECT-TYPE
    SYNTAX      Integer32(-140..120)
    UNITS       "tenth dB"
    MAX-ACCESS  read-only
    STATUS      current
    DESCRIPTION
       "The maximum transmit power at the ATUC (in tenth dB).  
        This value will be based on the spectrum management
        selection."

    ::= { newSpectrumMgmtLineInfoEntry 5 }


newSpectrumMgmtXturMax1TxRate OBJECT-TYPE
    SYNTAX      Unsigned32
    UNITS       "bps"
    MAX-ACCESS  read-only
    STATUS      current
    DESCRIPTION
       "This rate will be the max allowed Tx Rate(in bps) for 
        the port based on the Spectrum Management requirements for
        XTUR in a particular spectral compliance configuration.
	This object is the 
	
	Some measurement methods may have more than one range for
	the TxRate. Min1TxRate and Max1TxRate will always have
	the first range of values and the Min2TxRate and Max2TxRate
	will have the second range if the method demands it."
 
    ::= { newSpectrumMgmtLineInfoEntry 6 }

newSpectrumMgmtXturMin1TxRate OBJECT-TYPE
    SYNTAX      Unsigned32
    UNITS       "bps"
    MAX-ACCESS  read-only
    STATUS      current
    DESCRIPTION
       "This rate will be the min allowed Tx Rate based on the
        spectrum management requirements for the XTUR. The
        MinTxRate will be upper bounded by 
	'newSpectrumMgmtXturMax1TxRate' object.

	Some measurement methods may have more than one range for
	the TxRate. Min1TxRate and Max1TxRate will always have
	the first range of values and the Min2TxRate and Max2TxRate
	will have the second range if the method demands it."

    ::= { newSpectrumMgmtLineInfoEntry 7 }


newSpectrumMgmtXturMax2TxRate OBJECT-TYPE
    SYNTAX      Unsigned32
    UNITS       "bps"
    MAX-ACCESS  read-only
    STATUS      current
    DESCRIPTION
       "This rate will be the max allowed Tx Rate(in bps) for 
        the port based on the Spectrum Management requirements for
        XTUR in a particular spectral compliance configuration.
	
	Some measurement methods may have more than one range for
	the TxRate. Min1TxRate and Max1TxRate will always have
	the first range of values and the Min2TxRate and Max2TxRate
	will have the second range if the method demands it."
 
    ::= { newSpectrumMgmtLineInfoEntry 8 }

newSpectrumMgmtXturMin2TxRate OBJECT-TYPE
    SYNTAX      Unsigned32
    UNITS       "bps"
    MAX-ACCESS  read-only
    STATUS      current
    DESCRIPTION
       "This rate will be the min allowed Tx Rate based on the
        spectrum management requirements for the XTUR. The
        MinTxRate will be upper bounded by 
	'newSpectrumMgmtXtucMax1TxRate' object.

	Some measurement methods may have more than one range for
	the TxRate. Min1TxRate and Max1TxRate will always have
	the first range of values and the Min2TxRate and Max2TxRate
	will have the second range if the method demands it."

    ::= { newSpectrumMgmtLineInfoEntry 9 }

newSpectrumMgmtXturMaxTxPower OBJECT-TYPE
    SYNTAX      Integer32(-140..120)
    UNITS       "tenth dB"
    MAX-ACCESS  read-only
    STATUS      current
    DESCRIPTION
       "The maximum transmit power at the ATUR (in tenth dB).  This
        value will be based on the spectrum management selection."

    ::= { newSpectrumMgmtLineInfoEntry 10 }

newSpectrumMgmtMinEWL OBJECT-TYPE
    SYNTAX      Unsigned32
    MAX-ACCESS  read-only
    STATUS      current
    DESCRIPTION
       "The minimum value (in feet, if 'EWLUnits' is 'feet, or in
        meters, if 'EWLUnits' is 'meters') that the 'ConfEWL'
        object can accept. Together with the 'MaxEWL' object,
        this object indicates the range of EWL when 'EWLUnits' is
        either 'feet' or 'meters'.

        Note : This object is valid only if the
               'LoopMeasurementMethod' object is 'ewl'."

    ::= { newSpectrumMgmtLineInfoEntry 11 }

newSpectrumMgmtMaxEWL OBJECT-TYPE
    SYNTAX      Unsigned32
    MAX-ACCESS  read-only
    STATUS      current
    DESCRIPTION
       "The maximum value (in feet, if 'EWLUnits' is 'feet, or in
        meters, if 'EWLUnits' is 'meters') that the 'ConfEWL'
        object can accept. Together with the 'MinEWL' object,
        this object indicates the range of EWL when 'EWLUnits' is
        either 'feet' or 'meters'.

        Note : This object is valid only if the
               'LoopMeasurementMethod' object is 'ewl'."

    ::= { newSpectrumMgmtLineInfoEntry 12 }

-- 
--		D E P R E C A T E D
--  
-- The following objects are supported for the first version
-- of the shdsl cards. They are now deprecated and should not
-- be used for future products.
--


--
-- General options
--
spectrumMgmtSelection OBJECT-TYPE
     SYNTAX  INTEGER {
		enabled(1),
		disabled(2)
	 }
     MAX-ACCESS  read-write
     STATUS  deprecated
     DESCRIPTION
	"This object is used to Enable or Disable 
	 Spectrum Management on this device. Enabling
	 this Object limits the DSL speeds on each port
	 based on line length in order to meet ANSI T1.417
	 Spectrum Management requirements or BT Access
	 Network Spectrum requirements.

	 The values that this object can accept are
         controlled by the -Mode- object."

     ::= { pdnSpecMgmtObjects 1 }

spectrumMgmtCountryCode OBJECT-TYPE
     SYNTAX  INTEGER {
		usa(1),
		uk(2)
	 }
     MAX-ACCESS  read-write
     STATUS  deprecated
     DESCRIPTION
	"This object selects which Spectrum Management 
	 standard will be used on this device to calculate the 
	 'allowed speeds' to comply with Spectrum Management.

	 Note:Spectrum Management must be Enabled for 'Country
	 Code' to take effect. 

	 'USA' is the only valid selection for Region Setting
	 'Annex A', 'UK' will not be selectable.

	 'UK' for is the only valid selecton for Region Setting
	 'Annex B', 'USA' will not be selectable."

       DEFVAL { usa }
     ::= { pdnSpecMgmtObjects 2 }


spectrumMgmtTable OBJECT-TYPE
     SYNTAX  SEQUENCE OF SpectrumMgmtEntry
     MAX-ACCESS  not-accessible
     STATUS  deprecated
     DESCRIPTION
	"The Spectrum Management Table."
	::= { pdnSpecMgmtObjects 3 }

spectrumMgmtEntry OBJECT-TYPE
     SYNTAX  SpectrumMgmtEntry
     MAX-ACCESS  not-accessible
     STATUS  deprecated
     DESCRIPTION
	"An entry in the Spectrum Management table."
    INDEX   { ifIndex }
    ::= { spectrumMgmtTable 1 }

SpectrumMgmtEntry ::= SEQUENCE {
     spectrumMgmtEWL			Integer32,
     spectrumMgmtLineLength		INTEGER,
     spectrumMgmtAllowedSpeedsMin1	Integer32,
     spectrumMgmtAllowedSpeedsMax1	Integer32,
     spectrumMgmtAllowedSpeedsMin2	Integer32,
     spectrumMgmtAllowedSpeedsMax2	Integer32
 }

spectrumMgmtEWL OBJECT-TYPE
     SYNTAX Integer32
     MAX-ACCESS read-write
     STATUS deprecated
     DESCRIPTION
	"The Estimated Working Length [EWL(ft)].  The value
	selected is the estimated length of the line in ft.
	See the Deployment guideline Table below.
	This value is usually specified by the carrier.  This 
	value is only required if spectrumMgmt is Enabled and
	the spectrumMgmtCountryCode selected is 'USA'."
     ::= { spectrumMgmtEntry 1 }

--  Estimated Working Length Deployment guidelines for G.shdsl
--  --------------------------------------------------------- 
-- | Line Bit Rate(kbps)  | Deployment guideline,EWL (ft)    |
--  --------------------------------------------------------- 
-- |     LBR <= 592       |          15500                   |
--  --------------------------------------------------------- 
-- |  600 <= LBR <= 616   |          15000                   |
-- |  624 <= LBR <= 648   |          14500                   |
-- |---------------------------------------------------------|
-- |  656 <= LBR <= 688   |          14000                   |
-- |  696 <= LBR <= 800   |          13500                   |
-- |---------------------------------------------------------|
-- |  808 <= LBR <= 832   |          12500                   |
-- |  840 <= LBR <= 896   |          12000                   |
-- |---------------------------------------------------------|
-- |  904 <= LBR <= 952   |          13000                   |
-- |  960 <= LBR <= 1000  |          12500                   |
-- |---------------------------------------------------------|
-- | 1008 <= LBR <= 1088  |          12000                   |
-- | 1096 <= LBR <= 1160  |          11500                   |
-- |---------------------------------------------------------|
-- | 1168 <= LBR <= 1320  |          11000                   |
-- | 1328 <= LBR <= 1472  |          10500                   |
-- |---------------------------------------------------------|
-- | 1480 <= LBR <= 1536  |          10000                   |
-- | 1544 <= LBR <= 1552  |          10500                   |
-- |---------------------------------------------------------|
-- | 1560 <= LBR <= 1664  |          10000                   |
-- | 1672 <= LBR <= 1880  |           9500                   |
-- |---------------------------------------------------------|
-- | 1888 <= LBR <= 2008  |           9000                   |
-- | 2016 <= LBR <= 2320  |           8500                   |
--  --------------------------------------------------------- 
-- Where LBR = Line Bit Rate
--
-- Note:Equivalent Working Length(EWL):EWL=L26+3(L24)/4,
--      where L26 is the total length of 26-gauge cable
--      in the loop excluding any bridged tap and L24 is
--      the total length of 19,22 or 24-gauge cable in
--      the loop excluding any bridged tap.   All lengths
--      are in kilofeet (ft). This formula is suitable for
--      use with systems operating below 1.1MHz.  
--
--      Note: Some EWL may have more then one range i.e., EWL
--      =12.5 Kft - ranges 192 Kbit/s to 832Kbits and 960 kbits
--      to 1000 kbits
--

spectrumMgmtAllowedSpeedsMin1 OBJECT-TYPE
     SYNTAX  Integer32
     MAX-ACCESS  read-only
     STATUS  deprecated
     DESCRIPTION
	"This rate will be the Minimum Line Bit Rate based
	 on the Line Length selected. 
	 See the Deployment guideline Table above.
	 Example: EWL=12.5 this value may be 808kbps"
     ::= { spectrumMgmtEntry 2 }

spectrumMgmtAllowedSpeedsMax1 OBJECT-TYPE
     SYNTAX  Integer32
     MAX-ACCESS  read-only
     STATUS  deprecated
     DESCRIPTION
	"This rate will be the Maximum Line Bit Rate based
	 on the Line Length selected
	 See the Deployment guideline Table above.
	 Example: EWL=12.5 this value may be 832kbps"
     ::= { spectrumMgmtEntry 3 }

spectrumMgmtAllowedSpeedsMin2 OBJECT-TYPE
     SYNTAX  Integer32
     MAX-ACCESS  read-only
     STATUS  deprecated
     DESCRIPTION
	"This rate will be the Minimum Line Bit Rate based
	 on the Line Length selected.
	 See the Deployment guideline Table above.
	 Example: EWL=12.5 this value may be 960kbps"
     ::= { spectrumMgmtEntry 4 }

spectrumMgmtAllowedSpeedsMax2 OBJECT-TYPE
     SYNTAX  Integer32
     MAX-ACCESS  read-only
     STATUS  deprecated
     DESCRIPTION
	"This rate will be the Maximum Line Bit Rate based
	 on the Line Length selected.
	 See the Deployment guideline Table above.
	 Example: EWL=12.5 this value may be 1000kbps"
     ::= { spectrumMgmtEntry 5 }

spectrumMgmtLineLength OBJECT-TYPE
     SYNTAX INTEGER {
		short(1),
		medium(2),
		long(3),
                extraShort(4)
	 }
     MAX-ACCESS read-write
     STATUS deprecated
     DESCRIPTION
	"This 'Line Length' feature is only required if the
	 SpectrumMgmt is Enabled and the spectrumMgmtCountryCode
	 selected is 'UK'.
	 'Short' Line Length from the exchange can support speeds
	 up to 2056 Kbps.
	 'Medium' Line Length can support speeds up to 1496 Kbps.
	 'Long' Line Length can suppport speeds up to 872 Kbps.
         'extraShort' Line Length can support speeds up to 2312 kbps."
     ::= { spectrumMgmtEntry 6 }



--
--	C O N F O R M A N C E       S T A T E M E N T S
--

   pdnSpecMgmtConformance	OBJECT IDENTIFIER 
		::= { pdnSpectrumMgmt 3 }

   pdnSpecMgmtGroups		OBJECT IDENTIFIER
		::= { pdnSpecMgmtConformance 1 }

   pdnSpecMgmtCompliances	OBJECT IDENTIFIER
		::= { pdnSpecMgmtConformance 2 }


-- 
-- 	C O M P L I A N C E       S T A T E M E N T S
--

pdnSpecMgmtCompliance 	MODULE-COMPLIANCE
    STATUS      current
    DESCRIPTION
       "The compliance statement for SNMP entities that control
        spectrum management on interfaces."

    MODULE   -- this module
        MANDATORY-GROUPS { 
            pdnGeneralConfigGroup,
            pdnLineInfoGroup
        }

--
-- Groups
--
-- pdnEWLModeGroup,
-- pdnLoopLengthModeGroup,
-- pdnQuadModeGroup
--
-- are mutually exclusive; that is, at most one of these groups
-- is implemented for a particular DSL interface. If the
-- Loop Measurement Method is 'none', then none of these groups
-- should be implemented.
--
    GROUP   pdnEWLModeGroup
    DESCRIPTION
       "This group is mandatory for DSL interfaces whose
        loop/line length measurement method is EWL.
        i.e.the newSpectrumMgmtLoopMeasurementMethod object
        is 'ewl'."

    GROUP   pdnLoopLengthModeGroup
    DESCRIPTION
       "This group is mandatory for DSL interfaces whose
        loop/line length measurement method is LoopLength.
        i.e.the newSpectrumMgmtLoopMeasurementMethod object
        is 'loopLength'."

    GROUP   pdnQuadModeGroup
    DESCRIPTION
       "This group is mandatory for DSL interfaces whose
        loop/line length measurement method is based on Quads.
        i.e.the newSpectrumMgmtLoopMeasurementMethod object
        is 'quadMode'."

    GROUP  pdnSpectrumMgmtStdGroup
    DESCRIPTION
       "This group is mandator for entities that support
        the configuration of the spectrum management plan
        or standard the entity is compliant with."

    OBJECT  	newSpectrumMgmtSelection
    MIN-ACCESS  read-only
    DESCRIPTION 
       "Write access is not required."

    ::= { pdnSpecMgmtCompliances 1 }

pdnSpecMgmtDeprecatedCompliance  MODULE-COMPLIANCE
    STATUS      deprecated
    DESCRIPTION
       "Compliance statement for deprecated groups."

     MODULE  -- this module

    GROUP  pdnSpectrumMgmtDeprecatedGroup
    DESCRIPTION
       "This group contains deprecated objects and should
        no longer be implemented."

    ::= { pdnSpecMgmtCompliances 2 }


	
--
-- 	U N I T S    O F    C O N F O R M A N C E
--

-- Mandatory group
pdnGeneralConfigGroup	OBJECT-GROUP
	OBJECTS {
		newSpectrumMgmtSelection,
		newSpectrumMgmtMode,
		newSpectrumMgmtLoopMeasurementMethod,
		newSpectrumMgmtEWLUnits
	}
	STATUS	current
	DESCRIPTION
		"A collection of general configuration objects
		required for the spectrum management of
		interfaces."

	::= { pdnSpecMgmtGroups 1 }

-- Mandatory group
pdnLineInfoGroup	OBJECT-GROUP
	OBJECTS {
	        newSpectrumMgmtXtucMax1TxRate,
        	newSpectrumMgmtXtucMin1TxRate,
	        newSpectrumMgmtXtucMax2TxRate,
        	newSpectrumMgmtXtucMin2TxRate,
         	newSpectrumMgmtXtucMaxTxPower,
        	newSpectrumMgmtXturMax1TxRate,
        	newSpectrumMgmtXturMin1TxRate,
        	newSpectrumMgmtXturMax2TxRate,
        	newSpectrumMgmtXturMin2TxRate,
        	newSpectrumMgmtXturMaxTxPower,
        	newSpectrumMgmtMinEWL,
        	newSpectrumMgmtMaxEWL
	}
	STATUS	current
	DESCRIPTION
		"A collection of objects providing information
		regarding spectrum management of interfaces."

	::= { pdnSpecMgmtGroups 2 }

--
-- Optional group
-- (pdnEWLModeGroup, pdnLineLoopModeGroup or pdnQuadModeGroup
--  should be implemented)
--
pdnEWLModeGroup	OBJECT-GROUP
	OBJECTS {
		newSpectrumMgmtConfEWL,
		newSpectrumMgmtMinEWL,
		newSpectrumMgmtMaxEWL
	}
	STATUS	current
	DESCRIPTION
		" A collection of configuration objects used to
		  control spectrum management of DSL intfs when
		  the measurement method is 'EWL'."

	::= { pdnSpecMgmtGroups 3 }

--
-- Optional group
-- (pdnEWLModeGroup, pdnLineLoopModeGroup or pdnQuadModeGroup
--  should be implemented)
--
pdnLoopLengthModeGroup	OBJECT-GROUP
	OBJECTS {
		newSpectrumMgmtConfLoopLength
	}
	STATUS	current
	DESCRIPTION
		" A collection of configuration objects used to
		  control spectrum management of DSL intfs when
		  the measurement method is 'LoopLength' "

	::= { pdnSpecMgmtGroups 4 }

--
-- Optional group
-- (pdnEWLModeGroup, pdnLineLoopModeGroup or pdnQuadModeGroup
--  should be implemented)
--
pdnQuadModeGroup OBJECT-GROUP
    	OBJECTS {
        	newSpectrumMgmtConfQuadMode
    	}
	STATUS      current
    	DESCRIPTION 
       		"A collection of object(s) providing configuration
        	access and information specific to DSL interfaces
        	whose loop/line length measurement method is based on the
        	Quad configuration.
        	i.e.the newSpectrumMgmtLoopMeasurementMethod object
        	is 'quadMode'."

    	::= { pdnSpecMgmtGroups 5 }

--
-- Optional group
-- (pdnSpectrumMgmtStdGroup)
--
pdnSpectrumMgmtStdGroup OBJECT-GROUP
    	OBJECTS {
        	newSpectrumMgmtStd
    	}
	STATUS      current
    	DESCRIPTION 
       		"A collection of object(s) providing configuration
                to comply with a particular spectrum management plan
                or standard."

    	::= { pdnSpecMgmtGroups 6 }

--
--		D E P R E C A T E D       G R O U P S
--
pdnSpectrumMgmtDeprecatedGroup	OBJECT-GROUP
	OBJECTS {
		spectrumMgmtSelection,
                spectrumMgmtCountryCode,
		spectrumMgmtEWL,
		spectrumMgmtLineLength,
		spectrumMgmtAllowedSpeedsMin1,
		spectrumMgmtAllowedSpeedsMax1,
		spectrumMgmtAllowedSpeedsMin2,
		spectrumMgmtAllowedSpeedsMax2
	}
	STATUS	deprecated
	DESCRIPTION
		" Deprecated objects "

	::= { pdnSpecMgmtGroups 7 }

END

-- ===============================================================
-- ==                                                           ==
-- ==      Copyright (C) 2000-2005 Paradyne Networks, Inc.      ==
-- ==                                                           ==
-- ===============================================================

PDN-ATMEXT-MIB DEFINITIONS ::= BEGIN

    IMPORTS
        MODULE-IDENTITY, OBJECT-IDENTITY,
        OBJECT-TYPE, Integer32, NOTIFICATION-TYPE,
        Unsigned32
            FROM SNMPv2-SMI
        DisplayString,TruthValue
            FROM SNMPv2-TC
        NOTIFICATION-GROUP, OBJECT-GROUP, MODULE-COMPLIANCE
            FROM SNMPv2-CONF
        pdnAtm
            FROM PDN-HEADER-MIB
       ifIndex,ifOperStatus
            FROM IF-MIB
       atmInterfaceConfEntry, atmTrafficDescrParamEntry,
       atmVpCrossConnectAdminStatus, atmVcCrossConnectAdminStatus,
       aal5VccEntry, atmVclEntry
            FROM ATM-MIB;

    pdnAtmExtMIB MODULE-IDENTITY
        LAST-UPDATED "200503110000Z"     -- March 11, 2005
        ORGANIZATION "Paradyne Networks
                      MIB Working Group"
        CONTACT-INFO "Paradyne Networks, Inc
                      8454 126th Avenue North
                      Largo, FL 33773 
                      www.paradyne.com

                      General Comments to: mibwg_team@eng.paradyne.com"

        DESCRIPTION
            "This MIB Module extends the ATM-MIB defined in rfc2515

             =============================================================
             ==                                                         ==
             ==     Copyright (C) 2000-2005 Paradyne Networks, Inc.     ==
             ==                                                         ==
             ============================================================="
            
        REVISION "200503110000Z"
        DESCRIPTION "C Sikes
            o  Minor clean up.  White space and non-MIB related clean up."
        REVISION "200503010000Z"
        DESCRIPTION "I. Jasmin
            o  Added pdnAtmVclExtTable"
        REVISION "200305150000Z"
        DESCRIPTION "P. Easwar
            o  Changed object name pdnAtmTrafficRateShape
               to pdnAtmTrafficShaping"
        REVISION "200305110000Z"
        DESCRIPTION "P. Easwar
            o  Added Two New Traffic Descriptor Types
                  o pdnAtmNoClpTaggingNoScrCdvtMdcr
                  o pdnAtmNoClpNoScrCdvtMdcr"
        REVISION "200304310000Z"
        DESCRIPTION "P. Easwar
            o  Added pdnAtmTrafficRateShape."

        REVISION "200303310000Z"
        DESCRIPTION "C. Sikes
            o  Added pdnAal5VccExtTable."

        REVISION "200203270000Z"
        DESCRIPTION "J. Pinto
            o  Added pdnAtmIfConfExtRateShape"
        
        REVISION "200012290000Z"
        DESCRIPTION "P. Easwar
            o  modified the following traps (name/description)
                o pdnAtmIfConfExtLineRateAlarmSet
                o pdnAtmIfConfExtLineRateAlarmClear
                ...to the following 
                o pdnAtmIfConfExtEgressLineRateAlarmSet
                o pdnAtmIfConfExtEgressLineRateAlarmClear
            o  added the following traps
                o pdnAtmIfConfExtIngressLineRateAlarmSet
                o pdnAtmIfConfExtIngressLineRateAlarmClear
            o  deleted the following traps
                o pdnAtmCACGauranteeFailed
                o pdnAtmCACGauranteeRestored"

        REVISION "200012010000Z"
        DESCRIPTION "R. Steinberger
            o Added pdnAtmCACGauranteeFailed and pdnAtmCACGauranteeRestored.
            " 
        
        REVISION "200007060000Z"
        DESCRIPTION "P. Easwar
            o  added the following traps 
                o pdnAtmIfConfExtLineRateAlarmSet
                o pdnAtmIfConfExtLineRateAlarmClear
                o pdnAtmIfConfExtVplNoBandwidthAvail
                o pdnAtmIfConfExtVclNoBandwidthAvail
                o changed the description of the following objects
                o pdnAtmIfConfExtVbrRtBandwidthUtil
                o pdnAtmIfConfExtVbrNrtBandwidthUtil
                o  removed the DEFVAL clause from the following objects
                o pdnAtmIfConfExtVbrRtBandwidthUtil
                o pdnAtmIfConfExtVbrNrtBandwidthUtil"

        REVISION "200004280000Z"
        DESCRIPTION "J. Strain
            o  added the following objects to pdnAtmIfConfExtTable
                o pdnAtmIfConfExtBandwidthUtilCbrReserved
                o pdnAtmIfConfExtBandwidthUtilCbrAssigned
                o pdnAtmIfConfExtBandwidthUtilVbrRtReserved
                o pdnAtmIfConfExtBandwidthUtilVbrRtAssigned
                o pdnAtmIfConfExtBandwidthUtilVbrNrtReserved
                o pdnAtmIfConfExtBandwidthUtilVbrNrtAssigned
                o pdnAtmIfConfExtBandwidthUtilUbrReserved
                o pdnAtmIfConfExtBandwidthUtilUbrAssigned"

        REVISION "200003110000Z"
        DESCRIPTION "P. Easwar
            o  added pdnAtmIfConfExtUnknownCellThreshold
               and pdnAtmIfConfExtOcdEventThreshold"
        REVISION "200002180000Z"
        DESCRIPTION "P. Easwar
            o  Initial Release"

         ::= {  pdnAtm 5 }

    pdnAtmExtMIBObjects    OBJECT IDENTIFIER ::= { pdnAtmExtMIB 1 }
    pdnAtmExtMIBTraps      OBJECT IDENTIFIER ::= { pdnAtmExtMIB 2 }
    pdnAtmExtMIBTrapPrefix OBJECT IDENTIFIER ::= { pdnAtmExtMIBTraps 0 }
    pdnAtmExtMIBConformance OBJECT IDENTIFIER ::= { pdnAtmExtMIB 3 }
    pdnAtmExtMIBTrafficDescriptorTypes   OBJECT IDENTIFIER ::= { pdnAtmExtMIB 4 }

pdnAtmNoClpTaggingNoScrCdvtMdcr   OBJECT-IDENTITY
      STATUS   current
      DESCRIPTION
              "This Traffic Descriptor type is for no CLP with tagging
               and no Sustained Cell Rate. The Use of the Parameter
               Vector for this type:
               Parameter 1: Peak Cell Rate in cells/second
                            CLP=0+1 traffic
               Parameter 2: CDVT in tenths of a microsecond
               Parameter 3: Minimum Desired Cell Rate in cells/second (<= PCR)
               Parameter 4: Tolerance To the MDCR Commitment
                            (>= 1/MDCR) in milliseconds
               Parameter 5: not used

               This Traffic Descriptor type is applicable to connections
               following the UBR.2 conformance definition"
      REFERENCE
               "ATM Forum, ATM User-Network Interface,
                 Version 3.0 (UNI 3.0) Specification, 1994.
                ATM Forum, ATM User-Network Interface,
                 Version 3.1 (UNI 3.1) Specification
                 November 1994.
                ATM Forum, Traffic Management Specification,
                 Version 4.0, af-tm-0056.000, June 1996.
                ATM Forum, Traffic Management Specification,
                 Version 4.1, af-tm-0121.000, March 1999.
                ATM Forum, Addendum to Traffic Management Specification,
                 Version 4.1, for an optional Minimum Desired 
                 Cell Rate (MDCR), af-tm-0150.000, July 2000."
      ::= { pdnAtmExtMIBTrafficDescriptorTypes 1   }

pdnAtmNoClpNoScrCdvtMdcr   OBJECT-IDENTITY
      STATUS   current
      DESCRIPTION
              "This Traffic Descriptor type is for no CLP
               and no Sustained Cell Rate. The Use of the Parameter
               Vector for this type:
               Parameter 1: Peak Cell Rate in cells/second
                            CLP=0+1 traffic
               Parameter 2: CDVT in tenths of a microsecond
               Parameter 3: Minimum Desired Cell Rate in cells/second (<= PCR)
               Parameter 4: Tolerance To the MDCR Commitment
                            (>= 1/MDCR) in milliseconds
               Parameter 5: not used
               This Traffic Descriptor type is applicable to connections
               following the UBR.1 conformance definition"
      REFERENCE
               "ATM Forum, ATM User-Network Interface,
                 Version 3.0 (UNI 3.0) Specification, 1994.
                ATM Forum, ATM User-Network Interface,
                 Version 3.1 (UNI 3.1) Specification
                 November 1994.
                ATM Forum, Traffic Management Specification,
                 Version 4.0, af-tm-0056.000, June 1996.
                ATM Forum, Traffic Management Specification,
                 Version 4.1, af-tm-0121.000, March 1999.
                ATM Forum, Addendum to Traffic Management Specification,
                 Version 4.1, for an optional Minimum Desired 
                 Cell Rate (MDCR), af-tm-0150.000, July 2000."
      ::= { pdnAtmExtMIBTrafficDescriptorTypes 2   }

-- ===============================================================
--
--  Extentions to the ATM Interface Config Table (RFC 2515)
--
--  Release: 1.0  02/18/00 (Initial Release) Prakash Easwar
--
--  This MIB is intended to AUGMENT the atmInterfaceConfTable of the ATM-MIB
--

pdnAtmIfConfExtTable OBJECT-TYPE
    SYNTAX  SEQUENCE OF PdnAtmIfConfExtEntry
    MAX-ACCESS  not-accessible
    STATUS  current
    DESCRIPTION
      "The Paradyne Extension to the atmInterfaceConfTable of the ATM-MIB."
    ::= { pdnAtmExtMIBObjects 1   }

pdnAtmIfConfExtEntry OBJECT-TYPE
    SYNTAX  PdnAtmIfConfExtEntry
    MAX-ACCESS  not-accessible
    STATUS  current
    DESCRIPTION
       "An entry in the Paradyne Extension to the atmInterfaceConfTable of 
       the ATM-MIB."
    AUGMENTS { atmInterfaceConfEntry }
    ::= { pdnAtmIfConfExtTable  1 }

PdnAtmIfConfExtEntry ::=
    SEQUENCE {
    
    pdnAtmIfConfExtVbrRtBandwidthUtil
        Integer32,

    pdnAtmIfConfExtVbrNrtBandwidthUtil
        Integer32,
      
    pdnAtmIfConfExtHecErrorThreshold     
        Integer32,

    pdnAtmIfConfExtUnknownCellThreshold
        Integer32,

    pdnAtmIfConfExtOcdEventThreshold
        Integer32,

    pdnAtmIfConfExtBandwidthUtilCbrReserved
        Integer32,

    pdnAtmIfConfExtBandwidthUtilCbrAssigned
        Integer32,

    pdnAtmIfConfExtBandwidthUtilVbrRtReserved
        Integer32,

    pdnAtmIfConfExtBandwidthUtilVbrRtAssigned
        Integer32,

    pdnAtmIfConfExtBandwidthUtilVbrNrtReserved
        Integer32,

    pdnAtmIfConfExtBandwidthUtilVbrNrtAssigned
        Integer32,

    pdnAtmIfConfExtBandwidthUtilUbrReserved
        Integer32,

    pdnAtmIfConfExtBandwidthUtilUbrAssigned
        Integer32,

    pdnAtmIfConfExtRateShape
        Integer32
    }

pdnAtmIfConfExtVbrRtBandwidthUtil OBJECT-TYPE
    SYNTAX  Integer32 (0..9999)
    MAX-ACCESS  read-write
    STATUS  current
    DESCRIPTION
           "The bandwidth utilization for realtime vbr type traffic
            expressed as a percentage."
    ::= { pdnAtmIfConfExtEntry 1 }

pdnAtmIfConfExtVbrNrtBandwidthUtil OBJECT-TYPE
   SYNTAX  Integer32 (0..9999)
   MAX-ACCESS  read-write
   STATUS  current
   DESCRIPTION
           "The bandwidth utilization for non-realtime VBR type traffic
            expressed as a percentage."
   ::= { pdnAtmIfConfExtEntry 2 }
 
pdnAtmIfConfExtHecErrorThreshold OBJECT-TYPE
   SYNTAX  Integer32
   MAX-ACCESS  read-write
   STATUS  current
   DESCRIPTION
       "The value of this object represents the threshold value for
        the number of uncrorrectable HEC errors in a 15 minutes interval.
        An SNMP link Up/Down trap would be generated if the number of
        uncorrectable HEC errors in a 15 minutes interval exceeds this threshold.
        The valid range of this object is 0 to 1000. A value of 0 will cause
        a trap to be sent on each occurrence of a HEC error. A value of
        -9999 disables the threshold check.
        The default value for this object is 100. "
   DEFVAL  { 100 }
   ::= { pdnAtmIfConfExtEntry 3 }
  
 pdnAtmIfConfExtUnknownCellThreshold OBJECT-TYPE
   SYNTAX  Integer32
   MAX-ACCESS  read-write
   STATUS  current
   DESCRIPTION
       "The value of this object represents the threshold value for
        the number of unknown cells in a 15 minutes interval.
        An SNMP trap would be generated if the number of unknown
        cell in a 15 minutes interval exceeds this threshold.
        The valid range of this object is 0 to 1000. A value of 0 will
        cause a trap to be sent on each occurrence of an unknown cell.
        A value of -9999 disables the threshold check.
        The default value for this object is 10"
   DEFVAL  { 10 }
   ::= { pdnAtmIfConfExtEntry 4 }

 pdnAtmIfConfExtOcdEventThreshold OBJECT-TYPE
   SYNTAX  Integer32
   MAX-ACCESS  read-write
   STATUS  current
   DESCRIPTION
       "The value of this object represents the threshold value for
        the number of Out of Cell Delineation(OCD) events in a 15
        minutes interval. An SNMP trap would be generated if the number
        of OCD events in a 15 minutes interval exceeds this threshold.
        The valid range of this object is 0 to 1000. A value of 0 will
        cause a trap to be sent on each occurrence of a HEC error.
        A value of -9999 disables the threshold check.
        The default value for this object is 0"
   DEFVAL  { 0 }
   ::= { pdnAtmIfConfExtEntry 5 }


pdnAtmIfConfExtBandwidthUtilCbrReserved OBJECT-TYPE
          SYNTAX  Integer32
          MAX-ACCESS     read-write
          STATUS         current
          DESCRIPTION
           "This object specifies the percent of the interface bandwidth to
            be allocated to the CBR traffic class."
          ::= { pdnAtmIfConfExtEntry  6}

pdnAtmIfConfExtBandwidthUtilCbrAssigned OBJECT-TYPE
          SYNTAX  Integer32
          MAX-ACCESS     read-only
          STATUS         current
          DESCRIPTION
           "This object specifies the percent of bandwidth utilization
            (sometimes reffered to as over subscription) the connection
            Addmission Control algorithm has already allowed for the CBR class
            of service."
          ::= { pdnAtmIfConfExtEntry  7}

pdnAtmIfConfExtBandwidthUtilVbrRtReserved OBJECT-TYPE
          SYNTAX  Integer32
          MAX-ACCESS     read-write
          STATUS         current
          DESCRIPTION
           "This object specifies the percent of the interface bandwidth to
            be allocated to the VBR-rt traffic class."
          ::= { pdnAtmIfConfExtEntry  8}

pdnAtmIfConfExtBandwidthUtilVbrRtAssigned OBJECT-TYPE
          SYNTAX  Integer32
          MAX-ACCESS     read-only
          STATUS         current
          DESCRIPTION
           "This object specifies the percent of bandwidth utilization
            (sometimes reffered to as over subscription) the connection
            Addmission Control algorithm has already allowed for the VBR-rt class
            of service."
          ::= { pdnAtmIfConfExtEntry  9}

pdnAtmIfConfExtBandwidthUtilVbrNrtReserved OBJECT-TYPE
          SYNTAX  Integer32
          MAX-ACCESS     read-write
          STATUS         current
          DESCRIPTION
           "This object specifies the percent of the interface bandwidth to
            be allocated to the VBR-nrt traffic class."
          ::= { pdnAtmIfConfExtEntry  10}

pdnAtmIfConfExtBandwidthUtilVbrNrtAssigned OBJECT-TYPE
          SYNTAX  Integer32
          MAX-ACCESS     read-only
          STATUS         current
          DESCRIPTION
           "This object specifies the percent of bandwidth utilization
            (sometimes reffered to as over subscription) the connection
            Addmission Control algorithm has already allowed for the VBR-nrt class
            of service."
          ::= { pdnAtmIfConfExtEntry  11}

pdnAtmIfConfExtBandwidthUtilUbrReserved OBJECT-TYPE
          SYNTAX  Integer32
          MAX-ACCESS     read-write
          STATUS         current
          DESCRIPTION
           "This object specifies the percent of the interface bandwidth to
            be allocated to the UBR traffic class."
          ::= { pdnAtmIfConfExtEntry  12}

pdnAtmIfConfExtBandwidthUtilUbrAssigned OBJECT-TYPE
          SYNTAX  Integer32
          MAX-ACCESS     read-only
          STATUS         current
          DESCRIPTION
           "This object specifies the percent of bandwidth utilization
            (sometimes reffered to as over subscription) the connection
            Addmission Control algorithm has already allowed for the UBR class
            of service."
          ::= { pdnAtmIfConfExtEntry 13}

pdnAtmIfConfExtRateShape OBJECT-TYPE
          SYNTAX  Integer32 (512..46080)
      UNITS "Kbps"
          MAX-ACCESS     read-write
          STATUS         current
          DESCRIPTION
           "This object is used to specify rate shaping on this interface.
            The valid range of this object is 512 to 46080 [512K..46Mbps] 
        with increments of 64K. The default value will be set depending
        on the interface." 
          ::= { pdnAtmIfConfExtEntry 14}

-- ===============================================================
--
--   Extentions to the ATM Interface Config Table (RFC 2515)
--
--  Release: 1.0  02/18/00 (Initial Release) Prakash Easwar
--
-- This MIB is intended to AUGMENT the atmTrafficDescrParamTable of the ATM-MIB
--

pdnAtmTrafficDescrParamExtTable OBJECT-TYPE
    SYNTAX  SEQUENCE OF PdnAtmTrafficDescrParamExtEntry
    MAX-ACCESS  not-accessible
    STATUS  current
    DESCRIPTION
       "The Paradyne Extension to the atmTrafficDescrParamTable of the ATM-MIB."
    ::= { pdnAtmExtMIBObjects 2   }

pdnAtmTrafficDescrParamExtEntry OBJECT-TYPE
    SYNTAX  PdnAtmTrafficDescrParamExtEntry
    MAX-ACCESS  not-accessible
    STATUS  current
    DESCRIPTION
           "An entry in the Paradyne Extension to the atmTrafficDescrParamTable
           of the ATM-MIB."
    AUGMENTS { atmTrafficDescrParamEntry }
    ::= { pdnAtmTrafficDescrParamExtTable  1 }

PdnAtmTrafficDescrParamExtEntry ::=
    SEQUENCE {

    pdnAtmTrafficDescrParamName
        DisplayString,

    pdnAtmTrafficPolicing
        TruthValue,
    
    pdnAtmTrafficShaping
        TruthValue
    }

pdnAtmTrafficDescrParamName OBJECT-TYPE
          SYNTAX  DisplayString (SIZE(1..12))
          MAX-ACCESS     read-create
          STATUS         current
          DESCRIPTION
           "The value of this Object identifies the traffic descriptor by a
            by a name."
          ::= { pdnAtmTrafficDescrParamExtEntry  1}

pdnAtmTrafficPolicing OBJECT-TYPE
          SYNTAX  TruthValue
          MAX-ACCESS     read-create
          STATUS         current
          DESCRIPTION
           "The value of this Object determines whether or not
            the vcl/vpl to which this traffic descriptor
            is bound will be policed"
          ::= { pdnAtmTrafficDescrParamExtEntry  2}

pdnAtmTrafficShaping OBJECT-TYPE
          SYNTAX  TruthValue
          MAX-ACCESS     read-create
          STATUS         current
          DESCRIPTION
           "The value of this Object determines whether or not
            the vcl/vpl to which this traffic descriptor
            is bound will be rate shaped to the specified
            traffic contract"
          ::= { pdnAtmTrafficDescrParamExtEntry  3}

-- ===============================================================
--
--   Extentions to the ATM AAL5 Virtual Channel Connection 
--   Performance Statistics Table (aal5VccTable) in the ATM-MIB
--   (RFC 2515).
--
--
-- This MIB is intended to AUGMENT the aal5VccTable of the ATM-MIB.
--

pdnAal5VccExtTable OBJECT-TYPE
    SYNTAX  SEQUENCE OF PdnAal5VccExtEntry
    MAX-ACCESS  not-accessible
    STATUS  current
    DESCRIPTION
       "The Paradyne Extension to the aal5VccTable in the ATM-MIB."
    ::= { pdnAtmExtMIBObjects 3  }

pdnAal5VccExtEntry OBJECT-TYPE
    SYNTAX  PdnAal5VccExtEntry
    MAX-ACCESS  not-accessible
    STATUS  current
    DESCRIPTION
           "An entry in the Paradyne Extension to the aal5VccTable.
           in the ATM-MIB."
    AUGMENTS { aal5VccEntry }
    ::= { pdnAal5VccExtTable  1 }

PdnAal5VccExtEntry ::=
    SEQUENCE {
        pdnAal5VccExtOutPDUs        Unsigned32,
        pdnAal5VccExtInPDUs         Unsigned32
    }

pdnAal5VccExtOutPDUs OBJECT-TYPE
          SYNTAX         Unsigned32
          MAX-ACCESS     read-only
          STATUS         current
          DESCRIPTION
           "The total number of AAL5 CPCS PDUs transmitted on the
           interface associated with an AAL5 entry."
          ::= { pdnAal5VccExtEntry  1}

pdnAal5VccExtInPDUs OBJECT-TYPE
          SYNTAX         Unsigned32
          MAX-ACCESS     read-only
          STATUS         current
          DESCRIPTION
           "This total number of AAL5 CPCS PDUs transmitted on the
           interface associated with an AAL5 entry."
          ::= { pdnAal5VccExtEntry  2}

-- ===============================================================
--
--   Extentions to the ATM Interface Virtual Channel Link Table 
--   (atmVclTable) in the ATM-MIB (RFC 2515).
--
-- This MIB is intended to AUGMENT the atmVclTable of the ATM-MIB.
--

pdnAtmVclExtTable  OBJECT-TYPE
    SYNTAX         SEQUENCE OF PdnAtmVclExtEntry
    MAX-ACCESS     not-accessible
    STATUS         current
    DESCRIPTION    "The extension to the atmVcl table in the ATM-MIB.
                    This table defines the PPP over AAL5 encapsulation
                    types."                                       
    ::= { pdnAtmExtMIBObjects 4  }

pdnAtmVclExtEntry  OBJECT-TYPE
    SYNTAX         PdnAtmVclExtEntry
    MAX-ACCESS     not-accessible
    STATUS         current
    DESCRIPTION    "An entry in the extended VCL table."
    AUGMENTS       { atmVclEntry }
    ::= { pdnAtmVclExtTable 1}

PdnAtmVclExtEntry ::=
    SEQUENCE {
        pdnAtmVccAal5EncapsType    INTEGER
    }

pdnAtmVccAal5EncapsType  OBJECT-TYPE
    SYNTAX         INTEGER {
                       vcMultiplexPppoA(1),
                       llcEncapsulationPppoA(2),
                       invalid(3)
                   }
    MAX-ACCESS     read-create
    STATUS         current
    DESCRIPTION    "This object defines the type of PPP over AAL5 
                    encapsulation types.  If the atmVccAal5EncapsType 
                    in the atmVcl table, in the ATM-MIB, is set to 
                    'other', this object becomes valid. It will then 
                    contain a PPPoA encapsulation type, or 'invalid', 
                    otherwise.  Sets or writes on this object are only
                    permitted when the atmVccAal5EncapsType is set to
                    'other'."
    REFERENCE      "RFC 2515, Definitions of Managed Objects for 
                               ATM Management, Section 7.3, 
                               Support of AAL5 by ifTable.
                    RFC 2364, PPP Over AAL5"                 
    ::= { pdnAtmVclExtEntry 1}
    
-- ===============================================================
--
-- Trap group
--

pdnAtmIfConfExtExcessInvalidCellsAlarm NOTIFICATION-TYPE
   OBJECTS { ifOperStatus,
             pdnAtmIfConfExtUnknownCellThreshold
           }
   STATUS current
   DESCRIPTION
       "This alarm indicates that the number of cells with
        uncorrectable HEC erros has exceeded the used defined
        the threshold. "
   ::= { pdnAtmExtMIBTrapPrefix 1 }

pdnAtmIfConfExtEgressLineRateAlarmSet NOTIFICATION-TYPE
   OBJECTS { ifIndex }
   STATUS current
   DESCRIPTION
       "This alarm indicates that the line rate of the specified
        interface has dropped below a value which violates the
        traffic contracts of the admitted connections in the egress
        (transmit) direction"
   ::= { pdnAtmExtMIBTrapPrefix 2 }

pdnAtmIfConfExtEgressLineRateAlarmClear NOTIFICATION-TYPE
   OBJECTS { ifIndex }
   STATUS current
   DESCRIPTION
       "This alarm indicates that the line rate of the specified
        interface has risen above a value which would no longer violate the
        traffic contracts of the admitted connections in the egress 
        (transmit) direction"
   ::= { pdnAtmExtMIBTrapPrefix 102 }

pdnAtmIfConfExtVplNoBandwidthAvail NOTIFICATION-TYPE
   OBJECTS { atmVpCrossConnectAdminStatus }
   STATUS current
   DESCRIPTION
       "This alarm indicates that the traffic contract(s)
       associated with the Virtual Path (VP) Cross Connect
       cannot be satisfied by the ATM switch.
       It is left upto the implementation to decide whether or 
       not the VP cross connect will be admitted"
   ::= { pdnAtmExtMIBTrapPrefix 3 }

pdnAtmIfConfExtVclNoBandwidthAvail NOTIFICATION-TYPE
   OBJECTS { atmVcCrossConnectAdminStatus }
   STATUS current
   DESCRIPTION
       "This alarm indicates that the traffic contract(s)
       associated with the Virtual Channel (VC) Cross Connect
       cannot be satisfied by the ATM switch.
       It is left upto the implementation to decide whether or 
       not the VC cross connect will be admitted"
   ::= { pdnAtmExtMIBTrapPrefix 4 }

pdnAtmIfConfExtIngressLineRateAlarmSet NOTIFICATION-TYPE
   OBJECTS { ifIndex }
   STATUS current
   DESCRIPTION
       "This alarm indicates that the line rate of the specified
        interface has dropped below a value which violates the
        traffic contracts of the admitted connections in the ingress
        (receive) direction"
   ::= { pdnAtmExtMIBTrapPrefix 5 }

pdnAtmIfConfExtIngressLineRateAlarmClear NOTIFICATION-TYPE
   OBJECTS { ifIndex }
   STATUS current
   DESCRIPTION
       "This alarm indicates that the line rate of the specified
        interface has risen above a value which would no longer violate the
        traffic contracts of the admitted connections in the ingress
        (receive) direction"
   ::= { pdnAtmExtMIBTrapPrefix 105 }


-- ===============================================================
-- ==
-- == Conformance Information
-- ==
-- ===============================================================

pdnAtmExtMibCompliances   OBJECT IDENTIFIER ::= { pdnAtmExtMIBConformance 1 }
pdnAtmExtMibGroups        OBJECT IDENTIFIER ::= { pdnAtmExtMIBConformance 2 }


--
-- Compliance Statements
--
pdnAtmExtMIBCompliance MODULE-COMPLIANCE
    STATUS      current
    DESCRIPTION "The compliance statement for pdnAtmExtMIB entities which
                 implement the pdnAtmExtMIB."
    MODULE      -- this module

    GROUP       pdnAtmIfConfExtGroup
    DESCRIPTION "This group associates objects related to the DSL line
                 and is mandatory only for those entities which implement ADSL2 
                 or ADSL2plus capabilities and providing that no IETF standard
                 MIB exists that has objects allowing ADSL2 or ADSL2plus 
                 capabilities to be identified and controlled."      
                 
    GROUP       pdnAtmTrafficDescrParamExtGroup
    DESCRIPTION "A collection of objects providing ATM traffic descriptor
                 types and the associated parameters."                 
                 
    GROUP       pdnAal5VccExtGroup
    DESCRIPTION "A collection of objects providing the AAL5 performance 
                 statistics of a VCC at the interface associated with an 
                 AAL5 entity in an ATM host or ATM switch"           
                       
    GROUP       pdnAtmVccAal5EncapsGroup
    DESCRIPTION "A collection of objects providing AAL5 encapsulation
                 type configured."                                 
    
    GROUP       pdnAtmExtNotificationGroup
    DESCRIPTION "A collection of traps providing the state of the ATM VC 
                 or VP"                 

    OBJECT      pdnAtmVccAal5EncapsType
    MIN-ACCESS  read-only
    DESCRIPTION "Write access is not required."
                
    ::= { pdnAtmExtMibCompliances 1 }            



    
-- No MANDATORY-GROUPS are specified


--
-- Units of Conformance
--

pdnAtmIfConfExtGroup OBJECT-GROUP
   OBJECTS {
      pdnAtmIfConfExtVbrRtBandwidthUtil,
      pdnAtmIfConfExtVbrNrtBandwidthUtil,
      pdnAtmIfConfExtHecErrorThreshold,
      pdnAtmIfConfExtUnknownCellThreshold,
      pdnAtmIfConfExtOcdEventThreshold,
      pdnAtmIfConfExtBandwidthUtilCbrReserved,
      pdnAtmIfConfExtBandwidthUtilCbrAssigned,
      pdnAtmIfConfExtBandwidthUtilVbrRtReserved,
      pdnAtmIfConfExtBandwidthUtilVbrRtAssigned,
      pdnAtmIfConfExtBandwidthUtilVbrNrtReserved,
      pdnAtmIfConfExtBandwidthUtilVbrNrtAssigned,
      pdnAtmIfConfExtBandwidthUtilUbrReserved,
      pdnAtmIfConfExtBandwidthUtilUbrAssigned,
      pdnAtmIfConfExtRateShape
   }
   STATUS current
   DESCRIPTION
       "Objects grouped for the pdnAtmIfConfExtTable."
   ::= { pdnAtmExtMibGroups 1 }

pdnAtmTrafficDescrParamExtGroup OBJECT-GROUP
   OBJECTS {
      pdnAtmTrafficDescrParamName,
      pdnAtmTrafficPolicing,
      pdnAtmTrafficShaping
   }
   STATUS current
   DESCRIPTION
       "Objects grouped for the pdnAtmTrafficDescrParamExtTable."
   ::= { pdnAtmExtMibGroups 2 }

pdnAal5VccExtGroup OBJECT-GROUP
   OBJECTS {
      pdnAal5VccExtInPDUs,
      pdnAal5VccExtOutPDUs
   }
   STATUS current
   DESCRIPTION
       "Objects grouped for the pdnAal5VccExtTable."
   ::= { pdnAtmExtMibGroups 3 }                                
   
pdnAtmExtNotificationGroup NOTIFICATION-GROUP
   NOTIFICATIONS {
      pdnAtmIfConfExtExcessInvalidCellsAlarm,
      pdnAtmIfConfExtEgressLineRateAlarmSet, 
      pdnAtmIfConfExtEgressLineRateAlarmClear, 
      pdnAtmIfConfExtVplNoBandwidthAvail, 
      pdnAtmIfConfExtVclNoBandwidthAvail,
      pdnAtmIfConfExtIngressLineRateAlarmSet,
      pdnAtmIfConfExtIngressLineRateAlarmClear
   }
   STATUS current
   DESCRIPTION
       "Objects grouped for Notification defined in this
        MIB."
   ::= { pdnAtmExtMibGroups 4 }

pdnAtmVccAal5EncapsGroup OBJECT-GROUP
   OBJECTS {
      pdnAtmVccAal5EncapsType
   }
   STATUS current
   DESCRIPTION
       "Objects grouped for the pdnAtmVclExtTable."
   ::= { pdnAtmExtMibGroups 5 }



END

-- ===============================================================
-- Copyright (C) 2000 Paradyne Corporation.
--  ATM M4 Extension Group
PDN-ATMM4EXT-MIB DEFINITIONS ::= BEGIN

    IMPORTS
        MODULE-IDENTITY , OBJECT-TYPE, OBJECT-IDENTITY,
        Gauge32, TimeTicks
            FROM SNMPv2-SMI
        TEXTUAL-CONVENTION
            FROM SNMPv2-TC
        MODULE-COMPLIANCE, OBJECT-GROUP
            FROM SNMPv2-CONF
        pdnAtm
            FROM PDN-HEADER-MIB
        atmfM4VpTestEntry, atmfM4VcTestEntry, atmfM4TcProtoCurrEntry, atmfM4TcProtoHistEntry
            FROM ATM-FORUM-SNMP-M4-MIB
        ifIndex
            FROM IF-MIB;

-- ===============================================================
--
--  Extentions to the ATM Forum M4  Mib
--
-- ===============================================================

    pdnAtmfM4ExtMIB MODULE-IDENTITY
        LAST-UPDATED "200103080000Z"
        ORGANIZATION "Paradyne Corporation
                      MIB Working Group"
        CONTACT-INFO
                  "Paradyne Corporation
                   8545 126th Avenue North
                   Largo, FL 33773
                   www.paradyne.com

                   General Comments to: mibwg_team@eng.paradyne.com"

        DESCRIPTION
            "This MIB Module extends the ATM-FORUM-SNMP-M4-MI defined
             in the Atm Forums M4 Mib
            "
        REVISION "200401060000Z"
        DESCRIPTION "K. Wilson
            o  Added test error code of noVpFound(9)
		"

        REVISION "200208150000Z"
        DESCRIPTION "P. Easwar
            o  Added New Table pdnAtmfM4VpLoopbackTestTable.
		"

        REVISION "200103080000Z"
        DESCRIPTION "R.A.Bowhall
            o  Added error code of adminStatusDisabled(8).
	    "

        REVISION "200009260000Z"
        DESCRIPTION "R. Steinberger
            o  Added size to pdnAtmfM4Vc1CellLoopReportedLocation.
            "
        REVISION "200009220000Z"
        DESCRIPTION "R. Steinberger
            o  Added error code of testTimeOut(7).
            o  Added description of use of pdnAtmfM4Vc1CellLoopTable
            o  Changed pdnAtmfM4Vc1CellLoopReportedLocation type to 
               meet actual M4 definition of OCTET STRING(SIZE(16))
            o  Added the pdnAtmfM4LoopbackLocationTable
            "
        REVISION "200009210000Z"
        DESCRIPTION "J.Strain
            o  Added E2E and SEG as Multiple OAM Cell Tests
            o  documented mapping of atmfM4VcTestType to the corresponding
                                 atmfM4VcTestCode results table
            "
        REVISION "200009080000Z"
        DESCRIPTION "R. Steinberger
            o  Cleaned tabs throughout document.
            o  Fixed naming convention.
            o  Added pdnAtmfM4Vc1CellLoopTable for ATM OAM loopbacks 
               that send only single test cell.
            o  Added conformance section.
            "
        REVISION "200006290000Z"
        DESCRIPTION "Z. Pan
            o  added augmented atmfM4VcTestTable for ATM OAM loopback test.
            "
        ::= {  pdnAtm 6 }

    pdnAtmfM4ExtObjects     OBJECT IDENTIFIER  ::= { pdnAtmfM4ExtMIB 1 }
    pdnAtmfM4ExtTraps       OBJECT IDENTIFIER  ::= { pdnAtmfM4ExtMIB 2 }
    pdnAtmfM4ExtConformance OBJECT IDENTIFIER  ::= { pdnAtmfM4ExtMIB 3 }
    pdnAtmfM4ExtTrapPrefix  OBJECT IDENTIFIER  ::= { pdnAtmfM4ExtTraps 0 }
--
-- Textual Conventions Specific to this MIB Module
--
PdnAtmfM4TestErrorCode ::= TEXTUAL-CONVENTION
    STATUS  current
    DESCRIPTION
        "The specific error codes related to attempting to run a test. The
         codes have the following meanings:

           noError(0)             -- No Error Occurred
           badIfIndex(1)          -- Specified interface does not exist
           noVccFound(2)          -- The Vcc does not exist on the interface
           notOwner(3)            -- Not the current owner of the test
           noResourceAvailable(4) -- Device memory allocation failure
           noLoopbackAllocated(5) -- Could not start the test
           testCompleted(6)       -- Test completed or stopped normally
           testTimeOut(7)         -- Test unsuccessfully due to timeout
           adminStatusDisabled(8) -- ifAdminStatus is Disabled 
           noVpFound(9)           -- The Vp does not exist on the interface
        "
    SYNTAX  INTEGER {
                noError(0),
                badIfIndex(1),
                noVccFound(2),
                notOwner(3),
                noResourceAvailable(4),
                noLoopbackAllocated(5),
                testCompleted(6),
                testTimeOut(7),
                adminStatusDisabled(8),
                noVpFound(9)
            }

--
-- ATM TC layer current and historical fifteen-minute interval statistics 
-- pdnAtmfM4TcProtoCurrExtTable and pdnAtmfM4TcProtoHistExtTable
--

-- ATM TC layer current fifteen-minute interval data statistics 

pdnAtmfM4TcProtoCurrExtTable OBJECT-TYPE
    SYNTAX  SEQUENCE OF PdnAtmfM4TcProtoCurrExtEntry
    MAX-ACCESS  not-accessible
    STATUS  current
    DESCRIPTION
       "The Paradyne Extension to the atmfM4TcProtoCurrTable of the
        ATM-FORUM-SNMP-M4-MIB."
    ::= { pdnAtmfM4ExtObjects 1   }

pdnAtmfM4TcProtoCurrExtEntry OBJECT-TYPE
    SYNTAX  PdnAtmfM4TcProtoCurrExtEntry
    MAX-ACCESS  not-accessible
    STATUS  current
    DESCRIPTION
       "The Paradyne Extension to the atmfM4TcProtoCurrTable of the
        ATM-FORUM-SNMP-M4-MIB."
    AUGMENTS { atmfM4TcProtoCurrEntry }
    ::= { pdnAtmfM4TcProtoCurrExtTable  1 }

PdnAtmfM4TcProtoCurrExtEntry ::= SEQUENCE {
    pdnAtmfM4TcProtoCurrCellIns         Gauge32,
    pdnAtmfM4TcProtoCurrCellOuts        Gauge32,
    pdnAtmfM4TcProtoCurrInDiscards      Gauge32,
    pdnAtmfM4TcProtoCurrOutDiscards     Gauge32,
    pdnAtmfM4TcProtoCurrLCDEvents       Gauge32,
    pdnAtmfM4TcProtoCurrUnknownCells    Gauge32,
    pdnAtmfM4TcProtoCurrCorrectedHEC    Gauge32
    }

pdnAtmfM4TcProtoCurrCellIns OBJECT-TYPE
    SYNTAX Gauge32
    MAX-ACCESS read-only
    STATUS current
    DESCRIPTION
    "The number of ATM cells received on this interface since the
     start of this interval"
    ::= { pdnAtmfM4TcProtoCurrExtEntry 1 } 

pdnAtmfM4TcProtoCurrCellOuts OBJECT-TYPE
    SYNTAX Gauge32
    MAX-ACCESS read-only
    STATUS current
    DESCRIPTION
    "The number of ATM cells sent on this interface since the
     start of this interval"
    ::= { pdnAtmfM4TcProtoCurrExtEntry 2 } 

pdnAtmfM4TcProtoCurrInDiscards OBJECT-TYPE
    SYNTAX Gauge32
    MAX-ACCESS read-only
    STATUS current
    DESCRIPTION
    "The number of RX ATM cells dropped on this interface since the
     start of this interval"
    ::= { pdnAtmfM4TcProtoCurrExtEntry 3 } 

pdnAtmfM4TcProtoCurrOutDiscards OBJECT-TYPE
    SYNTAX Gauge32
    MAX-ACCESS read-only
    STATUS current
    DESCRIPTION
    "The number of TX ATM cells dropped on this interface since the
     start of this interval"
    ::= { pdnAtmfM4TcProtoCurrExtEntry 4 } 

pdnAtmfM4TcProtoCurrLCDEvents OBJECT-TYPE
    SYNTAX Gauge32
    MAX-ACCESS read-only
    STATUS current
    DESCRIPTION
    "The number of Loss of Cell Delineation (LCD) event occurred 
     on this interface since the start of this interval"
    ::= { pdnAtmfM4TcProtoCurrExtEntry 5 } 

pdnAtmfM4TcProtoCurrUnknownCells OBJECT-TYPE
    SYNTAX Gauge32
    MAX-ACCESS read-only
    STATUS current
    DESCRIPTION
    "The number of unknown Cells received on this interface since
     the start of this interval"
    ::= { pdnAtmfM4TcProtoCurrExtEntry 6 } 

pdnAtmfM4TcProtoCurrCorrectedHEC OBJECT-TYPE
    SYNTAX Gauge32
    MAX-ACCESS read-only
    STATUS current
    DESCRIPTION
    "The number of Cell with corrected HEC received on this interface
     since the start of this interval"
    ::= { pdnAtmfM4TcProtoCurrExtEntry 7 } 

--
-- ATM TC layer historical fifteen-minute interval statistics 
-- (per interface and time interval)
--

pdnAtmfM4TcProtoHistExtTable OBJECT-TYPE
    SYNTAX  SEQUENCE OF PdnAtmfM4TcProtoHistExtEntry
    MAX-ACCESS  not-accessible
    STATUS  current
    DESCRIPTION
       "The Paradyne Extension to the atmfM4TcProtoHistTable of the
        ATM-FORUM-SNMP-M4-MIB."
    ::= { pdnAtmfM4ExtObjects 2   }

pdnAtmfM4TcProtoHistExtEntry OBJECT-TYPE
    SYNTAX  PdnAtmfM4TcProtoHistExtEntry
    MAX-ACCESS  not-accessible
    STATUS  current
    DESCRIPTION
       "The Paradyne Extension to the atmfM4TcProtoHistTable of the
        ATM-FORUM-SNMP-M4-MIB."
    AUGMENTS { atmfM4TcProtoHistEntry }
    ::= { pdnAtmfM4TcProtoHistExtTable  1 }

PdnAtmfM4TcProtoHistExtEntry ::= SEQUENCE {
    pdnAtmfM4TcProtoHistCellIns         Gauge32,
    pdnAtmfM4TcProtoHistCellOuts        Gauge32,
    pdnAtmfM4TcProtoHistInDiscards      Gauge32,
    pdnAtmfM4TcProtoHistOutDiscards     Gauge32,
    pdnAtmfM4TcProtoHistLCDEvents       Gauge32,
    pdnAtmfM4TcProtoHistUnknownCells    Gauge32,
    pdnAtmfM4TcProtoHistCorrectedHEC    Gauge32
    }

pdnAtmfM4TcProtoHistCellIns OBJECT-TYPE
    SYNTAX Gauge32
    MAX-ACCESS read-only
    STATUS current
    DESCRIPTION
    "The number of ATM cells received on this interface
     during this interval"
    ::= { pdnAtmfM4TcProtoHistExtEntry 1 } 

pdnAtmfM4TcProtoHistCellOuts OBJECT-TYPE
    SYNTAX Gauge32
    MAX-ACCESS read-only
    STATUS current
    DESCRIPTION
    "The number of ATM cells sent on this interface during
     this interval"
    ::= { pdnAtmfM4TcProtoHistExtEntry 2 } 

pdnAtmfM4TcProtoHistInDiscards OBJECT-TYPE
    SYNTAX Gauge32
    MAX-ACCESS read-only
    STATUS current
    DESCRIPTION
    "The number of RX ATM cells dropped on this interface
     during this interval"
    ::= { pdnAtmfM4TcProtoHistExtEntry 3 } 

pdnAtmfM4TcProtoHistOutDiscards OBJECT-TYPE
    SYNTAX Gauge32
    MAX-ACCESS read-only
    STATUS current
    DESCRIPTION
    "The number of TX ATM cells dropped on this interface
     during this interval"
    ::= { pdnAtmfM4TcProtoHistExtEntry 4 } 

pdnAtmfM4TcProtoHistLCDEvents OBJECT-TYPE
    SYNTAX Gauge32
    MAX-ACCESS read-only
    STATUS current
    DESCRIPTION
    "The number of Loss of Cell Delineation (LCD) event occurred 
     on this interface during this interval"
    ::= { pdnAtmfM4TcProtoHistExtEntry 5 } 

pdnAtmfM4TcProtoHistUnknownCells OBJECT-TYPE
    SYNTAX Gauge32
    MAX-ACCESS read-only
    STATUS current
    DESCRIPTION
    "The number of unknown Cells received on this interface since
     the start of this interval"
    ::= { pdnAtmfM4TcProtoHistExtEntry 6 } 

pdnAtmfM4TcProtoHistCorrectedHEC OBJECT-TYPE
    SYNTAX Gauge32
    MAX-ACCESS read-only
    STATUS current
    DESCRIPTION
    "The number of Cell with corrected HEC received on this interface
     during this interval"
    ::= { pdnAtmfM4TcProtoHistExtEntry 7 } 


--
--  The following object defines a group of OAM test types.
--  This group is to contain any Paradyne Specific OAM test
--

pdnAtmfM4TestTypes OBJECT IDENTIFIER ::= { pdnAtmfM4ExtObjects 3 }

--
--  The following OID is defined to initiate continuous Segment OAM Cells
--  

pdnAtmfM4TestOAMLoopbackSegMultiCell OBJECT-IDENTITY
     STATUS    current
     DESCRIPTION
          "This identifies an OAM Loopback Test on a VPL, VPC,
          VCL, or VCC termination point, using a segment OAM
          cell.

          The test type must have appended to it a code that uniquely
          identifies an intermediate point responsible for looping
          back the cell.  If this is absent, the loopback is performed
          at the end of the segment or connection.

          E.g., the OID { pdnAtmfM4TestOAMLoopbackSegMultiCell 5 } identifies
          that the loopback should be performed at the intermediate
          point labeled 5."
     ::= { pdnAtmfM4TestTypes 1 }

--
--  The following OID is defined to initiate continuous End to End OAM cells
--  

pdnAtmfM4TestOAMLoopbackE2EMultiCell OBJECT-IDENTITY
     STATUS    current
     DESCRIPTION
          "This identifies an OAM Loopback Test on a VPL, VPC,
          VCL, or VCC termination point, using an end-to-end OAM
          cell."
     ::= { pdnAtmfM4TestTypes 2 }

--
--      Test Code to Test Results Matrix
--      
--      atmfM4VcTestType                atmfM4VcTestCode Result Table
--      ________________                _____________________________
--
--      atmfM4TestOAMLoopbackSeg(standard is a single cell test)
--                                      pdnAtmfM4Vc1CellLoopTable
--      atmfM4TestOAMLoopbackE2E(standard is a single cell test)
--                                      pdnAtmfM4Vc1CellLoopTable
--
--      pdnAtmfM4TestOAMLoopbackSegMultiCell
--                                      pdnAtmfM4VcLoopbackTestTable
--      pdnAtmfM4TestOAMLoopbackE2EMultiCell
--                                      pdnAtmfM4VcLoopbackTestTable
--

--
-- OAM Loopback test (multiple cell) detailed results table
--

pdnAtmfM4VcLoopbackTestTable   OBJECT-TYPE 
    SYNTAX       SEQUENCE OF PdnAtmfM4VcLoopbackTestEntry 
    MAX-ACCESS   not-accessible 
    STATUS       current 
    DESCRIPTION 
      "This table contains input and results for OAM loopback 
       tests. There can be only one test running per ATM VCC 
       This table should be used in conjunction with atmfM4VcTestTable
       with all the semantics of atmfM4VcTestTable." 
::= { pdnAtmfM4ExtObjects 4 } 

pdnAtmfM4VcLoopbackTestEntry OBJECT-TYPE 
    SYNTAX       PdnAtmfM4VcLoopbackTestEntry 
    MAX-ACCESS   not-accessible 
    STATUS       current 
    DESCRIPTION 
      "An entry containing objects for test results
       for ATM OAM loopback test" 
    AUGMENTS { atmfM4VcTestEntry } 
::= { pdnAtmfM4VcLoopbackTestTable 1 } 

PdnAtmfM4VcLoopbackTestEntry ::= 
    SEQUENCE { 
      pdnAtmfM4VcLoopbackTestElpsTime         TimeTicks,
      pdnAtmfM4VcLoopbackTestCellsSent        Gauge32,
      pdnAtmfM4VcLoopbackTestCellsRcvd        Gauge32,
      pdnAtmfM4VcLoopbackTestMinRTDelay       Gauge32,
      pdnAtmfM4VcLoopbackTestMaxRTDelay       Gauge32,
      pdnAtmfM4VcLoopbackTestAvgRTDelay       Gauge32,
      pdnAtmfM4VcLoopbackTestErrorCode        PdnAtmfM4TestErrorCode
    } 

pdnAtmfM4VcLoopbackTestElpsTime OBJECT-TYPE 
    SYNTAX       TimeTicks
    MAX-ACCESS   read-only 
    STATUS       current 
    DESCRIPTION 
      "This object contains the time that has elapsed since the test started."
::= { pdnAtmfM4VcLoopbackTestEntry 1 } 

pdnAtmfM4VcLoopbackTestCellsSent OBJECT-TYPE 
    SYNTAX       Gauge32
    MAX-ACCESS   read-only 
    STATUS       current 
    DESCRIPTION 
      "This object specifies a count of the number of test cells that
       have been sent. The value of this object stops increasing
       when it reaches its maximum value."
::= { pdnAtmfM4VcLoopbackTestEntry 2 } 

pdnAtmfM4VcLoopbackTestCellsRcvd OBJECT-TYPE 
    SYNTAX       Gauge32
    MAX-ACCESS   read-only 
    STATUS       current 
    DESCRIPTION 
      "This object specifies a count of the number of test cells that
       have been received.  The value of this object stops increasing
       when it reaches its maximum value."
::= { pdnAtmfM4VcLoopbackTestEntry 3 } 

pdnAtmfM4VcLoopbackTestMinRTDelay OBJECT-TYPE 
    SYNTAX       Gauge32
    UNITS        "milliseconds"
    MAX-ACCESS   read-only 
    STATUS       current 
    DESCRIPTION 
      "This object contains the value of the shortest round trip delay 
       since the test has been started. It is calculated only on the cells
       that have been received. Cells that were dropped are not counted."
::= { pdnAtmfM4VcLoopbackTestEntry 4 } 

pdnAtmfM4VcLoopbackTestMaxRTDelay OBJECT-TYPE 
    SYNTAX       Gauge32
    UNITS        "milliseconds"
    MAX-ACCESS   read-only 
    STATUS       current 
    DESCRIPTION 
      "This object contains the value of the longest round trip delay 
       since the test has been started. It is calculated only on the cells
       that have been received. Cells that were dropped are not counted."
::= { pdnAtmfM4VcLoopbackTestEntry 5 } 

pdnAtmfM4VcLoopbackTestAvgRTDelay OBJECT-TYPE 
    SYNTAX       Gauge32
    UNITS        "milliseconds"
    MAX-ACCESS   read-only 
    STATUS       current 
    DESCRIPTION 
      "This object contains the value of the average round trip delay 
       since the test has been started. It is calculated only on the cells
       that have been received. Cells that were dropped are not counted."
::= { pdnAtmfM4VcLoopbackTestEntry 6 } 

pdnAtmfM4VcLoopbackTestErrorCode OBJECT-TYPE 
    SYNTAX       PdnAtmfM4TestErrorCode
    MAX-ACCESS   read-only 
    STATUS       current 
    DESCRIPTION 
      "This object contains the specific error code on the test result."
::= { pdnAtmfM4VcLoopbackTestEntry 7 } 

--
-- Single Cell OAM Loopback test detailed results
--
-- This table contains results for single cell OAM tests that are not
-- of a broadcast variety.
--
-- Recommended Use:
--
-- 1) The NMS will start a test using the M4 MIB's atmfM4VcTestTable.
-- 2) Upon starting the test, the agent will put the corresponding OID
--    of a row in this table into the atmfM4VcTestCode object.
-- 3) When the value of atmfM4VcTestResult is not equal to inProgress(3),
--    the values contained in this table should be read.
--
pdnAtmfM4Vc1CellLoopTable   OBJECT-TYPE 
    SYNTAX       SEQUENCE OF PdnAtmfM4Vc1CellLoopEntry 
    MAX-ACCESS   not-accessible 
    STATUS       current 
    DESCRIPTION 
      "This table contains input and results for single cell OAM
       loopback tests. There can be only one test running per ATM VCC 
       This table should be used in conjunction with atmfM4VcTestTable
       with all the semantics of atmfM4VcTestTable." 
::= { pdnAtmfM4ExtObjects 5 } 

pdnAtmfM4Vc1CellLoopEntry OBJECT-TYPE 
    SYNTAX       PdnAtmfM4Vc1CellLoopEntry 
    MAX-ACCESS   not-accessible 
    STATUS       current 
    DESCRIPTION 
      "An entry containing objects for test results 
       for a single cell ATM OAM loopback test" 
    AUGMENTS { atmfM4VcTestEntry } 
::= { pdnAtmfM4Vc1CellLoopTable 1 } 

PdnAtmfM4Vc1CellLoopEntry ::= 
    SEQUENCE { 
      pdnAtmfM4Vc1CellLoopRTDelay             Gauge32,
      pdnAtmfM4Vc1CellLoopReportedLocation    OCTET STRING,
      pdnAtmfM4Vc1CellLoopErrorCode           PdnAtmfM4TestErrorCode
    } 

pdnAtmfM4Vc1CellLoopRTDelay OBJECT-TYPE 
    SYNTAX       Gauge32
    UNITS        "milliseconds"
    MAX-ACCESS   read-only 
    STATUS       current 
    DESCRIPTION 
      "This object contains the value of the round trip delay of the
       the test cell. A value of zero indicates that no cell has been
       received."
::= { pdnAtmfM4Vc1CellLoopEntry 1 } 

pdnAtmfM4Vc1CellLoopReportedLocation OBJECT-TYPE 
    SYNTAX       OCTET STRING(SIZE(16))
    MAX-ACCESS   read-only 
    STATUS       current 
    DESCRIPTION 
      "This object contains the value of the location identifier
       reported by the received cell."
::= { pdnAtmfM4Vc1CellLoopEntry 2 } 

pdnAtmfM4Vc1CellLoopErrorCode OBJECT-TYPE 
    SYNTAX       PdnAtmfM4TestErrorCode
    MAX-ACCESS   read-only 
    STATUS       current 
    DESCRIPTION 
      "This object contains the specific error code on the test result."
::= { pdnAtmfM4Vc1CellLoopEntry 3 }

--
-- OAM Segment Loopback Location Code
--
pdnAtmfM4LoopbackLocationTable   OBJECT-TYPE
    SYNTAX       SEQUENCE OF PdnAtmfM4LoopbackLocationEntry
    MAX-ACCESS   not-accessible
    STATUS       current
    DESCRIPTION
          "This table contains the ATM OAM loopback location codes
           for ATM cell layer interfaces."
    ::= { pdnAtmfM4ExtObjects 6 }

pdnAtmfM4LoopbackLocationEntry OBJECT-TYPE
    SYNTAX       PdnAtmfM4LoopbackLocationEntry
    MAX-ACCESS   not-accessible
    STATUS       current
    DESCRIPTION
          "An entry containing objects for ATM OAM loopback locations."
    INDEX { ifIndex }
    ::= { pdnAtmfM4LoopbackLocationTable 1 }

PdnAtmfM4LoopbackLocationEntry ::=
    SEQUENCE {
      pdnAtmfM4LoopbackLocationCode        OCTET STRING
    }

pdnAtmfM4LoopbackLocationCode OBJECT-TYPE
    SYNTAX       OCTET STRING(SIZE(16))
    MAX-ACCESS   read-write
    STATUS       current
    DESCRIPTION
          "This object contains the value of ATM OAM Loopback Location Code"
    ::= { pdnAtmfM4LoopbackLocationEntry 1 }

pdnAtmfM4VpLoopbackTestTable   OBJECT-TYPE 
    SYNTAX       SEQUENCE OF PdnAtmfM4VpLoopbackTestEntry 
    MAX-ACCESS   not-accessible 
    STATUS       current 
    DESCRIPTION 
      "This table contains input and results for OAM loopback 
       tests. There can be only one test running per ATM VPC
       This table should be used in conjunction with atmfM4VpTestTable
       with all the semantics of atmfM4VpTestTable." 
::= { pdnAtmfM4ExtObjects 7 }

pdnAtmfM4VpLoopbackTestEntry OBJECT-TYPE 
    SYNTAX       PdnAtmfM4VpLoopbackTestEntry 
    MAX-ACCESS   not-accessible 
    STATUS       current 
    DESCRIPTION 
      "An entry containing objects for test results
       for ATM OAM loopback test" 
    AUGMENTS { atmfM4VpTestEntry } 
::= { pdnAtmfM4VpLoopbackTestTable 1 } 

PdnAtmfM4VpLoopbackTestEntry ::= 
    SEQUENCE { 
      pdnAtmfM4VpLoopbackTestElpsTime         TimeTicks,
      pdnAtmfM4VpLoopbackTestCellsSent        Gauge32,
      pdnAtmfM4VpLoopbackTestCellsRcvd        Gauge32,
      pdnAtmfM4VpLoopbackTestMinRTDelay       Gauge32,
      pdnAtmfM4VpLoopbackTestMaxRTDelay       Gauge32,
      pdnAtmfM4VpLoopbackTestAvgRTDelay       Gauge32,
      pdnAtmfM4VpLoopbackTestErrorCode        PdnAtmfM4TestErrorCode
    } 

pdnAtmfM4VpLoopbackTestElpsTime OBJECT-TYPE 
    SYNTAX       TimeTicks
    MAX-ACCESS   read-only 
    STATUS       current 
    DESCRIPTION 
      "This object contains the time that has elapsed since the test started."
::= { pdnAtmfM4VpLoopbackTestEntry 1 } 

pdnAtmfM4VpLoopbackTestCellsSent OBJECT-TYPE 
    SYNTAX       Gauge32
    MAX-ACCESS   read-only 
    STATUS       current 
    DESCRIPTION 
      "This object specifies a count of the number of test cells that
       have been sent. The value of this object stops increasing
       when it reaches its maximum value."
::= { pdnAtmfM4VpLoopbackTestEntry 2 } 

pdnAtmfM4VpLoopbackTestCellsRcvd OBJECT-TYPE 
    SYNTAX       Gauge32
    MAX-ACCESS   read-only 
    STATUS       current 
    DESCRIPTION 
      "This object specifies a count of the number of test cells that
       have been received.  The value of this object stops increasing
       when it reaches its maximum value."
::= { pdnAtmfM4VpLoopbackTestEntry 3 } 

pdnAtmfM4VpLoopbackTestMinRTDelay OBJECT-TYPE 
    SYNTAX       Gauge32
    UNITS        "milliseconds"
    MAX-ACCESS   read-only 
    STATUS       current 
    DESCRIPTION 
      "This object contains the value of the shortest round trip delay 
       since the test has been started. It is calculated only on the cells
       that have been received. Cells that were dropped are not counted."
::= { pdnAtmfM4VpLoopbackTestEntry 4 } 

pdnAtmfM4VpLoopbackTestMaxRTDelay OBJECT-TYPE 
    SYNTAX       Gauge32
    UNITS        "milliseconds"
    MAX-ACCESS   read-only 
    STATUS       current 
    DESCRIPTION 
      "This object contains the value of the longest round trip delay 
       since the test has been started. It is calculated only on the cells
       that have been received. Cells that were dropped are not counted."
::= { pdnAtmfM4VpLoopbackTestEntry 5 } 

pdnAtmfM4VpLoopbackTestAvgRTDelay OBJECT-TYPE 
    SYNTAX       Gauge32
    UNITS        "milliseconds"
    MAX-ACCESS   read-only 
    STATUS       current 
    DESCRIPTION 
      "This object contains the value of the average round trip delay 
       since the test has been started. It is calculated only on the cells
       that have been received. Cells that were dropped are not counted."
::= { pdnAtmfM4VpLoopbackTestEntry 6 } 

pdnAtmfM4VpLoopbackTestErrorCode OBJECT-TYPE 
    SYNTAX       PdnAtmfM4TestErrorCode
    MAX-ACCESS   read-only 
    STATUS       current 
    DESCRIPTION 
      "This object contains the specific error code on the test result."
::= { pdnAtmfM4VpLoopbackTestEntry 7 } 

-- Conformance Information

pdnAtmfM4Groups       OBJECT IDENTIFIER ::= { pdnAtmfM4ExtConformance 1 }
pdnAtmfM4Compliances  OBJECT IDENTIFIER ::= { pdnAtmfM4ExtConformance 2 }

pdnAtmfM4Compliance MODULE-COMPLIANCE
    STATUS  current
    DESCRIPTION
        "The compliance statement for SNMP entities which support
         the ATM M4 extensions."
    MODULE
         GROUP pdnAtmfM4LoopbackLocationGroup
         DESCRIPTION
             "The conditional objects in the Loopback Location Group."
             OBJECT  pdnAtmfM4LoopbackLocationCode
             MIN-ACCESS  read-only
             DESCRIPTION
                "Write access is not required"
    ::= { pdnAtmfM4Compliances 1 }

--
-- Units of Conformance
--
 
pdnAtmfM4TcCurrGroup OBJECT-GROUP
    OBJECTS {
        pdnAtmfM4TcProtoCurrCellIns,
        pdnAtmfM4TcProtoCurrCellOuts,
        pdnAtmfM4TcProtoCurrInDiscards,
        pdnAtmfM4TcProtoCurrOutDiscards,
        pdnAtmfM4TcProtoCurrLCDEvents,
        pdnAtmfM4TcProtoCurrUnknownCells,
        pdnAtmfM4TcProtoCurrCorrectedHEC
    }
    STATUS  current
    DESCRIPTION
        "The objects in the ATM TC layer current table."
    ::= { pdnAtmfM4Groups 1 }

pdnAtmfM4TcHistGroup OBJECT-GROUP
    OBJECTS {
        pdnAtmfM4TcProtoHistCellIns,
        pdnAtmfM4TcProtoHistCellOuts,
        pdnAtmfM4TcProtoHistInDiscards,
        pdnAtmfM4TcProtoHistOutDiscards,
        pdnAtmfM4TcProtoHistLCDEvents,
        pdnAtmfM4TcProtoHistUnknownCells,
        pdnAtmfM4TcProtoHistCorrectedHEC
    }
    STATUS  current
    DESCRIPTION
        "The objects in the ATM TC layer history table."
    ::= { pdnAtmfM4Groups 2 }

pdnAtmfM4VcLoopbackTestGroup OBJECT-GROUP
    OBJECTS {
        pdnAtmfM4VcLoopbackTestElpsTime,
        pdnAtmfM4VcLoopbackTestCellsSent,
        pdnAtmfM4VcLoopbackTestCellsRcvd,
        pdnAtmfM4VcLoopbackTestMinRTDelay,
        pdnAtmfM4VcLoopbackTestMaxRTDelay,
        pdnAtmfM4VcLoopbackTestAvgRTDelay,
        pdnAtmfM4VcLoopbackTestErrorCode
    }
    STATUS  current
    DESCRIPTION
        "The objects in the ATM OAM Loopback Test (multiple cell) table for ATM VCC."
    ::= { pdnAtmfM4Groups 3 }

pdnAtmfM4Vc1CellLoopGroup OBJECT-GROUP
    OBJECTS {
        pdnAtmfM4Vc1CellLoopRTDelay,
        pdnAtmfM4Vc1CellLoopReportedLocation,
        pdnAtmfM4Vc1CellLoopErrorCode
    }
    STATUS  current
    DESCRIPTION
        "The objects in the ATM Single Cell OAM Loopback Test table."
    ::= { pdnAtmfM4Groups 4 }

pdnAtmfM4LoopbackLocationGroup OBJECT-GROUP
    OBJECTS {
        pdnAtmfM4LoopbackLocationCode
    }
    STATUS  current
    DESCRIPTION
        "The objects in the ATM Loopback Location table."
    ::= { pdnAtmfM4Groups 5 }

pdnAtmfM4VpLoopbackTestGroup OBJECT-GROUP
    OBJECTS {
        pdnAtmfM4VpLoopbackTestElpsTime,
        pdnAtmfM4VpLoopbackTestCellsSent,
        pdnAtmfM4VpLoopbackTestCellsRcvd,
        pdnAtmfM4VpLoopbackTestMinRTDelay,
        pdnAtmfM4VpLoopbackTestMaxRTDelay,
        pdnAtmfM4VpLoopbackTestAvgRTDelay,
        pdnAtmfM4VpLoopbackTestErrorCode
    }
    STATUS  current
    DESCRIPTION
        "The objects in the ATM OAM Loopback Test (multiple cell) table for ATM VPC."
    ::= { pdnAtmfM4Groups 6 }
END

-- ===============================================================
-- Copyright (C) 2003 Paradyne Corporation.
-- ===============================================================

PDN-ENTITY-SENSOR-EXT-MIB DEFINITIONS ::= BEGIN

IMPORTS
    MODULE-IDENTITY, OBJECT-TYPE, NOTIFICATION-TYPE
        FROM SNMPv2-SMI
    OBJECT-GROUP, NOTIFICATION-GROUP, MODULE-COMPLIANCE
        FROM SNMPv2-CONF
    EntitySensorValue, entPhySensorEntry, entPhySensorValue
        FROM ENTITY-SENSOR-MIB
    pdn-common
        FROM PDN-HEADER-MIB;
        
pdnEntitySensorExtMIB MODULE-IDENTITY
    LAST-UPDATED "200306060000Z"  -- June 6, 2003
    ORGANIZATION "Paradyne Networks
                  MIB Working Group
                  Other information about group editing the MIB"
    CONTACT-INFO "Paradyne Networks, Inc.
                  8545 126th Avenue North
                  Largo, FL 33733
                  www.paradyne.com
        
                  General Comments to: mibwg_team@paradyne.com

                  Editors
                      Jesus Pinto  
                      Clay Sikes"

    DESCRIPTION
        "This MIB module is a supplement to the ENTITY-SENSOR-MIB,
         RFC 3433."

    REVISION "200306060000Z"  -- June 6, 2003
    DESCRIPTION "Removed pdnEntPhySensorExtIndex. This object was originally
                added to be one of the objects each notification. However,
                this is redundent in that each notification object has the
                index as part of its instance. So the object is not needed."        

    REVISION "200304240000Z"  -- April 24, 2003
    DESCRIPTION "Change the conformance/compliance section to be
                consistent with standard MIBs."

    REVISION "200304160000Z"  -- April 16, 2003
    DESCRIPTION "Initial release."


::=  { pdn-common 45 }

pdnEntitySensorExtNotifications OBJECT IDENTIFIER ::= { pdnEntitySensorExtMIB 0 }
pdnEntitySensorExtObjects       OBJECT IDENTIFIER ::= { pdnEntitySensorExtMIB 1 }
pdnEntitySensorExtAFNs          OBJECT IDENTIFIER ::= { pdnEntitySensorExtMIB 2 }
pdnEntitySensorExtConformance   OBJECT IDENTIFIER ::= { pdnEntitySensorExtMIB 3 }


-- =============================================================================
-- ==                  MIB Objects                                            ==
-- =============================================================================

pdnEntPhySensorExtTable     OBJECT-TYPE
    SYNTAX      SEQUENCE OF PdnEntPhySensorExtEntry
    MAX-ACCESS  not-accessible
    STATUS      current
    DESCRIPTION "This table extends the entPhySensorTable."
    ::= { pdnEntitySensorExtObjects 1 }

pdnEntPhySensorExtEntry     OBJECT-TYPE
    SYNTAX      PdnEntPhySensorExtEntry
    MAX-ACCESS  not-accessible
    STATUS      current
    DESCRIPTION "An extended entry in the entPhySensorTable."
    AUGMENTS     { entPhySensorEntry }
    ::= { pdnEntPhySensorExtTable 1 }

PdnEntPhySensorExtEntry ::=
    SEQUENCE {
        pdnEntPhySensorExtNotificationEnable            BITS,
        pdnEntPhySensorExtUpperThreshold                EntitySensorValue,
        pdnEntPhySensorExtLowerThreshold                EntitySensorValue,
        pdnEntPhySensorExtThresholdState                INTEGER
    }

pdnEntPhySensorExtNotificationEnable OBJECT-TYPE
    SYNTAX      BITS {
                    thresholdExceeded(0)
                }
    MAX-ACCESS  read-write
    STATUS      current
    DESCRIPTION "Provides that ability to enable and disable notifications
                relative to objects in this table.

                When this bit is set, pdnEntPhySensorExtThesholdExceededSet
                and pdnEntPhySensorExtThesholdExceededCleared notifications
                should be generated.

                When this bit is reset, pdnEntPhySensorExtThesholdExceededSet,
                and pdnEntPhySensorExtThesholdExceededCleared notifications
                should be not be generated."
    ::= { pdnEntPhySensorExtEntry 1 }

pdnEntPhySensorExtUpperThreshold OBJECT-TYPE
    SYNTAX      EntitySensorValue
    MAX-ACCESS  read-write
    STATUS      current
    DESCRIPTION "This object sets the upper limit of a sensor's threshold. When the
                value of entPhySensorValue becomes greater than the value of this
                object, an 'Upper Threshold Exceeded' state is entered."
    ::= { pdnEntPhySensorExtEntry 2 }

pdnEntPhySensorExtLowerThreshold OBJECT-TYPE
    SYNTAX      EntitySensorValue
    MAX-ACCESS  read-write
    STATUS      current
    DESCRIPTION "This object sets the lower limit of a sensor's threshold. When the
                value of entPhySensorValue becomes less than the value of this
                object, a 'Lower Threshold Exceeded' state is entered."
    ::= { pdnEntPhySensorExtEntry 3 }

pdnEntPhySensorExtThresholdState OBJECT-TYPE
    SYNTAX      INTEGER {
                    noThresholdsExceeded(1),
                    upperThresholdExceeded(2),
                    lowerThresholdExceeded(3) 
                }
    MAX-ACCESS  read-only
    STATUS      current
    DESCRIPTION "This object returns the threshold state of the sensor."
    ::= { pdnEntPhySensorExtEntry 4 }



-- =============================================================================
-- ==                  Traps/Notifications                                    ==
-- =============================================================================

pdnEntPhySensorExtThresholdExceededSet NOTIFICATION-TYPE
    OBJECTS  {  
                entPhySensorValue,
                pdnEntPhySensorExtThresholdState
    }
    STATUS      current
    DESCRIPTION "This trap/notification signifies that a sensor value has 
                exceeded its threshold limit. i.e. its entPhySensorValue is
                greater than its pdnEntPhySensorExtUpperThreshold or less
                than its pdnEntPhySensorExtLowerThreshold."
    ::= { pdnEntitySensorExtNotifications 1 }

pdnEntPhySensorExtThresholdExceededCleared NOTIFICATION-TYPE
    OBJECTS  {  
                entPhySensorValue,
                pdnEntPhySensorExtThresholdState
    }
    STATUS      current
    DESCRIPTION "This trap/notification signifies that a sensor value that had
                exceeded its threshold limit, is now operating with in its
                threshold limits. i.e. its entPhySensorValue is
                less than or equal to its pdnEntPhySensorExtUpperThreshold and 
                greater than or equal to its pdnEntPhySensorExtLowerThreshold."
    ::= { pdnEntitySensorExtNotifications 100 }



-- =============================================================================
-- ==                  Conformance Information                                ==
-- =============================================================================

pdnEntitySensorExtCompliances  OBJECT IDENTIFIER ::= { pdnEntitySensorExtConformance 1 }
pdnEntitySensorExtGroups       OBJECT IDENTIFIER ::= { pdnEntitySensorExtConformance 2 }


-- ===========================
-- == Compliance Statements ==
-- ===========================


pdnEntitySensorExtMIBCompliance MODULE-COMPLIANCE
    STATUS      current
    DESCRIPTION "The compliance statement for pdnEntitySensorExt entities which
                implement the pdnEntitySensorExtMIB."
    MODULE      -- this module
    -- No mandatory groups are specified

    GROUP       pdnEntitySensorExtThresholdGroup
    DESCRIPTION "This group is mandatory only for those entities which
                implement setting and reporting of thresholds."

    GROUP       pdnEntitySensorExtThresholdNtfyGroup
    DESCRIPTION "This group is mandatory only for those entities which
                implement traps for thresholds being exceeded."

    OBJECT      pdnEntPhySensorExtNotificationEnable
    MIN-ACCESS  read-only
    DESCRIPTION "In some implementations, for some sensors, it may not be 
                allowable to enable/disable the notification."

    OBJECT      pdnEntPhySensorExtUpperThreshold
    MIN-ACCESS  read-only
    DESCRIPTION "In some implementations, sensor thresholds may not be
                configurable may the user. Specific hardware implementations
                may dictate thresholds. In these cases, the object can be
                supported as read-only access."

    OBJECT      pdnEntPhySensorExtLowerThreshold
    MIN-ACCESS  read-only
    DESCRIPTION "In some implementations, sensor thresholds may not be
                configurable may the user. Specific hardware implementations
                may dictate thresholds. In these cases, the object can be
                supported as read-only access."

    ::= { pdnEntitySensorExtCompliances 1 }


-- ==========================
-- == Units of Conformance ==
-- ==========================

pdnEntitySensorExtObjGroups   OBJECT IDENTIFIER ::= { pdnEntitySensorExtGroups 1 }
pdnEntitySensorExtAfnGroups   OBJECT IDENTIFIER ::= { pdnEntitySensorExtGroups 2 }
pdnEntitySensorExtNtfyGroups  OBJECT IDENTIFIER ::= { pdnEntitySensorExtGroups 3 }

-- ===================
-- == Object Groups ==
-- ===================

pdnEntitySensorExtThresholdGroup OBJECT-GROUP
    OBJECTS {
                     pdnEntPhySensorExtNotificationEnable,
                     pdnEntPhySensorExtUpperThreshold, 
                     pdnEntPhySensorExtLowerThreshold,
                     pdnEntPhySensorExtThresholdState
    }
    STATUS      current
    DESCRIPTION "A collection of objects for setting and reporting thresholds."
    ::= { pdnEntitySensorExtObjGroups  1 }



-- =========================
-- == Notification Groups ==
-- =========================

pdnEntitySensorExtThresholdNtfyGroup NOTIFICATION-GROUP
    NOTIFICATIONS {
                     pdnEntPhySensorExtThresholdExceededSet, 
                     pdnEntPhySensorExtThresholdExceededCleared         
    }
    STATUS      current
    DESCRIPTION "Notifications relative to thresholds going out of or in to
                specification."
    ::= { pdnEntitySensorExtNtfyGroups  1 }



-- =========
-- == END ==
-- =========
END

-- ===============================================================
-- Copyright (C) 2003 Paradyne Corporation.
-- ===============================================================

PDN-VLAN-MIB DEFINITIONS ::= BEGIN

IMPORTS
    MODULE-IDENTITY, OBJECT-TYPE
        FROM SNMPv2-SMI
    OBJECT-GROUP, MODULE-COMPLIANCE
        FROM SNMPv2-CONF
    VlanIndex
        FROM Q-BRIDGE-MIB
    pdn-common
        FROM PDN-HEADER-MIB;
        
pdnVlanMIB MODULE-IDENTITY
    LAST-UPDATED "200311120000Z"  -- Nov 12, 2003
    ORGANIZATION "Paradyne Networks
                  MIB Working Group
                  Other information about group editing the MIB"
    CONTACT-INFO "Paradyne Networks, Inc.
                  8545 126th Avenue North
                  Largo, FL 33733
                  www.paradyne.com
        
                  General Comments to: mibwg_team@paradyne.com

                  Editors
                      Clay Sikes,
		      Jesus A. Pinto"

    DESCRIPTION
        "This MIB module contains objects pertaining to VLANs."

    REVISION "200311120000Z"  -- Nov 19, 2003, pinto
    DESCRIPTION "Added a second VlanId for in-band mgmt"

    REVISION "200304240000Z"  -- April 24, 2003
    DESCRIPTION "Changed the compliance/conformance section to be
                consistent with standard MIBs."
        
    REVISION "200304110000Z"  -- April 11, 2003
    DESCRIPTION "Initial release."


::=  { pdn-common 46 }

pdnVlanNotifications OBJECT IDENTIFIER ::= { pdnVlanMIB 0 }
pdnVlanObjects       OBJECT IDENTIFIER ::= { pdnVlanMIB 1 }
pdnVlanAFNs          OBJECT IDENTIFIER ::= { pdnVlanMIB 2 }
pdnVlanConformance   OBJECT IDENTIFIER ::= { pdnVlanMIB 3 }


-- =============================================================================
-- ==                  MIB Objects                                            ==
-- =============================================================================


pdnVlanReservedBlockStart OBJECT-TYPE
    SYNTAX      VlanIndex
    MAX-ACCESS  read-write
    STATUS      current
    DESCRIPTION "This object defines the starting VLAN for a sequential block
                of VLANS that are to be reserved for internal use. The actual 
                size of the block reserved is not specified as it could be 
                implementation specific. The size of the actual block being 
                reserved should be clearly specified in the SNMP Operational 
                Specification for the particular implementaion."
    ::= { pdnVlanObjects 1 }

pdnVlanInbandMgmtVlanId  OBJECT-TYPE
    SYNTAX      VlanIndex
    MAX-ACCESS  read-write
    STATUS      current
    DESCRIPTION "The VLAN ID assigned to the In-Band Management Channel."
    ::= { pdnVlanObjects 2 }

pdnVlanInbandMgmtVlanId2  OBJECT-TYPE
    SYNTAX      VlanIndex
    MAX-ACCESS  read-write
    STATUS      current
    DESCRIPTION "The VLAN ID assigned to the second In-Band Management Channel.

		 If the agent does not support a second In-Band Management
		 Channel, it should return NO-SUCH-NAME for the object.

		 *** A VALUE OF 0 IS NOT PERMITTED TO BE RETURNED ***

		 "
    ::= { pdnVlanObjects 3 }


-- =============================================================================
-- ==                  Conformance Information                                ==
-- =============================================================================

pdnVlanCompliances        OBJECT IDENTIFIER ::= { pdnVlanConformance  1 }
pdnVlanGroups             OBJECT IDENTIFIER ::= { pdnVlanConformance  2 }


-- ===========================
-- == Compliance Statements ==
-- ===========================

pdnVlanMIBCompliance MODULE-COMPLIANCE
    STATUS      current
    DESCRIPTION "The compliance statement for the pdnVlan entities which
                implement the pdnVlanMIB."
    MODULE      -- this module
    -- No mandatory groups are specified

    GROUP       pdnVlanReservedBlockGroup
    DESCRIPTION "This group is mandatory only in those entities which 
                implement reserving a single sequential block of VLANs for 
                internal purposes."

    GROUP       pdnVlanInbandMgmtVlanGroup
    DESCRIPTION "This group is mandatory only in those entities which
                require the VLAN for the In-Band Management channel to
                be configured and identified."
    --
    -- All objects, if implemented, are expected to be implemented to the
    -- maximal level as specified in their OBJECT-TYPE macro.
    --
    ::= { pdnVlanCompliances 1 }



-- ==========================
-- == Units of Conformance ==
-- ==========================

pdnVlanObjGroups       OBJECT IDENTIFIER ::= { pdnVlanGroups 1 }
pdnVlanAfnGroups       OBJECT IDENTIFIER ::= { pdnVlanGroups 2 }
pdnVlanNtfyGroups      OBJECT IDENTIFIER ::= { pdnVlanGroups 3 }


-- ===================
-- == Object Groups ==
-- ===================

pdnVlanReservedBlockGroup OBJECT-GROUP
    OBJECTS {
                pdnVlanReservedBlockStart        
    }
    STATUS      current
    DESCRIPTION "Objects grouped for reserving a block of sequential VLANs."
    ::= { pdnVlanObjGroups  1 }

pdnVlanInbandMgmtVlanGroup OBJECT-GROUP
    OBJECTS {
                pdnVlanInbandMgmtVlanId

    }
    STATUS      current
    DESCRIPTION "Objects grouped relating to the In-Band Managment VLAN."
    ::= { pdnVlanObjGroups 2 }

pdnVlanInbandMgmtVlan2Group OBJECT-GROUP
    OBJECTS {
                pdnVlanInbandMgmtVlanId,
                pdnVlanInbandMgmtVlanId2

    }
    STATUS      current
    DESCRIPTION "Multiples objects grouped relating to the In-Band Managment VLAN."
    ::= { pdnVlanObjGroups 3 }


-- =========
-- == END ==
-- =========
END

-- =============================================================================
-- Copyright (C) 2004 Paradyne Corporation.
-- =============================================================================

PDN-IGMP-STD-EXT-MIB DEFINITIONS ::= BEGIN

IMPORTS
    MODULE-IDENTITY, OBJECT-TYPE, Counter32, Unsigned32
        FROM SNMPv2-SMI
    OBJECT-GROUP, MODULE-COMPLIANCE
        FROM SNMPv2-CONF
    igmpInterfaceEntry, igmpCacheEntry
        FROM IGMP-STD-MIB
    SwitchState
        FROM PDN-TC
    pdn-common
        FROM PDN-HEADER-MIB;
        
pdnIgmpStdExtMIB MODULE-IDENTITY
    LAST-UPDATED "200408170000Z"  -- Aug 17, 2004
    ORGANIZATION "Paradyne Networks
                  MIB Working Group
                  Other information about group editing the MIB."
    CONTACT-INFO "Paradyne Networks, Inc.
                  8545 126th Avenue North
                  Largo, FL 33733
                  www.paradyne.com
        
                  General Comments to: mibwg_team@paradyne.com

                  Editor(s)
                        Clay Sikes,
			Jesus Pinto"

    DESCRIPTION
        "This MIB module is a supplement to the IGMP-STD-MIB."

    REVISION "200408170000Z"  -- Aug 17, 2004
    DESCRIPTION "Added pdnIgmpGeneralQueryInterval object
		to configure this timer globally rather than
		per interface."

    REVISION "200401080000Z"  -- Jan 8, 2004
    DESCRIPTION "Added pdnIgmpSnoopingSelection to enabled/disable
		Igmp snooping on a system-wide basis."

    REVISION "200305060000Z"  -- May 6, 2003
    DESCRIPTION "Corrected a type where 
                 pdnIgmpIngerfaceLeaveJoinForwardingDelay should have
                 been pdnIgmpInterfaceLeaveJoinForwardingDelay."

    REVISION "200305010000Z"  -- May 1, 2003
    DESCRIPTION "Initial release."


::=  { pdn-common 47 }


pdnIgmpStdExtNotifications OBJECT IDENTIFIER ::= { pdnIgmpStdExtMIB 0 }
pdnIgmpStdExtObjects       OBJECT IDENTIFIER ::= { pdnIgmpStdExtMIB 1 }
pdnIgmpStdExtAFNs          OBJECT IDENTIFIER ::= { pdnIgmpStdExtMIB 2 }
pdnIgmpStdExtConformance   OBJECT IDENTIFIER ::= { pdnIgmpStdExtMIB 3 }

 

-- =============================================================================
-- ==                  MIB Objects                                            ==
-- =============================================================================


-- =====================================
-- == igmpInterfaceTable augmentation ==
-- =====================================

pdnIgmpInterfaceExtTable     OBJECT-TYPE
    SYNTAX      SEQUENCE OF PdnIgmpInterfaceExtEntry
    MAX-ACCESS  not-accessible
    STATUS      current
    DESCRIPTION "This table extends the igmpInterfaceTable."
    ::= { pdnIgmpStdExtObjects 1 }

pdnIgmpInterfaceExtEntry     OBJECT-TYPE
    SYNTAX      PdnIgmpInterfaceExtEntry
    MAX-ACCESS  not-accessible
    STATUS      current
    DESCRIPTION "An extended entry in the igmpInterfaceTable. Each entry corresonds
                to a particular interface."
    AUGMENTS     { igmpInterfaceEntry }
    ::= { pdnIgmpInterfaceExtTable 1 }

PdnIgmpInterfaceExtEntry ::=
    SEQUENCE {
        pdnIgmpInterfaceSnoopEnableDisable             SwitchState,
        pdnIgmpInterfaceLeaveDelay                     Unsigned32,
        pdnIgmpInterfaceLeaveJoinForwardingDelay       Unsigned32
    }

pdnIgmpInterfaceSnoopEnableDisable OBJECT-TYPE
    SYNTAX      SwitchState
    MAX-ACCESS  read-write
    STATUS      current
    DESCRIPTION "This object specifies whether or not IGMP Snooping is 
                enabled or disabled.
                   enabled(1)  - IGMP Snooping is Enabled
                   disabled(2) - IGMP Snooping is Disabled"
    DEFVAL      { disabled }
    ::= { pdnIgmpInterfaceExtEntry 1 }

pdnIgmpInterfaceLeaveDelay OBJECT-TYPE
    SYNTAX      Unsigned32(0..255)
    UNITS       "tenths of a second"
    MAX-ACCESS  read-write
    STATUS      current
    DESCRIPTION "This object specifies the leave-delay period.

                This value is defened as the period of time during which a 
                multicast stream will continue to be forwarded on an interface 
                after receipt of an IGMP leave message for that stream."
    DEFVAL      { 3 }
    ::= { pdnIgmpInterfaceExtEntry 2 }


pdnIgmpInterfaceLeaveJoinForwardingDelay OBJECT-TYPE
    SYNTAX      Unsigned32(0..255)
    UNITS       "tenths of a second"
    MAX-ACCESS  read-write
    STATUS      current
    DESCRIPTION "This object specifies the leave-join-delay period.

                This value is defined as the period of time during which new 
                multicast streams will not be forwarded on a port following 
                the receipt of an IGMP Leave message."
    DEFVAL      { 3 }
    ::= { pdnIgmpInterfaceExtEntry 3 }



-- =====================================
-- == igmpCacheTable augmentation ==
-- =====================================

pdnIgmpCacheExtTable     OBJECT-TYPE
    SYNTAX      SEQUENCE OF PdnIgmpCacheExtEntry
    MAX-ACCESS  not-accessible
    STATUS      current
    DESCRIPTION "This table extends the igmpCacheTable."
    ::= { pdnIgmpStdExtObjects 2 }

pdnIgmpCacheExtEntry     OBJECT-TYPE
    SYNTAX      PdnIgmpCacheExtEntry
    MAX-ACCESS  not-accessible
    STATUS      current
    DESCRIPTION "An extended entry in the igmpCacheTable. Each entry corresonds
                to a particular IP Multicast Group Destination Address on a 
                particular interface."
    AUGMENTS     { igmpCacheEntry }
    ::= { pdnIgmpCacheExtTable 1 }

PdnIgmpCacheExtEntry ::=
    SEQUENCE {
        pdnIgmpCacheStatsMulticastPktsIn      Counter32,
        pdnIgmpCacheStatsMulticastPktsOut     Counter32,
        pdnIgmpCacheStatsIgmpQueriesIn        Counter32,
        pdnIgmpCacheStatsIgmpQueriesOut       Counter32,
        pdnIgmpCacheStatsIgmpReportsIn        Counter32,
        pdnIgmpCacheStatsIgmpReportsOut       Counter32,
        pdnIgmpCacheStatsIgmpLeavesIn         Counter32,
        pdnIgmpCacheStatsIgmpLeavesOut        Counter32
    }

pdnIgmpCacheStatsMulticastPktsIn OBJECT-TYPE
    SYNTAX      Counter32
    MAX-ACCESS  read-only
    STATUS      current
    DESCRIPTION "The total number of IP Multicast packets received 
                excluding IGMP messages."
    ::= { pdnIgmpCacheExtEntry 1 }

pdnIgmpCacheStatsMulticastPktsOut OBJECT-TYPE
    SYNTAX      Counter32
    MAX-ACCESS  read-only
    STATUS      current
    DESCRIPTION "The total number of IP Multicast packets transmitted
                excluding IGMP messages."
    ::= { pdnIgmpCacheExtEntry 2 }

pdnIgmpCacheStatsIgmpQueriesIn OBJECT-TYPE
    SYNTAX      Counter32
    MAX-ACCESS  read-only
    STATUS      current
    DESCRIPTION "The total number of IGMP Query messages received."
    ::= { pdnIgmpCacheExtEntry 3 }

pdnIgmpCacheStatsIgmpQueriesOut OBJECT-TYPE
    SYNTAX      Counter32
    MAX-ACCESS  read-only
    STATUS      current
    DESCRIPTION "The total number of IGMP Query messages transmitted."
    ::= { pdnIgmpCacheExtEntry 4 }

pdnIgmpCacheStatsIgmpReportsIn OBJECT-TYPE
    SYNTAX      Counter32
    MAX-ACCESS  read-only
    STATUS      current
    DESCRIPTION "The total number of IGMP Report messages received."
    ::= { pdnIgmpCacheExtEntry 5 }

pdnIgmpCacheStatsIgmpReportsOut OBJECT-TYPE
    SYNTAX      Counter32
    MAX-ACCESS  read-only
    STATUS      current
    DESCRIPTION "The total number of IGMP Report messages transmitted."
    ::= { pdnIgmpCacheExtEntry 6 }

pdnIgmpCacheStatsIgmpLeavesIn OBJECT-TYPE
    SYNTAX      Counter32
    MAX-ACCESS  read-only
    STATUS      current
    DESCRIPTION "The total number of IGMP Leave messages received."
    ::= { pdnIgmpCacheExtEntry 7 }

pdnIgmpCacheStatsIgmpLeavesOut OBJECT-TYPE
    SYNTAX      Counter32
    MAX-ACCESS  read-only
    STATUS      current
    DESCRIPTION "The total number of IGMP Leave messages transmitted."
    ::= { pdnIgmpCacheExtEntry 8 }

pdnIgmpSnoopingSelection OBJECT-TYPE  
    SYNTAX      SwitchState
    MAX-ACCESS  read-write
    STATUS      current
    DESCRIPTION "This object specifies whether or not IGMP Snooping is 
                enabled or disabled on a system-wide basis.

                enabled(1)  - IGMP Snooping is Enabled  on the device
                disabled(2) - IGMP Snooping is Disabled on the device
		"

    DEFVAL      { disabled }
    ::= { pdnIgmpStdExtObjects 3 }


pdnIgmpGeneralQueryInterval OBJECT-TYPE
    SYNTAX     Unsigned32
    UNITS      "seconds"
    MAX-ACCESS read-write
    STATUS     current
    DESCRIPTION
        "This object is similar to the igmpInterfaceQueryInterval
	object defined in RFC2933. However, it can be used to set
	a global value that applies to all the interfaces in the
	system with IGMP enabled.

	A value of zero disables this option and thus the agent
	shall employ the value configured in the 
	igmpInterfaceQueryInterval for each interface running
	IGMP. In the other hands, if this object is set to a value
	greater than zero, the value takes precedence over the
	value configured in the igmpInterfaceQueryInterval for 
	that interface.
	"
    DEFVAL     { 125 }
    ::= { pdnIgmpStdExtObjects 4 }

-- =============================================================================
-- == Conformance Information                                                 ==
-- =============================================================================

pdnIgmpStdExtCompliances    OBJECT IDENTIFIER ::= { pdnIgmpStdExtConformance 1 }
pdnIgmpStdExtGroups         OBJECT IDENTIFIER ::= { pdnIgmpStdExtConformance 2 }

-- ===========================
-- == Compliance Statements ==
-- ===========================

pdnIgmpStdExtMIBCompliance MODULE-COMPLIANCE
    STATUS      deprecated
    DESCRIPTION "The compliance statement for IP Multicast products which
                implement the pdnIpMcaseMIB."
    MODULE      -- this module
    -- No mandatory groups are specified

    -- This compliance is deprecated

    GROUP       pdnIgmpStdExtConfigGroup
    DESCRIPTION "This group is mandatory only for implementations which
                the relative parameters to be configured for IP 
                Multicast and IGMP operation."

    GROUP       pdnIgmpStdExtStatsGroup
    DESCRIPTION "This group is mandatory only for implementations which
                require additional IP Multicast statistics."

    GROUP       pdnIgmpStdExtGeneralConfigGroup
    DESCRIPTION "This group is optional."

    ::= { pdnIgmpStdExtCompliances 1 }

pdnIgmpStdExtMIBComplianceV2 MODULE-COMPLIANCE
    STATUS      current
    DESCRIPTION "The compliance statement for Ip products which
                implement the IGMP protocol."

    MODULE      -- this module
    -- No mandatory groups are specified

    GROUP       pdnIgmpStdExtConfigGroup
    DESCRIPTION "This group is mandatory only for implementations which
                the relative parameters to be configured for IP 
                Multicast and IGMP operation."

    GROUP       pdnIgmpStdExtStatsGroup
    DESCRIPTION "This group is mandatory only for implementations which
                require additional IP Multicast statistics."

    GROUP       pdnIgmpStdExtGeneralConfigGroupV2
    DESCRIPTION "This group is optional."
    ::= { pdnIgmpStdExtCompliances 2 }

-- ==========================
-- == Units of Conformance ==
-- ==========================

pdnIgmpStdExtObjGroups     OBJECT IDENTIFIER ::= { pdnIgmpStdExtGroups 1 }
pdnIgmpStdExtAfnGroups     OBJECT IDENTIFIER ::= { pdnIgmpStdExtGroups 2 }
pdnIgmpStdExtNtfyGroups    OBJECT IDENTIFIER ::= { pdnIgmpStdExtGroups 3 }


-- ===================
-- == Object Groups ==
-- ===================

pdnIgmpStdExtConfigGroup OBJECT-GROUP
    OBJECTS     {
                     pdnIgmpInterfaceSnoopEnableDisable,
                     pdnIgmpInterfaceLeaveDelay,
                     pdnIgmpInterfaceLeaveJoinForwardingDelay
    }
    STATUS      current
    DESCRIPTION "Objects grouped for configuring IP Multicast and
                IGMP parameters. "
    ::= { pdnIgmpStdExtObjGroups  1 }

pdnIgmpStdExtStatsGroup OBJECT-GROUP
    OBJECTS     {
                     pdnIgmpCacheStatsMulticastPktsIn,
                     pdnIgmpCacheStatsMulticastPktsOut,
                     pdnIgmpCacheStatsIgmpQueriesIn,
                     pdnIgmpCacheStatsIgmpQueriesOut,
                     pdnIgmpCacheStatsIgmpReportsIn,
                     pdnIgmpCacheStatsIgmpReportsOut,
                     pdnIgmpCacheStatsIgmpLeavesIn,
                     pdnIgmpCacheStatsIgmpLeavesOut
    }
    STATUS      current
    DESCRIPTION "Objects grouped for IP Multicast and IGMP Statistics."
    ::= { pdnIgmpStdExtObjGroups  2 }

pdnIgmpStdExtGeneralConfigGroup OBJECT-GROUP
    OBJECTS     {
                     pdnIgmpSnoopingSelection
    }
    STATUS      deprecated
    DESCRIPTION "Objects grouped for general configuring of IP Multicast
                and IGMP parameters. 
		
		This group has been deprecated in favor of 
		pdnIgmpStdExtGeneralConfigGroupV2.
		"
    ::= { pdnIgmpStdExtObjGroups  3 }

pdnIgmpStdExtGeneralConfigGroupV2 OBJECT-GROUP
    OBJECTS     {
                     pdnIgmpSnoopingSelection,
		     pdnIgmpGeneralQueryInterval
    }
    STATUS      current
    DESCRIPTION "Objects grouped for general configuring of IP Multicast
                and IGMP parameters. "
    ::= { pdnIgmpStdExtObjGroups  4 }


-- ==================================
-- == Accessible for Notify Groups ==
-- ==================================

-- None defined.


-- =========================
-- == Notification Groups ==
-- =========================

-- None defined.



-- =========
-- == END ==
-- =========
END

-- =============================================================================
-- Copyright (C) 2003 Paradyne Corporation.
-- =============================================================================

PDN-IP-MULTICAST-MIB DEFINITIONS ::= BEGIN

IMPORTS
    MODULE-IDENTITY, OBJECT-TYPE
        FROM SNMPv2-SMI
    OBJECT-GROUP, MODULE-COMPLIANCE
        FROM SNMPv2-CONF
    SwitchState
        FROM PDN-TC
    pdn-common
        FROM PDN-HEADER-MIB;
        
pdnIpMcastMIB MODULE-IDENTITY
    LAST-UPDATED "200305010000Z"  -- May 1, 2003
    ORGANIZATION "Paradyne Networks
                  MIB Working Group
                  Other information about group editing the MIB."
    CONTACT-INFO "Paradyne Networks, Inc.
                  8545 126th Avenue North
                  Largo, FL 33733
                  www.paradyne.com
        
                  General Comments to: mibwg_team@paradyne.com

                  Editor(s)
                        Clay Sikes"

    DESCRIPTION
        "This MIB contains the objects pertaining to the configuration and 
        maintenance of the Internet Group Management Protocol (IGMP) and
        IP Multicast related operation in Paradyne devices."
        

    REVISION "200305010000Z"  -- May 1, 2003
    DESCRIPTION "Initial release."


::=  { pdn-common 48 }


pdnIpMcastNotifications OBJECT IDENTIFIER ::= { pdnIpMcastMIB 0 }
pdnIpMcastObjects       OBJECT IDENTIFIER ::= { pdnIpMcastMIB 1 }
pdnIpMcastAFNs          OBJECT IDENTIFIER ::= { pdnIpMcastMIB 2 }
pdnIpMcastConformance   OBJECT IDENTIFIER ::= { pdnIpMcastMIB 3 }

pdnIgmpProxy            OBJECT IDENTIFIER ::= { pdnIpMcastObjects 1 }
pdnIpMcastStats         OBJECT IDENTIFIER ::= { pdnIpMcastObjects 2 }
 

-- =============================================================================
-- == IGMP Proxy Objects                                                      ==
-- ==      IGMP Proxy is a process where a Paradyne device performs one or    ==
-- ==      more of the following:                                             ==
-- ==          1. Acts like a router by transmitting IGMP Query messages      ==
-- ==             towards hosts attached to one or more of its interfaces.    ==
-- ==          2. Acts like a host by transmitting IGMP Reports towards a     ==
-- ==             router attached to one of its interfaces.                   ==
-- ==          3. Acts like a host by transmitting IGMP Leaves towards a      ==
-- ==             router attached to one of its interfaces.                   ==
-- =============================================================================

pdnIgmpProxyEnableDisable  OBJECT-TYPE
    SYNTAX      SwitchState
    MAX-ACCESS  read-write
    STATUS      current
    DESCRIPTION "This object enables or disables IGMP Proxy."
    DEFVAL      { disabled }
    ::= { pdnIgmpProxy 1 }

pdnIgmpProxyReportSummaryEnableDisable  OBJECT-TYPE
    SYNTAX      SwitchState
    MAX-ACCESS  read-write
    STATUS      current
    DESCRIPTION "This object enables or disables the summarization of all 
                report messages into a single report message."
    DEFVAL      { disabled }
    ::= { pdnIgmpProxy 2 }



-- =============================================================================
-- == Conformance Information                                                 ==
-- =============================================================================


pdnIpMcastCompliances  OBJECT IDENTIFIER ::= { pdnIpMcastConformance 1 }
pdnIpMcastGroups       OBJECT IDENTIFIER ::= { pdnIpMcastConformance 2 }


-- ===========================
-- == Compliance Statements ==
-- ===========================

pdnIpMcastMIBCompliance MODULE-COMPLIANCE
    STATUS      current
    DESCRIPTION "The compliance statement for IP Multicast products which
                implement the pdnIpMcaseMIB."
    MODULE      -- this module
    -- No mandatory groups are specified

    GROUP       pdnIgmpProxyGroup
    DESCRIPTION "This group is mandatory only for implementations which
                require IGMP Proxy."

    ::= { pdnIpMcastCompliances 1 }


-- ==========================
-- == Units of Conformance ==
-- ==========================

pdnIpMcaseObjGroups    OBJECT IDENTIFIER ::= { pdnIpMcastGroups 1 }
pdnIpMcastAfnGroups    OBJECT IDENTIFIER ::= { pdnIpMcastGroups 2 }
pdnIpMcaseNtfyGroups   OBJECT IDENTIFIER ::= { pdnIpMcastGroups 3 }


-- ===================
-- == Object Groups ==
-- ===================

pdnIgmpProxyGroup OBJECT-GROUP
    OBJECTS     {
                     pdnIgmpProxyEnableDisable, 
                     pdnIgmpProxyReportSummaryEnableDisable
    }
    STATUS      current
    DESCRIPTION "Objects grouped for IGMP Proxy."
    ::= { pdnIpMcaseObjGroups  1 }


-- ==================================
-- == Accessible for Notify Groups ==
-- ==================================

-- None defined.


-- =========================
-- == Notification Groups ==
-- =========================

-- None defined.




-- =========
-- == END ==
-- =========
END


-- ===============================================================
-- == Copyright (C) 2003 Paradyne Corporation.                  ==
-- ===============================================================

PDN-HDSL2-SHDSL-LINE-MIB DEFINITIONS ::= BEGIN

IMPORTS
    MODULE-IDENTITY, OBJECT-TYPE, NOTIFICATION-TYPE, 
    Unsigned32, Counter32, Integer32
        FROM SNMPv2-SMI
    OBJECT-GROUP, NOTIFICATION-GROUP, MODULE-COMPLIANCE
        FROM SNMPv2-CONF
    TEXTUAL-CONVENTION
        FROM SNMPv2-TC
    SnmpAdminString
        FROM SNMP-FRAMEWORK-MIB
    ifIndex
        FROM IF-MIB
    PerfCurrentCount, PerfIntervalCount
        FROM PerfHist-TC-MIB
    Hdsl2ShdslPerfTimeElapsed, Hdsl2ShdslPerfCurrDayCount, 
    Hdsl2Shdsl1DayIntervalCount, hdsl2ShdslInvIndex, hdsl2ShdslEndpointSide, 
    hdsl2ShdslEndpointThreshLoopAttenuation,
    hdsl2ShdslEndpointThreshSNRMargin, hdsl2ShdslEndpointThreshES,
    hdsl2ShdslEndpointThreshSES, hdsl2ShdslEndpointThreshCRCanomalies,
    hdsl2ShdslEndpointThreshLOSWS, hdsl2ShdslEndpointThreshUAS, hdsl2ShdslSpanConfProfileName
        FROM HDSL2-SHDSL-LINE-MIB
    pdn-interfaces
        FROM PDN-HEADER-MIB;
        
pdnHdsl2ShdslLineMIB MODULE-IDENTITY
    LAST-UPDATED "200501280000Z"  -- January 28, 2005
    ORGANIZATION "Paradyne Networks
                  MIB Working Group
                  Other information about group editing the MIB"
    CONTACT-INFO "Paradyne Networks, Inc.
                  8545 126th Avenue North
                  Largo, FL 33733
                  www.paradyne.com
        
                  General Comments to: mibwg_team@paradyne.com

                  Editor
                      Clay Sikes"

    DESCRIPTION
        "The primary purpose of this MIB is to allow support of G.shdsl.bis based 
         on the ITU Temporary Document, DC-R15, April 2003, until such a time
         as the `standard' MIB, HDSL2-SHDSL-LINE-MIB, RFC 3276, May 2002 is
         updated to support G.shdsl.bis. In addition to providing support for
         G.shdsl.bis, this MIB may support SHDSL objects that are unique to the
         enterprise.

         Decisions as far as how this MIB is supported with respect to the 
         `standard' MIB will be made in an individual basis by those involved 
         with specific projects; those decisions are not dictated here.

         The following documents should be referenced with respect to this MIB:
         [G.991.2]     ITU-T G991.2 `Single-pair high-speed digital subscriber 
                       line (SHDSL) transceivers,' December 2003.
         [DC-R15]      ITU Study Group 15 Temporary Document `G.shdsl.bis: Draft
                       Text`, April 2003.
         [RFC 3276]    Ray, B., Abbi, R. `HDSL2-SHDSL-LINE-MIB', May 2002.

         =====================================================================
         ==                                                                 ==
         ==            Copyright (C) 2004 Paradyne Corporation.             ==
         ==                                                                 ==
         ====================================================================="

    REVISION "200501280000Z"  -- January 28, 2005
    DESCRIPTION "Added pdnHdsl2ShdslExtendedRateMode object since the
                 hardware implementation may require a different configuration
                 to support higher rates such as the 5696 kbits per second 
                 rate specified in 992.1, Annex F."

    REVISION "200404270000Z"  -- April 27, 2004
    DESCRIPTION "Make the index to pdnHdsl2ShdslSpanConfProfileExtTable IMPLIED 
                 to match with the RFC."

    REVISION "200404210000Z"  -- April 21, 2004
    DESCRIPTION "Changed the pdnHdsl2ShdslSpanStatusExtTable and the
                 pdnHdsl2ShdslSpanConfProfileExtTable from augments to be
                 indexed. Some SNMP agents do a read-modify-write on a table
                 row. As a result, the instrumentation code may not be able to 
                 determine which object the manager actually wants to set. For 
                 example, consider the case where a manager wants to set the 
                 wire interface to 8-wire operation. The instrumentation code, in
                 the case of a read-modify-write cycle, could result in receiving
                 a row where the hdsl2ShdslSpanConfWireInterface is set to 
                 twoWire(1) and pdnHdsl2ShdslSpanConfWireInterface is set to
                 eightWire(4). This could result in unpredictable results. 
                 This change will prevent the objects in the ExtTables from
                 existing in the same row as the objects in the standard tables
                 and prevent the unpredictable case from occurring."

    REVISION "200401161500Z"  -- January 16, 2004
    DESCRIPTION "Removed description text that implies that this MIB only applies 
                 to G.shdsl.bis. Add a table to allow the device to be configured
                 in CPE mode or CO mode."

    REVISION "200311061500Z"  -- November 6, 2003
    DESCRIPTION "Clean up, typo corrections, and clarifications."

    REVISION "200310231500Z"  -- October 23, 2003
    DESCRIPTION "Initial release."


::=  { pdn-interfaces 23 }


-- =============================================================================
-- == Define groups for Notifications, MIB Objects, Accessible for            ==
-- == Notifications (AFNs), and Conformance.                                  ==
-- == These may just be place holders.                                        ==
-- =============================================================================
pdnHdsl2ShdslLineNotifications OBJECT IDENTIFIER ::= { pdnHdsl2ShdslLineMIB 0 }
pdnHdsl2ShdslLineObjects       OBJECT IDENTIFIER ::= { pdnHdsl2ShdslLineMIB 1 }
pdnHdsl2ShdslLineAFNs          OBJECT IDENTIFIER ::= { pdnHdsl2ShdslLineMIB 2 } 
pdnHdsl2ShdslLineConformance   OBJECT IDENTIFIER ::= { pdnHdsl2ShdslLineMIB 3 }


-- =============================================================================
-- ==                  Textual Conventions                                    ==
-- =============================================================================

PdnHdsl2ShdslWirePair  ::= TEXTUAL-CONVENTION
    STATUS      current
    DESCRIPTION "This is the referenced pair of wires in a DSL Segment. HDSL2
                 only supports a single pair (wirePair1), while SHDSL supports an 
                 optional second pair (wirePair2), third pair (wirePair3), and a 
                 forth pair (wirePair4)."
    SYNTAX      INTEGER {
                    wirePair1(1),
                    wirePair2(2),
                    wirePair3(3),
                    wirePair4(4)
                }     



-- =============================================================================
-- ==                  MIB Objects                                            ==
-- =============================================================================


-- =============================================================================
-- == pdnHdsl2ShdslSpanStatusTable                                            ==
-- =============================================================================
pdnHdsl2ShdslSpanStatusExtTable   OBJECT-TYPE
    SYNTAX      SEQUENCE OF PdnHdsl2ShdslSpanStatusExtEntry
    MAX-ACCESS  not-accessible
    STATUS      current
    DESCRIPTION "This table extends the hdsl2ShdslSpanStatusTable defined in the
                 HDSL2-SHDSL-LINE-MIB (the `standard' MIB) which provides overall
                 information of DSL spans."
    ::= { pdnHdsl2ShdslLineObjects 1 }

pdnHdsl2ShdslSpanStatusExtEntry     OBJECT-TYPE
    SYNTAX      PdnHdsl2ShdslSpanStatusExtEntry
    MAX-ACCESS  not-accessible
    STATUS      current
    DESCRIPTION "An entry extends the hdsl2ShdslSpanStatusEntry defined in
                 [RFC 3276]. Each entry corresponds to a DSL line."
    INDEX       { ifIndex }
    ::= { pdnHdsl2ShdslSpanStatusExtTable 1 }

PdnHdsl2ShdslSpanStatusExtEntry ::=
    SEQUENCE {
        pdnHdsl2ShdslStatusMaxAttainableLineRate    Unsigned32,
        pdnHdsl2ShdslStatusActualLineRate           Unsigned32
    }

pdnHdsl2ShdslStatusMaxAttainableLineRate OBJECT-TYPE
    SYNTAX      Unsigned32
    UNITS       "bps"
    MAX-ACCESS  read-only
    STATUS      current
    DESCRIPTION "Contains the maximum attainable line rate, in bps, in this
                 DSL span."
    REFERENCE   "RFC 3276, hdsl2ShdslStatusMaxAttainableLineRate."
    ::= { pdnHdsl2ShdslSpanStatusExtEntry 1 }

pdnHdsl2ShdslStatusActualLineRate OBJECT-TYPE
    SYNTAX      Unsigned32
    UNITS       "bps"
    MAX-ACCESS  read-only
    STATUS      current
    DESCRIPTION "Contains the actual line rate, in bps, in this DSL span.
                 This is based upon measurements made during line probing."
    REFERENCE   "RFC 3276, hdsl2ShdslStatusActualLineRate."
    ::= { pdnHdsl2ShdslSpanStatusExtEntry 2 }


-- ===========================================================================
-- == pdnHdsl2ShdslEndpointConfTable                                        ==
-- ===========================================================================
pdnHdsl2ShdslEndpointConfTable OBJECT-TYPE
    SYNTAX      SEQUENCE OF PdnHdsl2ShdslEndpointConfEntry
    MAX-ACCESS  not-accessible
    STATUS      current
    DESCRIPTION "This table supports configuration parameters for segment
                 endpoints in a HDSL2/SHDSL line.  As this table is indexed
                 by ifIndex, it MUST be maintained in a persistent manner."
    REFERENCE   "RFC 3276, hdsl2ShdslEndpointConfTable."
    ::= { pdnHdsl2ShdslLineObjects 2 }

pdnHdsl2ShdslEndpointConfEntry OBJECT-TYPE
    SYNTAX      PdnHdsl2ShdslEndpointConfEntry
    MAX-ACCESS  not-accessible
    STATUS      current
    DESCRIPTION "Each entry represents a single segment endpoint in a HDSL2/SHDSL 
                 line. It is indexed by the ifIndex of the HDSL2/SHDSL line, the
                 UnitId of the associated unit, the side of the unit, and the
                 wire-pair of the associated modem."
    INDEX { ifIndex, hdsl2ShdslInvIndex, hdsl2ShdslEndpointSide, 
            pdnHdsl2ShdslEndpointWirePair }
    ::= { pdnHdsl2ShdslEndpointConfTable 1 }

PdnHdsl2ShdslEndpointConfEntry ::=
    SEQUENCE {
        pdnHdsl2ShdslEndpointWirePair               PdnHdsl2ShdslWirePair,
        pdnHdsl2ShdslEndpointAlarmConfProfile       SnmpAdminString
    }

pdnHdsl2ShdslEndpointWirePair OBJECT-TYPE
    SYNTAX      PdnHdsl2ShdslWirePair
    MAX-ACCESS  not-accessible
    STATUS      current
    DESCRIPTION "The wire-pair of the modem associated with this segment
                 endpoint as per the PdnHdsl2ShdslWirePair textual convention."
     REFERENCE   "RFC 3276, hdsl2ShdslEndpointWirePair."
   ::= { pdnHdsl2ShdslEndpointConfEntry 1 }

pdnHdsl2ShdslEndpointAlarmConfProfile OBJECT-TYPE
    SYNTAX      SnmpAdminString (SIZE(0..32))
    MAX-ACCESS  read-write
    STATUS      current
    DESCRIPTION "This object configures the alarm threshold values to be used
                 for this segment endpoint.  The values are obtained from the
                 alarm configuration profile referenced by this object.  The
                 value of this object is the index of the referenced profile in
                 the hdsl2ShdslEndpointAlarmConfProfileTable, or NULL (a zero-
                 length SnmpAdminString).  If the value is a zero-length
                 SnmpAdminString, the endpoint uses the default Alarm
                 Configuration Profile for the associated span as per the
                 hdsl2ShdslSpanConfAlarmProfile object in the
                 hdsl2ShdslSpanConfTable.  The default value of this object is
                 a zero-length SnmpAdminString.

                 Any attempt to set this object to a value that is not the value
                 of the index for an active entry in the profile table,
                 hdsl2ShdslEndpointAlarmConfProfileTable, MUST be rejected."
     REFERENCE   "RFC 3276, hdsl2ShdslEndpointAlarmConfProfile."
    ::= { pdnHdsl2ShdslEndpointConfEntry 2 }


-- =============================================================================
-- == pdnHdsl2ShdslEndpointCurrTable                                          ==
-- =============================================================================
pdnHdsl2ShdslEndpointCurrTable OBJECT-TYPE
    SYNTAX      SEQUENCE OF PdnHdsl2ShdslEndpointCurrEntry
    MAX-ACCESS  not-accessible
    STATUS      current
    DESCRIPTION "This table contains current status and performance information
                 for segment endpoints in HDSL2/SHDSL Lines.  As with other
                 tables in this MIB indexed by ifIndex, entries in this table
                 MUST be maintained in a persistent manner."
    REFERENCE   "RFC 3276, hdsl2ShdslEndpointCurrTable."
    ::= { pdnHdsl2ShdslLineObjects 3 }

pdnHdsl2ShdslEndpointCurrEntry OBJECT-TYPE
    SYNTAX      PdnHdsl2ShdslEndpointCurrEntry
    MAX-ACCESS  not-accessible
    STATUS      current
    DESCRIPTION "Each entry contains status and performance information relating 
                 to a single segment endpoint.  It is indexed by the ifIndex of 
                 the HDSL2/SHDSL line, the UnitId of the associated unit, the 
                 side of the unit, and the wire-pair of the associated modem."
    INDEX { ifIndex, hdsl2ShdslInvIndex, hdsl2ShdslEndpointSide,
            pdnHdsl2ShdslEndpointWirePair }
    ::= { pdnHdsl2ShdslEndpointCurrTable 1 }

PdnHdsl2ShdslEndpointCurrEntry ::=
    SEQUENCE {
        pdnHdsl2ShdslEndpointCurrAtn                Integer32,
        pdnHdsl2ShdslEndpointCurrSnrMgn             Integer32,
        pdnHdsl2ShdslEndpointCurrStatus             BITS,
        pdnHdsl2ShdslEndpointES                     Counter32,
        pdnHdsl2ShdslEndpointSES                    Counter32,
        pdnHdsl2ShdslEndpointCRCanomalies           Counter32,
        pdnHdsl2ShdslEndpointLOSWS                  Counter32,
        pdnHdsl2ShdslEndpointUAS                    Counter32,
        pdnHdsl2ShdslEndpointCurr15MinTimeElapsed   Hdsl2ShdslPerfTimeElapsed,
        pdnHdsl2ShdslEndpointCurr15MinES            PerfCurrentCount,
        pdnHdsl2ShdslEndpointCurr15MinSES           PerfCurrentCount,
        pdnHdsl2ShdslEndpointCurr15MinCRCanomalies  PerfCurrentCount,
        pdnHdsl2ShdslEndpointCurr15MinLOSWS         PerfCurrentCount,
        pdnHdsl2ShdslEndpointCurr15MinUAS           PerfCurrentCount,
        pdnHdsl2ShdslEndpointCurr1DayTimeElapsed    Hdsl2ShdslPerfTimeElapsed,
        pdnHdsl2ShdslEndpointCurr1DayES             Hdsl2ShdslPerfCurrDayCount,
        pdnHdsl2ShdslEndpointCurr1DaySES            Hdsl2ShdslPerfCurrDayCount,
        pdnHdsl2ShdslEndpointCurr1DayCRCanomalies   Hdsl2ShdslPerfCurrDayCount,
        pdnHdsl2ShdslEndpointCurr1DayLOSWS          Hdsl2ShdslPerfCurrDayCount,
        pdnHdsl2ShdslEndpointCurr1DayUAS            Hdsl2ShdslPerfCurrDayCount
    }

pdnHdsl2ShdslEndpointCurrAtn OBJECT-TYPE
    SYNTAX      Integer32(-127..128)
    UNITS       "dB"
    MAX-ACCESS  read-only
    STATUS      current
    DESCRIPTION "The current loop attenuation for this endpoint as reported in
                 a Network or Customer Side Performance Status message."
    REFERENCE   "RFC 3276, hdsl2ShdslEndpointCurrAtn."
   ::= { pdnHdsl2ShdslEndpointCurrEntry 1 }

pdnHdsl2ShdslEndpointCurrSnrMgn OBJECT-TYPE
    SYNTAX      Integer32(-127..128)
    UNITS       "dB"
    MAX-ACCESS  read-only
    STATUS      current
    DESCRIPTION "The current SNR margin for this endpoint as reported in a
                 Status Response/SNR message."
    REFERENCE   "RFC 3276, hdsl2ShdslEndpointCurrSnrMgn."
    ::= { pdnHdsl2ShdslEndpointCurrEntry 2 }

pdnHdsl2ShdslEndpointCurrStatus OBJECT-TYPE
    SYNTAX      BITS {
                    noDefect(0),
                    powerBackoff(1),
                    deviceFault(2),
                    dcContinuityFault(3),
                    snrMarginAlarm(4),
                    loopAttenuationAlarm(5),
                    loswFailureAlarm(6),
                    configInitFailure(7),
                    protocolInitFailure(8),
                    noNeighborPresent(9),
                    loopbackActive(10)
                }
    MAX-ACCESS  read-only
    STATUS      current
    DESCRIPTION "Contains the current state of the endpoint.  This is a
                 bitmap of possible conditions. The various bit positions
                 are:

                     noDefect               There no defects on the line.

                     powerBackoff           Indicates enhanced Power Backoff.

                     deviceFault            Indicates a vendor-dependent
                                            diagnostic or self-test fault
                                            has been detected.

                     dcContinuityFault      Indicates vendor-dependent
                                            conditions that interfere with
                                            span powering such as short and
                                            open circuits.

                     snrMarginAlarm         Indicates that the SNR margin
                                            has dropped below the alarm threshold.

                     loopAttenuationAlarm   Indicates that the loop attenuation
                                            exceeds the alarm threshold.

                     loswFailureAlarm       Indicates a forward LOSW alarm.

                     configInitFailure      Endpoint failure during initialization
                                            due to paired endpoint not able to
                                            support requested configuration.

                     protocolInitFailure    Endpoint failure during initialization
                                            due to incompatible protocol used by
                                            the paired endpoint.

                     noNeighborPresent      Endpoint failure during initialization
                                            due to no activation sequence detected
                                            from paired endpoint.

                     loopbackActive         A loopback is currently active at this
                                            Segment Endpoint.

                 This is intended to supplement ifOperStatus.  Note that there
                 is a 1-1 relationship between the status bits defined in this
                 object and the notification thresholds defined elsewhere in
                 this MIB."
    REFERENCE   "RFC 3276, hdsl2ShdslEndpointCurrStatus."
    ::= { pdnHdsl2ShdslEndpointCurrEntry 3 }

pdnHdsl2ShdslEndpointES OBJECT-TYPE
    SYNTAX      Counter32
    UNITS       "seconds"
    MAX-ACCESS  read-only
    STATUS      current
    DESCRIPTION "Count of Errored Seconds (ES) on this endpoint since the xU
                 was last restarted."
    REFERENCE   "RFC 3276, hdsl2ShdslEndpointES."
    ::= { pdnHdsl2ShdslEndpointCurrEntry 4 }

pdnHdsl2ShdslEndpointSES OBJECT-TYPE
    SYNTAX      Counter32
    UNITS       "seconds"
    MAX-ACCESS  read-only
    STATUS      current
    DESCRIPTION "Count of Severely Errored Seconds (SES) on this endpoint
                 since the xU was last restarted."
    REFERENCE   "RFC 3276, hdsl2ShdslEndpointSES."
    ::= { pdnHdsl2ShdslEndpointCurrEntry 5 }

pdnHdsl2ShdslEndpointCRCanomalies OBJECT-TYPE
    SYNTAX      Counter32
    UNITS       "detected CRC Anomalies"
    MAX-ACCESS  read-only
    STATUS      current
    DESCRIPTION "Count of CRC anomalies on this endpoint since the xU was
                 last restarted."
    REFERENCE   "RFC 3276, hdsl2ShdslEndpointCRCanomalies."
    ::= { pdnHdsl2ShdslEndpointCurrEntry 6 }

pdnHdsl2ShdslEndpointLOSWS OBJECT-TYPE
    SYNTAX      Counter32
    UNITS       "seconds"
    MAX-ACCESS  read-only
    STATUS      current
    DESCRIPTION "Count of Loss of Sync Word (LOSW) Seconds on this endpoint
                 since the xU was last restarted."
    REFERENCE   "RFC 3276, hdsl2ShdslEndpointLOSWS."
    ::= { pdnHdsl2ShdslEndpointCurrEntry 7 }

pdnHdsl2ShdslEndpointUAS OBJECT-TYPE
    SYNTAX      Counter32
    UNITS       "seconds"
    MAX-ACCESS  read-only
    STATUS      current
    DESCRIPTION "Count of Unavailable Seconds (UAS) on this endpoint since
                 the xU was last restarted."
    REFERENCE   "RFC 3276, hdsl2ShdslEndpointUAS."
    ::= { pdnHdsl2ShdslEndpointCurrEntry 8 }

pdnHdsl2ShdslEndpointCurr15MinTimeElapsed OBJECT-TYPE
    SYNTAX      Hdsl2ShdslPerfTimeElapsed
    UNITS       "seconds"
    MAX-ACCESS  read-only
    STATUS      current
    DESCRIPTION "Total elapsed seconds in the current 15-minute interval."
    REFERENCE   "RFC 3276, hdsl2ShdslEndpointCurr15MinTimeElapsed."
    ::= { pdnHdsl2ShdslEndpointCurrEntry 9 }

pdnHdsl2ShdslEndpointCurr15MinES OBJECT-TYPE
    SYNTAX      PerfCurrentCount
    UNITS       "seconds"
    MAX-ACCESS  read-only
    STATUS      current
    DESCRIPTION "Count of Errored Seconds (ES) in the current 15-minute
                 interval."
    REFERENCE   "RFC 3276, hdsl2ShdslEndpointCurr15MinES."
    ::= { pdnHdsl2ShdslEndpointCurrEntry 10 }

pdnHdsl2ShdslEndpointCurr15MinSES OBJECT-TYPE
    SYNTAX      PerfCurrentCount
    UNITS       "seconds"
    MAX-ACCESS  read-only
    STATUS      current
    DESCRIPTION "Count of Severely Errored Seconds (SES) in the current
                 15-minute interval."
    REFERENCE   "RFC 3276, hdsl2ShdslEndpointCurr15MinSES."
    ::= { pdnHdsl2ShdslEndpointCurrEntry 11 }

pdnHdsl2ShdslEndpointCurr15MinCRCanomalies OBJECT-TYPE
    SYNTAX      PerfCurrentCount
    UNITS       "detected CRC Anomalies"
    MAX-ACCESS  read-only
    STATUS      current
    DESCRIPTION "Count of CRC anomalies in the current 15-minute interval."
    REFERENCE   "RFC 3276, hdsl2ShdslEndpointCurr15MinCRCanomalies."
    ::= { pdnHdsl2ShdslEndpointCurrEntry 12 }

pdnHdsl2ShdslEndpointCurr15MinLOSWS OBJECT-TYPE
    SYNTAX      PerfCurrentCount
    UNITS       "seconds"
    MAX-ACCESS  read-only
    STATUS      current
    DESCRIPTION "Count of Loss of Sync Word (LOSW) Seconds in the current
                 15-minute interval."
    REFERENCE   "RFC 3276, hdsl2ShdslEndpointCurr15MinLOSWS."
    ::= { pdnHdsl2ShdslEndpointCurrEntry 13 }

pdnHdsl2ShdslEndpointCurr15MinUAS OBJECT-TYPE
    SYNTAX      PerfCurrentCount
    UNITS       "seconds"
    MAX-ACCESS  read-only
    STATUS      current
    DESCRIPTION "Count of Unavailable Seconds (UAS) in the current 15-minute
                 interval."
    REFERENCE   "RFC 3276, hdsl2ShdslEndpointCurr15MinUAS."
    ::= { pdnHdsl2ShdslEndpointCurrEntry 14 }

pdnHdsl2ShdslEndpointCurr1DayTimeElapsed OBJECT-TYPE
    SYNTAX      Hdsl2ShdslPerfTimeElapsed
    UNITS       "seconds"
    MAX-ACCESS  read-only
    STATUS      current
    DESCRIPTION "Number of seconds that have elapsed since the beginning of
                 the current 1-day interval."
    REFERENCE   "RFC 3276, hdsl2ShdslEndpointCurr1DayTimeElapsed."
    ::= { pdnHdsl2ShdslEndpointCurrEntry 15 }

pdnHdsl2ShdslEndpointCurr1DayES OBJECT-TYPE
    SYNTAX      Hdsl2ShdslPerfCurrDayCount
    UNITS       "seconds"
    MAX-ACCESS  read-only
    STATUS      current
    DESCRIPTION "Count of Errored Seconds (ES) during the current day as
                 measured by pdnHdsl2ShdslEndpointCurr1DayTimeElapsed."
    REFERENCE   "RFC 3276, hdsl2ShdslEndpointCurr1DayES."
    ::= { pdnHdsl2ShdslEndpointCurrEntry 16 }

pdnHdsl2ShdslEndpointCurr1DaySES OBJECT-TYPE
    SYNTAX      Hdsl2ShdslPerfCurrDayCount
    UNITS       "seconds"
    MAX-ACCESS  read-only
    STATUS      current
    DESCRIPTION "Count of Severely Errored Seconds (SES) during the current
                 day as measured by pdnHdsl2ShdslEndpointCurr1DayTimeElapsed."
    REFERENCE   "RFC 3276, hdsl2ShdslEndpointCurr1DaySES."
    ::= { pdnHdsl2ShdslEndpointCurrEntry 17 }

pdnHdsl2ShdslEndpointCurr1DayCRCanomalies OBJECT-TYPE
    SYNTAX      Hdsl2ShdslPerfCurrDayCount
    UNITS       "detected CRC Anomalies"
    MAX-ACCESS  read-only
    STATUS      current
    DESCRIPTION "Count of CRC anomalies during the current day as measured
                 by pdnHdsl2ShdslEndpointCurr1DayTimeElapsed."
    REFERENCE   "RFC 3276, hdsl2ShdslEndpointCurr1DayCRCanomalies."
    ::= { pdnHdsl2ShdslEndpointCurrEntry 18 }

pdnHdsl2ShdslEndpointCurr1DayLOSWS OBJECT-TYPE
    SYNTAX      Hdsl2ShdslPerfCurrDayCount
    UNITS       "seconds"
    MAX-ACCESS  read-only
    STATUS      current
    DESCRIPTION "Count of Loss of Sync Word (LOSW) Seconds during the current
                 day as measured by pdnHdsl2ShdslEndpointCurr1DayTimeElapsed."
    REFERENCE   "RFC 3276, hdsl2ShdslEndpointCurr1DayLOSWS."
    ::= { pdnHdsl2ShdslEndpointCurrEntry 19 }

pdnHdsl2ShdslEndpointCurr1DayUAS OBJECT-TYPE
    SYNTAX      Hdsl2ShdslPerfCurrDayCount
    UNITS       "seconds"
    MAX-ACCESS  read-only
    STATUS      current
    DESCRIPTION "Count of Unavailable Seconds (UAS) during the current day as
                 measured by pdnHdsl2ShdslEndpointCurr1DayTimeElapsed."
    REFERENCE   "RFC 3276, hdsl2ShdslEndpointCurr1DayUAS."
    ::= { pdnHdsl2ShdslEndpointCurrEntry 20 }


-- =============================================================================
-- == pdhHdsl2Shdsl15MinIntervalTable                                         ==
-- =============================================================================
pdnHdsl2Shdsl15MinIntervalTable OBJECT-TYPE
    SYNTAX      SEQUENCE OF PdnHdsl2Shdsl15MinIntervalEntry
    MAX-ACCESS  not-accessible
    STATUS      current
    DESCRIPTION "This table provides one row for each HDSL2/SHDSL endpoint
                 performance data collection interval.  This table contains
                 live data from equipment.  As such, it is NOT persistent."
    REFERENCE   "RFC 3276, hdsl2Shdsl15MinIntervalTable."
    ::= { pdnHdsl2ShdslLineObjects 4 }

pdnHdsl2Shdsl15MinIntervalEntry OBJECT-TYPE
    SYNTAX      PdnHdsl2Shdsl15MinIntervalEntry
    MAX-ACCESS  not-accessible
    STATUS      current
    DESCRIPTION "An entry in the pdnHdsl2Shdsl15MinIntervalTable."
    INDEX { ifIndex, hdsl2ShdslInvIndex, hdsl2ShdslEndpointSide,
            pdnHdsl2ShdslEndpointWirePair, pdnHdsl2Shdsl15MinIntervalNumber }
    ::= { pdnHdsl2Shdsl15MinIntervalTable 1 }

PdnHdsl2Shdsl15MinIntervalEntry ::=
    SEQUENCE {
        pdnHdsl2Shdsl15MinIntervalNumber         Unsigned32,
        pdnHdsl2Shdsl15MinIntervalES             PerfIntervalCount,
        pdnHdsl2Shdsl15MinIntervalSES            PerfIntervalCount,
        pdnHdsl2Shdsl15MinIntervalCRCanomalies   PerfIntervalCount,
        pdnHdsl2Shdsl15MinIntervalLOSWS          PerfIntervalCount,
        pdnHdsl2Shdsl15MinIntervalUAS            PerfIntervalCount
    }

pdnHdsl2Shdsl15MinIntervalNumber OBJECT-TYPE
    SYNTAX      Unsigned32(1..96)
    MAX-ACCESS  not-accessible
    STATUS      current
    DESCRIPTION "Performance Data Interval number. 1 is the the most recent
                 previous interval; interval 96 is 24 hours ago. Intervals
                 2..96 are optional."
    REFERENCE   "RFC 3276, hdsl2Shdsl15MinIntervalNumber."
    ::= { pdnHdsl2Shdsl15MinIntervalEntry 1 }

pdnHdsl2Shdsl15MinIntervalES OBJECT-TYPE
    SYNTAX      PerfIntervalCount
    UNITS       "seconds"
    MAX-ACCESS  read-only
    STATUS      current
    DESCRIPTION "Count of Errored Seconds (ES) during the interval."
    REFERENCE   "RFC 3276, hdsl2Shdsl15MinIntervalES."
    ::= { pdnHdsl2Shdsl15MinIntervalEntry 2 }

pdnHdsl2Shdsl15MinIntervalSES OBJECT-TYPE
    SYNTAX      PerfIntervalCount
    UNITS       "seconds"
    MAX-ACCESS  read-only
    STATUS      current
    DESCRIPTION "Count of Severely Errored Seconds (SES) during the interval."
    REFERENCE   "RFC 3276, hdsl2Shdsl15MinIntervalSES."
    ::= { pdnHdsl2Shdsl15MinIntervalEntry 3 }

pdnHdsl2Shdsl15MinIntervalCRCanomalies OBJECT-TYPE
    SYNTAX      PerfIntervalCount
    UNITS       "detected CRC Anomalies"
    MAX-ACCESS  read-only
    STATUS      current
    DESCRIPTION "Count of CRC anomalies during the interval."
    REFERENCE   "RFC 3276, hdsl2Shdsl15MinIntervalCRCanomalies."
    ::= { pdnHdsl2Shdsl15MinIntervalEntry 4 }

pdnHdsl2Shdsl15MinIntervalLOSWS OBJECT-TYPE
    SYNTAX      PerfIntervalCount
    UNITS       "seconds"
    MAX-ACCESS  read-only
    STATUS      current
    DESCRIPTION "Count of Loss of Sync Word (LOSW) Seconds during the
                 interval."
    REFERENCE   "RFC 3276, hdsl2Shdsl15MinIntervalLOSWS."
    ::= { pdnHdsl2Shdsl15MinIntervalEntry 5 }

pdnHdsl2Shdsl15MinIntervalUAS OBJECT-TYPE
    SYNTAX      PerfIntervalCount
    UNITS       "seconds"
    MAX-ACCESS  read-only
    STATUS      current
    DESCRIPTION "Count of Unavailable Seconds (UAS) during the interval."
    REFERENCE   "RFC 3276, hdsl2Shdsl15MinIntervalUAS."
    ::= { pdnHdsl2Shdsl15MinIntervalEntry 6 }


-- =============================================================================
-- == pdnHdsl2Shdsl1DayIntervalTable                                          ==
-- =============================================================================
pdnHdsl2Shdsl1DayIntervalTable OBJECT-TYPE
    SYNTAX      SEQUENCE OF PdnHdsl2Shdsl1DayIntervalEntry
    MAX-ACCESS  not-accessible
    STATUS      current
    DESCRIPTION "This table provides one row for each HDSL2/SHDSL endpoint
                 performance data collection interval.  This table contains
                 live data from equipment.  As such, it is NOT persistent."
    REFERENCE   "RFC 3276, hdsl2Shdsl1DayIntervalTable."
    ::= { pdnHdsl2ShdslLineObjects 5 }

pdnHdsl2Shdsl1DayIntervalEntry OBJECT-TYPE
    SYNTAX      PdnHdsl2Shdsl1DayIntervalEntry
    MAX-ACCESS  not-accessible
    STATUS      current

    DESCRIPTION "An entry in the pdnHdsl2Shdsl1DayIntervalTable."
    INDEX { ifIndex, hdsl2ShdslInvIndex, hdsl2ShdslEndpointSide,
            pdnHdsl2ShdslEndpointWirePair, pdnHdsl2Shdsl1DayIntervalNumber }
    ::= { pdnHdsl2Shdsl1DayIntervalTable 1 }

PdnHdsl2Shdsl1DayIntervalEntry ::=
    SEQUENCE {
        pdnHdsl2Shdsl1DayIntervalNumber         Unsigned32,
        pdnHdsl2Shdsl1DayIntervalMoniSecs       Hdsl2ShdslPerfTimeElapsed,
        pdnHdsl2Shdsl1DayIntervalES             Hdsl2Shdsl1DayIntervalCount,
        pdnHdsl2Shdsl1DayIntervalSES            Hdsl2Shdsl1DayIntervalCount,
        pdnHdsl2Shdsl1DayIntervalCRCanomalies   Hdsl2Shdsl1DayIntervalCount,
        pdnHdsl2Shdsl1DayIntervalLOSWS          Hdsl2Shdsl1DayIntervalCount,
        pdnHdsl2Shdsl1DayIntervalUAS            Hdsl2Shdsl1DayIntervalCount
    }

pdnHdsl2Shdsl1DayIntervalNumber OBJECT-TYPE
    SYNTAX      Unsigned32(1..30)
    MAX-ACCESS  not-accessible
    STATUS      current
    DESCRIPTION "History Data Interval number. Interval 1 is the the most
                 recent previous day; interval 30 is 30 days ago. Intervals
                 2..30 are optional."
    REFERENCE   "RFC 3276, hdsl2Shdsl1DayIntervalNumber."
    ::= { pdnHdsl2Shdsl1DayIntervalEntry 1 }

pdnHdsl2Shdsl1DayIntervalMoniSecs OBJECT-TYPE
    SYNTAX      Hdsl2ShdslPerfTimeElapsed
    UNITS       "seconds"
    MAX-ACCESS  read-only
    STATUS      current
    DESCRIPTION "The amount of time in the 1-day interval over which the
                 performance monitoring information is actually counted.
                 This value will be the same as the interval duration except
                 in a situation where performance monitoring data could not
                 be collected for any reason."
    REFERENCE   "RFC 3276, hdsl2Shdsl1DayIntervalMoniSecs."
    ::= { pdnHdsl2Shdsl1DayIntervalEntry 2 }

pdnHdsl2Shdsl1DayIntervalES OBJECT-TYPE
    SYNTAX       Hdsl2Shdsl1DayIntervalCount
    UNITS        "seconds"
    MAX-ACCESS   read-only
    STATUS       current
    DESCRIPTION "Count of Errored Seconds (ES) during the 1-day interval as
                 measured by pdnHdsl2Shdsl1DayIntervalMoniSecs."
    REFERENCE   "RFC 3276, hdsl2Shdsl1DayIntervalES."
    ::= { pdnHdsl2Shdsl1DayIntervalEntry 3 }

pdnHdsl2Shdsl1DayIntervalSES OBJECT-TYPE
    SYNTAX      Hdsl2Shdsl1DayIntervalCount
    UNITS       "seconds"
    MAX-ACCESS  read-only
    STATUS      current
    DESCRIPTION "Count of Severely Errored Seconds (SES) during the 1-day
                 interval as measured by pdnHdsl2Shdsl1DayIntervalMoniSecs."
    REFERENCE   "RFC 3276, hdsl2Shdsl1DayIntervalSES."
    ::= { pdnHdsl2Shdsl1DayIntervalEntry 4 }

pdnHdsl2Shdsl1DayIntervalCRCanomalies OBJECT-TYPE
    SYNTAX      Hdsl2Shdsl1DayIntervalCount
    UNITS       "detected CRC Anomalies"
    MAX-ACCESS  read-only
    STATUS      current
    DESCRIPTION "Count of CRC anomalies during the 1-day interval as
                 measured by pdnHdsl2Shdsl1DayIntervalMoniSecs."
    REFERENCE   "RFC 3276, hdsl2Shdsl1DayIntervalCRCanomalies."
    ::= { pdnHdsl2Shdsl1DayIntervalEntry 5 }

pdnHdsl2Shdsl1DayIntervalLOSWS OBJECT-TYPE
    SYNTAX      Hdsl2Shdsl1DayIntervalCount
    UNITS       "seconds"
    MAX-ACCESS  read-only
    STATUS      current
    DESCRIPTION "Count of Loss of Sync Word (LOSW) Seconds during the 1-day
                 interval as measured by pdnHdsl2Shdsl1DayIntervalMoniSecs."
    REFERENCE   "RFC 3276, hdsl2Shdsl1DayIntervalLOSWS."
    ::= { pdnHdsl2Shdsl1DayIntervalEntry 6 }

pdnHdsl2Shdsl1DayIntervalUAS OBJECT-TYPE
    SYNTAX      Hdsl2Shdsl1DayIntervalCount
    UNITS       "seconds"
    MAX-ACCESS  read-only
    STATUS      current
    DESCRIPTION "Count of Unavailable Seconds (UAS) during the 1-day interval
                 as measured by pdnHdsl2Shdsl1DayIntervalMoniSecs."
    REFERENCE   "RFC 3276, hdsl2Shdsl1DayIntervalUAS."
    ::= { pdnHdsl2Shdsl1DayIntervalEntry 7 }


-- =============================================================================
-- == pdnHdsl2ShdslSpanConfProfileExtTable                                    ==
-- =============================================================================
pdnHdsl2ShdslSpanConfProfileExtTable       OBJECT-TYPE
    SYNTAX      SEQUENCE OF PdnHdsl2ShdslSpanConfProfileExtEntry
    MAX-ACCESS  not-accessible
    STATUS      current
    DESCRIPTION "This table extends the hdsl2ShdslSpanConfProfileTable defined in 
                 the HDSL2-SHDSL-LINE-MIB (the `standard' MIB) which supports
                 definitions of span configuration profiles for DSL lines.

                 IMPORTANT NOTE:  This table is a 'pseudo-augments' of the
                 hdsl2ShdslSpanConfProfileTable. Refer to the April 21, 2004
                 revision description for a discussion on why the table is
                 indexed as opposed to augments. This table shares the same 
                 table table index as the hdsl2ShdslSpanConfProfileTable.
                 However, this table does not have a row status object. Therefore,
                 rows are created or deleted in this table by creating or 
                 deleting rows in the hdsl2ShdslSpanConfProfileTable."
    ::= { pdnHdsl2ShdslLineObjects 6 }

pdnHdsl2ShdslSpanConfProfileExtEntry     OBJECT-TYPE
    SYNTAX      PdnHdsl2ShdslSpanConfProfileExtEntry
    MAX-ACCESS  not-accessible
    STATUS      current
    DESCRIPTION "An entry extends the hdsl2ShdslSpanConfProfileEntry defined in
                 [RFC 3276]. Each entry corresponds to a profile for a span."
    INDEX       { IMPLIED hdsl2ShdslSpanConfProfileName }
    ::= { pdnHdsl2ShdslSpanConfProfileExtTable 1 }

PdnHdsl2ShdslSpanConfProfileExtEntry ::=
    SEQUENCE {
        pdnHdsl2ShdslSpanConfWireInterface  INTEGER,
        pdnHdsl2ShdslSpanConfMinLineRate    Unsigned32,
        pdnHdsl2ShdslSpanConfMaxLineRate    Unsigned32
    }


pdnHdsl2ShdslSpanConfWireInterface OBJECT-TYPE
    SYNTAX      INTEGER {
                    twoWire(1),
                    fourWire(2),
                    sixWire(3),
                    eightWire(4)
                }
    MAX-ACCESS  read-create
    STATUS      current
    DESCRIPTION "This object configures number of wires that are operational for
                 this span. The following values are defined for this object:
                     twoWire(1)    - 2-wire mode
                     fourWire(2)   - 4-wire mode
                     sixWire(3)    - 6-wire mode
                     eightWire(4)  - 8-wire mode"
    REFERENCE   "RFC 3276, hdsl2ShdslSpanConfWireInterface."
    DEFVAL      { twoWire }
    ::= { pdnHdsl2ShdslSpanConfProfileExtEntry 1 }

pdnHdsl2ShdslSpanConfMinLineRate OBJECT-TYPE
    SYNTAX      Unsigned32
    UNITS       "bps"
    MAX-ACCESS  read-create
    STATUS      current
    DESCRIPTION "This object configures the minimum transmission rate,
                 in multiples of 64 kbits per second, for the associated 
                 DSL Line in bits-per-second (bps). If the minimum line rate 
                 equals the maximum line rate (pdnHdsl2ShdslSpanConfMaxLineRate), 
                 the line rate is considered `fixed'. If the minimum line rate 
                 is less than the maximum line rate, the line is considered 
                 `rate-adaptive'."
    REFERENCE   "RFC 3276, hdsl2ShdslSpanConfMinLineRate."
    DEFVAL      { 155200 }
    ::= { pdnHdsl2ShdslSpanConfProfileExtEntry 2 }

pdnHdsl2ShdslSpanConfMaxLineRate OBJECT-TYPE
    SYNTAX      Unsigned32
    UNITS       "bps"
    MAX-ACCESS  read-create
    STATUS      current
    DESCRIPTION "This object configures the maximum transmission rate, in
                 multiples of 64 kbits per second, for the associated DSL Line 
                 in bits-per-second (bps). If the minimum line rate (pdnHdsl2Shdsl-
                 SpanConfMinLineRate) equals the maximum line rate, the line 
                 rate is considered `fixed'. if the minimum line rate is less 
                 than the maximum line rate, the line rate is considered 
                 `rate-adaptive'."
    REFERENCE   "RFC 3276, hdsl2ShdslSpanConfMaxLineRate."
    DEFVAL      { 155200 }
    ::= { pdnHdsl2ShdslSpanConfProfileExtEntry 3 }


-- =============================================================================
-- == pdhHdsl2ShdslIfTable                                                    ==
-- =============================================================================
pdnHdsl2ShdslIfTable OBJECT-TYPE
    SYNTAX      SEQUENCE OF PdnHdsl2ShdslIfEntry
    MAX-ACCESS  not-accessible
    STATUS      current
    DESCRIPTION "This table provides objects related to a particular interface
                 and each entry corresponds to an ifIndex."
    ::= { pdnHdsl2ShdslLineObjects 7 }

pdnHdsl2ShdslIfEntry OBJECT-TYPE
    SYNTAX      PdnHdsl2ShdslIfEntry
    MAX-ACCESS  not-accessible
    STATUS      current
    DESCRIPTION "An entry in the pdnHdsl2ShdslIfTableTable."
    INDEX { ifIndex }
    ::= { pdnHdsl2ShdslIfTable 1 }

PdnHdsl2ShdslIfEntry ::=
    SEQUENCE {
        pdnHdsl2ShdslIfTableEquipMode            INTEGER
    }

pdnHdsl2ShdslIfTableEquipMode OBJECT-TYPE
    SYNTAX      INTEGER {
                    coMode(1),      -- Central Office Mode
                    cpeMode(2)      -- Customer Premise Equipment Mode
    }
    MAX-ACCESS  read-write
    STATUS      current
    DESCRIPTION "This object allows the mode of the equipment to be set."                 
    ::= { pdnHdsl2ShdslIfEntry 1 }

-- =============================================================================
-- == Extended Rate Mode                                                      ==
-- =============================================================================
pdnHdsl2ShdslExtendedRateMode OBJECT-TYPE
    SYNTAX      INTEGER {
                    disabled(1),
                    payload5696(2)
    }
    MAX-ACCESS  read-write
    STATUS      current
    DESCRIPTION "This object is used to select a mode of operation that 
                 supports extended rates.  Some hardware implementations
                 require different configurations base on whether or not
                 higher speed rates are desired.  For example, an 
                 implementation may require different code be loaded in 
                 a digital signal processor or an implementation may 
                 dictate that fewer subscriber ports are supported for
                 a higher data rate.  The payload5696(2) corresponds to the
                 5696 kbits per second rate specified in G.991.2, Annex F."
    ::= { pdnHdsl2ShdslLineObjects 8 }



-- =============================================================================
-- ==                  Accessible for Notifications (AFNs)                    ==
-- =============================================================================
-- None defined



-- =============================================================================
-- ==                  Traps/Notifications                                    ==
-- =============================================================================

pdnHdsl2ShdslLoopAttenCrossing NOTIFICATION-TYPE
    OBJECTS {
        pdnHdsl2ShdslEndpointCurrAtn,
        hdsl2ShdslEndpointThreshLoopAttenuation
    }
    STATUS      current
    DESCRIPTION "This notification indicates that the loop attenuation
                 threshold (as per the hdsl2ShdslEndpointThreshLoopAttenuation
                 value) has been reached/exceeded for the DSL segment
                 endpoint."
    REFERENCE   "RFC 3276 hdsl2ShdslLoopAttenCrossing."
    ::= { pdnHdsl2ShdslLineNotifications 1 }

pdnHdsl2ShdslSNRMarginCrossing NOTIFICATION-TYPE
    OBJECTS {
        pdnHdsl2ShdslEndpointCurrSnrMgn,
        hdsl2ShdslEndpointThreshSNRMargin
    }
    STATUS      current
    DESCRIPTION "This notification indicates that the SNR margin threshold (as
                 per the hdsl2ShdslEndpointThreshSNRMargin value) has been
                 reached/exceeded for the DSL segment endpoint."
    REFERENCE   "RFC 3276 hdsl2ShdslSNRMarginCrossing."
    ::= { pdnHdsl2ShdslLineNotifications 2 }

pdnHdsl2ShdslPerfESThresh NOTIFICATION-TYPE
    OBJECTS {
        pdnHdsl2ShdslEndpointCurr15MinES,
        hdsl2ShdslEndpointThreshES
    }
    STATUS      current
    DESCRIPTION "This notification indicates that the errored seconds threshold
                 (as per the hdsl2ShdslEndpointThreshES value) has been reached/
                 exceeded for the DSL segment endpoint."
    REFERENCE   "RFC 3276 hdsl2ShdslPerfESThresh."
    ::= { pdnHdsl2ShdslLineNotifications 3 }

pdnHdsl2ShdslPerfSESThresh NOTIFICATION-TYPE
    OBJECTS {
        pdnHdsl2ShdslEndpointCurr15MinSES,
        hdsl2ShdslEndpointThreshSES
    }
    STATUS      current
    DESCRIPTION "This notification indicates that the severely errored seconds
                 threshold (as per the hdsl2ShdslEndpointThreshSES value) has
                 been reached/exceeded for the DSL Segment Endpoint."
    REFERENCE   "RFC 3276 hdsl2ShdslPerfSESThresh."
    ::= { pdnHdsl2ShdslLineNotifications 4 }

pdnHdsl2ShdslPerfCRCanomaliesThresh NOTIFICATION-TYPE
    OBJECTS {
        pdnHdsl2ShdslEndpointCurr15MinCRCanomalies,
        hdsl2ShdslEndpointThreshCRCanomalies
    }
    STATUS      current
    DESCRIPTION "This notification indicates that the CRC anomalies threshold
                 (as per the hdsl2ShdslEndpointThreshCRCanomalies value) has
                 been reached/exceeded for the DSL Segment Endpoint."
    REFERENCE   "RFC 3276 hdsl2ShdslPerfCRCanomaliesThresh."
    ::= { pdnHdsl2ShdslLineNotifications 5 }

pdnHdsl2ShdslPerfLOSWSThresh NOTIFICATION-TYPE
    OBJECTS {
        pdnHdsl2ShdslEndpointCurr15MinLOSWS,
        hdsl2ShdslEndpointThreshLOSWS
    }
    STATUS      current
    DESCRIPTION "This notification indicates that the LOSW seconds threshold
                 (as per the hdsl2ShdslEndpointThreshLOSWS value) has been
                 reached/exceeded for the DSL segment endpoint."
    REFERENCE   "RFC 3276 hdsl2ShdslPerfLOSWSThresh."
    ::= { pdnHdsl2ShdslLineNotifications 6 }

pdnHdsl2ShdslPerfUASThresh NOTIFICATION-TYPE
    OBJECTS {
        pdnHdsl2ShdslEndpointCurr15MinUAS,
        hdsl2ShdslEndpointThreshUAS
    }
    STATUS      current
    DESCRIPTION "This notification indicates that the unavailable seconds
                 threshold (as per the hdsl2ShdslEndpointThreshUAS value) has
                 been reached/exceeded for the HDSL2/SHDSL segment endpoint."
    REFERENCE   "RFC 3276 hdsl2ShdslPerfUASThresh."
    ::= { pdnHdsl2ShdslLineNotifications 7 }

pdnHdsl2ShdslpowerBackoff NOTIFICATION-TYPE
    OBJECTS {
        pdnHdsl2ShdslEndpointCurrStatus
    }
    STATUS      current
    DESCRIPTION "This notification indicates that the bit setting for
                 powerBackoff in the pdnHdsl2ShdslEndpointCurrStatus object for
                 this endpoint has changed."
    REFERENCE   "RFC 3276 hdsl2ShdslpowerBackoff."
    ::= { pdnHdsl2ShdslLineNotifications 8 }

pdnHdsl2ShdsldeviceFault NOTIFICATION-TYPE
    OBJECTS {
        pdnHdsl2ShdslEndpointCurrStatus
    }
    STATUS      current
    DESCRIPTION "This notification indicates that the bit setting for
                 deviceFault in the pdnHdsl2ShdslEndpointCurrStatus object for
                 this endpoint has changed."
    REFERENCE   "RFC 3276 hdsl2ShdsldeviceFault."
    ::= { pdnHdsl2ShdslLineNotifications 9 }

pdnHdsl2ShdsldcContinuityFault NOTIFICATION-TYPE
    OBJECTS {
        pdnHdsl2ShdslEndpointCurrStatus
    }
    STATUS      current
    DESCRIPTION "This notification indicates that the bit setting for
                 dcContinuityFault in the pdnHdsl2ShdslEndpointCurrStatus object
                 for this endpoint has changed."
    REFERENCE   "RFC 3276 hdsl2ShdsldcContinuityFault."
    ::= { pdnHdsl2ShdslLineNotifications 10 }

pdnHdsl2ShdslconfigInitFailure NOTIFICATION-TYPE
    OBJECTS {
        pdnHdsl2ShdslEndpointCurrStatus
    }
    STATUS      current
    DESCRIPTION "This notification indicates that the bit setting for
                 configInitFailure in the pdnHdsl2ShdslEndpointCurrStatus object
                 for this endpoint has changed."
    REFERENCE   "RFC 3276 hdsl2ShdslconfigInitFailure."
    ::= { pdnHdsl2ShdslLineNotifications 11 }

pdnHdsl2ShdslprotocolInitFailure NOTIFICATION-TYPE
    OBJECTS {
        pdnHdsl2ShdslEndpointCurrStatus
    }
    STATUS      current
    DESCRIPTION "This notification indicates that the bit setting for
                 protocolInitFailure in the pdnHdsl2ShdslEndpointCurrStatus
                 object for this endpoint has changed."
    REFERENCE   "RFC 3276 hdsl2ShdslprotocolInitFailure."
    ::= { pdnHdsl2ShdslLineNotifications 12 }

pdnHdsl2ShdslnoNeighborPresent NOTIFICATION-TYPE
    OBJECTS {
        pdnHdsl2ShdslEndpointCurrStatus
    }
    STATUS    current
    DESCRIPTION "This notification indicates that the bit setting for
                 noNeighborPresent in the pdnHdsl2ShdslEndpointCurrStatus object
                 for this endpoint has changed."
    REFERENCE   "RFC 3276 hdsl2ShdslnoNeighborPresent."
    ::= { pdnHdsl2ShdslLineNotifications 13 }




-- =============================================================================
-- ==                  Conformance Information                                ==
-- =============================================================================

pdnHdsl2ShdslLineCompliances  OBJECT IDENTIFIER ::= { pdnHdsl2ShdslLineConformance 1 }
pdnHdsl2ShdslLineGroups       OBJECT IDENTIFIER ::= { pdnHdsl2ShdslLineConformance 2 }


-- ===========================
-- == Compliance Statements ==
-- ===========================


pdnHdsl2ShdslLineMIBCompliance MODULE-COMPLIANCE
    STATUS      current
    DESCRIPTION "The compliance statement for pdnHdsl2ShdslLineMIB entities which
                 implement the pdnHdsl2ShdslLineMIB."
    MODULE      -- this module
    -- No mandatory groups are specified

    GROUP       pdnHdsl2ShdslSpanShdslStatusGroup
    DESCRIPTION "This group is only required for G.shdsl.bis implementations and
                 where the `standard' MIB does not support G.shdsl.bis."

    GROUP       pdnHdsl2ShdslEndpointConfGroup
    DESCRIPTION "This group is only required for G.shdsl.bis implementations and
                 where the `standard' MIB does not support G.shdsl.bis."

    GROUP       pdnHdsl2ShdslEndpointCurrGroup
    DESCRIPTION "This group is only required for G.shdsl.bis implementations and
                 where the `standard' MIB does not support G.shdsl.bis."

    GROUP       pdnHdsl2Shdsl15MinIntervalGroup
    DESCRIPTION "This group is only required for G.shdsl.bis implementations and
                 where the `standard' MIB does not support G.shdsl.bis."

    GROUP       pdnHdsl2Shdsl1DayIntervalGroup
    DESCRIPTION "This group is only required for G.shdsl.bis implementations and
                 where the `standard' MIB does not support G.shdsl.bis."

    GROUP       pdnHdsl2ShdslSpanConfProfileGroup
    DESCRIPTION "This group is only required for G.shdsl.bis implementations and
                 where the `standard' MIB does not support G.shdsl.bis."

    GROUP       pdnHdsl2ShdslIfTableGroup
    DESCRIPTION "This group is only required if the relevant objects are need on
                 a per-interface basis."

    GROUP       pdnHdsl2ShdslExtendedRateModeGroup
    DESCRIPTION "This group is only required if the hardware implementation
                 requires a different configuration to support higher rates
                 such as G.991.2 Annex F.  The object(s) in this group serve
                 to indicate if extended base data rates are desired."

    GROUP       pdnHdsl2ShdslNotificationGroup
    DESCRIPTION "This group is only required for G.shdsl.bis implementations and
                 where the `standard' MIB does not support G.shdsl.bis."


    --
    -- All objects, if implemented, are expected to be implemented to the
    -- maximal level as specified in their OBJECT-TYPE macro.
    --

    ::= { pdnHdsl2ShdslLineCompliances 1 }


-- ==========================
-- == Units of Conformance ==
-- ==========================

pdnHdsl2ShdslLineObjGroups   OBJECT IDENTIFIER ::= { pdnHdsl2ShdslLineGroups 1 }
pdnHdsl2ShdslLineAfnGroups   OBJECT IDENTIFIER ::= { pdnHdsl2ShdslLineGroups 2 }
pdnHdsl2ShdslLineNtfyGroups  OBJECT IDENTIFIER ::= { pdnHdsl2ShdslLineGroups 3 }

-- ===================
-- == Object Groups ==
-- ===================


pdnHdsl2ShdslSpanShdslStatusGroup OBJECT-GROUP
    OBJECTS {
        pdnHdsl2ShdslStatusMaxAttainableLineRate,
        pdnHdsl2ShdslStatusActualLineRate
    }
    STATUS      current
    DESCRIPTION "This group supports objects for retrieving SHDSL-specific
                 span related status."
    ::= { pdnHdsl2ShdslLineObjGroups 1 }

pdnHdsl2ShdslEndpointConfGroup OBJECT-GROUP
    OBJECTS {
        pdnHdsl2ShdslEndpointAlarmConfProfile
    }
    STATUS      current
    DESCRIPTION "This group supports objects for configuring parameters for
                 segment endpoints in SHDSL lines."
    ::= { pdnHdsl2ShdslLineObjGroups 2 }

pdnHdsl2ShdslEndpointCurrGroup OBJECT-GROUP
    OBJECTS {
        pdnHdsl2ShdslEndpointCurrAtn,
        pdnHdsl2ShdslEndpointCurrSnrMgn,
        pdnHdsl2ShdslEndpointCurrStatus,
        pdnHdsl2ShdslEndpointES,
        pdnHdsl2ShdslEndpointSES,
        pdnHdsl2ShdslEndpointCRCanomalies,
        pdnHdsl2ShdslEndpointLOSWS,
        pdnHdsl2ShdslEndpointUAS,
        pdnHdsl2ShdslEndpointCurr15MinTimeElapsed,
        pdnHdsl2ShdslEndpointCurr15MinES,
        pdnHdsl2ShdslEndpointCurr15MinSES,
        pdnHdsl2ShdslEndpointCurr15MinCRCanomalies,
        pdnHdsl2ShdslEndpointCurr15MinLOSWS,
        pdnHdsl2ShdslEndpointCurr15MinUAS,
        pdnHdsl2ShdslEndpointCurr1DayTimeElapsed,
        pdnHdsl2ShdslEndpointCurr1DayES,
        pdnHdsl2ShdslEndpointCurr1DaySES,
        pdnHdsl2ShdslEndpointCurr1DayCRCanomalies,
        pdnHdsl2ShdslEndpointCurr1DayLOSWS,
        pdnHdsl2ShdslEndpointCurr1DayUAS
    }
    STATUS      current
    DESCRIPTION "This group supports objects which provide current status
                 and performance measurements relating to segment endpoints
                 in DSL lines."
    ::= { pdnHdsl2ShdslLineObjGroups 3 }
  

pdnHdsl2Shdsl15MinIntervalGroup OBJECT-GROUP
    OBJECTS {
        pdnHdsl2Shdsl15MinIntervalES,
        pdnHdsl2Shdsl15MinIntervalSES,
        pdnHdsl2Shdsl15MinIntervalCRCanomalies,
        pdnHdsl2Shdsl15MinIntervalLOSWS,
        pdnHdsl2Shdsl15MinIntervalUAS
    }
    STATUS      current
    DESCRIPTION "This group supports objects which maintain historic performance
                 measurements relating to segment endpoints in DSL lines."
    ::= { pdnHdsl2ShdslLineObjGroups 4 }

pdnHdsl2Shdsl1DayIntervalGroup OBJECT-GROUP
    OBJECTS {
        pdnHdsl2Shdsl1DayIntervalMoniSecs,
        pdnHdsl2Shdsl1DayIntervalES,
        pdnHdsl2Shdsl1DayIntervalSES,
        pdnHdsl2Shdsl1DayIntervalCRCanomalies,
        pdnHdsl2Shdsl1DayIntervalLOSWS,
        pdnHdsl2Shdsl1DayIntervalUAS
    }
    STATUS      current
    DESCRIPTION "This group supports objects which maintain historic performance
                 measurements relating to segment endpoints in DSL line in
                 1-day intervals."
    ::= { pdnHdsl2ShdslLineObjGroups 5 }

pdnHdsl2ShdslSpanConfProfileGroup OBJECT-GROUP
    OBJECTS {
        pdnHdsl2ShdslSpanConfWireInterface,
        pdnHdsl2ShdslSpanConfMinLineRate,
        pdnHdsl2ShdslSpanConfMaxLineRate
    }
    STATUS      current
    DESCRIPTION "This group supports objects that constitute configuration
                 profiles for configuring span related parameters in DSL lines."
    ::= { pdnHdsl2ShdslLineObjGroups 6 }

pdnHdsl2ShdslIfTableGroup OBJECT-GROUP
    OBJECTS {
        pdnHdsl2ShdslIfTableEquipMode
    }
    STATUS      current
    DESCRIPTION "This group supports objects on a per-interface basis."
    ::= { pdnHdsl2ShdslLineObjGroups 7 }

pdnHdsl2ShdslExtendedRateModeGroup OBJECT-GROUP
    OBJECTS {
        pdnHdsl2ShdslExtendedRateMode
    }
    STATUS      current
    DESCRIPTION "This group supports objects to select the extended
                 base data rate mode."
    ::= { pdnHdsl2ShdslLineObjGroups 8 }



-- =========================
-- == Notification Groups ==
-- =========================


pdnHdsl2ShdslNotificationGroup NOTIFICATION-GROUP
    NOTIFICATIONS {
        pdnHdsl2ShdslLoopAttenCrossing,
        pdnHdsl2ShdslSNRMarginCrossing,
        pdnHdsl2ShdslPerfESThresh,
        pdnHdsl2ShdslPerfSESThresh,
        pdnHdsl2ShdslPerfCRCanomaliesThresh,
        pdnHdsl2ShdslPerfLOSWSThresh,
        pdnHdsl2ShdslPerfUASThresh,
        pdnHdsl2ShdslpowerBackoff,
        pdnHdsl2ShdsldeviceFault,
        pdnHdsl2ShdsldcContinuityFault,
        pdnHdsl2ShdslconfigInitFailure,
        pdnHdsl2ShdslprotocolInitFailure,
        pdnHdsl2ShdslnoNeighborPresent
    }
    STATUS      current
    DESCRIPTION "This group supports notifications of significant conditions
                 associated with DSL lines."
    ::= { pdnHdsl2ShdslLineNtfyGroups 1 }



-- =========
-- == END ==
-- =========
END

-- ===============================================================
-- Copyright (C) 2004 Paradyne Corporation.
-- ===============================================================

PDN-ADSL-LINE-EXT-MIB DEFINITIONS ::= BEGIN

IMPORTS
    MODULE-IDENTITY, OBJECT-TYPE, Unsigned32, Integer32, Gauge32
        FROM SNMPv2-SMI
    OBJECT-GROUP, MODULE-COMPLIANCE
        FROM SNMPv2-CONF
    TEXTUAL-CONVENTION, RowStatus
        FROM SNMPv2-TC
    SnmpAdminString
        FROM SNMP-FRAMEWORK-MIB
    ifIndex
        FROM IF-MIB
    pdn-interfaces
        FROM PDN-HEADER-MIB;
        
pdnAdslLineExtMIB MODULE-IDENTITY
    LAST-UPDATED "200503290000Z"  -- March 29, 2005
    ORGANIZATION "Paradyne Networks
                  MIB Working Group
                  Other information about group editing the MIB"
    CONTACT-INFO "Paradyne Networks, Inc.
                  8545 126th Avenue North
                  Largo, FL 33733
                  www.paradyne.com
        
                  General Comments to: mibwg_team@paradyne.com

                  Editor
                      Clay Sikes"

    DESCRIPTION
        "This MIB module is a supplement to the ADSL-LINE-MIB and to the
         ADSL-LINE-EXT-MIB, the `standard` MIBs, where additional objects
         are needed to support ADSL modes or flavors not covered in the
         `standard` MIBs.

         At the time this MIB was defined, the IETF ADSL MIB Working does 
         not have any work on the 'standard' MIBs planned and/or has not produced 
         a schedule to address ADSL2/ADSL2plus needs. As a result, these objects may 
         be a `temporary' solution until MIBs/Objects are defined or extended to 
         meet the needs of ADSL2/ADSL2plus.

         The following documents that should be referenced with respect
         to this MIB:
         [G.997.1]        ITU-T G997.1 `Physical layer management for Digital
                          Subscriber Line (DSL) transceivers', May 2003.
         [G.991.1 Am 1]   ITU-T-G997.1 Amendment 1 `Physical layer management
                          for Digital Subscriber Line (DSL) transceivers 
                          Amendment 1', December 2003.
         [OA 305]         Telenor Networks Specification, Specification 
                          Number OA 305, `Requirements for equipment to be 
                          connected to the local sub-loop in the access network 
                          of Telenor.  Equipment providing ADSL and PSTN or 
                          ISDN Basic Access Services, full unbundled access 
                          (service type EDF)', TN-NL-U-T/OA305/0101 2005, 
                          Edition 4.1, January 1, 2005.
         [WT-090]         DSL Forum Working Text WT-090 `Protocol Independent
                          Object Model for Managing Next Generation ADSL
                          Technologies', Revision-1, September 2003.
         [WT-090-4]       DSL Forum Working Text WT-090 `Protocol Independent
                          Object Model for Managing Next Generation ADSL
                          Technologies', Revision-4, June 2004.  
         [RFC 2662]       Bathrick, G., Ly, F. `ADSL-LINE-MIB', August 1999.
         [RFC 3440]       Ly, F., Bathrick, G. `ADSL-LINE-EXT-MIB', December 2002.

         Generally the MIB objects are defined using G.997.1 and the MIB
         objects are arranged using WT-090.

         =====================================================================
         ==                                                                 ==
         ==            Copyright (C) 2004 Paradyne Corporation.             ==
         ==                                                                 ==
         ====================================================================="

    REVISION "200503290000Z"  -- March 29, 2005
    DESCRIPTION "The `special' value was missing in the syntax for
                 pdnAdslLineStatusAtucActAtp and pdnAdslLineStatusAtucActAtp.

                 Added a note in the pdnAdslLineSubCarStatusTable indicating 
                 that some objects may not be valid if a loop diagnostic has
                 not completed execution.

                 pdnAdslLineSubCarAtucHlogMt and pdnAdslLineSubCarAturHlogMt
                 were incorrectly represented.  These object had the syntax
                 and description of HLOGpsds and HLOGpsus from G.997.1.
                 Corrected the syntax and description for the HlogMt objects
                 and added pdnAdslLineSubCarAtucHlogPs and 
                 pdnAdslLineSubCarAturHlogPs objects."

    REVISION "200501060000Z"  -- January 6, 2005
    DESCRIPTION "Changed the identifiers for the objects in the 
                 pdnAdslLineStatusTable and the pdnAdslLineSubCarStatusTable
                 from `Ds' to `Atuc' and from `Us' to `Atur'.  When these
                 tables were first created, it was not absolutely clear how 
                 `Ds' and `Us' mapped to `Atuc' and `Atur'.  However in 
                 December 2004, the DSL Forum released TR-090, `Protocol
                 Independent Object Model for Managing Next Generation ADSL
                 Technologies' which notes in Section 5.4.4, `ATU Channel
                 Thresholds' and in Section 5.5.1, `ATU Sub-Carrier Status'
                 that the object instances associated with the ATU-C use
                 the xxxds version of the parameter while those associated
                 with the ATU-R use the xxxus version of the parameter.

                 Paradyne's Compliance Engineering requested a change to
                 the ranges for Maximum Nominal Transmit PSD objects per
                 the Telenor Networks Specification [OA 305], Section 7.2.2,
                 `Downstream transmit spectral mask'.
                 The objects effected were: 
                     pdnAdslPsdConfAtucMaxNomPsd
                        from (-600..-400) to (-800..-400)
                     pdnAdslPsdConfAturMaxNomPsd
                        from (-600..-380) to (-650..-380)."

    REVISION "200410150000Z"  -- October 15, 2004
    DESCRIPTION "Fix transposed characters for PdnAdslTransmissionModeType
                 bits 38 and 39.
                 Added Line Status Table and Line Subcarrier Status Table.
                 Added missing range limits for pdnAdslLineL2Atpr."

    REVISION "200409100000Z"  -- September 10, 2004
    DESCRIPTION "Added new objects that were required for G.997.1 Amendment 1.
                 The additions include bit definitions for 
                 PdnAdslTransmissionModeType and the pdnAdslLineL2Atprt object."

    REVISION "200404210000Z"  -- April 21, 2004
    DESCRIPTION "The value for pdnAdslPsdConfAtucMaxNomPsd did not match the range in
                G.997.1 (05/2003), Section 7.3.1.2.1. The correct range is -60 to -40."

    REVISION "200404200000Z"  -- April 20, 2004
    DESCRIPTION "Change the pdnAdslLineExtTable from augments to be indexed. 
                 Some SNMP agents do a read-modify-write on a table row. As 
                 a result, the instrumentation code may not be able to  
                 determine which object the manager actually wants to set. For 
                 example, consider the case where a manager wants to set the 
                 transmission mode to allow ADSL2Plus modes. The instrumentation code, 
                 in the case of a read-modify-write cycle, could result in receiving
                 a row where the adslLineTransAtucConf is is set one way while the
                 pdnAdslLineTransAtucConfig is set another way. This could result 
                 in unpredictable results. This change will prevent the objects in 
                 the ExtTables from existing in the same row as the objects in the 
                 standard tables and prevent the unpredictable case from occurring."
    REVISION "200403010000Z"  -- March 1, 2004
    DESCRIPTION "Correct OID enumerations for objects in the pdnAdslPsdConfTable.
                 The OID 6 was skipped. That is pdnAdslPsdConfAturmaxNomAtp and
                 following objects were renumbered.
                 The pdnAdslLineLdsf object referred to the pdnAdslLinePmsf object
                 which was removed. pdnAdslLineLdsf was updated to remove the
                 reference."

    REVISION "200312080000Z"  -- December 8, 2003
    DESCRIPTION "Updated per MIBwg review. Change special case value for
                 pdnAdslPsdConfAtucMaxRxPwr from 9999 to 2048 to make it easier
                 for an NMS application to detect the special case. Collapse the
                 two Carrier Mask tables, one for upstream and one for downstream,
                 into a single table. The profile name can be used to distinguish
                 between an upstream and a downstream direction if needed."

    REVISION "200312030000Z"  -- December 3, 2003
    DESCRIPTION "Added objects to support MAXRXPWRus, CARMASKds, and CARMASKus per
                 new requirements."

    REVISION "200311191500Z"  -- November 19, 2003
    DESCRIPTION "Modified description text to clarify issues pertaining to
                 default profile names. General changes requested by
                 middleware and client implementors."

    REVISION "200311111500Z"  -- November 11, 2003
    DESCRIPTION "Changed the order of the indices for the
                 pdnAdslModeSpecificPsdTable to ease implementation in the
                 device."

    REVISION "200311061500Z"  -- November 6, 2003
    DESCRIPTION "Clean up, typo corrections, and clarifications."

    REVISION "200310311500Z"  -- October 31, 2003
    DESCRIPTION "Added pdnAdslLinePowerManagementStatus to provide a
                 mechanism to enable or disable power management
                 functionality."

    REVISION "200310231500Z"  -- October 23, 2003
    DESCRIPTION "Initial release."


::=  { pdn-interfaces 24 }

  
--
-- Define groups for Notifications, MIB Objects, Accessible for 
-- Notifications (AFNs), and Conformance.
-- These may just be place holders.
--
pdnAdslLineExtNotifications OBJECT IDENTIFIER ::= { pdnAdslLineExtMIB 0 }
pdnAdslLineExtObjects       OBJECT IDENTIFIER ::= { pdnAdslLineExtMIB 1 }
pdnAdslLineExtAFNs          OBJECT IDENTIFIER ::= { pdnAdslLineExtMIB 2 } 
pdnAdslLineExtConformance   OBJECT IDENTIFIER ::= { pdnAdslLineExtMIB 3 }


-- =============================================================================
-- ==                  Textual Conventions                                    ==
-- =============================================================================

PdnAdslTransmissionModeType  ::= TEXTUAL-CONVENTION
    STATUS      current
    DESCRIPTION "A set of ADSL line transmission modes, with one bit per mode."
    REFERENCE   "G.997.1, Section 7.3.1.1.1, ATU Transmission System Enabling (ATSE)."
    SYNTAX      BITS {
        -- Octet 1 --
        ansit1413(0),                   -- Bit 00 : Regional Std.  (ANSI T1.413)
        etsi(1),                        -- Bit 01 : Regional Std.  (ETSI DTS/TM06006)
        q9921PotsNonOverlapped(2),      -- Bit 02 : G.992.1  POTS non-overlapped spectrum
                                        --                   Annex A
        q9921PotsOverlapped(3),         -- Bit 03 : G.992.1  POTS overlapped spectrum
                                        --                   Annex A
        q9921IsdnNonOverlapped(4),      -- Bit 04 : G.992.1  ISDN non-overlapped spectrum
                                        --                   Annex B
        q9921isdnOverlapped(5),         -- Bit 05 : G.992.1  ISDN overlapped spectrum
                                        --                   Annex B
        q9921tcmIsdnNonOverlapped(6),   -- Bit 06 : G.992.1  TCM-ISDN non-overlapped spectrum
                                        --                   Annex C
        q9921tcmIsdnOverlapped(7),      -- Bit 07 : G.992.1  TCM-ISDN overlapped spectrum
                                        --                   Annex C

        -- Octet 2 --
        q9922potsNonOverlapeed(8),      -- Bit 08 : G.992.2  POTS non-overlapped spectrum
                                        --                   Annex A
        q9922potsOverlapped(9),         -- Bit 09 : G.992.2  POTS overlapped spectrum
                                        --                   Annex B
        q9922tcmIsdnNonOverlapped(10),  -- Bit 10 : G.992.2  TCM-ISDN non-overlapped spectrum
                                        --                   Annex C
        q9922tcmIsdnOverlapped(11),     -- Bit 11 : G.992.2  TCM-ISDN overlapped spectrum
                                        --                   Annex C
        q9921tcmIsdnSymmetric(12),      -- Bit 12 : G.992.1  TCM-ISDN symmetric
        reservedBit13(13),              -- Bit 13 : Reserved
        reservedBit14(14),              -- Bit 14 : Reserved
        reservedBit15(15),              -- Bit 15 : Reserved

        -- Octet 3 --
        reservedBit16(16),              -- Bit 16 : Reserved
        reservedBit17(17),              -- Bit 17 : Reserved
        q9923potsNonOverlapped(18),     -- Bit 18 : G.992.3  POTS non-overlapped spectrum
                                        --                   Annex A
        q9923potsOverlapped(19),        -- Bit 19 : G.992.3  POTS overlapped spectrum
                                        --                   Annex A
        q9923isdnNonOverlapped(20),     -- Bit 20 : G.992.3  ISDN non-overlapped spectrum
                                        --                   Annex B
        q9923isdnOverlapped(21),        -- Bit 21 : G.992.3  ISDN overlapped spectrum
                                        --                   Annex B
        reservedBit22(22),              -- Bit 22 : Reserved
        reservedBit23(23),              -- Bit 23 : Reserved

        -- Octet 4 --
        q9924potsNonOverlapped(24),     -- Bit 24 : G.992.4  POTS non-overlapped spectrum
                                        --                   Annex A
        q9924potsOverlapped(25),        -- Bit 25 : G.992.4  POTS overlapped spectrum
                                        --                   Annex A
        reservedBit26(26),              -- Bit 26 : Reserved
        reservedBit27(27),              -- Bit 27 : Reserved
        q9923DigitalNonOverlappedI(28), -- Bit 28 : G.992.3  All Digital Mode 
                                        --                   non-overlapped spectrum
                                        --                   Annex I
        q9923DigitalOverlappedI(29),    -- Bit 29 : G.992.3  All Digital Mode
                                        --                   overlapped spectrum
                                        --                   Annex I 
        q9923DigitalNonOverlappedJ(30), -- Bit 30 : G.992.3  All Digital Mode 
                                        --                   non-overlapped spectrum
                                        --                   Annex J
        q9923DigitalOverlappedJ(31),    -- Bit 31 : G.992.3  All Digital Mode
                                        --                   overlapped spectrum
                                        --                   Annex J

        -- Octet 5 --
        q9924DigitalNonOverlappedI(32), -- Bit 32 : G.992.4  All Digital Mode 
                                        --                   non-overlapped spectrum
                                        --                   Annex I
        q9924DigitalOverlappedI(33),    -- Bit 33 : G.992.4  All Digital Mode
                                        --                   overlapped spectrum
                                        --                   Annex I
        q9923ReachExtOverPotsMode1L(34), 
                                        -- Bit 34 : G.992.3  Reach Extended operation
                                        --                   over POTS Mode 1
                                        --                   (non-overlapped,
                                        --                   wide upstream)
                                        --                   Annex L
        q9923ReachExtOverPotsMode2L(35), 
                                        -- Bit 35 : G.992.3  Reach Extended operation
                                        --                   over POTS Mode 2
                                        --                   (non-overlapped,
                                        --                   narrow upstream)
                                        --                   Annex L    
        q9923ReachExtOverPotsMode3L(36), 
                                        -- Bit 36 : G.992.3  Reach Extended operation
                                        --                   over POTS Mode 3
                                        --                   (overlapped,
                                        --                   wide upstream)
                                        --                   Annex L        
        q9923ReachExtOverPotsMode4L(37), 
                                        -- Bit 37 : G.992.3  Reach Extended operation
                                        --                   over POTS Mode 4
                                        --                   (overlapped,
                                        --                   narrow upstream)
                                        --                   Annex L        
        q9923ExtUpOverPotsNonOverlappedM(38), 
                                        -- Bit 38 : G.992.3  Extended upstream operation
                                        --                   over POTS non-overlapped
                                        --                   spectrum
                                        --                   Annex M
        q9923ExtUpOverPotsOverlappedM(39),              
                                        -- Bit 39 : G.992.3  Extended upstream operation
                                        --                   over POTS overlapped spectrum
                                        --                   Annex M

        -- Octet 6 --
        q9925potsNonOverlapped(40),     -- Bit 40 : G.992.5  POTS non-overlapped spectrum
                                        --                   Annex A
        q9925potsOverlapped(41),        -- Bit 41 : G.992.5  POTS overlapped spectrum
                                        --                   Annex A
        q9925isdnNonOverlapped(42),     -- Bit 42 : G.992.5  ISDN non-overlapped spectrum
                                        --                   Annex B
        q9925isdnOverlapped(43),        -- Bit 43 : G.992.5  ISDN overlapped spectrum
                                        --                   Annex B 
        reserved44(44),                 -- Bit 44 : Reserved
        reserved45(45),                 -- Bit 45 : Reserved
        q9925DigitalNonOverlappedI(46), -- Bit 46 : G.992.5  All Digital Mode 
                                        --                   non-overlapped spectrum
                                        --                   Annex I
        q9925DigitalOverlappedI(47),    -- Bit 47 : G.992.5  All Digital Mode
                                        --                   overlapped spectrum
                                        --                   Annex I  

        -- Octet 7 --
        q9925DigitalNonOverlappedJ(48), -- Bit 48 : G.992.5  All Digital Mode
                                        --                   non-overlapped spectrum  
                                        --                   Annex J  
        q9925OverlappedJ(49),           -- Bit 49 : G.992.5  All Digital Mode
                                        --                   overlapped spectrum
                                        --                   Annex J
        q9925ExtUpOverPotsNonOverlappedM(50),              
                                        -- Bit 50 : G.992.5  Extended upstream over
                                        --                   POTS non-overlapped spectrum
                                        --                   Annex M
        q9925ExtUpOverPotsOverlappedM(51),              
                                        -- Bit 51 : G.992.5  Extended upstream over
                                        --                   POTS overlapped spectrum
                                        --                   Annex M
        reservedBit52(52),              -- Bit 52 : Reserved      
        reservedBit53(53),              -- Bit 53 : Reserved      
        reservedBit54(54),              -- Bit 54 : Reserved      
        reservedBit55(55)               -- Bit 55 : Reserved      
    }        


-- =============================================================================
-- ==                  MIB Objects                                            ==
-- =============================================================================


-- =============
-- == ADSL Line 
-- =============
pdnAdslLineExtTable OBJECT-TYPE
    SYNTAX      SEQUENCE OF PdnAdslLineExtEntry
    MAX-ACCESS  not-accessible
    STATUS      current
    DESCRIPTION "This table extends the adslLineTable in support of an 
                 ADSL Line object.

                 The objects pdnAdslLineTransAtucCap, pdnAdslLineTrans-
                 AtucConfig, and pdnAdslLineTransAtucActual exist along
                 with their PdnAdslTransmissionModeType TC because the 
                 AdslTransmissionModeType defined in the ADSL-LINE-EXT-MIB
                 does not include the ADSL2/ADSL2plus bits defined in
                 ITU G.997.1 (05/2003) ATU Transmission System Enabling (ATSE) 
                 section. 

                 When using the objects defined in this MIB with a syntax of 
                 type PdnAdslTransmissionModeType, the interworking relationship
                 between these objects and the objects defined in the ADSL-LINE-
                 EXT-MIB defined with a syntax of type AdslTransmissionModeType
                 must be considered and explained in an implementation-specific
                 document such as an Operational Specification. Note that the
                 PdnAdslTransmissionModeType is a super set of the AdslTransmis-
                 sionModeType. One possible implementation could be as follows:
                     1.  Both objects of syntax AdslTransmissionModeType defined 
                         in the ADSL-LINE-EXT-MIB and objects of syntax PdnAdsl-
                         TransmissionModeType defined in this MIB are supported.
                         By supporting both, a manager with the ADSL-LINE-EXT-MIB
                         loaded could manage the device with the restriction of
                         not being able to utilize ADSL2/ADSL2plus modes.
                     2.  When the ADSL2/ADSL2plus capabilities are desired, a manager
                         would have to use the objects defined in this MIB to 
                         configure the transmission modes, read capability, or
                         read the actual transmission mode of the ATU-C. 
                     3.  The transmission mode that the ATU-C is currently 
                         configured for is based on the last object, adslLineTrans-
                         AtucConfig or pdnAdslLineTransAtucConfig, that was written."
    REFERENCE "WT-090, Section 5.1.1, ADSL Line."
    ::= { pdnAdslLineExtObjects 1 }

pdnAdslLineExtEntry     OBJECT-TYPE
    SYNTAX      PdnAdslLineExtEntry
    MAX-ACCESS  not-accessible
    STATUS      current
    DESCRIPTION "An extended entry in the adslLineTable."
    INDEX     { ifIndex }
    ::= { pdnAdslLineExtTable 1 }

PdnAdslLineExtEntry ::=
    SEQUENCE {
        pdnAdslLineTransAtucCap          PdnAdslTransmissionModeType,
        pdnAdslLineTransAtucConfig       PdnAdslTransmissionModeType,
        pdnAdslLineTransAtucActual       PdnAdslTransmissionModeType,
        pdnAdslLinePowerManagementConfig INTEGER,
        pdnAdslLineSpectrumProfile       SnmpAdminString,
        pdnAdslLinePmMode                BITS,
        pdnAdslLineL0Time                Unsigned32,
        pdnAdslLineL2Time                Unsigned32,
        pdnAdslLineL2Atpr                Unsigned32,
        pdnAdslLineLdsf                  INTEGER,
        pdnAdslLineL2Atprt               Unsigned32
    }

pdnAdslLineTransAtucCap OBJECT-TYPE
    SYNTAX      PdnAdslTransmissionModeType
    MAX-ACCESS  read-only
    STATUS      current
    DESCRIPTION "The transmission modes, represented by a bitmask that the 
                 ATU-C is capable of supporting. The modes available are 
                 limited by the design of the equipment."
    REFERENCE   "G.997.1, Section 7.3.1.1.1, ATU Transmission System 
                 Enabling (ATSE).
                 RFC 3440, adslLineTransAtucCap."
    ::= { pdnAdslLineExtEntry 1 }

pdnAdslLineTransAtucConfig OBJECT-TYPE
    SYNTAX      PdnAdslTransmissionModeType
    MAX-ACCESS  read-write
    STATUS      current
    DESCRIPTION "The transmission modes, represented by a bitmask, currently 
                 enabled by the ATU-C.  The manager can only set those modes 
                 that are supported by the ATU-C. An ATU-C's supported modes 
                 are provided by pdnAdslLineTransAtucCap."
    REFERENCE   "G.997.1, Section 7.3.1.1.1, ATU Transmission System 
                 Enabling (ATSE).
                 RFC 3440 adslLineTransAtucConfig."
    ::= { pdnAdslLineExtEntry 2 }

pdnAdslLineTransAtucActual OBJECT-TYPE
    SYNTAX      PdnAdslTransmissionModeType
    MAX-ACCESS  read-only
    STATUS      current
    DESCRIPTION "The actual transmission mode of the ATU-C. During ADSL line 
                 initialization, the ADSL Transceiver Unit Remote terminal 
                 end (ATU-R) will determine the mode used for the link. This 
                 value will be limited a single transmission mode that is a 
                 subset of those modes enabled by the ATU-C and denoted by
                 pdnAdslLineTransAtucConfig. After an initialization has 
                 occurred, its mode is saved as the `Current' mode and is 
                 persistent should the link go down. This object returns 0 
                 (i.e. BITS with no mode bit set) if the mode is not known."
    REFERENCE   "G.997.1, Section 7.3.1.1.1, ATU Transmission
                 System Enabling (ATSE).
                 RFC 3440 adslLineTransAtucActual."
    ::= { pdnAdslLineExtEntry 3 }

pdnAdslLinePowerManagementConfig OBJECT-TYPE
    SYNTAX      INTEGER {
                    enabled(1),
                    disabled(2)
                }
    MAX-ACCESS  read-write
    STATUS      current
    DESCRIPTION "This object enables or disables power management functionality."
    DEFVAL      { disabled }
    ::= { pdnAdslLineExtEntry 4 }

pdnAdslLineSpectrumProfile OBJECT-TYPE
    SYNTAX      SnmpAdminString (SIZE(0 | 1..32))
    MAX-ACCESS  read-write
    STATUS      current
    DESCRIPTION "The value of this object identifies the row in the ADSL
                 Line Spectrum Profile Table, pdnAdslLineSpectrumProfileTable,
                 which applies for this ADSL line. If this object is not
                 a zero-length string, it should default to the default profile 
                 whose name is `DEFVAL'."
    REFERENCE   "WT-090, Section 5.1.1, ADSL Line."
    DEFVAL      { "DEFVAL" }
    ::= { pdnAdslLineExtEntry 5 }


pdnAdslLinePmMode OBJECT-TYPE
    SYNTAX      BITS {
                    idleStateL3(0),
                    lowPwrStateL1L2(1)
                }
    MAX-ACCESS  read-write
    STATUS      current
    DESCRIPTION "The line states the ATU-C or ATU-R may autonomously transition
                 to on this line. It is coded in a bit-map representation
                 (0 if not allowed, 1 if allowed) as follows:
                     idleStateL3(0)     - Bit 0  L3 state (Idle state)
                     lowPwrStateL1L2(1) - Bit 1  L1/L2 state (Low power state)"
    REFERENCE   "G.997.1, Section 7.3.1.1.4, Power Management State 
                 Enabling (PMMode)."
    ::= { pdnAdslLineExtEntry 6 }

pdnAdslLineL0Time OBJECT-TYPE
    SYNTAX      Unsigned32(0..255)
    UNITS       "seconds"
    MAX-ACCESS  read-write
    STATUS      current
    DESCRIPTION "The minimum time, in seconds, between and Exit from the L2 state
                 and the next Entry into the L2 state."
    REFERENCE   "G.997.1, Section 7.3.1.1.5, Minimum L0 Time interval,between L2 exit 
                 and next L2 entry (L0-TIME)."
    ::= { pdnAdslLineExtEntry 7 }

pdnAdslLineL2Time OBJECT-TYPE
    SYNTAX      Unsigned32(0..255)
    UNITS       "seconds"
    MAX-ACCESS  read-write
    STATUS      current
    DESCRIPTION "The minimum time, in seconds, between an Entry into the L2 state
                 and the first Power Trim in the L2 state and between two con-
                 secutive Power Trims in the L2 State."
    REFERENCE   "G.997.1, Section 7.3.1.1.6, Minimum L2 Time interval between L2 
                 entry and first L2 trim (L2-TIME)."
    ::= { pdnAdslLineExtEntry 8 }

pdnAdslLineL2Atpr OBJECT-TYPE
    SYNTAX      Unsigned32(0..31)
    UNITS       "dB"
    MAX-ACCESS  read-write
    STATUS      current
    DESCRIPTION "The maximum aggregate transmit power reduction, in dB, that can
                 be performed through a single Power Trim in the L2 state.

                 At the time this MIB was produced, the upper limit for this object
                 was not updated in the G.997.1 with respect to ADSL2plus. As such,
                 the upper limit of this object should be defined in an implementation-
                 specific document such as an Operational Specification."
    REFERENCE   "G.997.1, Section 7.3.1.1.7, Maximum Aggregate Transmit Power 
                 reduction per L2 trim (L2-ATPR)."
    ::= { pdnAdslLineExtEntry 9 }

pdnAdslLineLdsf OBJECT-TYPE
    SYNTAX      INTEGER {
                    ldsfMode0(1),
                    ldsfMode1(2)
                }
    MAX-ACCESS  read-write
    STATUS      current
    DESCRIPTION "Defines whether the line should be forced into the loop
                 diagnostics mode by the near-end ATU on this line.
                     ldsfMode0(1) - 0: Inhibits the near-end ATU from performing loop
                                       diagnostics mode procedures on the line. Loop
                                       diagnostic mode procedures may still be 
                                       initiated by the far-end ATU.
                     ldsModef1(2) - 1: Forces the near-end ATU to perform the loop
                                       diagnostics procedures.

                 The line needs to be forced to the L3 state (idle state) before 
                 it can be forced to the loop diagnostics mode. Only while the 
                 line power management state is the L3 state, the line can be forced 
                 into the loop diagnostics mode procedures. 

                 The following are ways to force the line to the L3 state: 
                 (1) Set the ifAdminStatus to down.

                 When the loop diagnostics mode procedures are completed successfully,
                 this object shall reset to ldsf0 and the line shall return to and
                 remain in the L3 idle state. The loop diagnostics data shall be
                 available at least until the line is forced to the L0 state. If the
                 loop diagnostics procedures can't be completed successfully, then
                 an Initialization Failure occurs. As long as loop diagnostics
                 procedures are not completed successfully, attempts shall be made
                 to do so, until the loop diagnostics mode is no longer forced on 
                 the line through this configuration parameter."
    REFERENCE   "G.997.1, Section 7.3.1.1.8, Loop Diagnostics Mode forced (LDSF)."
    ::= { pdnAdslLineExtEntry 10 }

pdnAdslLineL2Atprt OBJECT-TYPE
    SYNTAX      Unsigned32(0..31)
    UNITS       "dB"
    MAX-ACCESS  read-write
    STATUS      current
    DESCRIPTION "This parameter represents the total maximum aggregate transmit
                 power reduction (in dB) that can be performed in an L2 state.
                 This is the sum of all reductions of L2 Request (i.e., at
                 transition of L0 to L2 state) and Power Trims."
    REFERENCE   "G.997.1 Am 1 , Section 7.3.1.1.9, Total maximum aggregate
                 transmit power reduction in L2 (L2-ATPRT)."
    ::= { pdnAdslLineExtEntry 11 }


-- ==============================
-- == ADSL Line Spectrum Profile
-- ==============================
pdnAdslLineSpectrumProfileTable OBJECT-TYPE
    SYNTAX      SEQUENCE OF PdnAdslLineSpectrumProfileEntry
    MAX-ACCESS  not-accessible
    STATUS      current
    DESCRIPTION "This table contains specific configuration of transmission
                 spectrum and power spectral density related parameters that
                 can be mapped to one of the ADSL lines."
    REFERENCE   "WT-090, Section 5.1.6, ADSL Line Spectrum Profile."
    ::= { pdnAdslLineExtObjects 2 }

pdnAdslLineSpectrumProfileEntry     OBJECT-TYPE
    SYNTAX      PdnAdslLineSpectrumProfileEntry
    MAX-ACCESS  not-accessible
    STATUS      current
    DESCRIPTION "Each entry contains a specific profile for transmission
                 spectrum and power spectral density related parameters.
                 A default profile with an index of `DEFVAL', will always
                 exist and its parameters will be set to vendor or product
                 specific values, unless otherwise specified in this document."
    INDEX     { IMPLIED pdnAdslLineSpectrumProfileName }
    ::= { pdnAdslLineSpectrumProfileTable 1 }

PdnAdslLineSpectrumProfileEntry ::=
    SEQUENCE {
        pdnAdslLineSpectrumProfileName              SnmpAdminString,
        pdnAdslLineSpectrumProfileRowStatus         RowStatus,
        pdnAdslLineSpectrumModeSpecificPsdProfile   SnmpAdminString,
        pdnAdslLineSpectrumAtucCarMaskProfile       SnmpAdminString,
        pdnAdslLineSpectrumAturCarMaskProfile       SnmpAdminString
    }

pdnAdslLineSpectrumProfileName OBJECT-TYPE
    SYNTAX      SnmpAdminString (SIZE(1..32))
    MAX-ACCESS  not-accessible
    STATUS      current
    DESCRIPTION "This object identifies a row in the pdnAdslLineSpectrumProfile-
                 Table. The system will always provide a default profile whose
                 name is `DEFVAL'."
    REFERENCE   "G.997.1, Section 7.3.1.1.1 ATU Transmission System Enabling 
                 (ATSE)."
    ::= { pdnAdslLineSpectrumProfileEntry 1 }

pdnAdslLineSpectrumProfileRowStatus OBJECT-TYPE
    SYNTAX      RowStatus
    MAX-ACCESS  read-create
    STATUS      current
    DESCRIPTION "This object is used to create a new row or modify or delete an
                 existing row in this table. A profile is activated by setting
                 this object to `valid'.

                 Before a profile can be deleted or taken out of service, by
                 setting this object to `destroy' or `outOfService', the 
                 profile must be first unreferenced from all entries that 
                 referred to it (entries in the pdnAdslLineExtTable)."
    ::= { pdnAdslLineSpectrumProfileEntry 2 }

pdnAdslLineSpectrumModeSpecificPsdProfile OBJECT-TYPE
    SYNTAX      SnmpAdminString (SIZE(1..32))
    MAX-ACCESS  read-create
    STATUS      current
    DESCRIPTION "The value of this object identifies the row(s) in the ADSL
                 Mode-Specific PSD Configuration Table, pdnAdslModeSpecific-
                 PsdConfTable, which applies for this Line Spectrum Profile.

                 A particular ADSL line may need to support multiple mode-
                 specific power spectral density related settings. For example,
                 a ADSL line may need to support one set of settings for ADSL2
                 and another set of settings for ADSL2plus. See the pdnAdslMode-
                 SpecificPsdConfTable for additional detail. The system will always 
                 provide a default profile whose name is `DEFVAL'"
    REFERENCE   "WT-090, Section 5.1.6 ADSL LIne Spectrum Profile and Section
                 5.1.7 ADSL Mode-Specific PSD Configuration."
    DEFVAL      { "DEFVAL" }
    ::= { pdnAdslLineSpectrumProfileEntry 3 }

pdnAdslLineSpectrumAtucCarMaskProfile OBJECT-TYPE
    SYNTAX      SnmpAdminString(SIZE(0..32))
    MAX-ACCESS  read-create
    STATUS      current
    DESCRIPTION "This object identifies one or more rows in the pdnAdslCarMaskTable. 
                 The pdnAdslCarMaskTable is a table containing a list of subcarriers to 
                 be masked in the downstream or upstream direction; the profile in the
                 pdAdslCarMaskTable that this object identifies will apply the masks
                 in the downstream direction. 

                 This object defaults to an empty string meaning that no subcarriers are 
                 masked by an administrator."
    REFERENCE   "WT-090, Section 5.1.6, ADSL Line Spectrum Profile.
                 G.997.1, Section 7.3.1.2.6, Downstream subcarrier masking (CARMASKds)."
    DEFVAL      { "" }
    ::= { pdnAdslLineSpectrumProfileEntry 4 }

pdnAdslLineSpectrumAturCarMaskProfile OBJECT-TYPE
    SYNTAX      SnmpAdminString(SIZE(0..32))
    MAX-ACCESS  read-create
    STATUS      current
    DESCRIPTION "This object identifies one or more rows in the pdnAdslCarMaskTable. 
                 The pdnAdslCarMaskTable is a table containing a list of subcarriers to 
                 be masked in the downstream or upstream direction; the profile in the
                 pdAdslCarMaskTable that this object identifies will apply the masks
                 in the upstream direction. 

                 This object defaults to an empty string meaning that no subcarriers are 
                 masked by an administrator."
    REFERENCE   "WT-090, Section 5.1.6, ADSL Line Spectrum Profile.
                 G.997.1, Section 7.3.1.2.7, Upstream subcarrier masking (CARMASKus)."
    DEFVAL      { "" }
    ::= { pdnAdslLineSpectrumProfileEntry 5 }


-- ========================================
-- == ADSL Mode-Specific PSD Configuration
-- ========================================
pdnAdslModeSpecificPsdConfTable OBJECT-TYPE
    SYNTAX      SEQUENCE OF PdnAdslModeSpecificPsdConfEntry
    MAX-ACCESS  not-accessible
    STATUS      current
    DESCRIPTION "This table binds an entry indexed by a specific ADSL type or
                 flavor (e.g. ADSL2 or ADSL2+) and indexed by a profile name
                 to a specific DSL PSD Configuration Profile." 
    REFERENCE   "WT-090, Section 5.1, Configuration Management, and Section 5.1.6, 
                 ADSL Line Spectrum Profile."
    ::= { pdnAdslLineExtObjects 3 }

pdnAdslModeSpecificPsdConfEntry     OBJECT-TYPE
    SYNTAX      PdnAdslModeSpecificPsdConfEntry
    MAX-ACCESS  not-accessible
    STATUS      current
    DESCRIPTION "An entry in the table. For each particular ADSL mode or 
                 flavor supported (pdnAdslMOdeSpecificPsdConfAdslMode), there
                 will be an entry that points to an entry in the ADSL PSD
                 Configuration Table (pdnAdslPsdConfTable). For example,
                 if ADSL2 and ADSL2plus ADSL modes are supported, this
                 table will have the following two default entries:
                     1. An entry indexed by pdnAdslModeSpecificPsd-
                        ConfProfileName = 'DEFVAL' and pdnAdslModeSpecific-
                        PsdConfAdslMode = adsl2(1) and has pdnAdslModeSpecific-
                        PsdConfAdslPsdConfProfile = DEFVAL_ADSL2
                     2. An entry indexed by pdnAdslModeSpecificPsd-
                        ConfProfileName = 'DEFVAL' and pdnAdslModeSpecific-
                        PsdConfAdslMode = adsl2plus(3) and has pdnAdslModeSpecific-
                        PsdConfAdslPsdConfProfile = DEFVAL_ADSL2PLUS
                DEFVAL entries may be modified but not deleted."
    INDEX     { pdnAdslModeSpecificPsdConfProfileName,
                pdnAdslModeSpecificPsdConfAdslMode }
    ::= { pdnAdslModeSpecificPsdConfTable 1 }

PdnAdslModeSpecificPsdConfEntry ::=
    SEQUENCE {
        pdnAdslModeSpecificPsdConfProfileName         SnmpAdminString,
        pdnAdslModeSpecificPsdConfAdslMode            INTEGER,
        pdnAdslModeSpecificPsdConfRowStatus           RowStatus,
        pdnAdslModeSpecificPsdConfAdslPsdConfProfile  SnmpAdminString
    }

pdnAdslModeSpecificPsdConfProfileName OBJECT-TYPE
    SYNTAX      SnmpAdminString (SIZE(1..32))
    MAX-ACCESS  not-accessible
    STATUS      current
    DESCRIPTION "This object identifies a row in the pdnAdslModeSpecificPsdConfTable.
                 The system will always provide a default profile whose
                 name is 'DEFVAL'."
    REFERENCE   "WT-090, Section 5.1.7, ADSL Mode-Specific PSD Configuration."
    ::= { pdnAdslModeSpecificPsdConfEntry 1 }

pdnAdslModeSpecificPsdConfAdslMode OBJECT-TYPE
    SYNTAX      INTEGER {
                    adsl2(1),           -- G.992.3  ADSL transceivers - 2 
                                        --          (ADSL2)
                    adsl2NoSplitter(2), -- G.992.4  Splitterless ADSL transceivers - 2
                                        --          (Splitterless ADSL2)
                    adsl2plus(3)        -- G.992.5  Extended Bandwidth ADSL2 
                                        --          (ADSL2plus)
    }
    MAX-ACCESS  not-accessible
    STATUS      current
    DESCRIPTION "This object identifies a row in the pdnAdslModeSpecificPsdConfTable
                 containing parameters specific to a particular ADSL mode or
                 flavor identified by this object."
    REFERENCE   "WT-090, Section 5.1.7, ADSL Mode-Specific PSD Configuration."
    ::= { pdnAdslModeSpecificPsdConfEntry 2 }



pdnAdslModeSpecificPsdConfRowStatus OBJECT-TYPE
    SYNTAX      RowStatus
    MAX-ACCESS  read-create
    STATUS      current
    DESCRIPTION "This object is used to create a new row or modify or delete an
                 existing row in this table. A profile is activated by setting
                 this object to `valid'.

                 Before a profile can be deleted or taken out of service, by
                 setting this object to `destroy' or `outOfService', the 
                 profile must be first unreferenced from all entries that 
                 referred to it (entries in the pdnAdslLineSpectrumProfileTable)."
    ::= { pdnAdslModeSpecificPsdConfEntry 3 }

pdnAdslModeSpecificPsdConfAdslPsdConfProfile OBJECT-TYPE
    SYNTAX      SnmpAdminString (SIZE(1..32))
    MAX-ACCESS  read-create
    STATUS      current
    DESCRIPTION "This object identifies a row in the ADSL PSD Configuration
                 Table, pdnAdslPsdConfTable."
    REFERENCE   "WT-090, Section 5.1, Configuration Management, and Section 5.1.7,
                 ADSL Mode-Specific PSD Configuration.
                 G.997.1, Section 7.3.1.2, Power/PSD configuration parameters."
    ::= { pdnAdslModeSpecificPsdConfEntry 4 }


-- ==========================
-- == ADSL PSD Configuration
-- ==========================
pdnAdslPsdConfTable OBJECT-TYPE
    SYNTAX      SEQUENCE OF PdnAdslPsdConfEntry
    MAX-ACCESS  not-accessible
    STATUS      current
    DESCRIPTION "This table contains power spectral density settings."
    REFERENCE   "WT-090, Section 5.1.7, ADSL Mode-Specific PSD Configuration.
                 G.997.1, Section 7.3.1.2, Power/PSD configuration parameters."
    ::= { pdnAdslLineExtObjects 4 }

pdnAdslPsdConfEntry     OBJECT-TYPE
    SYNTAX      PdnAdslPsdConfEntry
    MAX-ACCESS  not-accessible
    STATUS      current
    DESCRIPTION "Each entry contains specific power spectral density settings for
                 a particular profile. A default profile for each particular
                 ADSL mode or flavor supporting PSD configuration will exist
                 (See the pdnAdslModeSpecificPsdConfAdslMode object the the
                 range of possible ADSL modes or flavors that are possible). 
                 For example, if only ADSL2 and ADSL2plus modes are supported,
                 the indices would be 'DEFVAL_ADSL2' and 'DEFVAL_ADSL2PLUS'.
                 The DEFVAL rows may be modified but not deleted. The DEFVAL rows            
                 will always exist and its parameters will be set to vendor or 
                 product specific values, unless otherwise specified in this document."
    INDEX     { IMPLIED pdnAdslPsdConfProfileName }
    ::= { pdnAdslPsdConfTable 1 }

PdnAdslPsdConfEntry ::=
    SEQUENCE {
        pdnAdslPsdConfProfileName      SnmpAdminString,
        pdnAdslPsdConfRowStatus        RowStatus,
        pdnAdslPsdConfAtucMaxNomPsd    Integer32,
        pdnAdslPsdConfAturMaxNomPsd    Integer32,
        pdnAdslPsdConfAtucMaxNomAtp    Unsigned32,
        pdnAdslPsdConfAturMaxNomAtp    Unsigned32,
        pdnAdslPsdConfAtucMaxRxPwr     Integer32
    }

pdnAdslPsdConfProfileName OBJECT-TYPE
    SYNTAX      SnmpAdminString (SIZE(1..32))
    MAX-ACCESS  not-accessible
    STATUS      current
    DESCRIPTION "This object identifies a row in the pdnAdslPsdConfTable."
    REFERENCE   "WT-090, Section 5.1.7, ADSL Mode-Specific PSD Configuration."
    ::= { pdnAdslPsdConfEntry 1 }

pdnAdslPsdConfRowStatus OBJECT-TYPE
    SYNTAX      RowStatus
    MAX-ACCESS  read-create
    STATUS      current
    DESCRIPTION "This object is used to create a new row or modify or delete an
                 existing row in this table. A profile is activated by setting
                 this object to `valid'.

                 Before a profile can be deleted or taken out of service, by
                 setting this object to `destroy' or `outOfService', the 
                 profile must be first unreferenced from all entries that 
                 referred to it such as pdnAdslModeSpecificPsdConfAdslPsdConfProfile."
    ::= { pdnAdslPsdConfEntry 2 }

pdnAdslPsdConfAtucMaxNomPsd OBJECT-TYPE
    SYNTAX      Integer32(-800..-400)
    UNITS       "tenth dBm/Hz"
    MAX-ACCESS  read-create
    STATUS      current
    DESCRIPTION "Represents the Maximum nominal transmit PSD for the ATU-C.
                 The values range from -80 to -40 dBm/Hz in 0.1 dB steps."
    REFERENCE   "G.997.1, Section 7.3.1.2.1, Downstream Maximum Nominal Power 
                 Spectral Density (MAXNOMPSDds), and Section 7.3.1.2.2, Upstream
                 Maximum Nominal Power Spectral Density (MAXNOMPSDus).
                 OA 305, Section 7.2.2, Downstream transmit spectral mask."
    ::= { pdnAdslPsdConfEntry 3 }

pdnAdslPsdConfAturMaxNomPsd OBJECT-TYPE
    SYNTAX      Integer32(-650..-380)
    UNITS       "tenth dBm/Hz"
    MAX-ACCESS  read-create
    STATUS      current
    DESCRIPTION "Represents the Maximum nominal transmit PSD for the ATU-R.
                 The values range from -65 to -38 dBm/Hz in 0.1 dB steps."
    REFERENCE   "G.997.1, Section 7.3.1.2.1, Downstream Maximum Nominal Power 
                 Spectral Density (MAXNOMPSDds), and Section 7.3.1.2.2, Upstream
                 Maximum Nominal Power Spectral Density (MAXNOMPSDus)."
    ::= { pdnAdslPsdConfEntry 4 }

pdnAdslPsdConfAtucMaxNomAtp OBJECT-TYPE
    SYNTAX      Unsigned32(0..255)
    UNITS       "tenth dBm"
    MAX-ACCESS  read-create
    STATUS      current
    DESCRIPTION "Represents the Maximum nominal aggregate transmit power for 
                 the ATU-C. The values range from 0 to 25.5 dBm in 0.1 dB steps."
    REFERENCE   "G.997.1, Section 7.3.1.2.3, Downstream Maximum Nominal Aggregate 
                 Transmit Power (MAXNOMATPds), and Section 7.3.1.2.4, Upstream
                 Maximum Nominal Aggregate Transmit Power (MAXNOMATPus)."
    ::= { pdnAdslPsdConfEntry 5 }

pdnAdslPsdConfAturMaxNomAtp OBJECT-TYPE
    SYNTAX      Unsigned32(0..255)
    UNITS       "tenth dBm"
    MAX-ACCESS  read-create
    STATUS      current
    DESCRIPTION "Represents the Maximum nominal aggregate transmit power for 
                 the ATU-R. The values range from 0 to 25.5 dBm in 0.1 dB steps."
    REFERENCE   "G.997.1, Section 7.3.1.2.3, Downstream Maximum Nominal Aggregate 
                 Transmit Power (MAXNOMATPds), and Section 7.3.1.2.4, Upstream
                 Maximum Nominal Aggregate Transmit Power (MAXNOMATPus)."
    ::= { pdnAdslPsdConfEntry 6 }

pdnAdslPsdConfAtucMaxRxPwr OBJECT-TYPE
    SYNTAX      Integer32(-255..255 | 2048)
    UNITS       "tenth dBm"
    MAX-ACCESS  read-create
    STATUS      current
    DESCRIPTION "Represents the maximum upstream aggregate receive power over a
                 set of subcarriers (in dBm). The ATU-C shall request an upstream
                 power cutback such that the upstream aggregate receive power
                 over that set of subcarriers is at or below the configured
                 maximum value. It ranges from -25.5 to 25.5 dBm, with 0.1 dB
                 steps. The value 2048 is a special value and indicates that 
                 no Upstream Maximum Aggregate Receive Power limit is to be
                 applied (i.e., the maximum value is infinite)."
    REFERENCE   "G.997.1, Section 7.3.1.2.5, Upstream Maximum Aggregate Receive 
                 Power (MAXRXPWRus)."
    ::= { pdnAdslPsdConfEntry 7 }



-- =============================================================================
-- ==                      ADSL Values for NSC  (Number of Subcarriers)       ==
-- =============================================================================
-- == The following ITU recommendations should be reference for specific      ==
-- == values for NSCds and NSCus:                                             ==
-- ==     G.997.1, Physical layer management for DSL transceivers             ==
-- ==     G.992.1, ADSL, G.dmt                                                ==
-- ==     G.992.2, Splitterless ADSL, G.lite                                  ==
-- ==     G.992.3, ADSL2, G.dmt.bis                                           ==
-- ==     G.992.4, Splitterless ADSL2                                         ==
-- ==     G.992.5, Extended Bandwidth ADSL2, ADSL2plus                        ==
-- =============================================================================



-- ===========================
-- == ADSL Carrier Mask Table
-- ===========================
pdnAdslCarMaskTable OBJECT-TYPE
    SYNTAX      SEQUENCE OF PdnAdslCarMaskEntry
    MAX-ACCESS  not-accessible
    STATUS      current
    DESCRIPTION "This table contains a list of subcarriers that are to be
                 masked (i.e. not transmitted). Subcarriers that are not
                 entries in this table are not masked."
    REFERENCE   "WT-090, Section 5.1.6, ADSL Line Spectrum Profile.
                 G.997.1, Section 7.3.1.2.6, Downstream subcarrier masking
                 (CARMASKds).
                 G.997.1, Section 7.3.1.2.7, Upstream subcarrier masking
                 (CARMASKus)."
    ::= { pdnAdslLineExtObjects 5 }

pdnAdslCarMaskEntry     OBJECT-TYPE
    SYNTAX      PdnAdslCarMaskEntry
    MAX-ACCESS  not-accessible
    STATUS      current
    DESCRIPTION "Each entry represents a specific subcarrier that is masked
                 for a particular profile."
    INDEX       { pdnAdslCarMaskProfileName,
                  pdnAdslCarMaskSubCarrierIndex }
    ::= { pdnAdslCarMaskTable 1 }

PdnAdslCarMaskEntry ::=
    SEQUENCE {
        pdnAdslCarMaskProfileName             SnmpAdminString,
        pdnAdslCarMaskSubCarrierIndex         Unsigned32,
        pdnAdslCarMaskRowStatus               RowStatus,
        pdnAdslCarMaskSubCarrierStatus        INTEGER
    }

pdnAdslCarMaskProfileName OBJECT-TYPE
    SYNTAX      SnmpAdminString (SIZE(1..32))
    MAX-ACCESS  not-accessible
    STATUS      current
    DESCRIPTION "This object identifies a row in the pdnAdslCarMaskTable 
                 based on a profile name."
    ::= { pdnAdslCarMaskEntry 1 }

pdnAdslCarMaskSubCarrierIndex OBJECT-TYPE
    SYNTAX      Unsigned32
    MAX-ACCESS  not-accessible
    STATUS      current
    DESCRIPTION "This object identifies a row in the pdnAdslCarMaskTable
                 based on subcarrier that is being masked. The subcarrier
                 index ranges from 0 to (NSCds-1 or NSCus-1 (NSC is Number of 
                 Subcarriers) as specified in G.997.1 where NSCds is the higher 
                 subcarrier that can be transmitted in the downstream direction and
                 NSCus is the higher subcarrier that can be transmitted in the
                 upstream direction. Please refer to the corresponding ITU 
                 recommendation for specific values of NSCds and NSCus. The 
                 `ADSL Values for NSC' comment above lists those recommendations."
    ::= { pdnAdslCarMaskEntry 2 }

pdnAdslCarMaskRowStatus OBJECT-TYPE
    SYNTAX      RowStatus
    MAX-ACCESS  read-create
    STATUS      current
    DESCRIPTION "This object is used to create a new row or delete an existing 
                 row in this table. A row is activated by setting this object 
                 to active(1)."
    ::= { pdnAdslCarMaskEntry 3 }

pdnAdslCarMaskSubCarrierStatus OBJECT-TYPE
    SYNTAX      INTEGER {
                    masked(1)
                }
    MAX-ACCESS  read-only
    STATUS      current
    DESCRIPTION "This object provides a clear indication that the subcarrier
                 is masked."
    ::= { pdnAdslCarMaskEntry 4 }


-- ================================
-- == ADSL Line Status Table
-- ================================
pdnAdslLineStatusTable OBJECT-TYPE
    SYNTAX      SEQUENCE OF PdnAdslLineStatusEntry
    MAX-ACCESS  not-accessible
    STATUS      current
    DESCRIPTION "This table contains current line status measurements."
    REFERENCE   "WT-090-4, Section 5.2.1, ADSL Line Status.
                 G.997.1, Section 7.5.1, Line test, diagnostics and status
                 parameters."
    ::= { pdnAdslLineExtObjects 6 }

pdnAdslLineStatusEntry     OBJECT-TYPE
    SYNTAX      PdnAdslLineStatusEntry
    MAX-ACCESS  not-accessible
    STATUS      current
    DESCRIPTION "Each entry represents an interface.
                 i.e. a row in the ifTable."
    INDEX       { ifIndex }
    ::= { pdnAdslLineStatusTable 1 }

PdnAdslLineStatusEntry ::=
    SEQUENCE {
        pdnAdslLineStatusAtucLineAtn                Unsigned32,
        pdnAdslLineStatusAturLineAtn                Unsigned32,
        pdnAdslLineStatusAtucSignalAtn              Unsigned32,
        pdnAdslLineStatusAturSignalAtn              Unsigned32,
        pdnAdslLineStatusAtucSnrMgn                 Integer32,
        pdnAdslLineStatusAturSnrMgn                 Integer32,
        pdnAdslLineStatusAtucMaxAttainableLineRate  Gauge32,
        pdnAdslLineStatusAturMaxAttainableLineRate  Gauge32,
        pdnAdslLineStatusAtucActAtp                 Integer32,
        pdnAdslLineStatusAturActAtp                 Integer32
    }

pdnAdslLineStatusAtucLineAtn OBJECT-TYPE
    SYNTAX      Unsigned32(0..1270 | 2048)
    UNITS       "tenth dB"
    MAX-ACCESS  read-only
    STATUS      current
    DESCRIPTION "The measured difference in the total power transmitted by
                 the ATU-C and the total power received by the ATU-R over all
                 subcarriers during diagnostics mode and initialization.  
                 The value 2048 is a special value and indicates the line 
                 attenuation is out of the range to be represented."
    REFERENCE   "G.997.1, Section 7.5.1.6, Downstream Line Attenuation
                 (LATNds)."
    ::= { pdnAdslLineStatusEntry 1 }

pdnAdslLineStatusAturLineAtn OBJECT-TYPE
    SYNTAX      Unsigned32(0..1270 | 2048)
    UNITS       "tenth dB"
    MAX-ACCESS  read-only
    STATUS      current
    DESCRIPTION "The measured difference in the total power transmitted by
                 the ATU-R and the total power received by the ATU-C over all
                 subcarriers during diagnostics mode and initialization.   
                 The value 2048 is a special value and indicates the line 
                 attenuation is out of the range to be represented."
    REFERENCE   "G.997.1, Section 7.5.1.7, Upstream Line Attenuation
                 (LATNus)."
    ::= { pdnAdslLineStatusEntry 2 }

pdnAdslLineStatusAtucSignalAtn OBJECT-TYPE
    SYNTAX      Unsigned32(0..1270 | 2048)
    UNITS       "tenth dB"
    MAX-ACCESS  read-only
    STATUS      current
    DESCRIPTION "The measured difference in the total power transmitted by
                 the ATU-C and the total power received by the ATU-R over all
                 subcarriers during showtime.  The value 2048 is a special 
                 value and indicates the line attenuation is out of the 
                 range to be represented."
    REFERENCE   "G.997.1, Section 7.5.1.8, Downstream Signal Attenuation
                 (SATNds)."
    ::= { pdnAdslLineStatusEntry 3 }

pdnAdslLineStatusAturSignalAtn OBJECT-TYPE
    SYNTAX      Unsigned32(0..1270 | 2048)
    UNITS       "tenth dB"
    MAX-ACCESS  read-only
    STATUS      current
    DESCRIPTION "The measured difference in the total power transmitted by
                 the ATU-R and the total power received by the ATU-C over all
                 subcarriers during showtime.  The value 2048 is a special 
                 value and indicates the line attenuation is out of the 
                 range to be represented."
    REFERENCE   "G.997.1, Section 7.5.1.9, Upstream Signal Attenuation
                 (SATNus)."
    ::= { pdnAdslLineStatusEntry 4 }

pdnAdslLineStatusAtucSnrMgn OBJECT-TYPE
    SYNTAX      Integer32(-640..630 | 2048)
    UNITS       "tenth dB"
    MAX-ACCESS  read-only
    STATUS      current
    DESCRIPTION "The upstream signal-to-noise ratio margin is the increase
                 in dB of the noise power received at the ATU-R, such that 
                 the BER requirements are met for all upstream bearer 
                 channels.  The value 2048 is a special value and indicates 
                 the parameter is out of range to be represented."
    REFERENCE   "G.997.1, Section 7.5.1.10, Downstream Signal-to-Noise Ratio
                 Margin (SNRMds)."
    ::= { pdnAdslLineStatusEntry 5 }

pdnAdslLineStatusAturSnrMgn OBJECT-TYPE
    SYNTAX      Integer32(-640..630 | 2048)
    UNITS       "tenth dB"
    MAX-ACCESS  read-only
    STATUS      current
    DESCRIPTION "The downstream signal-to-noise ratio margin is the increase
                 in dB of the noise power received at the ATU-C, such that 
                 the BER requirements are met for all upstream bearer 
                 channels.  The value 2048 is a special value and indicates 
                 the parameter is out of range to be represented."
    REFERENCE   "G.997.1, Section 7.5.1.11, Upstream Signal-to-Noise Ratio
                 Margin (SNRMus)."
    ::= { pdnAdslLineStatusEntry 6 }

pdnAdslLineStatusAtucMaxAttainableLineRate OBJECT-TYPE
    SYNTAX      Gauge32
    UNITS       "bps"
    MAX-ACCESS  read-only
    STATUS      current
    DESCRIPTION "The maximum downstream net data rate currently attainable 
                 by the ATU-C transmitter and the ATU-R receiver."
    REFERENCE   "G.997.1, Section 7.5.1.12, Downstream Maximum Attainable 
                 Data Rate (ATTNDRds)."
    ::= { pdnAdslLineStatusEntry 7 }

pdnAdslLineStatusAturMaxAttainableLineRate OBJECT-TYPE
    SYNTAX      Gauge32
    UNITS       "bps"
    MAX-ACCESS  read-only
    STATUS      current
    DESCRIPTION "The maximum upstream net data rate currently attainable 
                 by the ATU-R transmitter and the ATU-C receiver."
    REFERENCE   "G.997.1, Section 7.5.1.13, Upstream Maximum Attainable 
                 Data Rate (ATTNDRus)."
    ::= { pdnAdslLineStatusEntry 8 }

pdnAdslLineStatusAtucActAtp OBJECT-TYPE
    SYNTAX      Integer32(-310..310 | 2048)
    UNITS       "tenth dBm"
    MAX-ACCESS  read-only
    STATUS      current
    DESCRIPTION "The total amount of transmit power delivered by the ATU-C
                 at the U-R reference point, at the instant of the 
                 measurement.  The value 2048 is a special value and 
                 indicates the parameter is out of range to be represented."
    REFERENCE   "G.997.1, Section 7.5.1.16, Downstream Actual Aggregate 
                 Transmit Power (ACTATPus)."
    ::= { pdnAdslLineStatusEntry 9 }

pdnAdslLineStatusAturActAtp OBJECT-TYPE
    SYNTAX      Integer32(-310..310 | 2048)
    UNITS       "tenth dBm"
    MAX-ACCESS  read-only
    STATUS      current
    DESCRIPTION "The total amount of transmit power delivered by the ATU-R
                 at the U-R reference point, at the instant of the 
                 measurement.  The value 2048 is a special value and 
                 indicates the parameter is out of range to be represented."
    REFERENCE   "G.997.1, Section 7.5.1.17, Upstream Actual Aggregate 
                 Transmit Power (ACTATPds)."
    ::= { pdnAdslLineStatusEntry 10 }



-- =====================================
-- == ADSL Line Subcarrier Status Table
-- =====================================
pdnAdslLineSubCarStatusTable OBJECT-TYPE
    SYNTAX      SEQUENCE OF PdnAdslLineSubCarStatusEntry
    MAX-ACCESS  not-accessible
    STATUS      current
    DESCRIPTION "This table contains current line status measurements."
    REFERENCE   "WT-090-4, Section 5.2.1, ADSL Line Status.
                 G.997.1, Section 7.5.1, Line test, diagnostics and status
                 parameters."
    ::= { pdnAdslLineExtObjects 7 }

pdnAdslLineSubCarStatusEntry     OBJECT-TYPE
    SYNTAX      PdnAdslLineSubCarStatusEntry
    MAX-ACCESS  not-accessible
    STATUS      current
    DESCRIPTION "Each entry represents an interface.
                 i.e. a row in the ifTable.

                 Some objects in this table are only valid if a loop diagnostic
                 has successfully completed.  Those objects will return a 
                 noSuchName for a Get or Get Next operation if no loop diagnostic 
                 has completed."
    INDEX       { ifIndex, 
                  pdnAdslLineCarrierIndex }
    ::= { pdnAdslLineSubCarStatusTable 1 }

PdnAdslLineSubCarStatusEntry ::=
    SEQUENCE {
        pdnAdslLineCarrierIndex           Unsigned32,
        pdnAdslLineSubCarAtucHlinPs       Integer32,
        pdnAdslLineSubCarAturHlinPs       Integer32,
        pdnAdslLineSubCarAtucHlogMt       Unsigned32,
        pdnAdslLineSubCarAturHlogMt       Unsigned32,
        pdnAdslLineSubCarAtucQlnPs        Unsigned32,
        pdnAdslLineSubCarAturQlnPs        Unsigned32,
        pdnAdslLineSubCarAtucSnrPs        Unsigned32,
        pdnAdslLineSubCarAturSnrPs        Unsigned32,
        pdnAdslLineSubCarAtucBitsPs       Unsigned32,                
        pdnAdslLineSubCarAturBitsPs       Unsigned32,
        pdnAdslLineSubCarAtucHlogPs       Unsigned32,
        pdnAdslLineSubCarAturHlogPs       Unsigned32
    }

pdnAdslLineCarrierIndex OBJECT-TYPE
    SYNTAX      Unsigned32
    MAX-ACCESS  not-accessible
    STATUS      current
    DESCRIPTION "Identifies a row in the table based on a subcarrier. 
                 The subcarrier index ranges from 0 to (NSCds-1 or NSCus-1
                 (NSC is Number of Subcarriers) as specified in G.997.1 
                 where NSCds is the higher subcarrier that can be 
                 transmitted in the downstream direction and NSCus is the 
                 higher subcarrier that can be transmitted in the upstream 
                 direction. Please refer to the corresponding ITU 
                 recommendation for specific values of NSCds and NSCus.  
                 The `ADSL Values for NSC' comment above lists those 
                 recommendations."
    ::= { pdnAdslLineSubCarStatusEntry 1 }

pdnAdslLineSubCarAtucHlinPs OBJECT-TYPE
    SYNTAX      Integer32(-32768 | -32767..32767)
    MAX-ACCESS  read-only
    STATUS      current
    DESCRIPTION "The downstream linear representation, Hlin(f), of the 
                 Channel Characteristics Function, H(f).  This value is 
                 only available after a loop diagnostic procedure.  The 
                 special value -32768 indicates that no measurement could 
                 be done for the subcarrier because it is out of the 
                 passband or that the attenuation is out of the range to 
                 be represented."
    REFERENCE   "G.997.1, Section 7.5.1.18.2, Downstream H(f) Linear 
                 Representation (HLINpsds)."
    ::= { pdnAdslLineSubCarStatusEntry 2 }

pdnAdslLineSubCarAturHlinPs OBJECT-TYPE
    SYNTAX      Integer32(-32768 | -32767..32767)
    MAX-ACCESS  read-only
    STATUS      current
    DESCRIPTION "The upstream linear representation, Hlin(f), of the 
                 Channel Characteristics Function, H(f).  This value is 
                 only available after a loop diagnostic procedure.  The 
                 special value -32768 indicates that no measurement could 
                 be done for the subcarrier because it is out of the 
                 passband or that the attenuation is out of the range to 
                 be represented."
    REFERENCE   "G.997.1, Section 7.5.1.18.6, Upstream H(f) Linear 
                 Representation (HLINpsus)."
    ::= { pdnAdslLineSubCarStatusEntry 3 }

pdnAdslLineSubCarAtucHlogMt OBJECT-TYPE
    SYNTAX      Unsigned32(0..65535)
    MAX-ACCESS  read-only
    STATUS      current
    DESCRIPTION "The number of symbols used to measure downstream H(f)
                 logarithmic measurement values.  After a loop
                 diagnostic procedure, this parameter shall contain the
                 number of symbols used to generate the associate parameter.
                 It should correspond to the value specified in the 
                 recommendation (e.g. the number of symbols in 1 s. time
                 interval for G.992.3)."
    REFERENCE   "G.997.1, Section 7.5.1.18.3, Downstream H(f) Logarithmic
                 Measurement Time (HLOGMTds)."
    ::= { pdnAdslLineSubCarStatusEntry 4 }

pdnAdslLineSubCarAturHlogMt OBJECT-TYPE
    SYNTAX      Unsigned32(0..65535)
    MAX-ACCESS  read-only
    STATUS      current
    DESCRIPTION "The number of symbols used to measure downstream H(f)
                 logarithmic measurement values.  After a loop
                 diagnostic procedure, this parameter shall contain the
                 number of symbols used to generate the associate parameter.
                 It should correspond to the value specified in the 
                 recommendation (e.g. the number of symbols in 1 s. time
                 interval for G.992.3)."
    REFERENCE   "G.997.1, Section 7.5.1.18.7, Upstream H(f) Logarithmic
                 Measurement Time (HLOGMTus)."
    ::= { pdnAdslLineSubCarStatusEntry 5 }

pdnAdslLineSubCarAtucQlnPs OBJECT-TYPE
    SYNTAX      Unsigned32(0..254 | 255)
    UNITS       "dB"
    MAX-ACCESS  read-only
    STATUS      current
    DESCRIPTION "Downstream Quiet Line Noise.  The special value 255 
                 indicates that no measurement could be done for the
                 subcarrier because it is out of the passband or that
                 the noise power Spectral Density (PSD) is out of the 
                 range to be represented."
    REFERENCE   "G.997.1, Section 7.5.1.19.2, Downstream QLN(f) (QLNpsds)."
    ::= { pdnAdslLineSubCarStatusEntry 6 }

pdnAdslLineSubCarAturQlnPs OBJECT-TYPE
    SYNTAX      Unsigned32(0..254 | 255)
    UNITS       "dB"
    MAX-ACCESS  read-only
    STATUS      current
    DESCRIPTION "Upstream Quiet Line Noise.  The special value 255 
                 indicates that no measurement could be done for the
                 subcarrier because it is out of the passband or that
                 the noise power spectral density (PSD) is out of the 
                 range to be represented."
    REFERENCE   "G.997.1, Section 7.5.1.19.4, Upstream QLN(f) (QLNpsus)."
    ::= { pdnAdslLineSubCarStatusEntry 7 }

pdnAdslLineSubCarAtucSnrPs OBJECT-TYPE
    SYNTAX      Unsigned32(0..254 | 255 )
    UNITS       "dB"
    MAX-ACCESS  read-only
    STATUS      current
    DESCRIPTION "Downstream Signal-to-Noise Ratio.  The special value 255
                 indicates that no measurement could be done for the 
                 subcarrier because it is out of the passband or that the 
                 noise power spectral density (PSD) is out of the range to 
                 be represented."
    REFERENCE   "G.997.1, Section 7.5.1.20.2, Downstream SNR(f) (SNRpsds)."
    ::= { pdnAdslLineSubCarStatusEntry 8 }

pdnAdslLineSubCarAturSnrPs OBJECT-TYPE
    SYNTAX      Unsigned32(0..254 | 255 )
    UNITS       "dB"
    MAX-ACCESS  read-only
    STATUS      current
    DESCRIPTION "Upstream Signal-to-Noise Ratio.  The special value 255
                 indicates that no measurement could be done for the 
                 subcarrier because it is out of the passband or that the 
                 noise power spectral density (PSD) is out of the range to 
                 be represented."
    REFERENCE   "G.997.1, Section 7.5.1.20.4, Upstream SNR(f) (SNRpsus)."
    ::= { pdnAdslLineSubCarStatusEntry 9 }

pdnAdslLineSubCarAtucBitsPs OBJECT-TYPE
    SYNTAX      Unsigned32(0..15) 
    UNITS       "Bits"
    MAX-ACCESS  read-only
    STATUS      current
    DESCRIPTION "Downstream bits allocation."
    REFERENCE   "G.997.1, Section 7.5.1.21.1, Downstream Bits Allocation 
                 (BITSpsds)."
    ::= { pdnAdslLineSubCarStatusEntry 10 }

pdnAdslLineSubCarAturBitsPs OBJECT-TYPE
    SYNTAX      Unsigned32(0..15) 
    UNITS       "Bits"
    MAX-ACCESS  read-only
    STATUS      current
    DESCRIPTION "Upstream bits allocation."
    REFERENCE   "G.997.1, Section 7.5.1.21.2, Upstream Bits Allocation 
                 (BITSpsus)."
    ::= { pdnAdslLineSubCarStatusEntry 11 }

pdnAdslLineSubCarAtucHlogPs OBJECT-TYPE
    SYNTAX      Unsigned32(0..1022 | 1023)
    UNITS       "dB"
    MAX-ACCESS  read-only
    STATUS      current
    DESCRIPTION "The downstream logarithmic representation, Hlog(f), of 
                 the Channel Characteristics function, H(f), providing 
                 magnitude values.  The special value 1023 indicates 
                 that no measurement could be done for the subcarrier 
                 because it is out of the passband or that the attenuation 
                 is out of the range to be represented."
    REFERENCE   "G.997.1, Section 7.5.1.18.4, Downstream H(f) Logarithmic
                 Representation (HLOGpsds)."
    ::= { pdnAdslLineSubCarStatusEntry 12 }

pdnAdslLineSubCarAturHlogPs OBJECT-TYPE
    SYNTAX      Unsigned32(0..1022 | 1023)
    UNITS       "dB"
    MAX-ACCESS  read-only
    STATUS      current
    DESCRIPTION "The upstream logarithmic representation, Hlog(f), of 
                 the Channel Characteristics function, H(f), providing 
                 magnitude values.  The special value 1023 indicates 
                 that no measurement could be done for the subcarrier 
                 because it is out of the passband or that the attenuation 
                 is out of the range to be represented."
    REFERENCE   "G.997.1, Section 7.5.1.18.8, Upstream H(f) Logarithmic
                 Representation (HLOGpsus)."
    ::= { pdnAdslLineSubCarStatusEntry 13 }




-- =============================================================================
-- ==                  Accessible for Notifications (AFNs)                    ==
-- =============================================================================
-- None defined



-- =============================================================================
-- ==                  Traps/Notifications                                    ==
-- =============================================================================
-- None defined



-- =============================================================================
-- ==                  Conformance Information                                ==
-- =============================================================================

pdnAdslLineExtCompliances  OBJECT IDENTIFIER ::= { pdnAdslLineExtConformance 1 }
pdnAdslLineExtGroups       OBJECT IDENTIFIER ::= { pdnAdslLineExtConformance 2 }


-- ===========================
-- == Compliance Statements ==
-- ===========================


pdnAdslLineExtMIBCompliance MODULE-COMPLIANCE
    STATUS      current
    DESCRIPTION "The compliance statement for pdnAdslLineMIB entities which
                 implement the pdnAdslLineMIB."
    MODULE      -- this module
    -- No mandatory groups are specified

    GROUP       pdnAdslLineExtGroup
    DESCRIPTION "This group associates objects related to the DSL line
                 and is mandatory only for those entities which implement ADSL2 
                 or ADSL2plus capabilities and providing that no IETF standard
                 MIB exists that has objects allowing ADSL2 or ADSL2plus 
                 capabilities to be identified and controlled."

    GROUP       pdnAdslLineSpectrumGroup
    DESCRIPTION "This group associates objects related to spectrum and power
                 spectral configurations and is mandatory only for those 
                 entities which implement ADSL2 or ADSL2plus capabilities and 
                 providing that no IETF standard MIB exists that has objects 
                 allowing ADSL2 or ADSL2plus capabilities to be identified and 
                 controlled."

    GROUP       pdnAdslModeSpecificPsdGroup
    DESCRIPTION "This group associates objects related to spectrum and power
                 spectral configurations that are specific to a particular
                 type of ADSL mode is mandatory only for those entities which
                 implement ADSL2 or ADSL2plus capabilities and providing that
                 no IETF standard MIB exists that has objects allowing 
                 ADSL2 or ADSL2plus capabilities to be identified and controlled."

    GROUP       pdnAdslPsdGroup
    DESCRIPTION "This group associates objects related to configuring profiles
                 for power spectral density setting and is mandatory only for 
                 those entities which implement ADSL2 or ADSL2plus capabilities 
                 and providing that no IETF standard MIB exists that has objects 
                 allowing ADSL2 or ADSL2plus capabilities to be identified and 
                 controlled."

    GROUP       pdnAdslCarMaskGroup
    DESCRIPTION "This group associates objects related to defining subcarriers
                 to be masked in the downstream direction."

    GROUP       pdnAdslLineL2AtprtGroup
    DESCRIPTION "This group adds an object for total maximum aggregate transmit
                 power reduction in L2."

    GROUP       pdnAdslLineStatusLineAtnGroup
    DESCRIPTION "This group associates status objects related to line 
                 attenuation during diagnostic mode and initialization."

    GROUP       pdnAdslLineStatusSignalAtnGroup
    DESCRIPTION "This group associates status objects related to line
                 attenuation during showtime."

    GROUP       pdnAdslLineStatusSnrMgnGroup
    DESCRIPTION "This group associates status objects related to SNR margin
                 ratio."

    GROUP       pdnAdslLineStatusMaxattainableLineRateGroup
    DESCRIPTION "This group associates status objects related to the
                 current maximum attainable net data rate."

    GROUP       pdnAdslLineStatusActAtpGroup
    DESCRIPTION "This group associates status objects related to the
                 actual aggregate transmit power."

    GROUP       pdnAdslLineSubCarStatusHlinGroup
    DESCRIPTION "This group associates the status objects related to the
                 linear representation of the Channel Characteristics 
                 Function on a per-subcarrier basis for a line."

    GROUP       pdnAdslLineSubCarStatusHlogMtGroup
    DESCRIPTION "This group associates the status objects related to the
                 logarithmic measurement time on a per-subcarrier basis 
                 for the line"

    GROUP       pdnAdslLineSubCarStatusQlnGroup
    DESCRIPTION "This group associates the status objects related to the
                 Quiet Line Noise on a per-subcarrier basis for the line."

    GROUP       pdnAdslLineSubCarStatusSnrGroup
    DESCRIPTION "This group associates the status objects related to the
                 Signal-to-Noise Ratio on a per-subcarrier basis for the
                 line."

    GROUP       pdnAdslLineSubCarStatusBitsGroup
    DESCRIPTION "The group associates the status objects related to the
                 bits allocation on a per-subcarrier basis for the line."

    GROUP       pdnAdslLineSubCarStatusHlogGroup
    DESCRIPTION "The group associates the status objects related to the
                 logarithmic representation of the Channel Characteristics 
                 function on a per-subcarrier basis for the line."




    -- All objects, if implemented, are expected to be implemented to the
    -- maximal level as specified in their OBJECT-TYPE macro.
    --

    ::= { pdnAdslLineExtCompliances 1 }


-- ==========================
-- == Units of Conformance ==
-- ==========================

pdnAdslLineExtObjGroups   OBJECT IDENTIFIER ::= { pdnAdslLineExtGroups 1 }
pdnAdslLineExtAfnGroups   OBJECT IDENTIFIER ::= { pdnAdslLineExtGroups 2 }
pdnAdslLineExtNtfyGroups  OBJECT IDENTIFIER ::= { pdnAdslLineExtGroups 3 }

-- ===================
-- == Object Groups ==
-- ===================

pdnAdslLineExtGroup OBJECT-GROUP
    OBJECTS {
        pdnAdslLineTransAtucCap,
        pdnAdslLineTransAtucConfig,
        pdnAdslLineTransAtucActual,
        pdnAdslLinePowerManagementConfig,
        pdnAdslLineSpectrumProfile,
        pdnAdslLinePmMode,
        pdnAdslLineL0Time,
        pdnAdslLineL2Time,
        pdnAdslLineL2Atpr,
        pdnAdslLineLdsf
    }
    STATUS      current
    DESCRIPTION "A collection of objects providing extended
                 configuration information about an ADSL Line."
    ::= { pdnAdslLineExtObjGroups 1 }

pdnAdslLineSpectrumGroup OBJECT-GROUP
    OBJECTS {
        pdnAdslLineSpectrumProfileRowStatus,
        pdnAdslLineSpectrumModeSpecificPsdProfile,
        pdnAdslLineSpectrumAtucCarMaskProfile,
        pdnAdslLineSpectrumAturCarMaskProfile
    }
    STATUS      current
    DESCRIPTION "A collection of objects providing transmission 
                 spectrum and power spectral density related profiles."
    ::= { pdnAdslLineExtObjGroups 2 }

pdnAdslModeSpecificPsdGroup OBJECT-GROUP
    OBJECTS {
        pdnAdslModeSpecificPsdConfAdslPsdConfProfile,
        pdnAdslModeSpecificPsdConfRowStatus
    }
    STATUS      current
    DESCRIPTION "A collection of objects providing a mapping from an entry
                 into the ADSL Line Spectrum Table to a profile defining a
                 specific set of power spectral density settings."
    ::= { pdnAdslLineExtObjGroups 3 }

pdnAdslPsdGroup OBJECT-GROUP
    OBJECTS {
        pdnAdslPsdConfRowStatus,
        pdnAdslPsdConfAtucMaxNomPsd,
        pdnAdslPsdConfAturMaxNomPsd,
        pdnAdslPsdConfAtucMaxNomAtp,
        pdnAdslPsdConfAturMaxNomAtp,
        pdnAdslPsdConfAtucMaxRxPwr
    }
    STATUS      current
    DESCRIPTION "A collection of objects providing specific power spectral 
                 density settings based on a named profile." 
    ::= { pdnAdslLineExtObjGroups 4 }

pdnAdslCarMaskGroup OBJECT-GROUP
    OBJECTS {
        pdnAdslCarMaskRowStatus,
        pdnAdslCarMaskSubCarrierStatus
    }
    STATUS      current
    DESCRIPTION "A collection of objects providing the ability for an
                 administrator to mask out specific subcarriers in
                 the downstream or the upstream direction."
    ::= { pdnAdslLineExtObjGroups 5 }

pdnAdslLineL2AtprtGroup OBJECT-GROUP
    OBJECTS {
        pdnAdslLineL2Atprt
    }
    STATUS      current
    DESCRIPTION "Total maximum aggregate transmit power reduction in L2."
    ::= { pdnAdslLineExtObjGroups 6 }

pdnAdslLineStatusLineAtnGroup OBJECT-GROUP
    OBJECTS {
        pdnAdslLineStatusAtucLineAtn,
        pdnAdslLineStatusAturLineAtn
    }
    STATUS      current
    DESCRIPTION "Line attenuation during diagnostic mode and initialization."
    ::= { pdnAdslLineExtObjGroups 7 }

pdnAdslLineStatusSignalAtnGroup OBJECT-GROUP
    OBJECTS {
        pdnAdslLineStatusAtucSignalAtn,
        pdnAdslLineStatusAturSignalAtn
    }
    STATUS      current
    DESCRIPTION "Line attenuation during showtime."
    ::= { pdnAdslLineExtObjGroups 8 }

pdnAdslLineStatusSnrMgnGroup OBJECT-GROUP
    OBJECTS {
        pdnAdslLineStatusAtucSnrMgn,
        pdnAdslLineStatusAturSnrMgn
    }
    STATUS      current
    DESCRIPTION "SNR margin ratio."
    ::= { pdnAdslLineExtObjGroups 9 }

pdnAdslLineStatusMaxattainableLineRateGroup OBJECT-GROUP
    OBJECTS {
        pdnAdslLineStatusAtucMaxAttainableLineRate,
        pdnAdslLineStatusAturMaxAttainableLineRate
    }
    STATUS      current
    DESCRIPTION "Current maximum attainable net data rate."
    ::= { pdnAdslLineExtObjGroups 10 }

pdnAdslLineStatusActAtpGroup OBJECT-GROUP
    OBJECTS {
        pdnAdslLineStatusAtucActAtp,
        pdnAdslLineStatusAturActAtp
    }
    STATUS      current
    DESCRIPTION "Actual aggregate transmit power."
    ::= { pdnAdslLineExtObjGroups 11 }

pdnAdslLineSubCarStatusHlinGroup OBJECT-GROUP
    OBJECTS {
        pdnAdslLineSubCarAtucHlinPs,
        pdnAdslLineSubCarAturHlinPs
    }
    STATUS      current
    DESCRIPTION "Linear representation of the Channel 
                 Characteristics function for a subcarrier on a line."
    ::= { pdnAdslLineExtObjGroups 12 }

pdnAdslLineSubCarStatusHlogMtGroup OBJECT-GROUP
    OBJECTS {
        pdnAdslLineSubCarAtucHlogMt,
        pdnAdslLineSubCarAturHlogMt
    }
    STATUS      current
    DESCRIPTION "Logarithmic measurement time of the Channel 
                 Characteristics function for a subcarrier on a line."
    ::= { pdnAdslLineExtObjGroups 13 }

pdnAdslLineSubCarStatusQlnGroup OBJECT-GROUP
    OBJECTS {
        pdnAdslLineSubCarAtucQlnPs,
        pdnAdslLineSubCarAturQlnPs
    }
    STATUS      current
    DESCRIPTION "Quiet Line Noise for a subcarrier on a line."
    ::= { pdnAdslLineExtObjGroups 14 }

pdnAdslLineSubCarStatusSnrGroup OBJECT-GROUP
    OBJECTS {
        pdnAdslLineSubCarAtucSnrPs,
        pdnAdslLineSubCarAturSnrPs
    }
    STATUS      current
    DESCRIPTION "Signal-to-Noise Ratio for a subcarrier on a line."
    ::= { pdnAdslLineExtObjGroups 15 }

pdnAdslLineSubCarStatusBitsGroup OBJECT-GROUP
    OBJECTS {
        pdnAdslLineSubCarAtucBitsPs,
        pdnAdslLineSubCarAturBitsPs
    }
    STATUS      current
    DESCRIPTION "Bits allocation for a subcarrier on a line."
    ::= { pdnAdslLineExtObjGroups 16 }

pdnAdslLineSubCarStatusHlogGroup OBJECT-GROUP
    OBJECTS {
        pdnAdslLineSubCarAtucHlogPs,
        pdnAdslLineSubCarAturHlogPs
    }
    STATUS      current
    DESCRIPTION "Logarithmic representation of the Channel Characteristics 
                 function for a subcarrier on a line."
    ::= { pdnAdslLineExtObjGroups 17 }
 



-- ==================================
-- == Accessible for Notify Groups ==
-- ==================================
-- None.



-- =========================
-- == Notification Groups ==
-- =========================
-- None.



-- =========
-- == END ==
-- =========
END

-- ===============================================================
-- Copyright (C) 2005 Paradyne Corporation.
-- ===============================================================

PDN-ADSL-SELT-MIB DEFINITIONS ::= BEGIN

IMPORTS
    MODULE-IDENTITY, OBJECT-TYPE, Integer32, Unsigned32
        FROM SNMPv2-SMI
    OBJECT-GROUP, MODULE-COMPLIANCE
        FROM SNMPv2-CONF
    TEXTUAL-CONVENTION
        FROM SNMPv2-TC
    ifIndex
        FROM IF-MIB
    pdn-interfaces
        FROM PDN-HEADER-MIB;
        
pdnAdslSeltMIB MODULE-IDENTITY
    LAST-UPDATED "200403280000Z"  -- March 28, 2005
    ORGANIZATION "Paradyne Networks
                  MIB Working Group
                  Other information about group editing the MIB"
    CONTACT-INFO "Paradyne Networks, Inc.
                  8545 126th Avenue North
                  Largo, FL 33733
                  www.paradyne.com
        
                  General Comments to: mibwg_team@paradyne.com

                  Editors
                      Jesus Pinto,
                      Clay Sikes"

    DESCRIPTION
        "This MIB module defines a portion of the management information base
         (MIB) for managing configuration and monitoring results of SELT
         (Single Ended Line Test) tests over ADSL interfaces.

         At the time this MIB was defined, the IETF ADSL MIB Working does 
         not have any work on the 'standard' MIBs planned and/or has not produced 
         a schedule to address G.SELT needs. As a result, these objects may 
         be a `temporary' solution until MIBs/Objects are defined
         meet the needs of ADSL SELT testing.

         =====================================================================
         ==                                                                 ==
         ==            Copyright (C) 2005 Paradyne Corporation.             ==
         ==                                                                 ==
         ====================================================================="

    REVISION "200503280000Z"  -- March 28, 2005
    DESCRIPTION "Added clearResults(4) to pdnAdslSeltCmd to allow an entry in 
                 the pdnAdslSeltLcTable or the pdnAdslSeltLnfTable to be removed.
                 Added resultsCleared(5) to pdnAdslSeltStatus to indicate that
                 clearResults(4) have been executed."

    REVISION "200503100000Z"  -- March 10, 2005
    DESCRIPTION "Added notStarted(4) to pdnAdslSeltStatus.  This solves the
                 problem of what to return when the pdnAdslSeltTable is walked
                 prior to a test being run on an interface."

    REVISION "200412020000Z"  -- Dec 02, 2004
    DESCRIPTION "Initial release."


::=  { pdn-interfaces 31 }
  
--
-- Define groups for Notifications, MIB Objects, Accessible for 
-- Notifications (AFNs), and Conformance.
-- These may just be place holders.
--
pdnAdslSeltNotifications OBJECT IDENTIFIER ::= { pdnAdslSeltMIB 0 }
pdnAdslSeltObjects       OBJECT IDENTIFIER ::= { pdnAdslSeltMIB 1 }
pdnAdslSeltAFNs          OBJECT IDENTIFIER ::= { pdnAdslSeltMIB 2 } 
pdnAdslSeltConformance   OBJECT IDENTIFIER ::= { pdnAdslSeltMIB 3 }


-- =============================================================================
-- ==                  Textual Conventions                                    ==
-- =============================================================================

PdnSeltTypes  ::= TEXTUAL-CONVENTION
	STATUS	 current
	DESCRIPTION
  	  "This textual convention defines the SELT test types
           available for configuration."

	SYNTAX	INTEGER {
		  loopCharacterization  (1), -- Loop Characterization
		  loopNoiseFloor        (2)  -- Loop noise floor
		}

-- =============================================================================
-- ==                  MIB Objects                                            ==
-- =============================================================================

pdnAdslSeltWireSize OBJECT-TYPE
    SYNTAX      INTEGER {	
		 awg         (1), -- AWG
		 metric      (2), -- Metric
		 metricJapan (3)  -- Metric Japan
		}
	       
    MAX-ACCESS  read-write
    STATUS      current
    DESCRIPTION "This object permits the selection of the metric unit
                 to be used when reporting SELT test results.
                 (i.e for AWG results are in feet and for 
                 metric/metricJapan results are in meters).

                 This configuration parameter applies to all the SELT
                 tests run in the device.
                "
    ::= { pdnAdslSeltObjects 1 }


-- =================================================
-- == G.Selt (Single Ended Line Test) Configuration
-- ==
-- == This section defines the tables requires to
-- == support the SELT feature in the system.
-- ==
-- == For now, we require Loop Characterization and
-- == Loop Noise Floor Measurement Tests. Both tests
-- == types can be started/stopped via a common table
-- == described below 
--
-- ================================================
pdnAdslSeltTable OBJECT-TYPE
    SYNTAX      SEQUENCE OF PdnAdslSeltEntry
    MAX-ACCESS  not-accessible
    STATUS      current
    DESCRIPTION "This table allows initiation/termination of 
	         SELT Tests."
    ::= { pdnAdslSeltObjects 2 }

pdnAdslSeltEntry     OBJECT-TYPE
    SYNTAX      PdnAdslSeltEntry
    MAX-ACCESS  not-accessible
    STATUS      current
    DESCRIPTION "Each entry represents an instance of a SELT test
                 currently running or ever run (since last system reset)
                 on an ADSL interface.

		 There should be entries in this table for every
                 active running tests and test that are in the process
                 of being stopped or have terminated already.

                 There should be no entries for ADSL interfaces that
                 have not run a test since last since reset; thus,
                 the agent should return NO_SUCH_NAME for those cases.
                "
    INDEX       { ifIndex, pdnAdslSeltType }
    ::= { pdnAdslSeltTable 1 }

PdnAdslSeltEntry ::=
    SEQUENCE {
        pdnAdslSeltType                PdnSeltTypes,
        pdnAdslSeltCmd                 INTEGER,
        pdnAdslSeltStatus              INTEGER,
        pdnAdslSeltDuration            Unsigned32,
        pdnAdslSeltTimeLeft            Unsigned32
    }

pdnAdslSeltType OBJECT-TYPE
    SYNTAX      PdnSeltTypes
    MAX-ACCESS  not-accessible
    STATUS      current
    DESCRIPTION "This object is used to specify the SELT test type
	         that will be initiated.

		 If a SELT Test is already running on the ADSL interface,
	         writing to this object is prohibited by the agent until
                 the previous test is completed or terminated.
		"
    ::= { pdnAdslSeltEntry 1 }

pdnAdslSeltCmd OBJECT-TYPE
    SYNTAX      INTEGER {
	            noOp         (1),  -- used when reading the object
		    start        (2),  -- start test
		    stop         (3),  -- stop an initiated test
                    clearResults (4)   -- clears the results for the 
                                       -- pdnAdslSeltType
                }
    MAX-ACCESS  read-write
    STATUS      current
    DESCRIPTION "This object corresponds to the list of test operations
                 that can be performed.

		 The possible values are noOp(1), start(2), stop(3), or
                 clearResults(4).
		 
	         Reading this object will always return the value 'noOp (1)'.

		 If SELT test is already running on an ADSL interface, 
		 the only possible test command is 'stop (1)'.

                 The clearResults(4) command clears test results by removing
                 and entry in the pdnAdslSeltLcTable or the 
                 pdnAdslSeltLnfTable.  After the execution of this command, 
                 the appropriate value for pdnAdslSeltStatus would be
                 resultsCleared(5).
		"
    ::= { pdnAdslSeltEntry 2 }

pdnAdslSeltStatus OBJECT-TYPE
    SYNTAX      INTEGER {
	           inProgress        (1),
	           stoppedInProgress (2),
	           complete          (3),
                   notStarted        (4),
                   resultsCleared    (5)
                }
	         
    MAX-ACCESS  read-only
    STATUS      current
    DESCRIPTION "This object provides status about any SELT test
	         running or ever run (since last reset) on an ADSL
		 interface. This object can be read by NMS managers
		 to determine the status of a test; that is:
			
		 inProgress (1)        - if the test is currently running.

		 stoppedInProgress (2) - if a request to stop the test
                                         is still in progress.

		 complete (3)          - if the test has been run at least 
                                         once since system reset and has 
                                         completed.

	         notStarted (4)        - if the test has not been run on 
                                         this interface since last system 
                                         reset. 

                 resultsCleared (5)    - if the  entry in the test results table,
                                         Lc or Lnf, was removed as the result
                                         of the execution of the clearResults(4)
                                         pdnAdslSeltCmd.
		"
    ::= { pdnAdslSeltEntry 3 }


pdnAdslSeltDuration OBJECT-TYPE
    SYNTAX      Unsigned32
    UNITS       "seconds"
    MAX-ACCESS  read-write
    STATUS      current
    DESCRIPTION  "This object provides the approximate time in Seconds that
                  the SELT test measurement will take.

		  This object should return 0 if no test is actively
		  running on the ADSL interface specified.
                 "
    ::= { pdnAdslSeltEntry 4 }

pdnAdslSeltTimeLeft OBJECT-TYPE
    SYNTAX      Unsigned32
    UNITS       "seconds"
    MAX-ACCESS  read-only
    STATUS      current
    DESCRIPTION  "This object provides the approximate time left in Seconds
                  for the test running on this ADSL interface.

		  This object should return 0 if no test is actively 
		  running on the ADSL interface specified.
                 "
    ::= { pdnAdslSeltEntry 5 }


-- =================================================
-- == G.Selt (Single Ended Line Test) Results
-- ==
-- == LOOP CHARACTERIZATION (Lc) Results Table
-- == 
-- == This table is used to post results from an 
-- == initiated Loop Characterization test.
--
-- ================================================
pdnAdslSeltLcTable OBJECT-TYPE
    SYNTAX      SEQUENCE OF PdnAdslSeltLcEntry
    MAX-ACCESS  not-accessible
    STATUS      current
    DESCRIPTION "This table post results for loop
		 characterization tests completed.
	        "
    ::= { pdnAdslSeltObjects 3 }

pdnAdslSeltLcEntry     OBJECT-TYPE
    SYNTAX      PdnAdslSeltLcEntry
    MAX-ACCESS  not-accessible
    STATUS      current
    DESCRIPTION "Each entry represents the results of a loop
		characterization test performed over an ADSL interface.
		"
    INDEX       { ifIndex, pdnAdslSeltLcSegmentIndex }
    ::= { pdnAdslSeltLcTable 1 }

PdnAdslSeltLcEntry ::=
    SEQUENCE {
        pdnAdslSeltLcSegmentIndex	Integer32,
        pdnAdslSeltLcSegmentLength	Integer32,
        pdnAdslSeltLcSegmentGauge       INTEGER,
        pdnAdslSeltLcSegmentType        INTEGER
    }

pdnAdslSeltLcSegmentIndex OBJECT-TYPE
    SYNTAX      Integer32(0..9)
    MAX-ACCESS  not-accessible
    STATUS      current
    DESCRIPTION "This object indicates the index of the segment being reported.
		 From no segments to a possible of 10 segments could be
                 identified in the loop topology.
		        "
    ::= { pdnAdslSeltLcEntry 1 }

pdnAdslSeltLcSegmentLength OBJECT-TYPE
    SYNTAX      Integer32(0..65534)
    MAX-ACCESS  read-only
    STATUS      current
    DESCRIPTION "This object indicates an estimate of the segment Length
                 being  reported
	        "
    ::= { pdnAdslSeltLcEntry 2 }

pdnAdslSeltLcSegmentGauge OBJECT-TYPE
    SYNTAX      INTEGER {
			unknown  (1),

                        --AWG--
			awg26    (2),
			awg24    (3),
			awg22    (4),
			awg19    (5),

                        --Metric--
			metric32 (10), -- (0.32mm)
			metric40 (11), -- (0.40mm)
			metric50 (12), -- (0.50mm)
			metric63 (13), -- (0.63mm)
			metric90 (14), -- (0.90mm)

                        --Metric/Japan--
			metricJapan32 (20), -- (0.32mm)
			metricJapan40 (21), -- (0.40mm)
			metricJapan50 (22), -- (0.50mm)
			metricJapan65 (23), -- (0.65mm)
			metricJapan90 (24)  -- (0.90mm)
		}

    MAX-ACCESS  read-only
    STATUS      current
    DESCRIPTION "This object indicates the estimated Gauge of the segment
                 being reported.  The gauge reported back is based on the
                 pdnAdslSeltWireSizeWireSize configuration parameter passed
                 when the test is started.
	        "
    ::= { pdnAdslSeltLcEntry 3 }

pdnAdslSeltLcSegmentType OBJECT-TYPE
    SYNTAX      INTEGER {
			notPresent (1),
			inline     (2),
			bridgeTap  (3)
		}

    MAX-ACCESS  read-only
    STATUS      current
    DESCRIPTION "This object indicates the segment type being reported.
		"
    ::= { pdnAdslSeltLcEntry 4 }

-- =================================================
-- == G.Selt (Single Ended Line Test) Results
-- ==
-- == LOOP NOISE FLOOR (Lnf) Results Table
-- == 
-- == This table is used to post results from an 
-- == initiated Loop Noise Floor test.
--
-- ================================================
pdnAdslSeltLnfTable OBJECT-TYPE
    SYNTAX      SEQUENCE OF PdnAdslSeltLnfEntry
    MAX-ACCESS  not-accessible
    STATUS      current
    DESCRIPTION "This table post results for loop
		 noise floor tests completed.
	        "
    ::= { pdnAdslSeltObjects 4 }

pdnAdslSeltLnfEntry     OBJECT-TYPE
    SYNTAX      PdnAdslSeltLnfEntry
    MAX-ACCESS  not-accessible
    STATUS      current
    DESCRIPTION "Each entry represents the results of a Loop
		Noise Floor test performed over an ADSL interface.
		"
    INDEX       { ifIndex, pdnAdslSeltLnfSubCarrierIndex  }
    ::= { pdnAdslSeltLnfTable 1 }

PdnAdslSeltLnfEntry ::=
    SEQUENCE {
        pdnAdslSeltLnfSubCarrierIndex	    Integer32,
        pdnAdslSeltLnfPeakPsd		    Integer32,
        pdnAdslSeltLnfTotalPsd              Integer32,
        pdnAdslSeltLnfSignalPsd             Integer32
    }

pdnAdslSeltLnfSubCarrierIndex OBJECT-TYPE
    SYNTAX      Integer32(0..63)
    MAX-ACCESS  not-accessible
    STATUS      current
    DESCRIPTION "Identifies a row in the table based on a subcarrier. 
                 The subcarrier index ranges from 0 to NSCus-1
                 (NSC is Number of Subcarriers) as specified in G.997.1 
                 where NSCus is the higher subcarrier that can be transmitted
                 in the upstream direction. Please refer to the corresponding
                 ITU recommendation for specific values of NSCus.  
                 The `ADSL Values for NSC' comment above lists those 
                 recommendations."
    ::= { pdnAdslSeltLnfEntry 1 }

pdnAdslSeltLnfPeakPsd OBJECT-TYPE
    SYNTAX      Integer32(0..65534)
    MAX-ACCESS  read-only
    STATUS      current
    DESCRIPTION "This object indicates the peak Psd of the tone indicated by
                 the sub-carrier index.

                 The value returned by the agent for this object is 
                 expressed in units of 1/256 dBm.
		"
    ::= { pdnAdslSeltLnfEntry 2 }

pdnAdslSeltLnfTotalPsd OBJECT-TYPE
    SYNTAX      Integer32(0..65534)
    MAX-ACCESS  read-only
    STATUS      current
    DESCRIPTION "This object indicates the total Psd of the tone indicated by
                 the sub-carrier index.

                 The value returned by the agent for this object is 
                 expressed in units of 1/256 dBm.
		"
    ::= { pdnAdslSeltLnfEntry 3 }

pdnAdslSeltLnfSignalPsd OBJECT-TYPE
    SYNTAX      Integer32(0..65534)
    MAX-ACCESS  read-only
    STATUS      current
    DESCRIPTION "This object indicates the signal Psd of the tone indicated by
                 the sub-carrier index.

                 The value returned by the agent for this object is 
                 expressed in units of 1/256 dBm.
		"
    ::= { pdnAdslSeltLnfEntry 4 }

-- =============================================================================
-- ==                  Accessible for Notifications (AFNs)                    ==
-- =============================================================================
-- None defined



-- =============================================================================
-- ==                  Traps/Notifications                                    ==
-- =============================================================================
-- None defined



-- =============================================================================
-- ==                  Conformance Information                                ==
-- =============================================================================

pdnAdslSeltCompliances  OBJECT IDENTIFIER ::= { pdnAdslSeltConformance 1 }
pdnAdslSeltGroups       OBJECT IDENTIFIER ::= { pdnAdslSeltConformance 2 }


-- ===========================
-- == Compliance Statements ==
-- ===========================


pdnAdslSeltMIBCompliance MODULE-COMPLIANCE
    STATUS      current
    DESCRIPTION "The compliance statement for the entities which
                 implement the pdnAdslSeltMIB."
    MODULE      -- this module
    -- No mandatory groups are specified

    GROUP       pdnAdslSeltGroup
    DESCRIPTION "The group associates the objects related to the
                 configuration of SELT tests in General."

    GROUP       pdnAdslSeltLcGroup
    DESCRIPTION "The group associates the objects related to the
                 results of a Loop characterization SELT test."

    GROUP       pdnAdslSeltLnfGroup
    DESCRIPTION "The group associates the objects related to the
                 results  of a Loop Noise Floor SELT test."


    -- All objects, if implemented, are expected to be implemented to the
    -- maximal level as specified in their OBJECT-TYPE macro.
    --

    ::= { pdnAdslSeltCompliances 1 }


-- ==========================
-- == Units of Conformance ==
-- ==========================

pdnAdslSeltObjGroups   OBJECT IDENTIFIER ::= { pdnAdslSeltGroups 1 }
pdnAdslSeltAfnGroups   OBJECT IDENTIFIER ::= { pdnAdslSeltGroups 2 }
pdnAdslSeltNtfyGroups  OBJECT IDENTIFIER ::= { pdnAdslSeltGroups 3 }

-- ===================
-- == Object Groups ==
-- ===================

pdnAdslSeltGroup OBJECT-GROUP
    OBJECTS {
        pdnAdslSeltCmd,
        pdnAdslSeltStatus,
        pdnAdslSeltWireSize,
        pdnAdslSeltDuration,
        pdnAdslSeltTimeLeft
    }
    STATUS      current
    DESCRIPTION "General configuration of SELT tests."

    ::= { pdnAdslSeltObjGroups 1 }
 
pdnAdslSeltLcGroup OBJECT-GROUP
    OBJECTS {
        pdnAdslSeltLcSegmentLength,
        pdnAdslSeltLcSegmentGauge,
        pdnAdslSeltLcSegmentType
    }
    STATUS      current
    DESCRIPTION "Objects related to results posted for Loop 
		Characterization Test."

    ::= { pdnAdslSeltObjGroups 2 }

pdnAdslSeltLnfGroup OBJECT-GROUP
    OBJECTS {
        pdnAdslSeltLnfPeakPsd,
        pdnAdslSeltLnfTotalPsd,
        pdnAdslSeltLnfSignalPsd
    }
    STATUS      current
    DESCRIPTION "Objects related to results posted for Loop 
		Signal Floor Test."

    ::= { pdnAdslSeltObjGroups 3 }

-- ==================================
-- == Accessible for Notify Groups ==
-- ==================================
-- None.



-- =========================
-- == Notification Groups ==
-- =========================
-- None.



-- =========
-- == END ==
-- =========
END

PDN-DOT1QEXT-MIB DEFINITIONS ::= BEGIN

-------------------------------------------------------------------
--	Copyright (C) 2002, Paradyne. All rights reserved.
--
--	This MIB is an extension to the standard DOT1Q MIB (rfc2674 q).
-------------------------------------------------------------------

IMPORTS
	MODULE-IDENTITY, OBJECT-TYPE,
	IpAddress, Integer32, Unsigned32
	    FROM SNMPv2-SMI
	MODULE-COMPLIANCE, OBJECT-GROUP
	    FROM SNMPv2-CONF
	TblCmd
	    FROM PDN-TC
	ifIndex
            FROM IF-MIB
        dot1qVlanStaticEntry
	    FROM Q-BRIDGE-MIB
	pdn-dot1q
	    FROM PDN-HEADER-MIB;
	
pdnDot1qExt  MODULE-IDENTITY
	    LAST-UPDATED "200507260000Z" -- July 26, 2005
	    ORGANIZATION "Paradyne Corp MIB Working Group"
	    CONTACT-INFO "Paradyne Networks, Inc.
			  8545, 126th Ave. N.,
			  Largo, FL 33779
			  www.paradyne.com

			  General Comments to:
			    mibwg_team@paradyne.com

			  Editors: Dragana Gough
				   Jesus A. Pinto
				   Dave Hammers" 

	    DESCRIPTION 
               "The Paradyne enterprise DOT1q extension MIB.
                This MIB provides additional DOT1q configuration
                objects not provided by rfc2674."

	    REVISION "200507260000Z" -- July 26, 2005
            DESCRIPTION "
		o Added objects for VLAN stacking (Q in Q)
		"

	    REVISION "200311120000Z" -- Nov 19, 2003
            DESCRIPTION "
                o Added table that maps Bridge Ports (Dot1dBasePort)
		  with Priorities (PIWG).
		o Added a new object to clear the Bridge Forwarding Table."
		  
	    REVISION "200211300000Z"
            DESCRIPTION "DG
                Changed INTEGER to Integer32 in Uplink object SYNTAX
		Added default values for uplink and nhr in case
		SecureMode is disabled."


	    ::= { pdn-dot1q 1 }

pdnDot1qExtObjects  OBJECT IDENTIFIER ::= { pdnDot1qExt 1 }

--
-- START OF pdnDot1qExt mib definitions
--

pdnDot1qVlanStaticExtTable OBJECT-TYPE
     SYNTAX	 SEQUENCE OF PdnDot1qVlanStaticExtEntry
     MAX-ACCESS  not-accessible
     STATUS  	 current
     DESCRIPTION
	"The Paradyne dot1qVlanStatic extension table.
	 This table is used for configuring extensions 
	 to static vlans."
	::= { pdnDot1qExtObjects 1 }

pdnDot1qVlanStaticExtEntry OBJECT-TYPE
     SYNTAX	 PdnDot1qVlanStaticExtEntry
     MAX-ACCESS  not-accessible
     STATUS  	 current

    DESCRIPTION
	"An entry in the Paradyne dot1q extension  to 
         Static Vlan Table"
    AUGMENTS  { dot1qVlanStaticEntry }
    ::= { pdnDot1qVlanStaticExtTable 1 }

PdnDot1qVlanStaticExtEntry ::=
     SEQUENCE {
     pdnDot1qVlanStaticSecureModeStatus 	INTEGER, 
     pdnDot1qVlanStaticProxyArpStatus		INTEGER, 
     pdnDot1qVlanStaticUplink	        	Integer32, 
     pdnDot1qVlanStaticDefaultNHR		IpAddress,
     pdnDot1qVlanStaticOuterTag			Integer32,
     pdnDot1qVlanStaticOuterDefaultPriority	Integer32,
     pdnDot1qVlanStaticOuterEthertype		Integer32
     }

pdnDot1qVlanStaticSecureModeStatus OBJECT-TYPE
     SYNTAX  	INTEGER {
		  enable(1),
		  disable(2)
     }
     MAX-ACCESS read-write
     STATUS	current
     DESCRIPTION
         "This is objects configure secure mode status for the 
          selected VLAN. The secure VLAN mode implies that the users
	  on this VLAN cannot talk to users on a different VLAN. This
	  setting also validates the configuration of the next three
	  objects in this table. If the pdnDot1qVlanStaticSecureModeStatus
	  is disabled non of the other three objects configurations
	  apply."
     ::= { pdnDot1qVlanStaticExtEntry 1 }

pdnDot1qVlanStaticProxyArpStatus OBJECT-TYPE
     SYNTAX  	INTEGER {
		  enable(1),
		  disable(2)
     }
     MAX-ACCESS read-write
     STATUS	current
     DESCRIPTION
         "This objects enables/disabled proxy arp on secure VLAN. If the 
	  VLAN is secure, it can optionally have Proxy ARP enabled.
          This object is not valid unless pdnDot1qVlanStaticSecureModeStatus
          is set to ENABLED.This object will be disabled(1) by default."
     ::= { pdnDot1qVlanStaticExtEntry 2 }


pdnDot1qVlanStaticUplink OBJECT-TYPE
     SYNTAX  	Integer32
     MAX-ACCESS read-write
     STATUS	current
     DESCRIPTION
         "This is used to configure the port number of the port on 
          which all frames belonging to secure VLAN are to be forwarded.
          This object is not valid unless pdnDot1qVlanStaticSecureModeStatus
          is set to ENABLED. If pdnDot1qVlanStaticSecureModeStatus is disabled
	  this object will read 0 port."
     ::= { pdnDot1qVlanStaticExtEntry 3 }


pdnDot1qVlanStaticDefaultNHR OBJECT-TYPE
     SYNTAX  	IpAddress
     MAX-ACCESS read-write
     STATUS	current
     DESCRIPTION
         "This object is used to configure Default Next Hop Router
          Ip Address that would be used only if the Next Hop Router
          cannot be learned (i.e from snooping messages).
          This object is not valid unless pdnDot1qVlanStaticSecureModeStatus
          is set to ENABLED. If pdnDot1qVlanStaticSecureModeStatus is disabled
	  this object will read 0.0.0.0 address."
     ::= { pdnDot1qVlanStaticExtEntry 4 }

pdnDot1qVlanStaticOuterTag  OBJECT-TYPE
    SYNTAX      Integer32 (0..4094)
    MAX-ACCESS  read-write
    STATUS      current
    DESCRIPTION
       "When VLAN stacking (Q in Q) is desired, this object contains the
	value of the outer 802.1q VLAN outer tag.

	A value of zero (0) indicates that VLAN stacking is not enabled.
        "
    DEFVAL      { 0 }
    ::= { pdnDot1qVlanStaticExtEntry 5 }

pdnDot1qVlanStaticOuterDefaultPriority  OBJECT-TYPE
    SYNTAX      Integer32 (0..7)
    MAX-ACCESS  read-write
    STATUS      current
    DESCRIPTION
       "When VLAN stacking (Q in Q) is desired, this object contains the
	default value of the priority bits in the 802.1q VLAN outer tag
	for unknown unicast, broadcast and multicast packets.

	For known unicast traffic, the inner VLAN tag priority is copied to
	the outer tag priority.

	If pdnDot1qVlanStaticOuterTag (above) is zero (0) this object is ignored.
        "
    DEFVAL      { 0 }
    ::= { pdnDot1qVlanStaticExtEntry 6 }

pdnDot1qVlanStaticOuterEthertype  OBJECT-TYPE
    SYNTAX      Integer32 (0..65535)
    MAX-ACCESS  read-write
    STATUS      current
    DESCRIPTION
	"When VLAN stacking (Q in Q) is desired, this object contains the
	 value of the ethertype in the 802.1q VLAN outer tag.

	 If pdnDot1qVlanStaticOuterTag (above) is zero (0) this object is ignored.
         "
    DEFVAL      { 33024 } -- 0x8100 hexidecimal
    ::= { pdnDot1qVlanStaticExtEntry 7 }


--
-- Start of pdnDot1BasePIWGTable
--
-- Read-Only table that defines the priorities on the Bridge Ports (BasePorts).
--

pdnDot1BasePortPIWGTable     OBJECT-TYPE
    SYNTAX      SEQUENCE OF PdnDot1BasePortPIWGEntry
    MAX-ACCESS  not-accessible
    STATUS      current
    DESCRIPTION "This table allows mapping of Bridge Ports and Priorities.

		 In General, every bridge port has an associated physical port
	         port (identified by its ifIndex). This relationship is defined
		 in the Dot1dBasePortTable (RFC1493).

		 In addition, each bridge port is associated with one priority
		 (PIWG) from a range of valid priorities. This table defines 
		 this relationship. 

		 The range of priorities can vary from product to product.

		 "
    ::= { pdnDot1qExtObjects 2 }

pdnDot1BasePortPIWGEntry     OBJECT-TYPE
    SYNTAX      PdnDot1BasePortPIWGEntry
    MAX-ACCESS  not-accessible
    STATUS      current
    DESCRIPTION "The priority (PIWG) defined on a Bridge port."
    INDEX       { ifIndex,
                  pdnDot1BasePort }
    ::= { pdnDot1BasePortPIWGTable 1 }

PdnDot1BasePortPIWGEntry ::=
    SEQUENCE {
	pdnDot1BasePort		       Unsigned32,
	pdnDot1BasePortPIWGId          Unsigned32,
        pdnDot1BasePortPIWGCircuit     OBJECT IDENTIFIER
    }

pdnDot1BasePort OBJECT-TYPE
    SYNTAX      Unsigned32(1..65535)
    MAX-ACCESS  not-accessible
    STATUS      current
    DESCRIPTION "This object specifies the bridge port associated
                with this PIWG"
    ::= { pdnDot1BasePortPIWGEntry 1 }


pdnDot1BasePortPIWGId OBJECT-TYPE
    SYNTAX      Unsigned32(1..8)
    MAX-ACCESS  read-only
    STATUS      current
    DESCRIPTION "This is the integer identifier of the priority (PIWG)"
    ::= { pdnDot1BasePortPIWGEntry 2 }

pdnDot1BasePortPIWGCircuit OBJECT-TYPE
    SYNTAX      OBJECT IDENTIFIER
    MAX-ACCESS  read-only
    STATUS      current
    DESCRIPTION "This is the object identifier of the priority (PIWG),
		 
		 The value of this object must be a valid identifier
		 defined under the Paradyne Enterprise Definitions
	         (pdn_Header.mib).
		 "
    ::= { pdnDot1BasePortPIWGEntry 3 }


pdnDot1TpFdbClear OBJECT-TYPE
    SYNTAX      TblCmd
    MAX-ACCESS  read-write
    STATUS      current
    DESCRIPTION "This object is used to perform a clear on the 
		 Bridge Forwarding Table (dot1dTpFdbTable).
		 
		 A set operation to this object with the value of 'clear (2)'
		 will clear the entire Bridge Forwarding Table. 

		 A get operation will always return the value of 'noCmd (1)'.
		"

     ::= { pdnDot1qExtObjects 3 }





------------------------------------------
-- Conformance information
------------------------------------------

pdnDot1qExtConformance OBJECT IDENTIFIER ::= { pdnDot1qExt 2 }
pdnDot1qExtGroups      OBJECT IDENTIFIER ::= { pdnDot1qExtConformance 1 }
pdnDot1qExtCompliances OBJECT IDENTIFIER ::= { pdnDot1qExtConformance 2 }

pdnDot1qExtCompliance MODULE-COMPLIANCE
     STATUS  current
     DESCRIPTION
         "Compliance statement for using this MIB for configuring
          Dot1q Static Vlan table."
       MODULE  -- this module
         GROUP       pdnDot1qVlanExtGroup
         DESCRIPTION
             "Implementation of this group is required for systems
              wishing to conform to this MIB for the purposes of
              configuring Static Vlan table."

         GROUP       pdnDot1BasePortPIWGGroup
         DESCRIPTION
             "Implementation of this group is optional."

         GROUP       pdnDot1GeneralGroup
         DESCRIPTION
             "Implementation of this group is optional."

         GROUP      pdnDot1dVlanStackingGroup
         DESCRIPTION
             "This group is only required for implementations that
              require VLAN Stacking (Q in Q)."

         OBJECT pdnDot1qVlanStaticSecureModeStatus
         MIN-ACCESS read-only
         DESCRIPTION
             "The ability to set pdnDot1qVlanStaticSecureModeStatus is not required."

         OBJECT  pdnDot1qVlanStaticProxyArpStatus   
         MIN-ACCESS read-only
         DESCRIPTION
             "The ability to set pdnDot1qVlanStaticProxyArpStatus is not required."

         OBJECT     pdnDot1qVlanStaticUplink
         MIN-ACCESS read-only
         DESCRIPTION
             "The ability to set pdnDot1qVlanStaticUplink is not required."

         OBJECT     pdnDot1qVlanStaticDefaultNHR
         MIN-ACCESS read-only
         DESCRIPTION
             "The ability to set pdnDot1qVlanStaticDefaultNHR is not required."

 ::= { pdnDot1qExtCompliances 1 }


--
-- Units of Conformance
--

pdnDot1qVlanExtGroup OBJECT-GROUP
	OBJECTS {
             pdnDot1qVlanStaticSecureModeStatus, 
             pdnDot1qVlanStaticProxyArpStatus, 
             pdnDot1qVlanStaticUplink, 
             pdnDot1qVlanStaticDefaultNHR
        }
	STATUS  current -- Set as required for the group
	DESCRIPTION 
	   "A collection of configuration objects required 
	    for configuring Static Vlan Table."

	::= { pdnDot1qExtGroups 1 }

pdnDot1BasePortPIWGGroup OBJECT-GROUP
	OBJECTS {
             pdnDot1BasePortPIWGId, 
             pdnDot1BasePortPIWGCircuit
        }
	STATUS  current -- Set as required for the group
	DESCRIPTION 
	   "A collection of read-only objects to provide
	    associations between bridge ports and priorities."

	::= { pdnDot1qExtGroups 2 }

pdnDot1GeneralGroup OBJECT-GROUP
	OBJECTS {
             pdnDot1TpFdbClear
        }
	STATUS  current -- Set as required for the group
	DESCRIPTION 
	   "This group is optional, but if suppported it 
	    should be read-writtable."

	::= { pdnDot1qExtGroups 3 }

pdnDot1dVlanStackingGroup OBJECT-GROUP
	OBJECTS {
             pdnDot1qVlanStaticOuterTag,
             pdnDot1qVlanStaticOuterDefaultPriority,
             pdnDot1qVlanStaticOuterEthertype
        }
	STATUS  current
	DESCRIPTION 
	   "Provides the ability to configure VLAN
            Stacking (Q in Q) parameters."
	::= { pdnDot1qExtGroups 4 }

END

PDN-DS1CONFIG-MIB DEFINITIONS ::= BEGIN

IMPORTS
	DisplayString
		FROM RFC1213-MIB
	Gauge
		FROM RFC1155-SMI
	OBJECT-TYPE
		FROM RFC-1212
     	pdn-interfaces
		FROM PDN-HEADER-MIB;

-- ===============================================================
-- 
-- The Paradyne DS1 Interface Configuration Table.
-- Last Updated: 07/09/02 by C. Sikes (csikes@paradyne.com)
--               Added support for (2^7-1) framed test pattern and
--               (2^11-1) framed test pattern.
--
-- Release: 0.0.3 (6/27/96) DRAFT
-- 
ent-ds1		OBJECT IDENTIFIER ::= { pdn-interfaces 5 }

--  The following definitions are used to allow an SNMP
--  management system to control certain test functions
--  of a Paradyne device.

devDS1Test   OBJECT IDENTIFIER ::= { ent-ds1 1 }

-- The Paradyne DS1 Interface Test Table.

-- This table is used to define objects which allow a network
-- manager to instruct the agent to test a DS1 interface for various
-- faults.

-- More than one test can be active on a particular interface.
-- The valid combinations of tests allowed per interface are
-- described in the Operator's Guide of the product.

devDS1TestTable OBJECT-TYPE
    SYNTAX  SEQUENCE OF DevDS1TestEntry
    ACCESS  not-accessible
    STATUS  mandatory
    DESCRIPTION
           "The Paradyne DS1 Interface Test Table."
    ::= { devDS1Test 1 }

devDS1TestEntry OBJECT-TYPE
    SYNTAX  DevDS1TestEntry
    ACCESS  not-accessible
    STATUS  mandatory
    DESCRIPTION
           "An entry in the Paradyne DS1 Interface Test Table."
    INDEX   { devDS1TestIfIndex, devDS1TestType }
    ::= { devDS1TestTable 1 }

-- Layout of one entry in devDS1TestTable.

DevDS1TestEntry ::=
    SEQUENCE {
        devDS1TestIfIndex			INTEGER,
        devDS1TestType				INTEGER,
        devDS1TestControl			INTEGER,
        devDS1TestArgument			DisplayString
    }

devDS1TestIfIndex OBJECT-TYPE
    SYNTAX  INTEGER
    ACCESS  read-only
    STATUS  mandatory
    DESCRIPTION
           "The index value which uniquely identifies the
            interface for which this entry contains information
            on interface tests.  The interface identified by a
            particular value of this index is the same interface
            as identified by the same value of ifIndex from the
            Interfaces table of MIB II (RFC 1213)."
    ::= { devDS1TestEntry 1 }

devDS1TestType OBJECT-TYPE
    SYNTAX  INTEGER {
-- Remote Loopback Tests
                llbup(1),	     -- line loopback up code sent to
                                     -- the remote DSU/CSU for 10 secs
                llbdn(2),	     -- line loopback down code sent to
                                     -- the remote DSU/CSU for 10 secs
-- Local Loopback Tests
                llb(3),		     -- line loopback
                plb(4),		     -- payload loopback
                rlb(5),		     -- repeater loopback
-- Test Patterns
                sendQRSS(6),	     -- sends QRSS test pattern
		sendZeros(7),	     -- sends an all zeros test pattern
		sendOnes(8),	     -- sends an all ones test pattern
                send1in8(9),	     -- sends a 1-in-8 test pattern
		send3in24(10),	     -- sends a 3-in-24 test pattern
		send63(11),	     -- sends a 63 test pattern
                send511(12),	     -- sends a 511 test pattern
		send2047(13),	     -- sends a 2047 test pattern
		send2E15(14),	     -- sends a 2E15-1 test pattern
		send2E20(15),	     -- sends a 2E20-1 test pattern
		sendUserDefined(16), -- sends a user defined test pattern
				     -- (requires use of devDS1TestArgument)
                monQRSS(17),	     -- monitors a QRSS pattern
		monZeros(18),	     -- monitors an all zeros test pattern
		monOnes(19),	     -- monitors an all ones test pattern
                mon1in8(20),	     -- monitors a 1-in-8 test pattern
		mon3in24(21),	     -- monitors a 3-in-24 test pattern
		mon63(22),	     -- monitors a 63 test pattern
                mon11(23),	     -- monitors a 511 pattern
		mon2047(24),	     -- monitors a 2047 test pattern
		mon2E15(25),	     -- monitors a 2E15-1 test pattern
		mon2E20(26),	     -- monitors a 2E20-1 test pattern
		monUserDefined(27),  -- monitors a user defined test pattern
				     -- (requires use of devDS1TestArgument)

                send2E7(28),         -- sends      a 2E7-1  test pattern
                mon2E7(29),          -- monitors   a 2E7-1  test pattern
                send2E11(30),        -- sends      a 2E11-1 test pattern
                mon2E11(31)          -- monitors   a 2E11-1 test pattern
            }
    ACCESS  read-only
    STATUS  mandatory
    DESCRIPTION
           "The index value which uniquely identifies the test for
            which this entry contains information."
    ::= { devDS1TestEntry 2 }

devDS1TestControl OBJECT-TYPE
    SYNTAX  INTEGER {
                idle(1),	-- stop the currently running test or no
				-- test currently active
                running(2)	-- start the test or the test is
				-- currently active
            }
    ACCESS  read-write
    STATUS  mandatory
    DESCRIPTION
           "A control variable used to start and stop operator-
            initiated interface tests.  Writing idle(1) to the
            test table entry terminates the specified test
            for the interface associated with the entry.  Writing
            running(2) activates the specified test for the interface,
            if allowed (i.e., the test must be allowed for the 
            interface and in combination with any other tests currently
            executing for the interface).  The rules for executing
            tests for the product are specified in the product's
            Operator's Guide.
            This variable is read to determine the current status of
            the test for the interface.  A value of running(2) indicates
            the test is currently in progress on the interface.  A value
            of idle(1) indicates that the test is currently not active
            on the interface."
    ::= { devDS1TestEntry 3 }

devDS1TestArgument OBJECT-TYPE
    SYNTAX  DisplayString (SIZE (0..255))
    ACCESS  read-write
    STATUS  mandatory
    DESCRIPTION
       "Any argument required by the test being executed."
    ::= { devDS1TestEntry 4 }


-- The Paradyne Device Monitor Test Pattern Result Table.

-- This table is used to define objects which reflect the result
-- of a monitor test pattern request.

devDS1MonResultTable OBJECT-TYPE
    SYNTAX  SEQUENCE OF DevDS1MonResultEntry
    ACCESS  not-accessible
    STATUS  mandatory
    DESCRIPTION
           "The Paradyne Device Monitor Test Pattern Result Table."
    ::= { devDS1Test 2 }

devDS1MonResultEntry OBJECT-TYPE
    SYNTAX  DevDS1MonResultEntry
    ACCESS  not-accessible
    STATUS  mandatory
    DESCRIPTION
           "An entry in the Paradyne Device Monitor Test
            Pattern Result Table."
    INDEX   { devDS1MonResultIfIndex, devDS1MonResultTestType }
    ::= { devDS1MonResultTable 1 }

-- Layout of one entry in devDS1MonResultTable.

DevDS1MonResultEntry ::=
    SEQUENCE {
        devDS1MonResultIfIndex		INTEGER,
        devDS1MonResultTestType		INTEGER,
        devDS1MonResultCode		INTEGER,
        devDS1MonResultErrorCount	Gauge
    }

devDS1MonResultIfIndex OBJECT-TYPE
    SYNTAX  INTEGER
    ACCESS  read-only
    STATUS  mandatory
    DESCRIPTION
           "The index value which uniquely identifies the
            interface for which this entry contains information
            on the result of the monitor test pattern request.
            The interface identified by a particular value of this
            index is the same interface as identified by the same
            value of ifIndex from the Interfaces table of MIB II
            (RFC 1213)."
    ::= { devDS1MonResultEntry 1 }

devDS1MonResultTestType OBJECT-TYPE
    SYNTAX  INTEGER {
                monQRSS(17),	     -- monitor QRSS pattern
		monZeros(18),	     -- monitor all zeros test pattern
		monOnes(19),	     -- monitor all ones test pattern
                mon1in8(20),	     -- monitor 1-in-8 test pattern
		mon3in24(21),	     -- monitor 3-in-24 test pattern
		mon63(22),	     -- monitor 63 test pattern
                mon11(23),	     -- monitor 511 pattern
		mon2047(24),	     -- monitor 2047 test pattern
		mon2E15(25),	     -- monitor 2E15-1 test pattern
		mon2E20(26),	     -- monitor 2E20-1 test pattern
		monUserDefined(27),  -- monitor user defined test pattern
                mon2E7(29),          -- monitor 2E7-1  test pattern
                mon2E11(31)          -- monitor 2E11-1 test pattern
            }
    ACCESS  read-only
    STATUS  mandatory
    DESCRIPTION
           "The index value which uniquely identifies the test for
            which this entry contains information."
    ::= { devDS1MonResultEntry 2 }

devDS1MonResultCode OBJECT-TYPE
    SYNTAX  INTEGER {
                none(1),                 -- no further information is available
                inSyncNoBitErrors(2),    -- the monitor pattern test has
                                         -- synchronized on the pattern and has
                                         -- not detected any bit errors
                inSyncWithBitErrors(3),  -- the monitor pattern test has
                                         -- synchronized on the pattern and has
                                         -- detected bit errors
                notInSync(4)             -- a monitor pattern test has not
                                         -- synchronized on the requested pattern
            }
    ACCESS  read-only
    STATUS  mandatory
    DESCRIPTION
           "This object contains a code for more specific information
            on the test pattern monitoring result.  A value of none(1)
            indicates that no further information is available.
            inSyncNoBitErrors(2) notes that the monitor pattern test
            has synchronized on the pattern and has not detected any
            bit errors.  inSyncWithBitErrors indicates that the monitor
            pattern test has synchronized on the pattern and has detected
            bit errors.  A monitor pattern test that has not synchronized
            on the request pattern returns a value of notInSync(4)."
    ::= { devDS1MonResultEntry 3 }

devDS1MonResultErrorCount OBJECT-TYPE
    SYNTAX  Gauge
    ACCESS  read-write
    STATUS  mandatory
    DESCRIPTION
           "The number of bit errors detected in the received
            monitoring test pattern.  The error count is updated
            once every second.  The error count does not increment
            during periods when the pattern is not synchronized, or
            once synchronization is lost.  The maximum value of this
            object is 99,999.
	    
	    Writing any value to this object will reset it to zero."
    ::= { devDS1MonResultEntry 4 }

-- The Paradyne Device Send Test Pattern Control Table.

-- This table is used to define objects related to a send test
-- pattern request.

devDS1SendControlTable OBJECT-TYPE
    SYNTAX  SEQUENCE OF DevDS1SendControlEntry
    ACCESS  not-accessible
    STATUS  mandatory
    DESCRIPTION
           "The Paradyne Device Send Test Pattern Control Table."
    ::= { devDS1Test 3 }

devDS1SendControlEntry OBJECT-TYPE
    SYNTAX  DevDS1SendControlEntry
    ACCESS  not-accessible
    STATUS  mandatory
    DESCRIPTION
           "An entry in the Paradyne Device Send Test
            Pattern Control Table."
    INDEX   { devDS1SendControlIfIndex }
    ::= { devDS1SendControlTable 1 }

-- Layout of one entry in devDS1SendControlTable.

DevDS1SendControlEntry ::=
    SEQUENCE {
        devDS1SendControlIfIndex		INTEGER,
        devDS1SendControlInjectErr		INTEGER,
        devDS1SendControlErrorCount		Gauge
    }

devDS1SendControlIfIndex OBJECT-TYPE
    SYNTAX  INTEGER
    ACCESS  read-only
    STATUS  mandatory
    DESCRIPTION
       "The index value which uniquely identifies the
	interface for which this entry contains information
	on the result of the monitor test pattern request.
	The interface identified by a particular value of this
	index is the same interface as identified by the same
	value of ifIndex from the Interfaces table of MIB II
            (RFC 1213)."
    ::= { devDS1SendControlEntry 1 }

devDS1SendControlInjectErr OBJECT-TYPE
    SYNTAX  INTEGER {
                noOp(1),
                inject(2)
            }
    ACCESS  read-write
    STATUS  mandatory
    DESCRIPTION
       "Setting this object to inject(2) will inject one error
	in the data pattern being sent.  If no pattern is being
	sent, the agent will return BAD VALUE.  Reading this
	value will always return noOp(1)."
    ::= { devDS1SendControlEntry 2 }

devDS1SendControlErrorCount OBJECT-TYPE
    SYNTAX  Gauge
    ACCESS  read-only
    STATUS  mandatory
    DESCRIPTION
       "The number of bit errors injected into the test pattern
	being sent.  The maximum value of this object is 99,999."
    ::= { devDS1SendControlEntry 3 }

END
PDN-DS1EXT-MIB DEFINITIONS ::= BEGIN

-------------------------------------------------------------------
--	Copyright (C) 2002, Paradyne. All rights reserved.
--
--	This MIB is an extension to the standard DS1 MIB (rfc2495).
-------------------------------------------------------------------

IMPORTS
	MODULE-IDENTITY, OBJECT-TYPE
	    FROM SNMPv2-SMI
	ifIndex
	    FROM IF-MIB
	MODULE-COMPLIANCE, OBJECT-GROUP
	    FROM SNMPv2-CONF
	ent-ds1
	    FROM PDN-HEADER-MIB;
	
pdnDs1Ext  MODULE-IDENTITY
	    LAST-UPDATED "200204050000Z"
	    ORGANIZATION "Paradyne Corp MIB Working Group"
	    CONTACT-INFO "Paradyne Networks, Inc.
			  8545, 126th Ave. N.,
			  Largo, FL 33779
			  www.paradyne.com

			  General Comments to:
			    mibwg_team@paradyne.com

			  Editors: Vic Sperry" 

	    DESCRIPTION 
               "The Paradyne enterprise DS1/G.703 extension MIB.
                This MIB provides additional DS1 and G.703 (E1) configuration
                objects not provided by rfc2495."

	    ::= { ent-ds1 5 }

pdnDs1ExtObjects  OBJECT IDENTIFIER ::= { pdnDs1Ext 1 }

--
-- START OF pdnDs1Ext mib definitions
--

pdnDs1ExtConfTable OBJECT-TYPE
     SYNTAX	 SEQUENCE OF PdnDs1ExtConfEntry
     MAX-ACCESS  not-accessible
     STATUS  	 current
     DESCRIPTION
	"The Paradyne DS1/G.703 extension configuration table.
	 This table is used for configuring extensions to DS1
         and G.703 interfaces."
	::= { pdnDs1ExtObjects 1 }

pdnDs1ExtConfEntry OBJECT-TYPE
     SYNTAX	 PdnDs1ExtConfEntry
     MAX-ACCESS  not-accessible
     STATUS  	 current
     DESCRIPTION
	"An entry in the Paradyne DS1/G.703 extension configuration table.
         Note: The objects used depend on the type of interface.

         For DS1: use pdnDs1ExtConfLineLengthType and one of
                      (pdnDs1ExtConfLineLength or pdnDs1ExtConfLineBuildOut)

         For G.703: use pdnDs1ExtConfLineLengthType and pdnDs1ExtConfConnector
        "
    INDEX   { ifIndex }
    ::= { pdnDs1ExtConfTable 1 }

PdnDs1ExtConfEntry ::=
     SEQUENCE {
     pdnDs1ExtConfLineLengthType   INTEGER,
     pdnDs1ExtConfLineLength       INTEGER,
     pdnDs1ExtConfLineBuildOut     INTEGER,
     pdnDs1ExtConfConnector        INTEGER
     }

pdnDs1ExtConfLineLengthType OBJECT-TYPE
     SYNTAX  	INTEGER {
		  shortHaul(1),
		  longHaul(2)
     }
     MAX-ACCESS read-write
     STATUS	current
     DESCRIPTION
	"This entry specifies the type of loop length for the interface.
         short-haul is intended for intra-building use.
         long-haul is intended for inter-building use."

     DEFVAL { longHaul }
     ::= { pdnDs1ExtConfEntry 1 }

pdnDs1ExtConfLineLength OBJECT-TYPE
     SYNTAX  	INTEGER {
		  feet000To133(1),
		  feet134To266(2),
		  feet267To399(3),
		  feet400To533(4),
		  feet534To655(5)
     }
     MAX-ACCESS read-write
     STATUS	current
     DESCRIPTION
	"This entry specifies the loop length, in feet, for a short-haul
         DS1 line. This object only applies to DS1 interfaces.
	 Note: This object shares a mutually exclusive relationship 
	 with the pdnDs1ExtConfLineBuildOut object i.e. only one of the
         two can be used for configuration at one time, based on the
         pdnDs1ExtConfLineLengthType object."
     DEFVAL { feet000To133 }
     ::= { pdnDs1ExtConfEntry 2 }

pdnDs1ExtConfLineBuildOut OBJECT-TYPE
     SYNTAX  	INTEGER {
		  dB0Pnt0(1),
		  dB7Pnt5(2),
		  dB15Pnt0(3),
		  dB22Pnt5(4)
     }
     MAX-ACCESS read-write
     STATUS	current
     DESCRIPTION
	"This entry specifies the line build out, in decibels, for a
         long-haul DS1 line.
         dB0Pnt0  = 0.0 dB         
         dB7Pnt5  = -7.5 dB         
         dB15Pnt0 = -15.0 dB         
         dB22Pnt5 = -22.5 dB         
         This object only applies to DS1 interfaces.
	 Note: This object shares a mutually exclusive relationship 
	 with the pdnDs1ExtConfLineLength object i.e. only one of the
         two can be used for configuration at one time, based on the
         pdnDs1ExtConfLineLengthType object."
     DEFVAL { dB0Pnt0 }
     ::= { pdnDs1ExtConfEntry 3 }

pdnDs1ExtConfConnector OBJECT-TYPE
     SYNTAX  	INTEGER {
		  bnc(1),
		  rj48(2)
     }
     MAX-ACCESS read-write
     STATUS	current
     DESCRIPTION
	"This entry specifies the type of connector to be used.
         This object only applies to G.703 interfaces.

         bnc: 75-Ohm connector supporting only short-haul.
         rj48: 120-Ohm connector supporting both short-haul and long-haul."

     DEFVAL { rj48 }
     ::= { pdnDs1ExtConfEntry 4 }

------------------------------------------
-- Conformance information
------------------------------------------

pdnDs1ExtConformance OBJECT IDENTIFIER ::= { pdnDs1Ext 2 }
pdnDs1ExtGroups      OBJECT IDENTIFIER ::= { pdnDs1ExtConformance 1 }
pdnDs1ExtCompliances OBJECT IDENTIFIER ::= { pdnDs1ExtConformance 2 }

pdnDs1ExtCompliance MODULE-COMPLIANCE
     STATUS  current
     DESCRIPTION
         "Compliance statement for using this MIB for configuring
          DS1 interfaces."
     MODULE  -- this module

         GROUP       pdnDs1ExtT1ConfigGroup
         DESCRIPTION
             "Implementation of this group is required for systems
              wishing to conform to this MIB for the purposes of
              configuring a DS1 interface."

         OBJECT     pdnDs1ExtConfLineLengthType
         MIN-ACCESS read-only
         DESCRIPTION
             "The ability to set pdnDs1ExtConfLineLengthType is not required."

         OBJECT     pdnDs1ExtConfLineLength
         MIN-ACCESS read-only
         DESCRIPTION
             "The ability to set pdnDs1ExtConfLineLength is not required."

         OBJECT     pdnDs1ExtConfLineBuildOut
         MIN-ACCESS read-only
         DESCRIPTION
             "The ability to set pdnDs1ExtConfLineBuildOut is not required."

 ::= { pdnDs1ExtCompliances 1 }


pdnDs1ExtG703Compliance MODULE-COMPLIANCE
     STATUS  current
     DESCRIPTION
         "Compliance statement for using this MIB for configuring
          G.703 interfaces."
     MODULE  -- this module

         GROUP       pdnDs1ExtE1ConfigGroup
         DESCRIPTION
             "Implementation of this group is required for systems
              wishing to conform to this MIB for the purposes of
              configuring a G.703 interface."

         OBJECT     pdnDs1ExtConfLineLengthType
         MIN-ACCESS read-only
         DESCRIPTION
             "The ability to set pdnDs1ExtConfLineLengthType is not required."

         OBJECT     pdnDs1ExtConfConnector
         MIN-ACCESS read-only
         DESCRIPTION
             "The ability to set pdnDs1ExtConfConnector is not required."

 ::= { pdnDs1ExtCompliances 2 }


--
-- Units of Conformance
--

pdnDs1ExtT1ConfigGroup OBJECT-GROUP
	OBJECTS {
           pdnDs1ExtConfLineLengthType,
           pdnDs1ExtConfLineLength,
           pdnDs1ExtConfLineBuildOut
        }
	STATUS  current -- Set as required for the group
	DESCRIPTION 
	   "A collection of configuration objects required 
	    for configuring a T1 interface."

	::= { pdnDs1ExtGroups 1 }

pdnDs1ExtE1ConfigGroup OBJECT-GROUP
	OBJECTS {
           pdnDs1ExtConfLineLengthType,
           pdnDs1ExtConfConnector
        }
	STATUS  current -- Set as required for the group
	DESCRIPTION 
	   "A collection of configuration objects required 
	    for configuring a G.703 (E1) interface."

	::= { pdnDs1ExtGroups 2 }
END

-- ===================================================================
-- == Copyright (C) 2004 Paradyne Corporation.                      ==
-- ===================================================================

PDN-DHCP-MIB DEFINITIONS ::= BEGIN

IMPORTS
   MODULE-IDENTITY, OBJECT-TYPE
      FROM SNMPv2-SMI
   OBJECT-GROUP, MODULE-COMPLIANCE
      FROM SNMPv2-CONF
   SwitchState
       FROM PDN-TC
   dot1qVlanStaticEntry
       FROM Q-BRIDGE-MIB  
   pdn-common
      FROM PDN-HEADER-MIB;
        
pdnDhcpMIB MODULE-IDENTITY
   LAST-UPDATED "200409130000Z"  -- September 13, 2004
   ORGANIZATION "Paradyne Networks
                 MIB Working Group
                 Other information about group editing the MIB"
   CONTACT-INFO "Paradyne Networks, Inc.
                 8545 126th Avenue North
                 Largo, FL 33733
                 www.paradyne.com
        
                 General Comments to: mibwg_team@paradyne.com

                 Editor
                    Clay Sikes"

   DESCRIPTION  "The MIB module provides objects to manage an 
                 interface's Dynamic Host Configuration Protocol 
                 (DHCP)."

   REVISION     "200409140000Z"  -- September 13, 2004
   DESCRIPTION  "Initial release."

::=  { pdn-common 57 }



-- ====================================================================
-- == Define groups for Notifications, MIB Objects, Accessible for   ==
-- == Notifications (AFNs), and Conformance.                         ==
-- == These may just be place holders.                               ==
-- ====================================================================
pdnDhcpNotifications OBJECT IDENTIFIER ::= { pdnDhcpMIB 0 }
pdnDhcpObjects       OBJECT IDENTIFIER ::= { pdnDhcpMIB 1 }
pdnDhcpAFNs          OBJECT IDENTIFIER ::= { pdnDhcpMIB 2 } 
pdnDhcpConformance   OBJECT IDENTIFIER ::= { pdnDhcpMIB 3 }




-- ====================================================================
-- ==                  Textual Conventions                           ==
-- ====================================================================
-- None defined.




-- ====================================================================
-- ==                  MIB Objects                                   ==
-- ====================================================================


-- ===================================================================
-- == pdnDhcpVlanConfigTable                                        ==
-- ===================================================================
pdnDhcpVlanConfigTable  OBJECT-TYPE
   SYNTAX      SEQUENCE OF PdnDhcpVlanConfigEntry
   MAX-ACCESS  not-accessible
   STATUS      current
   DESCRIPTION "The PDN DHCP VLAN Configuration Table.  This table
                manages DHCP configuration options.  The index allows
                the configuration to be applied on a per VLAN basis."
   ::= { pdnDhcpObjects 1 }

pdnDhcpVlanConfigEntry  OBJECT-TYPE
   SYNTAX      PdnDhcpVlanConfigEntry
   MAX-ACCESS  not-accessible
   STATUS      current
   DESCRIPTION "An entry in the PDN DHCP VLAN Configuration Table."
   AUGMENTS    { dot1qVlanStaticEntry }
   ::= { pdnDhcpVlanConfigTable 1 }

PdnDhcpVlanConfigEntry ::=
   SEQUENCE {
      pdnDhcpVlanConfigOption82      SwitchState
   }

pdnDhcpVlanConfigOption82  OBJECT-TYPE
   SYNTAX      SwitchState
   MAX-ACCESS  read-create
   STATUS      current
   DESCRIPTION "The DHCP Relay Agent Information (Option 82) circuit
                identifier suboption.  When enabled, Option82  will be
                supported.  When disabled, Option 82 will not be
                supported."
   DEFVAL      { disabled }
   ::= { pdnDhcpVlanConfigEntry 1 }



-- ====================================================================
-- ==                  Accessible for Notifications (AFNs)           ==
-- ====================================================================
-- None defined



-- ===================================================================
-- ==                  Traps/Notifications                          ==
-- ===================================================================
-- None defined



-- ====================================================================
-- ==                  Conformance Information                       ==
-- ====================================================================

pdnDhcpCompliances  OBJECT IDENTIFIER ::= { pdnDhcpConformance 1 }
pdnDhcpGroups       OBJECT IDENTIFIER ::= { pdnDhcpConformance 2 }


-- ===========================
-- == Compliance Statements ==
-- ===========================


pdnDhcpCompliance  MODULE-COMPLIANCE
   STATUS      current
   DESCRIPTION "The compliance statement for network elements 
                implementing DHCP."
   MODULE      -- this module
   -- No mandatory groups are specified.    

   GROUP       pdnDhcpVlanConfigOpt82Group
   DESCRIPTION "This group is only required for implementations that
                need to configure DHCP Option 82 on a per-VLAN basis."
    ::= { pdnDhcpCompliances 1 }


-- ==========================
-- == Units of Conformance ==
-- ==========================

pdnDhcpObjGroups   OBJECT IDENTIFIER ::= { pdnDhcpGroups 1 }
pdnDhcpAfnGroups   OBJECT IDENTIFIER ::= { pdnDhcpGroups 2 }
pdnDhcpNtfyGroups  OBJECT IDENTIFIER ::= { pdnDhcpGroups 3 }


-- ===================
-- == Object Groups ==
-- ===================


pdnDhcpVlanConfigOpt82Group  OBJECT-GROUP
   OBJECTS {
      pdnDhcpVlanConfigOption82
   }
   STATUS      current
   DESCRIPTION "Configures DHCP Option 82 on a per-VLAN basis."
   ::= { pdnDhcpObjGroups 2 }



-- =========================================
-- == Accessible for Notifications Groups ==
-- =========================================
-- None defined



-- =========================
-- == Notification Groups ==
-- =========================
-- None defined




-- =========
-- == END ==
-- =========
END

-- ===================================================================
-- == Copyright (C) 2004 Paradyne Corporation.                      ==
-- ===================================================================

PDN-HDLC-MIB DEFINITIONS ::= BEGIN

IMPORTS
   MODULE-IDENTITY, OBJECT-TYPE, Counter32
      FROM SNMPv2-SMI
   OBJECT-GROUP, MODULE-COMPLIANCE
      FROM SNMPv2-CONF
   ifIndex
      FROM IF-MIB
   pdn-interfaces
      FROM PDN-HEADER-MIB;
        
pdnHdlcMIB MODULE-IDENTITY
   LAST-UPDATED "200409100000Z"  -- September 10, 2004
   ORGANIZATION "Paradyne Networks
                 MIB Working Group
                 Other information about group editing the MIB"
   CONTACT-INFO "Paradyne Networks, Inc.
                 8545 126th Avenue North
                 Largo, FL 33733
                 www.paradyne.com
        
                 General Comments to: mibwg_team@paradyne.com

                 Editor
                    Clay Sikes"

   DESCRIPTION  "The MIB module provides objects to manage an 
                 interface's High-level Data Link Control (HDLC)
                 protocol."

   REVISION     "200409100000Z"  -- September 10, 2004
   DESCRIPTION  "Initial release."

::=  { pdn-interfaces 26 }



-- ====================================================================
-- == Define groups for Notifications, MIB Objects, Accessible for   ==
-- == Notifications (AFNs), and Conformance.                         ==
-- == These may just be place holders.                               ==
-- ====================================================================
pdnHdlcNotifications OBJECT IDENTIFIER ::= { pdnHdlcMIB 0 }
pdnHdlcObjects       OBJECT IDENTIFIER ::= { pdnHdlcMIB 1 }
pdnHdlcAFNs          OBJECT IDENTIFIER ::= { pdnHdlcMIB 2 } 
pdnHdlcConformance   OBJECT IDENTIFIER ::= { pdnHdlcMIB 3 }




-- ====================================================================
-- ==                  Textual Conventions                           ==
-- ====================================================================
-- None defined.




-- ====================================================================
-- ==                  MIB Objects                                   ==
-- ====================================================================




-- ===================================================================
-- == pdnHdlcStatsTotalTable                                        ==
-- ===================================================================
pdnHdlcStatsTotalTable  OBJECT-TYPE
   SYNTAX      SEQUENCE OF PdnHdlcStatsTotalEntry
   MAX-ACCESS  not-accessible
   STATUS      current
   DESCRIPTION "The HDLC Total Statistics Table.  This table contains 
                counters for statistics.  Counters in this group 
                contain `total' counts which are marked from the time 
                the system was last re-initialized."
   ::= { pdnHdlcObjects 1 }

pdnHdlcStatsTotalEntry  OBJECT-TYPE
   SYNTAX      PdnHdlcStatsTotalEntry
   MAX-ACCESS  not-accessible
   STATUS      current
   DESCRIPTION "An entry in the HDLC Total Statistics Table."
   INDEX       { ifIndex }
   ::= { pdnHdlcStatsTotalTable 1 }

PdnHdlcStatsTotalEntry ::=
   SEQUENCE {
      pdnHdlcStatsTotalRxGood              Counter32,
      pdnHdlcStatsTotalRxCRCErrors         Counter32,
      pdnHdlcStatsTotalRxAborts            Counter32,
      pdnHdlcStatsTotalRxBadAddress        Counter32,
      pdnHdlcStatsTotalRxNoBufAvail        Counter32,
      pdnHdlcStatsTotalReceiverOverrun     Counter32,
      pdnHdlcStatsTotalRxMaxSizeExceeded   Counter32,
      pdnHdlcStatsTotalTx                  Counter32,
      pdnHdlcStatsTotalTxBufUnderrun       Counter32
   }

pdnHdlcStatsTotalRxGood  OBJECT-TYPE
   SYNTAX      Counter32
   MAX-ACCESS  read-only
   STATUS      current
   DESCRIPTION "The number of HDLC frames that were received without
                any errors."
   ::= { pdnHdlcStatsTotalEntry 1 }

pdnHdlcStatsTotalRxCRCErrors  OBJECT-TYPE
   SYNTAX      Counter32
   MAX-ACCESS  read-only
   STATUS      current
   DESCRIPTION "The number of HDLC frames that were received with 
                CRC errors."
   ::= { pdnHdlcStatsTotalEntry 2 }

pdnHdlcStatsTotalRxAborts  OBJECT-TYPE
   SYNTAX      Counter32
   MAX-ACCESS  read-only
   STATUS      current
   DESCRIPTION "The number of HDLC frames that were aborted during
                receive."
   ::= { pdnHdlcStatsTotalEntry 3 }

pdnHdlcStatsTotalRxBadAddress  OBJECT-TYPE
   SYNTAX      Counter32
   MAX-ACCESS  read-only
   STATUS      current
   DESCRIPTION "The number of HDLC frames that were discarded due
                to a bad address."
   ::= { pdnHdlcStatsTotalEntry 4 }

pdnHdlcStatsTotalRxNoBufAvail  OBJECT-TYPE
   SYNTAX      Counter32
   MAX-ACCESS  read-only
   STATUS      current
   DESCRIPTION "The number of HDLC frames that were discarded because
                no receive buffers were available."
   ::= { pdnHdlcStatsTotalEntry 5 }

pdnHdlcStatsTotalReceiverOverrun  OBJECT-TYPE
   SYNTAX      Counter32
   MAX-ACCESS  read-only
   STATUS      current
   DESCRIPTION "The number of times a receiver overrun occurred."
   ::= { pdnHdlcStatsTotalEntry 6 }

pdnHdlcStatsTotalRxMaxSizeExceeded  OBJECT-TYPE
   SYNTAX      Counter32
   MAX-ACCESS  read-only
   STATUS      current
   DESCRIPTION "The number of times a frame was received which was 
                discarded due to the frame size exceeding the maximum
                frame size for the receiver."
   ::= { pdnHdlcStatsTotalEntry 7 }

pdnHdlcStatsTotalTx  OBJECT-TYPE
   SYNTAX      Counter32
   MAX-ACCESS  read-only
   STATUS      current
   DESCRIPTION "The number of HDLC frames transmitted."
   ::= { pdnHdlcStatsTotalEntry 8 }

pdnHdlcStatsTotalTxBufUnderrun  OBJECT-TYPE
   SYNTAX      Counter32
   MAX-ACCESS  read-only
   STATUS      current
   DESCRIPTION "The number of times a transmitter underrun occurred."
   ::= { pdnHdlcStatsTotalEntry 9 }



-- ====================================================================
-- ==                  Accessible for Notifications (AFNs)           ==
-- ====================================================================
-- None defined



-- ===================================================================
-- ==                  Traps/Notifications                          ==
-- ===================================================================
-- None defined



-- ====================================================================
-- ==                  Conformance Information                       ==
-- ====================================================================

pdnHdlcCompliances  OBJECT IDENTIFIER ::= { pdnHdlcConformance 1 }
pdnHdlcGroups       OBJECT IDENTIFIER ::= { pdnHdlcConformance 2 }


-- ===========================
-- == Compliance Statements ==
-- ===========================


pdnHdlcCompliance  MODULE-COMPLIANCE
   STATUS      current
   DESCRIPTION "The compliance statement for network elements 
                implementing HDLC Protocol."
   MODULE      -- this module
   -- No mandatory groups are specified.  
   
   GROUP       pdnHdlcStatsTotalGroup
   DESCRIPTION "This group is only required for implementations that
                need to display total HDLC statistics."
    ::= { pdnHdlcCompliances 1 }


-- ==========================
-- == Units of Conformance ==
-- ==========================

pdnHdlcObjGroups   OBJECT IDENTIFIER ::= { pdnHdlcGroups 1 }
pdnHdlcAfnGroups   OBJECT IDENTIFIER ::= { pdnHdlcGroups 2 }
pdnHdlcNtfyGroups  OBJECT IDENTIFIER ::= { pdnHdlcGroups 3 }


-- ===================
-- == Object Groups ==
-- ===================


pdnHdlcStatsTotalGroup  OBJECT-GROUP
   OBJECTS {
      pdnHdlcStatsTotalRxGood,
      pdnHdlcStatsTotalRxCRCErrors,
      pdnHdlcStatsTotalRxAborts,
      pdnHdlcStatsTotalRxBadAddress,
      pdnHdlcStatsTotalRxNoBufAvail,
      pdnHdlcStatsTotalReceiverOverrun,
      pdnHdlcStatsTotalRxMaxSizeExceeded,
      pdnHdlcStatsTotalTx,
      pdnHdlcStatsTotalTxBufUnderrun
   }
   STATUS      current
   DESCRIPTION "Displays various HDLC related total counters."
   ::= { pdnHdlcObjGroups 1 }



-- =========================================
-- == Accessible for Notifications Groups ==
-- =========================================
-- None defined



-- =========================
-- == Notification Groups ==
-- =========================
-- None defined




-- =========
-- == END ==
-- =========
END

-- ===================================================================
-- == Copyright (C) 2004 Paradyne Corporation.                      ==
-- ===================================================================

PDN-IFDEV-IWF-MIB DEFINITIONS ::= BEGIN

IMPORTS
   MODULE-IDENTITY, OBJECT-TYPE, Counter32
      FROM SNMPv2-SMI
   OBJECT-GROUP, MODULE-COMPLIANCE
      FROM SNMPv2-CONF
   TEXTUAL-CONVENTION
       FROM SNMPv2-TC
   ifIndex
      FROM IF-MIB
   pdn-interfaces
      FROM PDN-HEADER-MIB;
        
pdnIfDevIwfMIB MODULE-IDENTITY
   LAST-UPDATED "200409100000Z"  -- September 10, 2004
   ORGANIZATION "Paradyne Networks
                 MIB Working Group
                 Other information about group editing the MIB"
   CONTACT-INFO "Paradyne Networks, Inc.
                 8545 126th Avenue North
                 Largo, FL 33733
                 www.paradyne.com
        
                 General Comments to: mibwg_team@paradyne.com

                 Editor
                    Clay Sikes"

   DESCRIPTION  "This module provides objects pertaining to the
                 management of an `Interface Device Interworking
                 Function' (IfDev IWF).

                 The following documents should be referenced with 
                 respect to this MIB module:
                 [RFC 1662]    Simpson, W., `PPP in HDLC-like 
                               framing', July 1994."

   REVISION     "200409100000Z"  -- September 10, 2004
   DESCRIPTION  "Initial release."

::=  { pdn-interfaces 27 }



-- ====================================================================
-- == Define groups for Notifications, MIB Objects, Accessible for   ==
-- == Notifications (AFNs), and Conformance.                         ==
-- == These may just be place holders.                               ==
-- ====================================================================
pdnIfDevIwfNotifications OBJECT IDENTIFIER ::= { pdnIfDevIwfMIB 0 }
pdnIfDevIwfObjects       OBJECT IDENTIFIER ::= { pdnIfDevIwfMIB 1 }
pdnIfDevIwfAFNs          OBJECT IDENTIFIER ::= { pdnIfDevIwfMIB 2 } 
pdnIfDevIwfConformance   OBJECT IDENTIFIER ::= { pdnIfDevIwfMIB 3 }




-- ====================================================================
-- ==                  Textual Conventions                           ==
-- ====================================================================
TxRxUnit ::= TEXTUAL-CONVENTION
   STATUS      current
   DESCRIPTION "Identifies the unit of transmission.

                The unit other(1) is used when none of the other 
                enumerations apply.  

                The unit bits(2) is used when bits are being 
                transmitted.  

                The unit octets(3) is used for groups of 8 bits.
  
                The unit frames(4) is used for transmission at the data 
                link layer.  A frame may include a header and/or a 
                trailer, along with some number of units of data.

                The unit packets(5) is a basic unit of encapsulation,
                which typically is passed across the interface between
                the network layer and the data link layer.  A packet
                is usually mapped to a frame;  the exceptions are
                when data link layer fragmentation is being performed,
                or when multiple packets are incorporated into a single 
                frame.

                The unit datagrams(6) is a unit of transmission in the
                network layer (such as IP).  A datagram may be 
                encapsulated in one or more packets passed to the data
                link layer."

   REFERENCE   "RFC 1662, Section 1.2, `Terminology'."
   SYNTAX      INTEGER {
                  other(1),
                  bits(2),
                  octets(3),
                  frames(4),
                  packets(5),
                  datagrams(6)
               }




-- ====================================================================
-- ==                  MIB Objects                                   ==
-- ====================================================================




-- ===================================================================
-- == pdnIfDevIwfStatsTotalTable                                    ==
-- ===================================================================
pdnIfDevIwfStatsTotalTable  OBJECT-TYPE
   SYNTAX      SEQUENCE OF PdnIfDevIwfStatsTotalEntry
   MAX-ACCESS  not-accessible
   STATUS      current
   DESCRIPTION "The IfDev IWF Total Statistics Table.  This table 
                contains counters for statistics.  Counters in this 
                group contain `total' counts which are marked from the 
                time the system was last re-initialized."
   ::= { pdnIfDevIwfObjects 1 }

pdnIfDevIwfStatsTotalEntry  OBJECT-TYPE
   SYNTAX      PdnIfDevIwfStatsTotalEntry
   MAX-ACCESS  not-accessible
   STATUS      current
   DESCRIPTION "An entry in the IfDev IWF Total Statistics Table."
   INDEX       { ifIndex }
   ::= { pdnIfDevIwfStatsTotalTable 1 }

PdnIfDevIwfStatsTotalEntry ::=
   SEQUENCE {
      pdnIfDevIwfStatsTotalBufferUnderruns        Counter32,
      pdnIfDevIwfStatsTotalMRUErrors              Counter32,
      pdnIfDevIwfStatsTotalRxUnit                 TxRxUnit,
      pdnIfDevIwfStatsTotalRx                     Counter32
   }

pdnIfDevIwfStatsTotalBufferUnderruns  OBJECT-TYPE
   SYNTAX      Counter32
   MAX-ACCESS  read-only
   STATUS      current
   DESCRIPTION "The number of times there was a buffer underrun."
   ::= { pdnIfDevIwfStatsTotalEntry 1 }

pdnIfDevIwfStatsTotalMRUErrors  OBJECT-TYPE
   SYNTAX      Counter32
   MAX-ACCESS  read-only
   STATUS      current
   DESCRIPTION "The number of times the Maximum Receive Unit size
                was exceeded."
   ::= { pdnIfDevIwfStatsTotalEntry 2 }

pdnIfDevIwfStatsTotalRxUnit  OBJECT-TYPE
   SYNTAX      TxRxUnit
   MAX-ACCESS  read-only
   STATUS      current
   DESCRIPTION "The unit type of data being received by the IWF."
   ::= { pdnIfDevIwfStatsTotalEntry 3 }

pdnIfDevIwfStatsTotalRx  OBJECT-TYPE
   SYNTAX      Counter32
   MAX-ACCESS  read-only
   STATUS      current
   DESCRIPTION "The number of units received by the IWF."
   ::= { pdnIfDevIwfStatsTotalEntry 4 }



-- ====================================================================
-- ==                  Accessible for Notifications (AFNs)           ==
-- ====================================================================
-- None defined



-- ===================================================================
-- ==                  Traps/Notifications                          ==
-- ===================================================================
-- None defined



-- ====================================================================
-- ==                  Conformance Information                       ==
-- ====================================================================

pdnIfDevIwfCompliances  OBJECT IDENTIFIER ::= 
   { pdnIfDevIwfConformance 1 }
pdnIfDevIwfGroups       OBJECT IDENTIFIER ::= 
   { pdnIfDevIwfConformance 2 }


-- ===========================
-- == Compliance Statements ==
-- ===========================


pdnIfDevIwfCompliance  MODULE-COMPLIANCE
   STATUS      current
   DESCRIPTION "The compliance statement for IfDev IWFs."
   MODULE      -- this module
   -- No mandatory groups are specified.
   
   GROUP       pdnIfDevIwfStatsTotalBufferUnderrunsGroup
   DESCRIPTION "This group is required for implementations that need
                to display IWF buffer underruns and the particular
                IfDev can support the underrun detection."

   GROUP       pdnIfDevIwfStatsTotalMRUErrorsGroup
   DESCRIPTION "This group is required for implementations that need
                to display IWF MRU errors and the particular IfDev
                can support MRU error detection."

   GROUP       pdnIfDevIwfStatsTotalRxGroup
   DESCRIPTION "This group is required for implementations that need
                to display the units of transmission received by the
                IWF and the IfDev can support the detection. "

    ::= { pdnIfDevIwfCompliances 1 }


-- ==========================
-- == Units of Conformance ==
-- ==========================

pdnIfDevIwfObjGroups   OBJECT IDENTIFIER ::= { pdnIfDevIwfGroups 1 }
pdnIfDevIwfAfnGroups   OBJECT IDENTIFIER ::= { pdnIfDevIwfGroups 2 }
pdnIfDevIwfNtfyGroups  OBJECT IDENTIFIER ::= { pdnIfDevIwfGroups 3 }


-- ===================
-- == Object Groups ==
-- ===================


pdnIfDevIwfStatsTotalBufferUnderrunsGroup  OBJECT-GROUP
   OBJECTS {
      pdnIfDevIwfStatsTotalBufferUnderruns
   }
   STATUS      current
   DESCRIPTION "The number of times there was a buffer underrun."
   ::= { pdnIfDevIwfObjGroups 1 }

pdnIfDevIwfStatsTotalMRUErrorsGroup  OBJECT-GROUP
   OBJECTS {
      pdnIfDevIwfStatsTotalMRUErrors
   }
   STATUS      current
   DESCRIPTION "The number of times the Maximum Receive Unit size
                was exceeded."
   ::= { pdnIfDevIwfObjGroups 2 }

pdnIfDevIwfStatsTotalRxGroup  OBJECT-GROUP
   OBJECTS {
      pdnIfDevIwfStatsTotalRxUnit,
      pdnIfDevIwfStatsTotalRx
   }
   STATUS      current
   DESCRIPTION "The number of units received by the IWF."
   ::= { pdnIfDevIwfObjGroups 3 }



-- =========================================
-- == Accessible for Notifications Groups ==
-- =========================================
-- None defined



-- =========================
-- == Notification Groups ==
-- =========================
-- None defined




-- =========
-- == END ==
-- =========
END

-- ===============================================================
-- == Copyright (C) 2004 Paradyne Corporation.                  ==
-- ===============================================================

PDN-PPP-LCP-EXT-MIB DEFINITIONS ::= BEGIN

IMPORTS
   MODULE-IDENTITY, OBJECT-TYPE, 
   Unsigned32, Counter32
      FROM SNMPv2-SMI
   OBJECT-GROUP, MODULE-COMPLIANCE
      FROM SNMPv2-CONF
   DisplayString
      FROM SNMPv2-TC
   ifIndex
      FROM IF-MIB
   pppLinkStatusEntry, pppLinkConfigEntry
      FROM PPP-LCP-MIB
   SwitchState, PdnPPPState
      FROM PDN-TC
   pdn-interfaces
      FROM PDN-HEADER-MIB;
        
pdnPppLcpExtMIB MODULE-IDENTITY
   LAST-UPDATED "200409100000Z"  -- September 10, 2004
   ORGANIZATION "Paradyne Networks
                 MIB Working Group
                 Other information about group editing the MIB"
   CONTACT-INFO "Paradyne Networks, Inc.
                 8545 126th Avenue North
                 Largo, FL 33733
                 www.paradyne.com
        
                 General Comments to: mibwg_team@paradyne.com

                 Editor
                    Clay Sikes"

   DESCRIPTION "The MIB module provides enterprise-specific extensions
                to the PPP-LCP-MIB for managing the Link Control 
                Protocol (LCP) and  Line Quality Monitoring on 
                subnetwork interfaces that use the family of 
                Point-to-Point protocols.

                The following documents should be referenced with 
                respect to this MIB module:
                [RFC 1471]    Kastenholz, F., `The Definitions of 
                              Managed Objects for the Link Control 
                              Protocol of the Point-to-Point Protocol,
                              PPP-LCP-MIB', June 1993.
                [RFC 1661]    Simpson, W., `The Point-to-Point 
                              Protocol', July 1994."

   REVISION    "200409100000Z"  -- September 10, 2004
   DESCRIPTION "Initial release."

::=  { pdn-interfaces 28 }



-- ====================================================================
-- == Define groups for Notifications, MIB Objects, Accessible for   ==
-- == Notifications (AFNs), and Conformance.                         ==
-- == These may just be place holders.                               ==
-- ====================================================================
pdnPppLcpExtNotifications OBJECT IDENTIFIER ::= { pdnPppLcpExtMIB 0 }
pdnPppLcpExtObjects       OBJECT IDENTIFIER ::= { pdnPppLcpExtMIB 1 }
pdnPppLcpExtAFNs          OBJECT IDENTIFIER ::= { pdnPppLcpExtMIB 2 } 
pdnPppLcpExtConformance   OBJECT IDENTIFIER ::= { pdnPppLcpExtMIB 3 }




-- ====================================================================
-- ==                  Textual Conventions                           ==
-- ====================================================================
-- None defined.



-- ====================================================================
-- ==                  MIB Objects                                   ==
-- ====================================================================




-- ====================================================================
-- == pdnPppLinkStatusExtTable                                       ==
-- ====================================================================
pdnPppLinkStatusExtTable  OBJECT-TYPE
   SYNTAX      SEQUENCE OF PdnPppLinkStatusExtEntry
   MAX-ACCESS  not-accessible
   STATUS      current
   DESCRIPTION "Extensions to the PPP LCP Link Status Table, 
                pppLinkStatusTable.  Counters in this group contain
                `total' counts which are marked from the time the
                system was last re-initialized."
   ::= { pdnPppLcpExtObjects 1 }

pdnPppLinkStatusExtEntry  OBJECT-TYPE
   SYNTAX      PdnPppLinkStatusExtEntry
   MAX-ACCESS  not-accessible
   STATUS      current
   DESCRIPTION "An entry in the PPP LCP Link Status Table."
   AUGMENTS    { pppLinkStatusEntry }
   ::= { pdnPppLinkStatusExtTable 1 }

PdnPppLinkStatusExtEntry ::=
   SEQUENCE {
      pdnPppLinkStatusCurrState                       PdnPPPState,
      pdnPppLinkStatusEstablishFailedReason           DisplayString,
      pdnPppLinkStatusLocalToRemoteMagicNumber        Unsigned32,
      pdnPppLinkStatusRemoteToLocalMagicNumber        Unsigned32,
      pdnPppLinkStatusTotalSentConfigRequests         Counter32,
      pdnPppLinkStatusTotalReceivedConfigRequests     Counter32,
      pdnPppLinkStatusTotalSentConfigAcks             Counter32,
      pdnPppLinkStatusTotalReceivedConfigAcks         Counter32,
      pdnPppLinkStatusTotalSentConfigNaks             Counter32,
      pdnPppLinkStatusTotalReceivedConfigNaks         Counter32,
      pdnPppLinkStatusTotalSentConfigRejects          Counter32,
      pdnPppLinkStatusTotalReceivedConfigRejects      Counter32,
      pdnPppLinkStatusTotalSentTerminateRequests      Counter32,
      pdnPppLinkStatusTotalReceivedTerminateRequests  Counter32,
      pdnPppLinkStatusTotalSentTerminateAcks          Counter32,
      pdnPppLinkStatusTotalReceivedTerminateAcks      Counter32,
      pdnPppLinkStatusTotalSentCodeRejects            Counter32,
      pdnPppLinkStatusTotalReceivedCodeRejects        Counter32,
      pdnPppLinkStatusTotalSentProtocolRejects        Counter32,
      pdnPppLinkStatusTotalReceivedProtocolRejects    Counter32,
      pdnPppLinkStatusTotalSentEchoRequests           Counter32,
      pdnPppLinkStatusTotalReceivedEchoRequests       Counter32,
      pdnPppLinkStatusTotalSentEchoReplies            Counter32,
      pdnPppLinkStatusTotalReceivedEchoReplies        Counter32,
      pdnPppLinkStatusTotalSentDiscardRequests        Counter32,
      pdnPppLinkStatusTotalReceivedDiscardRequests    Counter32,
      pdnPppLinkStatusTotalSentKeepAlives             Counter32,
      pdnPppLinkStatusTotalReceivedKeepAlives         Counter32,
      pdnPppLinkStatusTotalEchoRequestsTimeOuts       Counter32,
      pdnPppLinkStatusTotalEchoRequestsBadData        Counter32,
      pdnPppLinkStatusTotalEchoRequestsPassed         Counter32,
      pdnPppLinkStatusTotalKeepAlivesLost             Counter32,
      pdnPppLinkStatusTotalTerminates                 Counter32
   }

pdnPppLinkStatusCurrState OBJECT-TYPE
   SYNTAX      PdnPPPState
   MAX-ACCESS  read-only
   STATUS      current
   DESCRIPTION "The current state of the LCP State Machine."
   REFERENCE   "RFC 1661, Section 4.2, `State Transition Table'."
   ::= { pdnPppLinkStatusExtEntry 1 }

pdnPppLinkStatusEstablishFailedReason OBJECT-TYPE
   SYNTAX      DisplayString
   MAX-ACCESS  read-only
   STATUS      current
   DESCRIPTION "Indicates why the PPP link failed to establish 
                a connection to the Network-Layer Protocol
                phase.  If the link was successfully established,
                a zero-length string will be returned. Otherwise,
                a string will be returned indicating why the LCP
                could not establish the phase."
   REFERENCE   "RFC 1661, Section 4.2, `State Transition Table'."
   ::= { pdnPppLinkStatusExtEntry 2 }

pdnPppLinkStatusLocalToRemoteMagicNumber  OBJECT-TYPE
   SYNTAX      Unsigned32
   MAX-ACCESS  read-only
   STATUS      current
   DESCRIPTION "The Magic-Number negotiated for packets in the local 
                to remote direction."
   REFERENCE    "RFC 1661, Section 6.4, `Magic-Number'."
   ::= { pdnPppLinkStatusExtEntry 3 }

pdnPppLinkStatusRemoteToLocalMagicNumber  OBJECT-TYPE
   SYNTAX      Unsigned32
   MAX-ACCESS  read-only
   STATUS      current
   DESCRIPTION "The Magic-Number negotiated for packets in the remote 
                to local direction."
   REFERENCE    "RFC 1661, Section 6.4, `Magic-Number'."
   ::= { pdnPppLinkStatusExtEntry 4 }

pdnPppLinkStatusTotalSentConfigRequests  OBJECT-TYPE
   SYNTAX      Counter32
   MAX-ACCESS  read-only
   STATUS      current
   DESCRIPTION "The number of Configure-Requests packets sent on this 
                link."
   REFERENCE    "RFC 1661, Section 5.1, `Configure-Request'."
   ::= { pdnPppLinkStatusExtEntry 5 }

pdnPppLinkStatusTotalReceivedConfigRequests  OBJECT-TYPE
   SYNTAX      Counter32
   MAX-ACCESS  read-only
   STATUS      current
   DESCRIPTION "The number of Configure-Requests packets received on 
                this link."
   REFERENCE    "RFC 1661, Section 5.1, `Configure-Request'."
   ::= { pdnPppLinkStatusExtEntry 6 }

pdnPppLinkStatusTotalSentConfigAcks  OBJECT-TYPE
   SYNTAX      Counter32
   MAX-ACCESS  read-only
   STATUS      current
   DESCRIPTION "The number of Configure-Ack packets sent on this 
                link."
   REFERENCE    "RFC 1661, Section 5.2, `Configure-Ack'."
   ::= { pdnPppLinkStatusExtEntry 7 }

pdnPppLinkStatusTotalReceivedConfigAcks  OBJECT-TYPE
   SYNTAX      Counter32
   MAX-ACCESS  read-only
   STATUS      current
   DESCRIPTION "The number of Configure-Ack packets received on this 
                link."
   REFERENCE    "RFC 1661, Section 5.2, `Configure-Ack'."
   ::= { pdnPppLinkStatusExtEntry 8 }

pdnPppLinkStatusTotalSentConfigNaks  OBJECT-TYPE
   SYNTAX      Counter32
   MAX-ACCESS  read-only
   STATUS      current
   DESCRIPTION "The number of Configure-Nak packets sent on this 
                link."
   REFERENCE    "RFC 1661, Section 5.3, `Configure-Nak'."
   ::= { pdnPppLinkStatusExtEntry 9 }

pdnPppLinkStatusTotalReceivedConfigNaks  OBJECT-TYPE
   SYNTAX      Counter32
   MAX-ACCESS  read-only
   STATUS      current
   DESCRIPTION "The number of Configure-Nak packets received on this 
                link."
   REFERENCE    "RFC 1661, Section 5.3, `Configure-Nak'."
   ::= { pdnPppLinkStatusExtEntry 10 }

pdnPppLinkStatusTotalSentConfigRejects  OBJECT-TYPE
   SYNTAX      Counter32
   MAX-ACCESS  read-only
   STATUS      current
   DESCRIPTION "The number of Configure-Reject packets sent on this 
                link."
   REFERENCE    "RFC 1661, Section 5.4, `Configure-Reject'."
   ::= { pdnPppLinkStatusExtEntry 11 }

pdnPppLinkStatusTotalReceivedConfigRejects  OBJECT-TYPE
   SYNTAX      Counter32
   MAX-ACCESS  read-only
   STATUS      current
   DESCRIPTION "The number of Configure-Reject packets received on 
                this link."
   REFERENCE    "RFC 1661, Section 5.4, `Configure-Reject'."
   ::= { pdnPppLinkStatusExtEntry 12 }

pdnPppLinkStatusTotalSentTerminateRequests  OBJECT-TYPE
   SYNTAX      Counter32
   MAX-ACCESS  read-only
   STATUS      current
   DESCRIPTION "The number of Terminate-Request packets sent on this 
                link."
   REFERENCE    "RFC 1661, Section 5.5, `Terminate-Request and
                 Terminate-Ack'."
   ::= { pdnPppLinkStatusExtEntry 13 }

pdnPppLinkStatusTotalReceivedTerminateRequests  OBJECT-TYPE
   SYNTAX      Counter32
   MAX-ACCESS  read-only
   STATUS      current
   DESCRIPTION "The number of Terminate-Request packets received on 
                this link."
   REFERENCE    "RFC 1661, Section 5.5, `Terminate-Request and
                 Terminate-Ack'."
   ::= { pdnPppLinkStatusExtEntry 14 }

pdnPppLinkStatusTotalSentTerminateAcks  OBJECT-TYPE
   SYNTAX      Counter32
   MAX-ACCESS  read-only
   STATUS      current
   DESCRIPTION "The number of Terminate-Ack packets sent on this 
                link."
   REFERENCE    "RFC 1661, Section 5.5, `Terminate-Request and
                 Terminate-Ack'."   
   ::= { pdnPppLinkStatusExtEntry 15 }

pdnPppLinkStatusTotalReceivedTerminateAcks  OBJECT-TYPE
   SYNTAX      Counter32
   MAX-ACCESS  read-only
   STATUS      current
   DESCRIPTION "The number of Terminate-Ack packets received on this 
                link."
   REFERENCE    "RFC 1661, Section 5.5, `Terminate-Request and
                 Terminate-Ack'."
   ::= { pdnPppLinkStatusExtEntry 16 }

pdnPppLinkStatusTotalSentCodeRejects  OBJECT-TYPE
   SYNTAX      Counter32
   MAX-ACCESS  read-only
   STATUS      current
   DESCRIPTION "The number of Code-Reject packets sent on this 
                link."
   REFERENCE    "RFC 1661, Section 5.6, `Code-Reject'."
   ::= { pdnPppLinkStatusExtEntry 17 }

pdnPppLinkStatusTotalReceivedCodeRejects  OBJECT-TYPE
   SYNTAX      Counter32
   MAX-ACCESS  read-only
   STATUS      current
   DESCRIPTION "The number of Code-Reject packets received on this 
                link."
   REFERENCE    "RFC 1661, Section 5.6, `Code-Reject'."
   ::= { pdnPppLinkStatusExtEntry 18 }

pdnPppLinkStatusTotalSentProtocolRejects  OBJECT-TYPE
   SYNTAX      Counter32
   MAX-ACCESS  read-only
   STATUS      current
   DESCRIPTION "The number of Protocol-Reject packets sent on this 
                link."
   REFERENCE    "RFC 1661, Section 5.7, `Protocol-Reject'."
   ::= { pdnPppLinkStatusExtEntry 19 }

pdnPppLinkStatusTotalReceivedProtocolRejects  OBJECT-TYPE
   SYNTAX      Counter32
   MAX-ACCESS  read-only
   STATUS      current
   DESCRIPTION "The number of Protocol-Reject packets received on this 
                link."
   REFERENCE    "RFC 1661, Section 5.7, `Protocol-Reject'."
   ::= { pdnPppLinkStatusExtEntry 20 }

pdnPppLinkStatusTotalSentEchoRequests  OBJECT-TYPE
   SYNTAX      Counter32
   MAX-ACCESS  read-only
   STATUS      current
   DESCRIPTION "The number of Echo-Request packets sent on this 
                link."
   REFERENCE    "RFC 1661, Section 5.8, `Echo-Request and
                 Echo-Reply'."
   ::= { pdnPppLinkStatusExtEntry 21 }

pdnPppLinkStatusTotalReceivedEchoRequests  OBJECT-TYPE
   SYNTAX      Counter32
   MAX-ACCESS  read-only
   STATUS      current
   DESCRIPTION "The number of Echo-Request packets received on this 
                link."
   REFERENCE    "RFC 1661, Section 5.8, `Echo-Request and
                 Echo-Reply'."
   ::= { pdnPppLinkStatusExtEntry 22 }

pdnPppLinkStatusTotalSentEchoReplies  OBJECT-TYPE
   SYNTAX      Counter32
   MAX-ACCESS  read-only
   STATUS      current
   DESCRIPTION "The number of Echo-Reply packets sent on this 
                link."
   REFERENCE    "RFC 1661, Section 5.8, `Echo-Request and
                 Echo-Reply'."
   ::= { pdnPppLinkStatusExtEntry 23 }

pdnPppLinkStatusTotalReceivedEchoReplies  OBJECT-TYPE
   SYNTAX      Counter32
   MAX-ACCESS  read-only
   STATUS      current
   DESCRIPTION "The number of Echo-Reply packets received on this 
                link."
   REFERENCE    "RFC 1661, Section 5.8, `Echo-Request and
                 Echo-Reply'."
   ::= { pdnPppLinkStatusExtEntry 24 }

pdnPppLinkStatusTotalSentDiscardRequests  OBJECT-TYPE
   SYNTAX      Counter32
   MAX-ACCESS  read-only
   STATUS      current
   DESCRIPTION "The number of Discard-Request packets sent on this 
                link."
   REFERENCE    "RFC 1661, Section 5.8, `Discard-Request'."
   ::= { pdnPppLinkStatusExtEntry 25 }

pdnPppLinkStatusTotalReceivedDiscardRequests  OBJECT-TYPE
   SYNTAX      Counter32
   MAX-ACCESS  read-only
   STATUS      current
   DESCRIPTION "The number of Discard-Request packets received on this
                link."
   REFERENCE    "RFC 1661, Section 5.8, `Discard-Request'."
   ::= { pdnPppLinkStatusExtEntry 26 }

pdnPppLinkStatusTotalSentKeepAlives OBJECT-TYPE
   SYNTAX      Counter32
   MAX-ACCESS  read-only
   STATUS      current
   DESCRIPTION "The number of automatically generated Echo-Request 
                packets sent on this link as a `Keep Alive' mechanism."
   REFERENCE    "RFC 1661, Section 5.8, `Echo-Request and
                 Echo-Reply'."
   ::= { pdnPppLinkStatusExtEntry 27 }

pdnPppLinkStatusTotalReceivedKeepAlives OBJECT-TYPE
   SYNTAX      Counter32
   MAX-ACCESS  read-only
   STATUS      current
   DESCRIPTION "The number of Echo-Request packets received on this 
                link as a `Keep Alive' mechanism."
   REFERENCE    "RFC 1661, Section 5.8, `Echo-Request and
                 Echo-Reply'."
   ::= { pdnPppLinkStatusExtEntry 28 }

pdnPppLinkStatusTotalEchoRequestsTimeOuts  OBJECT-TYPE
   SYNTAX      Counter32
   MAX-ACCESS  read-only
   STATUS      current
   DESCRIPTION "The number of Echo-Request packets that have been sent,
                but no Echo-Reply packet was received."
   ::= { pdnPppLinkStatusExtEntry 29 }

pdnPppLinkStatusTotalEchoRequestsBadData  OBJECT-TYPE
   SYNTAX      Counter32
   MAX-ACCESS  read-only
   STATUS      current
   DESCRIPTION "The number of Echo-Request packets that have been 
                received, but the data field in the packet received 
                did not match the data in the packet sent."
   ::= { pdnPppLinkStatusExtEntry 30 }

pdnPppLinkStatusTotalEchoRequestsPassed  OBJECT-TYPE
   SYNTAX      Counter32
   MAX-ACCESS  read-only
   STATUS      current
   DESCRIPTION "The number of Echo-Request packets that have been 
                received and the data field in the packet received 
                matched the data in the packet sent."
   ::= { pdnPppLinkStatusExtEntry 31 }

pdnPppLinkStatusTotalKeepAlivesLost  OBJECT-TYPE
   SYNTAX      Counter32
   MAX-ACCESS  read-only
   STATUS      current
   DESCRIPTION "The number of Echo-Request packets that have been sent
                as a `Keep Alive' mechanism which have not been
                replied and are considered 'lost'."
   ::= { pdnPppLinkStatusExtEntry 32 }

pdnPppLinkStatusTotalTerminates  OBJECT-TYPE
   SYNTAX      Counter32
   MAX-ACCESS  read-only
   STATUS      current
   DESCRIPTION "The number of times the link was terminated where
                user traffic could not be sent."
   ::= { pdnPppLinkStatusExtEntry 33 }



-- ====================================================================
-- == pdnPppLinkConfigExtTable                                       ==
-- ====================================================================
pdnPppLinkConfigExtTable  OBJECT-TYPE
   SYNTAX      SEQUENCE OF PdnPppLcpLinkConfigExtEntry
   MAX-ACCESS  not-accessible
   STATUS      current
   DESCRIPTION "Extensions to the PPP LCP Link Configuration Table, 
                pppLinkconfigTable."
   ::= { pdnPppLcpExtObjects 2 }

pdnPppLinkConfigExtEntry  OBJECT-TYPE
   SYNTAX      PdnPppLcpLinkConfigExtEntry
   MAX-ACCESS  not-accessible
   STATUS      current
   DESCRIPTION "An entry in the PPP LCP Link Configuration Table."
   AUGMENTS    { pppLinkConfigEntry }
   ::= { pdnPppLinkConfigExtTable 1 }

PdnPppLcpLinkConfigExtEntry ::=
   SEQUENCE {
      pdnPppLinkConfigPFC                 SwitchState,
      pdnPppLinkConfigACFC                SwitchState,
      pdnPppLinkConfigKeepAliveQuietTime  Unsigned32,
      pdnPppLinkConfigKeepAliveTimeout    Unsigned32
   }

pdnPppLinkConfigPFC  OBJECT-TYPE
   SYNTAX      SwitchState         
   MAX-ACCESS  read-write
   STATUS      current
   DESCRIPTION "Configures whether or not Protocol-Field-Compression
                is desired.

                When set to enabled(1), the local entity will attempt
                to negotiate the compression of the Protocol Field.
 
                When set to disabled(2), the local entity will not
                negotiate compression of the Protocol Field. 

                The result of the negotiation is indicated in the 
                pppLinkStatusLocalToRemoteProtocolCompression and the
                pppLinkStatusRemoteToLocalProtocolCompression objects."
   REFERENCE    "RFC 1661, Section 6.5, `Protocol-Field-Compression'."
   ::= { pdnPppLinkConfigExtEntry 1 }

pdnPppLinkConfigACFC  OBJECT-TYPE
   SYNTAX      SwitchState       
   MAX-ACCESS  read-write
   STATUS      current
   DESCRIPTION "Configures whether or not Data Link Layer Address and
                Control fields compression is desired.

                When set to enabled(1), the local entity will attempt
                to negotiate the compression of the fields.

                When set to disabled(2), the local entity will not
                negotiate compression of the fields.

                The result of the negotiation is indicated in the 
                pppLinkStatusLocalToRemoteACCompression and the
                pppLinkStatusRemoteToLocalACCompression objects."
   REFERENCE    "RFC 1661, Section 6.6, 
                 `Address-and-Control-Field-Compression'."
   ::= { pdnPppLinkConfigExtEntry 2 }

pdnPppLinkConfigKeepAliveQuietTime  OBJECT-TYPE
   SYNTAX      Unsigned32(0..3600)
   UNITS       "seconds"        
   MAX-ACCESS  read-write
   STATUS      current
   DESCRIPTION "If no PPP packets are received for this amount of 
                time, the local PPP entity will send an Echo-Request
                as a `Keep Alive' mechanism to make sure the link
                is still active.  A value of 0 indicates that the
                `Keep Alive' mechanism is disabled.  The largest
                `quit time` as supported by the syntax is an hour."
   REFERENCE   "RFC 1661, Section 5.8, `Echo-Request and Echo-Reply'."
   ::= { pdnPppLinkConfigExtEntry 3 }

pdnPppLinkConfigKeepAliveTimeout  OBJECT-TYPE
   SYNTAX      Unsigned32(1..300)   
   UNITS       "seconds"        
   MAX-ACCESS  read-write
   STATUS      current
   DESCRIPTION "The maximum amount of time to wait for an Echo-Reply 
                in response to an Echo-Request sent as a `Keep Alive' 
                mechanism.  When this time has exceeded, the link will
                be terminated and will attempt to reestablish a
                connection with its remote peer. The maximum amount of 
                time to wait as supported by the syntax is 5 minutes." 
   REFERENCE   "RFC 1661, Section 5.8, `Echo-Request and Echo-Reply'."
   ::= { pdnPppLinkConfigExtEntry 4 }


-- =====================================================================
-- == pdnPppLinkTestTable                                             ==
-- =====================================================================
pdnPppLinkTestTable  OBJECT-TYPE
   SYNTAX      SEQUENCE OF PdnPppLinkTestExtEntry
   MAX-ACCESS  not-accessible
   STATUS      current
   DESCRIPTION "A table to support the testing of a PPP link."
   ::= { pdnPppLcpExtObjects 3 }

pdnPppLinkTestEntry  OBJECT-TYPE
   SYNTAX      PdnPppLinkTestExtEntry
   MAX-ACCESS  not-accessible
   STATUS      current
   DESCRIPTION "An entry in the PPP LCP Link Test Table."
   INDEX       { ifIndex }
   ::= { pdnPppLinkTestTable 1 }

PdnPppLinkTestExtEntry ::=
   SEQUENCE {
      pdnPppLinkTestSendEchoTest           INTEGER,
      pdnPppLinkTestEchoTestTimeout        Unsigned32,
      pdnPppLinkTestSendDiscardTest        INTEGER,
      pdnPppLinkTestLastEchoTestResults    INTEGER
   }

pdnPppLinkTestSendEchoTest  OBJECT-TYPE
   SYNTAX      INTEGER {
                  noOp(1),
                  runTest(2)                
               }                    
   MAX-ACCESS  read-write
   STATUS      current
   DESCRIPTION "Controls the initiation of a PPP Echo-Request to the
                remote PPP entity.  The agent fills in the data to
                be echoed.  The value read from this object is 
                noOp(1).  If an Echo Test is in progress and this
                object is set to noOp(1),the test will be aborted
                and the result object below will be set to none(1)."
   REFERENCE   "RFC 1661, Section 5.8, `Echo-Request and Echo-Reply'."
   ::= { pdnPppLinkTestEntry 1 }

pdnPppLinkTestEchoTestTimeout  OBJECT-TYPE
   SYNTAX      Unsigned32(1..300)   
   UNITS       "seconds"        
   MAX-ACCESS  read-write
   STATUS      current
   DESCRIPTION "The maximum amount of time to wait for an Echo-Reply 
                in response to an Echo-Request.  If an Echo-Reply
                is not seen in the amount of time specified, the test
                will be considered `timed-out'.  The maximum amount 
                of time to wait as supported by the syntax is 
                5 minutes."
   REFERENCE   "RFC 1661, Section 5.8, `Echo-Request and Echo-Reply'."
   ::= { pdnPppLinkTestEntry 2 }

pdnPppLinkTestSendDiscardTest  OBJECT-TYPE
   SYNTAX      INTEGER {
                   noOp(1),
                   sendDiscard(2)                
               }                    
   MAX-ACCESS  read-write
   STATUS      current
   DESCRIPTION "Controls the initiation of a PPP Discard-Request to 
                the remote PPP entity.  The value read from this 
                object is noOp(1)."
   REFERENCE   "RFC 1661, Section 5.9, `Discard-Request'."
   ::= { pdnPppLinkTestEntry 3 }

pdnPppLinkTestLastEchoTestResults  OBJECT-TYPE
   SYNTAX      INTEGER {
                  none(1),
                  inProgress(2),
                  success(3),
                  timedOut(4),
                  compareFailed(5)
               }                    
   MAX-ACCESS  read-only
   STATUS      current
   DESCRIPTION "Displays the results of the last Echo Test.  A value 
                of none(1) will be returned if no Echo Tests have
                been performed.  If an Echo Test is currently being
                performed and neither a Echo Reply was received nor
                the Echo Timeout Period has been satisfied, 
                inProgress(2) will be read.  If the last Echo Test 
                received a Echo Reply and the echo data received 
                matched that which was sent, a success(3) will be 
                returned.  If an Echo Test was initiated and no Echo
                Reply was received within the Echo Timeout Period, 
                a timedOut(4) will be read.  If the Echo Reply was 
                returned, but the data received did not match the
                data that was sent, a compareFailed(5) will be read."
   REFERENCE   "RFC 1661, Section 5.8, `Echo-Request and Echo-Reply'."
   ::= { pdnPppLinkTestEntry 4 }



-- =====================================================================
-- ==                  Accessible for Notifications (AFNs)            ==
-- =====================================================================
-- None defined



-- =====================================================================
-- ==                  Traps/Notifications                            ==
-- =====================================================================
-- None defined



-- =====================================================================
-- ==                  Conformance Information                        ==
-- =====================================================================

pdnPppLcpExtCompliances  OBJECT IDENTIFIER ::= 
   { pdnPppLcpExtConformance 1 }
pdnPppLcpExtGroups       OBJECT IDENTIFIER ::= 
   { pdnPppLcpExtConformance 2 }


-- ===========================
-- == Compliance Statements ==
-- ===========================


pdnPppLcpExtCompliance  MODULE-COMPLIANCE
   STATUS      current
   DESCRIPTION "The compliance statement for network elements 
                implementing PPP Link Control Protocol."
   MODULE      -- this module
   -- No mandatory groups are specified.  PPP LCP can be implemented
   -- with only objects defined in the PPP-LCP-MIB.  However, this MIB
   -- module specifies optional objects to enhance a PPP LCP 
   -- implementation.

   GROUP       pdnPppLcpExtStateMachineGroup
   DESCRIPTION "This group is only required for implementations that
                need to display the LCP State Machine's state."

   GROUP       pdnPppLcpExtEstablishFailedGroup
   DESCRIPTION "This group is only required for implementations that
                need to display the reason the LCP establishment
                failed."

   GROUP       pdnPppLcpExtMagicNumberGroup
   DESCRIPTION "This group is only required for implementations that
                need to display the Magic Number that has been 
                negotiated for a particular direction."

   GROUP       pdnPppLcpExtPacketCountersGroup
   DESCRIPTION "This group is only required for implementations that
                need to display counters for LCP packets."

   GROUP       pdnPppLcpExtKeepAliveCountersGroup
   DESCRIPTION "This group is only required for implementations that
                 need to display counters for `Keep Alive' packets."

   GROUP       pdnPppLcpExtPFCGroup
   DESCRIPTION "This group is only required for implementations that
                need to configure Protocol-Field-Compression."

   GROUP       pdnPppLcpExtACFCGroup
   DESCRIPTION "This group is only required for implementations that
                need to configure Data Link Layer Address and Control
                field compression."

   GROUP       pdnPppLcpExtKeepAliveConfGroup
   DESCRIPTION "This group is only required for implementations that
                need to configure Keep Alive parameters."

   GROUP       pdnPppLcpExtEchoTestGroup
   DESCRIPTION "This group is only required for implementations that
                need to allow an Echo Test to be performed."

   GROUP       pdnPpppLcpExtDiscardTestGroup
   DESCRIPTION "This group is only required for implementations that
                need to allow a Discard Test to be performed."

   GROUP       pdnPpppLcpExtLinkStateCounterGroup
   DESCRIPTION "This group is only required for implementations that
                need to count state machine states."

   ::= { pdnPppLcpExtCompliances 1 }


-- ==========================
-- == Units of Conformance ==
-- ==========================

pdnPppLcpExtObjGroups   OBJECT IDENTIFIER ::= { pdnPppLcpExtGroups 1 }
pdnPppLcpExtAfnGroups   OBJECT IDENTIFIER ::= { pdnPppLcpExtGroups 2 }
pdnPppLcpExtNtfyGroups  OBJECT IDENTIFIER ::= { pdnPppLcpExtGroups 3 }


-- ===================
-- == Object Groups ==
-- ===================


pdnPppLcpExtStateMachineGroup OBJECT-GROUP
   OBJECTS {
      pdnPppLinkStatusCurrState
   }
   STATUS      current
   DESCRIPTION "Displays LCP State Machine's state."
   ::= { pdnPppLcpExtObjGroups 1 }

pdnPppLcpExtEstablishFailedGroup OBJECT-GROUP
   OBJECTS {
      pdnPppLinkStatusEstablishFailedReason
   }
   STATUS      current
   DESCRIPTION "Displays the reason the last link establishment 
                failed."
   ::= { pdnPppLcpExtObjGroups 2 }

pdnPppLcpExtMagicNumberGroup OBJECT-GROUP
   OBJECTS {
      pdnPppLinkStatusLocalToRemoteMagicNumber,
      pdnPppLinkStatusRemoteToLocalMagicNumber
   }
   STATUS      current
   DESCRIPTION "Displays the Magic Number negotiated."
   ::= { pdnPppLcpExtObjGroups 3 }

pdnPppLcpExtPacketCountersGroup OBJECT-GROUP
   OBJECTS {
      pdnPppLinkStatusTotalSentConfigRequests,
      pdnPppLinkStatusTotalReceivedConfigRequests,
      pdnPppLinkStatusTotalSentConfigAcks,
      pdnPppLinkStatusTotalReceivedConfigAcks,
      pdnPppLinkStatusTotalSentConfigNaks,
      pdnPppLinkStatusTotalReceivedConfigNaks,
      pdnPppLinkStatusTotalSentConfigRejects,
      pdnPppLinkStatusTotalReceivedConfigRejects,
      pdnPppLinkStatusTotalSentTerminateRequests,
      pdnPppLinkStatusTotalReceivedTerminateRequests,
      pdnPppLinkStatusTotalSentTerminateAcks,
      pdnPppLinkStatusTotalReceivedTerminateAcks,
      pdnPppLinkStatusTotalSentCodeRejects,
      pdnPppLinkStatusTotalReceivedCodeRejects,
      pdnPppLinkStatusTotalSentProtocolRejects,
      pdnPppLinkStatusTotalReceivedProtocolRejects,
      pdnPppLinkStatusTotalSentEchoRequests,
      pdnPppLinkStatusTotalReceivedEchoRequests,
      pdnPppLinkStatusTotalSentEchoReplies,
      pdnPppLinkStatusTotalReceivedEchoReplies,
      pdnPppLinkStatusTotalSentDiscardRequests,
      pdnPppLinkStatusTotalReceivedDiscardRequests      
   }
   STATUS      current
   DESCRIPTION "Counters for various PPP LCP packets."
   ::= { pdnPppLcpExtObjGroups 4 }

pdnPppLcpExtKeepAliveCountersGroup OBJECT-GROUP
   OBJECTS {
      pdnPppLinkStatusTotalSentKeepAlives,
      pdnPppLinkStatusTotalReceivedKeepAlives,
      pdnPppLinkStatusTotalKeepAlivesLost
   }
   STATUS      current
   DESCRIPTION "Counters relative to `Keep Alive'."
   ::= { pdnPppLcpExtObjGroups 5 }

pdnPppLcpExtPFCGroup OBJECT-GROUP
   OBJECTS {
      pdnPppLinkConfigPFC
   }
   STATUS      current
   DESCRIPTION "Configuration for Protocol-Field Compression."
   ::= { pdnPppLcpExtObjGroups 6 }

pdnPppLcpExtACFCGroup OBJECT-GROUP
   OBJECTS {
      pdnPppLinkConfigACFC
   }
   STATUS      current
   DESCRIPTION "Configuration for Data Link Layer Address and Control
                field compression."
   ::= { pdnPppLcpExtObjGroups 7 }

pdnPppLcpExtKeepAliveConfGroup OBJECT-GROUP
   OBJECTS {
        pdnPppLinkConfigKeepAliveQuietTime,
        pdnPppLinkConfigKeepAliveTimeout
   }
   STATUS      current
   DESCRIPTION "Configuration of parameters relative to `Keep Alive'."
   ::= { pdnPppLcpExtObjGroups 8 }

pdnPppLcpExtEchoTestGroup OBJECT-GROUP
   OBJECTS {
      pdnPppLinkTestSendEchoTest,
      pdnPppLinkTestEchoTestTimeout,
      pdnPppLinkTestLastEchoTestResults,
      pdnPppLinkStatusTotalEchoRequestsTimeOuts,
      pdnPppLinkStatusTotalEchoRequestsBadData,
      pdnPppLinkStatusTotalEchoRequestsPassed
   }
   STATUS      current
   DESCRIPTION "Support configuration, initiation, and results of
                an Echo Test."
   ::= { pdnPppLcpExtObjGroups 9 }

pdnPpppLcpExtDiscardTestGroup OBJECT-GROUP
   OBJECTS {
      pdnPppLinkTestSendDiscardTest
   }
   STATUS      current
   DESCRIPTION "Supports the initiation of a Discard Test."
   ::= { pdnPppLcpExtObjGroups 10 }

pdnPpppLcpExtLinkStateCounterGroup OBJECT-GROUP
   OBJECTS {
      pdnPppLinkStatusTotalTerminates
   }
   STATUS      current
   DESCRIPTION "Counters relative to the link state."
   ::= { pdnPppLcpExtObjGroups 11 }




-- =========================================
-- == Accessible for Notifications Groups ==
-- =========================================
-- None defined



-- =========================
-- == Notification Groups ==
-- =========================
-- None defined




-- =========
-- == END ==
-- =========
END

-- ===================================================================
-- == Copyright (C) 2004 Paradyne Corporation.                      ==
-- ===================================================================

PDN-PPP-BRIDGE-NCP-EXT-MIB DEFINITIONS ::= BEGIN

IMPORTS
   MODULE-IDENTITY, OBJECT-TYPE
      FROM SNMPv2-SMI
   OBJECT-GROUP, MODULE-COMPLIANCE
      FROM SNMPv2-CONF
   pppBridgeEntry, pppBridgeMediaConfigEntry
      FROM PPP-BRIDGE-NCP-MIB
   SwitchState, PdnPPPState
      FROM PDN-TC
   pdn-interfaces
      FROM PDN-HEADER-MIB;
        
pdnPppBridgeExtMIB MODULE-IDENTITY
   LAST-UPDATED "200409100000Z"  -- September 10, 2004
   ORGANIZATION "Paradyne Networks
                 MIB Working Group
                 Other information about group editing the MIB"
   CONTACT-INFO "Paradyne Networks, Inc.
                 8545 126th Avenue North
                 Largo, FL 33733
                 www.paradyne.com
        
                 General Comments to: mibwg_team@paradyne.com

                 Editor
                    Clay Sikes"

   DESCRIPTION  "The MIB module provides enterprise-specific extensions
                 to the PPP-BRIDGE-MIB for managing the Bridge Control
                 Protocol (BCP) on subnetwork interfaces that use the 
                 family of point-to-Point Protocols (PPP).  BCP is a 
                 member of the Network Control Protocol suite of 
                 point-to-point protocols.

                 The following documents should be referenced with 
                 respect to this MIB module:
                 [RFC 1474]    Kastenholz, F., `The Definitions of 
                               Managed Objects for the Bridge Network 
                               Control Protocol of the Point-to-Point 
                               Protocol', June 1993.
                 [RFC 1661]    Simpson, W., `The Point-to-Point 
                               Protocol', July 1994.
                 [RFC 3518]    Higashiyama, M., Baker, F., and Liao, T.,
                               `Point-to-Point Protocol (PPP) Bridging 
                               Control Protocol (BCP)', April 2003."

   REVISION     "200409100000Z"  -- September 10, 2004
   DESCRIPTION  "Initial release."

::=  { pdn-interfaces 29 }



-- ====================================================================
-- == Define groups for Notifications, MIB Objects, Accessible for   ==
-- == Notifications (AFNs), and Conformance.                         ==
-- == These may just be place holders.                               ==
-- ====================================================================
pdnPppBridgeExtNotifications OBJECT IDENTIFIER ::= 
   { pdnPppBridgeExtMIB 0 }
pdnPppBridgeExtObjects       OBJECT IDENTIFIER ::= 
   { pdnPppBridgeExtMIB 1 }
pdnPppBridgeExtAFNs          OBJECT IDENTIFIER ::= 
   { pdnPppBridgeExtMIB 2 } 
pdnPppBridgeExtConformance   OBJECT IDENTIFIER ::= 
   { pdnPppBridgeExtMIB 3 }




-- ====================================================================
-- ==                  Textual Conventions                           ==
-- ====================================================================
-- None defined.



-- ====================================================================
-- ==                  MIB Objects                                   ==
-- ====================================================================




-- ===================================================================
-- == pdnPppBridgeExtTable                                          ==
-- ===================================================================
pdnPppBridgeExtTable  OBJECT-TYPE
   SYNTAX      SEQUENCE OF PdnPppBridgeExtEntry
   MAX-ACCESS  not-accessible
   STATUS      current
   DESCRIPTION "An entry in the PPP Bridge Table, pppBridgeTable.
                The PPP Bridge Table contains parameters and 
                statistics for the local PPP entity."
   ::= { pdnPppBridgeExtObjects 1 }

pdnPppBridgeExtEntry  OBJECT-TYPE
   SYNTAX      PdnPppBridgeExtEntry
   MAX-ACCESS  not-accessible
   STATUS      current
   DESCRIPTION "An entry in the Multilink PPP Configuration Table."
   AUGMENTS    { pppBridgeEntry }
   ::= { pdnPppBridgeExtTable 1 }

PdnPppBridgeExtEntry ::=
   SEQUENCE {
      pdnPppBridgeBcpLinkStatusCurrState     PdnPPPState,
      pdnPppBridgeLocalToRemote802Tagged     SwitchState,
      pdnPppBridgeRemoteToLocal802Tagged     SwitchState        
   }

pdnPppBridgeBcpLinkStatusCurrState OBJECT-TYPE
   SYNTAX      PdnPPPState
   MAX-ACCESS  read-only
   STATUS      current
   DESCRIPTION "The current state of the BCP State Machine."
   REFERENCE   "RFC 1661, Section 4.2, `State Transition Table'."
   ::= { pdnPppBridgeExtEntry 1 }

pdnPppBridgeLocalToRemote802Tagged  OBJECT-TYPE
   SYNTAX      SwitchState
   MAX-ACCESS  read-only
   STATUS      current
   DESCRIPTION "Indicates whether or not the local PPP entity is 
                transmitting IEEE 802 tagged frames.  An enabled(1) 
                indicates that frames will be transmitted 802 tagged.
                A disabled(2) indicate that frames will not be 
                transmitted 802 tagged."
   REFERENCE    "RFC 3518, Section 5.7, `IEEE-802-Tagged-Frame'."
   ::= { pdnPppBridgeExtEntry 2 }

pdnPppBridgeRemoteToLocal802Tagged  OBJECT-TYPE
   SYNTAX      SwitchState
   MAX-ACCESS  read-only
   STATUS      current
   DESCRIPTION "Indicates whether or not the remote PPP entity is 
                transmitting IEEE 802 tagged frames.  An enabled(1) 
                indicates that frames will be transmitted 802 tagged.
                A disabled(2) indicate that frames will not be 
                transmitted 802 tagged."
   REFERENCE    "RFC 3518, Section 5.7, `IEEE-802-Tagged-Frame'."
   ::= { pdnPppBridgeExtEntry 3 }



-- ===================================================================
-- == pdnPppBridgeMediaConfigExtTable                               ==
-- ===================================================================
pdnPppBridgeMediaConfigExtTable  OBJECT-TYPE
   SYNTAX      SEQUENCE OF PdnPppBridgeMediaConfigExtEntry
   MAX-ACCESS  not-accessible
   STATUS      current
   DESCRIPTION "An entry in the PPP Bridge Media Configuration Table,
                pppBridgeTable.  The PPP Bridge Media Configuration 
                Table contains objects relative to MAC media types."
   ::= { pdnPppBridgeExtObjects 2 }

pdnPppBridgeMediaConfigExtEntry  OBJECT-TYPE
   SYNTAX      PdnPppBridgeMediaConfigExtEntry
   MAX-ACCESS  not-accessible
   STATUS      current
   DESCRIPTION "An entry in the Multilink PPP Media Configuration 
                Table."
   AUGMENTS    { pppBridgeMediaConfigEntry }
   ::= { pdnPppBridgeMediaConfigExtTable 1 }

PdnPppBridgeMediaConfigExtEntry ::=
   SEQUENCE {
      pdnPppBridgeMediaIeee802Tagged     SwitchState
   }

pdnPppBridgeMediaIeee802Tagged OBJECT-TYPE
   SYNTAX      SwitchState
   MAX-ACCESS  read-write
   STATUS      current
   DESCRIPTION "Configures whether or not the local PPP entity will
                attempt to negotiate the IEEE-802-Tagged Frame option.
                An enabled(1) will result in the option being 
                supported.  A disabled(2) will result in the options
                not being supported."
   REFERENCE   "RFC 3518, Section 5.7, `IEEE-802-Tagged-Frame'."
   ::= { pdnPppBridgeMediaConfigExtEntry 1 }



-- ====================================================================
-- ==                  Accessible for Notifications (AFNs)           ==
-- ====================================================================
-- None defined



-- ===================================================================
-- ==                  Traps/Notifications                          ==
-- ===================================================================
-- None defined



-- ====================================================================
-- ==                  Conformance Information                       ==
-- ====================================================================

pdnPppBridgeExtCompliances  OBJECT IDENTIFIER ::= 
   { pdnPppBridgeExtConformance 1 }
pdnPppBridgeExtGroups       OBJECT IDENTIFIER ::= 
   { pdnPppBridgeExtConformance 2 }


-- ===========================
-- == Compliance Statements ==
-- ===========================


pdnPppBridgeExtCompliance  MODULE-COMPLIANCE
   STATUS      current
   DESCRIPTION "The compliance statement for network elements 
                implementing PPP Bridging Control Protocol."
   MODULE      -- this module
   -- No mandatory groups are specified.  PPP BRIDGE NCP can be 
   -- implemented with only object defined in 
   -- the PPP-BRIDGE-NCP-MIB.  However, this MIB module specifies
   -- optional objects to enhance a PPP BRIDGE NCP implementation.
   
   GROUP       pdnPppBridgeExtStateMachineGroup
   DESCRIPTION "This group is only required for implementations that
                need to display the BCP State Machine's state."

   GROUP       pdnPppBridgeExt802TaggedGroup
   DESCRIPTION "This group is only required for implementations that
                need to display whether or not IEEE 802 tagged frames
                are being transmitted."

    ::= { pdnPppBridgeExtCompliances 1 }


-- ==========================
-- == Units of Conformance ==
-- ==========================

pdnPppBridgeExtObjGroups   OBJECT IDENTIFIER ::= 
   { pdnPppBridgeExtGroups 1 }
pdnPppBridgeExtAfnGroups   OBJECT IDENTIFIER ::= 
   { pdnPppBridgeExtGroups 2 }
pdnPppBridgeExtNtfyGroups  OBJECT IDENTIFIER ::= 
   { pdnPppBridgeExtGroups 3 }


-- ===================
-- == Object Groups ==
-- ===================


pdnPppBridgeExtStateMachineGroup OBJECT-GROUP
   OBJECTS {
      pdnPppBridgeBcpLinkStatusCurrState
   }
   STATUS      current
   DESCRIPTION "Displays the BCP State Machine's state."
   ::= { pdnPppBridgeExtObjGroups 1 }

pdnPppBridgeExt802TaggedGroup OBJECT-GROUP
   OBJECTS {
       pdnPppBridgeMediaIeee802Tagged,
       pdnPppBridgeLocalToRemote802Tagged,
       pdnPppBridgeRemoteToLocal802Tagged
   }
   STATUS      current
   DESCRIPTION "Displays whether or not IEEE 802 tagged frames
                are being transmitted."
   ::= { pdnPppBridgeExtObjGroups 2 }



-- =========================================
-- == Accessible for Notifications Groups ==
-- =========================================
-- None defined



-- =========================
-- == Notification Groups ==
-- =========================
-- None defined




-- =========
-- == END ==
-- =========
END

-- ===============================================================
-- == Copyright (C) 2004 Paradyne Corporation.                  ==
-- ===============================================================

PDN-PPP-ML-MIB DEFINITIONS ::= BEGIN

IMPORTS
   MODULE-IDENTITY, OBJECT-TYPE, 
   Unsigned32
       FROM SNMPv2-SMI
   OBJECT-GROUP, MODULE-COMPLIANCE
       FROM SNMPv2-CONF
   TEXTUAL-CONVENTION, RowStatus, DisplayString
       FROM SNMPv2-TC
   ifIndex, InterfaceIndex
       FROM IF-MIB
   SwitchState, PdnPPPState
       FROM PDN-TC
   pdn-interfaces
       FROM PDN-HEADER-MIB;
        
pdnPppMlMIB MODULE-IDENTITY
   LAST-UPDATED "200409140000Z"  -- September 14, 2004
   ORGANIZATION "Paradyne Networks
                 MIB Working Group
                 Other information about group editing the MIB"
   CONTACT-INFO "Paradyne Networks, Inc.
                 8545 126th Avenue North
                 Largo, FL 33733
                 www.paradyne.com
        
                 General Comments to: mibwg_team@paradyne.com

                 Editor
                    Clay Sikes"

   DESCRIPTION  "The MIB module for configuring and managing multilink 
                 PPP.

                 The following documents should be referenced with 
                 respect to this MIB:
                 [PPP]         Carlson, J, `PPP Design and Debugging',
                               Addison-Wesley, December 1997.
                 [RFC 1661]    Simpson, W., `The Point-to-Point 
                               Protocol', July 1994.
                 [RFC 1990]    Sklower, K. et al., `The PPP Multilink 
                               Protocol (MP)', August 1996."                 

   REVISION "200409140000Z"  -- September 14, 2004
   DESCRIPTION "Initial release."

::=  { pdn-interfaces 30 }



-- ====================================================================
-- == Define groups for Notifications, MIB Objects, Accessible for   ==
-- == Notifications (AFNs), and Conformance.                         ==
-- == These may just be place holders.                               ==
-- ====================================================================
pdnPppMlNotifications OBJECT IDENTIFIER ::= { pdnPppMlMIB 0 }
pdnPppMlObjects       OBJECT IDENTIFIER ::= { pdnPppMlMIB 1 }
pdnPppMlAFNs          OBJECT IDENTIFIER ::= { pdnPppMlMIB 2 } 
pdnPppMlConformance   OBJECT IDENTIFIER ::= { pdnPppMlMIB 3 }




-- ====================================================================
-- ==                  Textual Conventions                           ==
-- ====================================================================

MRRU ::= TEXTUAL-CONVENTION
   DISPLAY-HINT "d"
   STATUS       current
   DESCRIPTION  "Multilink Maximum Received Reconstructed Units 
                 (MMRU).  The maximum number of octets in the 
                 Information Fields of reassembled packets." 
   REFERENCE    "RFC 1990, Section 5.1.1, `Multilink MRRU LCP Option'."
   SYNTAX       Unsigned32(1..65535)


SSNHF ::= TEXTUAL-CONVENTION
   STATUS       current
   DESCRIPTION  "The Short Sequence Number Header Format value."
   REFERENCE    "RFC 1990, Section 5.1.2, `Short Sequence Number
                 Header Option'."   
   SYNTAX       INTEGER {
                   ssnhfUnknown(1),        -- Unknown
                   ssnhf12BitSeqNbrs(2),   -- 12-bit sequence numbers
                   ssnhf24BitSeqNbrs(3)    -- 24-bit sequence numbers
                }


EDClass ::= TEXTUAL-CONVENTION
   STATUS       current
   DESCRIPTION  "Endpoint Discriminator Option Class."
   REFERENCE    "RFC 1990, Section 5.1.3, `Endpoint Discriminator 
                 Option'."
   SYNTAX       INTEGER {
                   nullClass(0),        -- Default if the option wasn't
                                        -- present in the 
                                        -- Configure-Request.
                   locallyAssigned(1),  -- Deprecated. Exists only for
                                        -- backward compatibility.
                   ipAddr(2),           -- Internet Protocol Address.
                   ieee802(3),          -- IEEE 802.1 Globally
                                        -- assigned MAC Address.
                   pppMagicNbrBlk(4),   -- PPP Magic-Number Block.
                   publicSwNetDirNbr(5) -- Public Switch Network
                                        -- Directory Number.
                }



-- ====================================================================
-- ==                  MIB Objects                                   ==
-- ====================================================================



pdnPppMlBundleNumber   OBJECT-TYPE
   SYNTAX      Unsigned32
   MAX-ACCESS  read-only
   STATUS      current
   DESCRIPTION "The number of multilink PPP bundles configured on 
                this system."
   ::= { pdnPppMlObjects 1 }


-- ====================================================================
-- == pdnPppMlBundleTable                                            ==
-- ====================================================================
pdnPppMlBundleConfigTable  OBJECT-TYPE
   SYNTAX      SEQUENCE OF PdnPppMlBundleConfigEntry
   MAX-ACCESS  not-accessible
   STATUS      current
   DESCRIPTION "The Multilink PPP Bundle Configuration Table."
   ::= { pdnPppMlObjects 2 }

pdnPppMlBundleConfigEntry  OBJECT-TYPE
   SYNTAX      PdnPppMlBundleConfigEntry
   MAX-ACCESS  not-accessible
   STATUS      current
   DESCRIPTION "An entry in the Multilink PPP Configuration Table."
   INDEX       { pdnPppMlBundleIfIndex }
   ::= { pdnPppMlBundleConfigTable 1 }

PdnPppMlBundleConfigEntry ::=
   SEQUENCE {
      pdnPppMlBundleIfIndex            InterfaceIndex,
      pdnPppMlBundleConfigRowStatus    RowStatus,
      pdnPppMlBundleConfigMRRU         MRRU,
      pdnPppMlBundleConfigSSNHF        SwitchState,
      pdnPppMlBundleConfigFragmentSize Unsigned32
   }

pdnPppMlBundleIfIndex  OBJECT-TYPE
   SYNTAX      InterfaceIndex
   MAX-ACCESS  not-accessible
   STATUS      current
   DESCRIPTION "Identifies the interface number assigned to this 
                bundle and is used to identify corresponding rows 
                in the Interfaces MIB."
   ::= { pdnPppMlBundleConfigEntry 1 }

pdnPppMlBundleConfigRowStatus  OBJECT-TYPE
   SYNTAX      RowStatus
   MAX-ACCESS  read-create
   STATUS      current
   DESCRIPTION "Used to create, modify, or delete rows in the table."
   ::= { pdnPppMlBundleConfigEntry 2 }

pdnPppMlBundleConfigMRRU  OBJECT-TYPE
   SYNTAX      MRRU
   UNITS       "Number of octets"
   MAX-ACCESS  read-create
   STATUS      current
   DESCRIPTION "The Multilink Maximum Received Reconstructed Units
                LCP option. This option specifies the maximum number
                of octets in the Information fields of reassembled
                packets."
   REFERENCE    "RFC 1990, Section 5.1.1, `Multilink MRRU LCP Option'."
   ::= { pdnPppMlBundleConfigEntry 3 }

pdnPppMlBundleConfigSSNHF  OBJECT-TYPE
   SYNTAX      SwitchState
   MAX-ACCESS  read-create
   STATUS      current
   DESCRIPTION "The Short Sequence Number Header Format option.
                When set to enabled(1), the local PPP entity will
                indicate to the remote PPP entity that fragments
                with 12-bit sequence numbers are desired.  When set
                to disabled(2), the local PPP entity will indicate to
                the remote PPP entity that fragments with 24-bit
                sequence numbers are desired."
   REFERENCE   "RFC 1990, Section 5.1.2, `Short Sequence Number
                Header Format Option'."
   ::= { pdnPppMlBundleConfigEntry 4 }

pdnPppMlBundleConfigFragmentSize  OBJECT-TYPE
   SYNTAX      Unsigned32(0..4294967296)
   MAX-ACCESS  read-create
   STATUS      current
   DESCRIPTION "Configures the maximum number of octets of data in
                the packet's fragment data field.  The value `0'
                has a special meaning which is to say `fragmentation
                is disabled'."
   REFERENCE   "RFC 1990, Section 3, `Packet Formats'.
                `PPP Design and Debugging', page 121, `Fragmentation 
                and Reassembly'."
   ::= { pdnPppMlBundleConfigEntry 5 }


-- ====================================================================
-- == pdnPppMlBundleMappingTable                                     ==
-- ====================================================================
pdnPppMlBundleMappingTable  OBJECT-TYPE
   SYNTAX      SEQUENCE OF PdnPppMlBundleMappingEntry
   MAX-ACCESS  not-accessible
   STATUS      current
   DESCRIPTION "The Multilink PPP Bundle Mapping Table.
                A table mapping the ifIndex of interfaces to a 
                particular multilink PPP bundle identified by the 
                pdnPppMlBundleIfIndex."
   ::= { pdnPppMlObjects 3 }

pdnPppMlBundleMappingEntry  OBJECT-TYPE
   SYNTAX      PdnPppMlBundleMappingEntry
   MAX-ACCESS  not-accessible
   STATUS      current
   DESCRIPTION "Each row describes one ifIndex to pdnPppMlBundleIfIndex
                mapping."
   INDEX       { ifIndex }
   ::= { pdnPppMlBundleMappingTable 1 }

PdnPppMlBundleMappingEntry ::=
   SEQUENCE {
      pdnPppMlBundleMappingRowStatus       RowStatus,
      pdnPppMlBundleMappingBundleIfIndex   InterfaceIndex
   }

pdnPppMlBundleMappingRowStatus  OBJECT-TYPE
   SYNTAX      RowStatus
   MAX-ACCESS  read-create
   STATUS      current
   DESCRIPTION "Used to create, modify, or delete rows in the table."
   ::= { pdnPppMlBundleMappingEntry 1 }

pdnPppMlBundleMappingBundleIfIndex  OBJECT-TYPE
   SYNTAX      InterfaceIndex
   MAX-ACCESS  read-create
   STATUS      current
   DESCRIPTION "The pdnPppMlBundleIndex of the PPP bundle which 
                implements the specified interface."
   ::= { pdnPppMlBundleMappingEntry 2 }


-- ====================================================================
-- == pdnPppMlBundleStatusTable                                      ==
-- ====================================================================
pdnPppMlBundleStatusTable  OBJECT-TYPE
   SYNTAX      SEQUENCE OF PdnPppMlBundleStatusEntry
   MAX-ACCESS  not-accessible
   STATUS      current
   DESCRIPTION "The Multilink PPP Bundle Status Table."
   ::= { pdnPppMlObjects 4 }

pdnPppMlBundleStatusEntry  OBJECT-TYPE
   SYNTAX      PdnPppMlBundleStatusEntry
   MAX-ACCESS  not-accessible
   STATUS      current
   DESCRIPTION "An entry in the Multilink PPP Status Table."
   INDEX       { pdnPppMlBundleIfIndex }
   ::= { pdnPppMlBundleStatusTable 1 }

PdnPppMlBundleStatusEntry ::=
   SEQUENCE {
      pdnPppMlBundleStatusCurrState              PdnPPPState,
      pdnPppMlBundleStatusLocalToRemoteMRRU      MRRU,
      pdnPppMlBundleStatusRemoteToLocalMRRU      MRRU,
      pdnPppMlBundleStatusLocalToRemoteSSNHF     SSNHF,
      pdnPppMlBundleStatusRemoteToLocalSSNHF     SSNHF,
      pdnPppMlBundleStatusLocalToRemoteEDClass   EDClass,
      pdnPppMlBundleStatusLocalToRemoteEDAddr    DisplayString,
      pdnPppMlBundleStatusRemoteToLocalEDClass   EDClass,
      pdnPppMlBundleStatusRemoteToLocalEDAddr    DisplayString
   }

pdnPppMlBundleStatusCurrState OBJECT-TYPE
   SYNTAX      PdnPPPState
   MAX-ACCESS  read-only
   STATUS      current
   DESCRIPTION "The current state of the ML PPP State Machine."
   REFERENCE   "RFC 1661, Section 4.2, `State Transition Table'."
   ::= { pdnPppMlBundleStatusEntry 1 }

pdnPppMlBundleStatusLocalToRemoteMRRU  OBJECT-TYPE
   SYNTAX      MRRU
   UNITS       "Number of octets"
   MAX-ACCESS  read-only
   STATUS      current
   DESCRIPTION "Identifies the result of the negotiation for
                the Multilink Maximum Received Reconstructed Units 
                LCP option for the local to remote direction."
   REFERENCE    "RFC 1990, Section 5.1.1, `Multilink MRRU LCP Option'."
   ::= { pdnPppMlBundleStatusEntry 2 }

pdnPppMlBundleStatusRemoteToLocalMRRU  OBJECT-TYPE
   SYNTAX      MRRU
   UNITS       "Number of octets"
   MAX-ACCESS  read-only
   STATUS      current
   DESCRIPTION "Identifies the result of the negotiation for 
                the Multilink Maximum Received Reconstructed Units 
                LCP option for the remote to local direction."
   REFERENCE    "RFC 1990, Section 5.1.1, `Multilink MRRU LCP Option'."
   ::= { pdnPppMlBundleStatusEntry 3 }


pdnPppMlBundleStatusLocalToRemoteSSNHF  OBJECT-TYPE
   SYNTAX      SSNHF
   MAX-ACCESS  read-only
   STATUS      current
   DESCRIPTION "Identifies the result of the negotiation for the
                Short Sequence Number Header Format option for the
                local to remote direction.  If negotiation has not
                completed, ssnhfUnknown(1) will be returned."
   REFERENCE    "RFC 1990, Section 5.1.2, `Short Sequence Number
                 Header Format Option'."
   ::= { pdnPppMlBundleStatusEntry 4 }

pdnPppMlBundleStatusRemoteToLocalSSNHF  OBJECT-TYPE
   SYNTAX      SSNHF
   MAX-ACCESS  read-only
   STATUS      current
   DESCRIPTION "Identifies the result of the negotiation for the
                Short Sequence Number Header Format option for the
                remote to local direction.  If negotiation has not
                completed, ssnhfUnknown(1) will be returned."
   REFERENCE    "RFC 1990, Section 5.1.2, `Short Sequence Number
                 Header Format Option'."
   ::= { pdnPppMlBundleStatusEntry 5 }

pdnPppMlBundleStatusLocalToRemoteEDClass  OBJECT-TYPE
   SYNTAX      EDClass
   MAX-ACCESS  read-only
   STATUS      current
   DESCRIPTION "Identifies the result of the negotiation for the
                Endpoint Discriminator Option's class for the local
                PPP entity." 
   REFERENCE    "RFC 1990, Section 5.1.3, `Endpoint Discriminator 
                 Option'."
   ::= { pdnPppMlBundleStatusEntry 6 }

pdnPppMlBundleStatusLocalToRemoteEDAddr  OBJECT-TYPE
   SYNTAX      DisplayString
   MAX-ACCESS  read-only
   STATUS      current
   DESCRIPTION "Identifies the result of the negotiation for the
                Endpoint Discriminator Option's address for the local
                PPP entity." 
   REFERENCE    "RFC 1990, Section 5.1.3, `Endpoint Discriminator 
                 Option'."
   ::= { pdnPppMlBundleStatusEntry 7 }

pdnPppMlBundleStatusRemoteToLocalEDClass  OBJECT-TYPE
   SYNTAX      EDClass
   MAX-ACCESS  read-only
   STATUS      current
   DESCRIPTION "Identifies the result of the negotiation for the
                Endpoint Discriminator Option's class for the remote
                PPP entity." 
   REFERENCE    "RFC 1990, Section 5.1.3, `Endpoint Discriminator 
                 Option'."
   ::= { pdnPppMlBundleStatusEntry 8 }

pdnPppMlBundleStatusRemoteToLocalEDAddr  OBJECT-TYPE
   SYNTAX      DisplayString
   MAX-ACCESS  read-only
   STATUS      current
   DESCRIPTION "Identifies the result of the negotiation for the
                Endpoint Discriminator Option's address for the remote
                PPP entity." 
   REFERENCE    "RFC 1990, Section 5.1.3, `Endpoint Discriminator 
                 Option'."
   ::= { pdnPppMlBundleStatusEntry 9 }




-- ====================================================================
-- ==                  Accessible for Notifications (AFNs)           ==
-- ====================================================================
-- None defined



-- ====================================================================
-- ==                  Traps/Notifications                           ==
-- ====================================================================
-- None defined



-- ====================================================================
-- ==                  Conformance Information                       ==
-- ====================================================================

pdnPppMlCompliances  OBJECT IDENTIFIER ::= { pdnPppMlConformance 1 }
pdnPppMlGroups       OBJECT IDENTIFIER ::= { pdnPppMlConformance 2 }


-- ===========================
-- == Compliance Statements ==
-- ===========================


pdnPppMlCompliance  MODULE-COMPLIANCE
   STATUS      current
   DESCRIPTION "The compliance statement for network elements 
                implementing multilink PPP."
   MODULE      -- this module

   MANDATORY-GROUPS {
      pdnPppMlBundleDefinitionGroup
   }

   -- Optional Groups  

   GROUP       pdnPppMlBundleStateMachineGroup
   DESCRIPTION "This group is only required for implementations that
                need to display the ML PPP State Machine's state."

   GROUP       pdnPppMlBundleMRRUGroup
   DESCRIPTION "This group is only required for implementations that
                need to configure and display the Multilink Maximum
                Received Reconstructed Units LCP Option."

   GROUP       pdnPppMlBundleSSNHFGroup
   DESCRIPTION "This group is only required for implementations that
                need to configure and display the Short Sequence Number
                Header Format Option."

   GROUP       pdnPppMlBundleEDGroup
   DESCRIPTION "This group is only required for implementations that
                need to display the results of negotiation for the
                Endpoint Discriminator Option."

   GROUP       pdnPppMlBundleFragmentSizeGroup
   DESCRIPTION "This group is only required for implementations that
                need to configure the fragment size."

   ::= { pdnPppMlCompliances 1 }


-- ==========================
-- == Units of Conformance ==
-- ==========================

pdnPppMlObjGroups   OBJECT IDENTIFIER ::= { pdnPppMlGroups 1 }
pdnPppMlAfnGroups   OBJECT IDENTIFIER ::= { pdnPppMlGroups 2 }
pdnPppmlNtfyGroups  OBJECT IDENTIFIER ::= { pdnPppMlGroups 3 }


-- ===================
-- == Object Groups ==
-- ===================


pdnPppMlBundleDefinitionGroup  OBJECT-GROUP
   OBJECTS {
      pdnPppMlBundleNumber,
      pdnPppMlBundleConfigRowStatus,
      pdnPppMlBundleMappingBundleIfIndex,
      pdnPppMlBundleMappingRowStatus
   }
   STATUS      current
   DESCRIPTION "Define a bundle and map ifIndices to it."
   ::= { pdnPppMlObjGroups 1 }

pdnPppMlBundleStateMachineGroup OBJECT-GROUP
   OBJECTS {
      pdnPppMlBundleStatusCurrState
   }
   STATUS      current
   DESCRIPTION "Displays the ML PPP State Machine's state."
   ::= { pdnPppMlObjGroups 2 }

pdnPppMlBundleMRRUGroup OBJECT-GROUP
   OBJECTS {
      pdnPppMlBundleConfigRowStatus,
      pdnPppMlBundleConfigMRRU,
      pdnPppMlBundleStatusLocalToRemoteMRRU,
      pdnPppMlBundleStatusRemoteToLocalMRRU
   }
   STATUS      current
   DESCRIPTION "Configures and displays the results of the negotiation
                of the Multilink Maximum Received Reconstructed Units
                LCP Option."
   ::= { pdnPppMlObjGroups 3 }

pdnPppMlBundleSSNHFGroup OBJECT-GROUP
   OBJECTS {
      pdnPppMlBundleConfigRowStatus,
      pdnPppMlBundleConfigSSNHF,
      pdnPppMlBundleStatusLocalToRemoteSSNHF,
      pdnPppMlBundleStatusRemoteToLocalSSNHF
   }
   STATUS      current
   DESCRIPTION "Configures and displays the results of the negotiation 
                of the Short Sequence Number Header Format Option."
   ::= { pdnPppMlObjGroups 4 }

pdnPppMlBundleEDGroup OBJECT-GROUP
   OBJECTS {
      pdnPppMlBundleStatusLocalToRemoteEDClass,
      pdnPppMlBundleStatusLocalToRemoteEDAddr,
      pdnPppMlBundleStatusRemoteToLocalEDClass,
      pdnPppMlBundleStatusRemoteToLocalEDAddr
   }
   STATUS      current
   DESCRIPTION "Displays the results of the negotiation of the 
                Endpoint Discriminator Option."
   ::= { pdnPppMlObjGroups 5 }

pdnPppMlBundleFragmentSizeGroup OBJECT-GROUP
   OBJECTS {
      pdnPppMlBundleConfigRowStatus,
      pdnPppMlBundleConfigFragmentSize
   }
   STATUS      current
   DESCRIPTION "Configures the fragment size."
   ::= { pdnPppMlObjGroups 6 }




-- =========================================
-- == Accessible for Notifications Groups ==
-- =========================================
-- None defined



-- =========================
-- == Notification Groups ==
-- =========================
-- None defined




-- =========
-- == END ==
-- =========
END

-- =================================================================
-- ==                                                             ==
-- ==  Paradyne Extension to the BRIDGE-MIB.                      ==
-- ==                                                             ==
-- ==  Paradyne Networks was acquired by Zhone Technologies on    ==
-- ==  September 1, 2005.                                         ==
-- ==                                                             ==
-- ==         Copyright (C) 2005 Zhone Technologies, Inc.         ==
-- ==                                                             ==
-- =================================================================


PDN-BRIDGE-EXT-MIB DEFINITIONS ::= BEGIN

IMPORTS
   MODULE-IDENTITY, OBJECT-TYPE, Integer32, Unsigned32
      FROM SNMPv2-SMI
   OBJECT-GROUP, MODULE-COMPLIANCE
      FROM SNMPv2-CONF
   RowStatus, TestAndIncr
        FROM SNMPv2-TC
   SnmpAdminString
      FROM SNMP-FRAMEWORK-MIB
   dot1dBasePortEntry, dot1dBasePort
      FROM BRIDGE-MIB
   PdnTestAndIncrDerivedIndexTC
      FROM PDN-TC
   pdn-common
      FROM PDN-HEADER-MIB;

pdnBridgeExtMIB MODULE-IDENTITY
   LAST-UPDATED "200510260000Z"  -- October 26, 2005
   ORGANIZATION "Paradyne Networks
                 MIB Working Group
                 Other information about group editing the MIB"
   CONTACT-INFO "Paradyne Networks, Inc.
                 8545 126th Avenue North
                 Largo, FL 33733
                 www.paradyne.com
        
                 General Comments to: mibwg_team@paradyne.com

                 Editors
                    Clay Sikes,
                    Jesus Pinto,
                    Dave Hammers,
                    Prakash Easwar"

   DESCRIPTION  "This MIB module provides objects that extend the
                 BRIDGE-MIB.

                 ====================================================
                 ==                                                ==
                 ==   Copyright (C) 2005 Zhone Technologies, Inc   ==
                 ==                                                ==
                 ===================================================="
   
   REVISION     "200510260000Z"  -- October 26, 2005
   DESCRIPTION  "VLAN stacking (Q in Q) extentions for Dot1dBasePort."

   REVISION     "200510050000Z"  -- October 5, 2005
   DESCRIPTION  "Added IMPLIED keyword to index for the
                 pdnDot1dTrafficProfileInvMappingTable."

   REVISION     "200509290000Z"  -- September 29, 2005
   DESCRIPTION  "Change the size restriction for 
                 pdnDot1dTrafficProfileName such that a 
                 zero-length string is not supported."

   REVISION     "200509120000Z"  -- September 12, 2005
   DESCRIPTION  "Added a Layer 2 Traffic Profile Group to support the 
                 configuration of attributes associated with traffic
                 profiles."

   REVISION     "200508150000Z"  -- August 15, 2005
   DESCRIPTION  "Added pdnDot1dBasePortUnknownMulticastForwardingMode to
                 direct what to do with unknown layer 2 multicast 
                 frames."

   REVISION     "200412100000Z"  -- December 10, 2004
   DESCRIPTION  "Initial release."

::=  { pdn-common 58 }



-- ====================================================================
-- == Define groups for Notifications, MIB Objects, Accessible for   ==
-- == Notifications (AFNs), and Conformance.                         ==
-- == These may just be place holders.                               ==
-- ====================================================================
pdnBridgeExtNotifications OBJECT IDENTIFIER ::= { pdnBridgeExtMIB 0 }
pdnBridgeExtObjects       OBJECT IDENTIFIER ::= { pdnBridgeExtMIB 1 }
pdnBridgeExtAFNs          OBJECT IDENTIFIER ::= { pdnBridgeExtMIB 2 } 
pdnBridgeExtConformance   OBJECT IDENTIFIER ::= { pdnBridgeExtMIB 3 }


-- ====================================================================
-- ==                     Groups                                     ==
-- ====================================================================
pdnDot1dTrafficProfile   OBJECT IDENTIFIER ::= { pdnBridgeExtObjects 2 }



-- ====================================================================
-- ==              Textual Conventions                               ==
-- ====================================================================
-- None defined.




-- ====================================================================
-- ==                  MIB Objects                                   ==
-- ====================================================================


-- ===================================================================
-- == pdnDot1dBasePortExtTable                                      ==
-- ===================================================================
pdnDot1dBasePortExtTable  OBJECT-TYPE
   SYNTAX      SEQUENCE OF PdnDot1dBasePortExtEntry
   MAX-ACCESS  not-accessible
   STATUS      current
   DESCRIPTION "Extends the dot1dBasePortTable in the BRIDGE-MIB."                              
   ::= { pdnBridgeExtObjects 1 }

pdnDot1dBasePortExtEntry  OBJECT-TYPE
   SYNTAX      PdnDot1dBasePortExtEntry
   MAX-ACCESS  not-accessible
   STATUS      current
   DESCRIPTION "An entry in the dot1dBasePortTable Table."
   AUGMENTS    { dot1dBasePortEntry }
   ::= { pdnDot1dBasePortExtTable 1 }

PdnDot1dBasePortExtEntry ::=
   SEQUENCE {
      pdnDot1dBasePortMaxFdbEntries                   Integer32,
      pdnDot1dBasePortRole                            INTEGER,
      pdnDot1dBasePortUnknownMulticastForwardingMode  INTEGER,
      pdnDot1dBasePortOuterTag                        Integer32,
      pdnDot1dBasePortOuterPriority                   Integer32,
      pdnDot1dBasePortOuterEthertype                  Integer32
   }

pdnDot1dBasePortMaxFdbEntries  OBJECT-TYPE
   SYNTAX      Integer32(0..99999)
   MAX-ACCESS  read-write
   STATUS      current
   DESCRIPTION "This object configures the maximum number of entries
                in the bridge port's Forwarding Database.  The value
                `0' is a special case that indicates that there is
                no limit to the number of entries in the database."
   DEFVAL      { 0 }
   ::= { pdnDot1dBasePortExtEntry 1 }

pdnDot1dBasePortRole  OBJECT-TYPE
   SYNTAX      INTEGER {
                 subscriber (1),
                 network    (2)
               }
   MAX-ACCESS  read-write
   STATUS      current
   DESCRIPTION "This object defines the role of a bridge port.

               The role on a bridge port role can be defined as
               subscriber or network as follows:

               Subscriber:
               ----------
               A port on the IP DSLAM or Aggregator that faces toward
               or directly connects to a DSL interface on which an end
               user (subscriber) would be located.

               This would typically be the DSL ports directly on a unit
               or the ports on an aggregator that connect to another DSLAM.

               Network:
               -------
               A Port that connects to the service providers network,
               aggregation device or to a shared resource such as a server.
               "
   ::= { pdnDot1dBasePortExtEntry 2 }

pdnDot1dBasePortUnknownMulticastForwardingMode  OBJECT-TYPE
   SYNTAX      INTEGER {
                   flood (1),
                   drop  (2)
               }
   MAX-ACCESS  read-write
   STATUS      current
   DESCRIPTION "Configures the layer 2 unknown multicast forwarding 
                mode.  A layer 2 frame is `unknown' if there is no
                entry in the Forwarding Database which identifies
                the set of ports to forward the multicast frame on.
                When set to `flood(1)', the `unknown' multicast frame 
                will be forwarded on all bridge ports.  When set to 
                `drop(2)', the `unknown' multicast frame will be 
                dropped and not be forwarded on any bridge port."
   ::= { pdnDot1dBasePortExtEntry 3 }

pdnDot1dBasePortOuterTag  OBJECT-TYPE
    SYNTAX      Integer32 (0..4094)
    MAX-ACCESS  read-write
    STATUS      current
    DESCRIPTION "When VLAN stacking (Q in Q) is desired for untagged 
                 packets on a port, this object contains the value 
                 of the outer 802.1q VLAN outer tag. A value of 
                 zero (0) indicates that VLAN stacking is not enabled."
    DEFVAL      { 0 }
    ::= { pdnDot1dBasePortExtEntry 4 }

pdnDot1dBasePortOuterPriority  OBJECT-TYPE
    SYNTAX      Integer32 (0..7)
    MAX-ACCESS  read-write
    STATUS      current
    DESCRIPTION "When VLAN stacking (Q in Q) is desired for untagged
                 packets on a port, this object contains the value 
                 of the priority bits in the 802.1q VLAN outer tag.
                 If pdnDot1dBasePortOuterTag (above) is zero (0) this
                 object is ignored."
    DEFVAL      { 0 }
    ::= { pdnDot1dBasePortExtEntry 5 }

pdnDot1dBasePortOuterEthertype  OBJECT-TYPE
    SYNTAX      Integer32 (0..65535)
    MAX-ACCESS  read-write
    STATUS      current
    DESCRIPTION "When VLAN stacking (Q in Q) is desired for untagged 
                 packets on a port, this object contains the value of
                 the ethertype in the 802.1q VLAN outer tag.  If 
                 pdnDot1dBasePortOuterTag (above) is zero (0) this 
                 object is ignored."
    DEFVAL      { 33024 } -- 0x8100 hexidecimal
    ::= { pdnDot1dBasePortExtEntry 6 }


-- ===================================================================
-- ==                                                               ==
-- ==            Layer 2 Traffic Profile Group                      ==
-- ==                                                               ==
-- ===================================================================



-- ===================================================================
-- == Next Index for the Paradyne Layer 2 Traffic Profile Table     ==
-- ==                                                               ==
-- == (for the pdnDot1dTrafficProfileTable)                         ==
-- ===================================================================
pdnDot1dTrafficProfileNextIndex  OBJECT-TYPE
   SYNTAX      TestAndIncr
   MAX-ACCESS  read-write
   STATUS      current
   DESCRIPTION "This object is used to establish the next unused 
                index (pdnDot1dTrafficProfileIndex) for the 
                pdnDot1dTrafficProfileTable.

                This object is used to assist the manager in
                selecting a value for pdnDot1dTrafficProfileIndex.  
                Because this object is of syntax TestAndIncr (see the
                SNMPv2-TC document, RFC 2579), it can also be used
                to avoid race conditions with multiple managers
                trying to create rows in the table.

                If the result of the SET for 
                pdnDot1dTrafficProfileIndex is not success, this means
                the value has been changed from index (i.e. another 
                manager used the value), so a new value is required.

                The algorithm is:
                done = false
                while done == false
                   index = GET (pdnDot1dTrafficProfileNextIndex.0)
                   SET (pdnDot1dTrafficProfileNextIndex.0=index)
                   if (set failed)
                      done = false
                   else
                      pdnDot1dTrafficProfileRowStatus.index=createAndGo
                      SET (pdnDot1dTrafficProfileRowStatus.index)
                      if (set failed)
                         done = false
                      else
                         done = true
                         other error handling

                This description was modeled from RFC2494, 
                DS0BUNDLE-MIB."
   ::= { pdnDot1dTrafficProfile 1 }



-- ===================================================================
-- == Paradyne Layer 2 Traffic Profile Table                        ==
-- ==                                                               ==
-- == pdnDot1dTrafficProfileTable                                   ==
-- ===================================================================
pdnDot1dTrafficProfileTable  OBJECT-TYPE
   SYNTAX      SEQUENCE OF PdnDot1dTrafficProfileEntry
   MAX-ACCESS  not-accessible
   STATUS      current
   DESCRIPTION "The Paradyne Layer 2 Traffic Profile Table.
                Provides attributes for traffic profiles for MAC 
                bridges based on the IEEE 802.1D standard."
   ::= { pdnDot1dTrafficProfile 2 }

pdnDot1dTrafficProfileEntry  OBJECT-TYPE
   SYNTAX      PdnDot1dTrafficProfileEntry
   MAX-ACCESS  not-accessible
   STATUS      current
   DESCRIPTION "Each entry represents a particular traffic profile.
                Another table in this module will map to entries in 
                this table."
   INDEX       { pdnDot1dTrafficProfileIndex }
   ::= { pdnDot1dTrafficProfileTable 1 }

PdnDot1dTrafficProfileEntry ::=
   SEQUENCE {
      pdnDot1dTrafficProfileIndex          PdnTestAndIncrDerivedIndexTC,
      pdnDot1dTrafficProfileRowStatus      RowStatus,
      pdnDot1dTrafficProfileName           SnmpAdminString,
      pdnDot1dTrafficProfileNbrRefs        Unsigned32,
      pdnDot1dTrafficProfileTrafficClass   INTEGER,
      pdnDot1dTrafficProfileMaxRate        Unsigned32
   }

pdnDot1dTrafficProfileIndex  OBJECT-TYPE
   SYNTAX      PdnTestAndIncrDerivedIndexTC
   MAX-ACCESS  not-accessible
   STATUS      current
   DESCRIPTION "A unique identifier for a table entry.  This object
                is expected to be derived from the use of 
                pdnDot1dTrafficProfileNextIndex object above."
   ::= { pdnDot1dTrafficProfileEntry 1 }

pdnDot1dTrafficProfileRowStatus OBJECT-TYPE
   SYNTAX      RowStatus
   MAX-ACCESS  read-create
   STATUS      current
   DESCRIPTION "This object allows create, change, and delete 
                operations on the table.  The delete operation can
                only occur when the pdnDot1dTrafficProfileNbrRefs
                is 0 meaning that there are no references to this
                particular traffic profile."
   ::= { pdnDot1dTrafficProfileEntry 2 }

pdnDot1dTrafficProfileName  OBJECT-TYPE
   SYNTAX      SnmpAdminString (SIZE(1..32))
   MAX-ACCESS  read-create
   STATUS      current
   DESCRIPTION "An alphanumeric string to name the profile for the
                table entry."
   ::= { pdnDot1dTrafficProfileEntry 3 }

pdnDot1dTrafficProfileNbrRefs OBJECT-TYPE
   SYNTAX      Unsigned32(0..2147483647)
   MAX-ACCESS  read-only
   STATUS      current
   DESCRIPTION "The number of entries in the Traffic Profile Mapping
                Table that reference this traffic profile entry."
   ::= { pdnDot1dTrafficProfileEntry 4 }

pdnDot1dTrafficProfileTrafficClass   OBJECT-TYPE
   SYNTAX      INTEGER {
                  data  (1),
                  video (2),
                  voice (3)
               }
   MAX-ACCESS  read-create
   STATUS      current
   DESCRIPTION "The classification of traffic the entry is to be
                associated with."
   ::= { pdnDot1dTrafficProfileEntry 5 }

pdnDot1dTrafficProfileMaxRate  OBJECT-TYPE
   SYNTAX      Unsigned32(0..4294967295)
   UNITS       "bps"
   MAX-ACCESS  read-create
   STATUS      current
   DESCRIPTION "The maximum rate attribute in bits per second.  This
                provides `rate limiting' functionality.  If the value
                of this object is `0', then this attribute is not
                applied to the traffic profile.  That is, the traffic
                classified for this entry in the table is not `rate
                limited'."
   ::= { pdnDot1dTrafficProfileEntry 6 }



-- ===================================================================
-- == Paradyne Layer 2 Traffic Profile Inverse Mapping Table        ==
-- ==                                                               ==
-- == pdnDot1dTrafficProfileInvMappingTable                         ==
-- ===================================================================
pdnDot1dTrafficProfileInvMappingTable  OBJECT-TYPE
   SYNTAX      SEQUENCE OF PdnDot1dTrafficProfileInvMappingEntry
   MAX-ACCESS  not-accessible
   STATUS      current
   DESCRIPTION "This table identifies the mapping from a 
                profile name (pdnDot1dTrafficProfileName) to a 
                profile index (pdnDot1dTrafficProfileIndex)."
   ::= { pdnDot1dTrafficProfile 3 }

pdnDot1dTrafficProfileInvMappingEntry  OBJECT-TYPE
   SYNTAX      PdnDot1dTrafficProfileInvMappingEntry
   MAX-ACCESS  not-accessible
   STATUS      current
   DESCRIPTION "Each entry represents the profile index that is mapped
                from the profile name."
   INDEX       { IMPLIED pdnDot1dTrafficProfileName }
   ::= { pdnDot1dTrafficProfileInvMappingTable 1 }

PdnDot1dTrafficProfileInvMappingEntry ::=
   SEQUENCE {
      pdnDot1dTrafficProfileInvIndex       PdnTestAndIncrDerivedIndexTC
   }

pdnDot1dTrafficProfileInvIndex   OBJECT-TYPE
   SYNTAX      PdnTestAndIncrDerivedIndexTC
   MAX-ACCESS  read-only
   STATUS      current
   DESCRIPTION "The profile index that corresponds to the table 
                entry."
   ::= { pdnDot1dTrafficProfileInvMappingEntry 1 }



-- ===================================================================
-- == Paradyne Layer 2 Traffic Profile Mapping Table                ==
-- ==                                                               ==
-- == pdnDot1dTrafficProfileMappingTable                            ==
-- ===================================================================
pdnDot1dTrafficProfileMappingTable  OBJECT-TYPE
   SYNTAX      SEQUENCE OF PdnDot1dTrafficProfileMappingEntry
   MAX-ACCESS  not-accessible
   STATUS      current
   DESCRIPTION "Maps a MAC bridge port and traffic class to an entry
                in the Traffic Profile Table 
                (pdnDot1dTrafficProfileTable)."
   ::= { pdnDot1dTrafficProfile 4 }

pdnDot1dTrafficProfileMappingEntry  OBJECT-TYPE
   SYNTAX      PdnDot1dTrafficProfileMappingEntry
   MAX-ACCESS  not-accessible
   STATUS      current
   DESCRIPTION "An entry maps a MAC bridge port and a subport to a
                traffic class profile.

                The pdnDot1dTrafficProfileNbrRefs object in the
                pdnDot1dTrafficProfileTable indicates the number of 
                entries in this table that references or maps to a
                particular entry in the pdnDot1dTrafficProfileTable."
   INDEX       { dot1dBasePort, 
                 pdnDot1dTrafficProfileMappingSubPort }
   ::= { pdnDot1dTrafficProfileMappingTable 1 }

PdnDot1dTrafficProfileMappingEntry ::=
   SEQUENCE {
      pdnDot1dTrafficProfileMappingSubPort         Integer32,
      pdnDot1dTrafficProfileMappingRowStatus       RowStatus,
      pdnDot1dTrafficProfileMappingIndex   PdnTestAndIncrDerivedIndexTC
   }

pdnDot1dTrafficProfileMappingSubPort   OBJECT-TYPE
   SYNTAX      Integer32(1..8)
   MAX-ACCESS  not-accessible
   STATUS      current
   DESCRIPTION "The subport portion of the entry definition.  Subports
                are supported in implementations where MAC bridge 
                ports can be subdivided.  Implementations that do not
                support the subdividing of MAC bridge ports should set
                this object to `1'."
   ::= { pdnDot1dTrafficProfileMappingEntry 1 }

pdnDot1dTrafficProfileMappingRowStatus OBJECT-TYPE
   SYNTAX      RowStatus
   MAX-ACCESS  read-create
   STATUS      current
   DESCRIPTION "This object allows create, change, and delete 
                operations on the table."
   ::= { pdnDot1dTrafficProfileMappingEntry 2 }

pdnDot1dTrafficProfileMappingIndex   OBJECT-TYPE
   SYNTAX      PdnTestAndIncrDerivedIndexTC
   MAX-ACCESS  read-create
   STATUS      current
   DESCRIPTION "The traffic profile in the pdnDot1dTrafficProfileTable,
                identified by the pdnDot1dTrafficProfileIndex that this
                entry maps to."
   ::= { pdnDot1dTrafficProfileMappingEntry 3 }



-- ====================================================================
-- ==                  Accessible for Notifications (AFNs)           ==
-- ====================================================================
-- None defined



-- ===================================================================
-- ==                  Traps/Notifications                          ==
-- ===================================================================
-- None defined



-- ====================================================================
-- ==                  Conformance Information                       ==
-- ====================================================================

pdnBridgeExtCompliances  OBJECT IDENTIFIER ::= { pdnBridgeExtConformance 1 }
pdnBridgeExtGroups       OBJECT IDENTIFIER ::= { pdnBridgeExtConformance 2 }


-- ===========================
-- == Compliance Statements ==
-- ===========================


pdnBridgeExtCompliance  MODULE-COMPLIANCE
   STATUS      current
   DESCRIPTION "The compliance statement for network elements 
                implementing extensions to the BRIDGE-MIB."
   MODULE      -- this module
   -- No mandatory groups are specified.    

   GROUP       pdnDot1dBasePortMaxFdbEntriesGroup
   DESCRIPTION "This group is only required for implementations that
                need to allow a user-configurable limit to the 
                maximum number of entries allowed in the Forwarding
                Database for a bridge port."

   GROUP       pdnDot1dBasePortRoleGroup
   DESCRIPTION "This group contains the objects related to 
                the configuration of the bridge port's role attribute."

   GROUP       pdnDot1dBasePortUnknownMulticastForwardingModeGroup
   DESCRIPTION "This group is only required for implementations that
                need to configure the forwarding mode of unknown
                multicast frames."

   GROUP       pdnDot1dTrafficProfileBasicGroup
   DESCRIPTION "This group is only required for implementations that
                need to support the configuration of traffic profiles."

   GROUP       pdnDot1dTrafficProfileMaxRateGroup
   DESCRIPTION "This group is only require for implementations that
                need to support the configuration of a maximum
                rate traffic profile attribute."

   GROUP       pdnDot1dQinQVlanGroup
   DESCRIPTION "This group is only required for implementations that
                need to support the QinQ for VLANS (802.1ad)."
   ::= { pdnBridgeExtCompliances 1 }


-- ==========================
-- == Units of Conformance ==
-- ==========================

pdnBridgeExtObjGroups   OBJECT IDENTIFIER ::= { pdnBridgeExtGroups 1 }
pdnBridgeExtAfnGroups   OBJECT IDENTIFIER ::= { pdnBridgeExtGroups 2 }
pdnBridgeExtNtfyGroups  OBJECT IDENTIFIER ::= { pdnBridgeExtGroups 3 }


pdnBridgeExtTPGroups    OBJECT IDENTIFIER ::= { pdnBridgeExtObjGroups 4 }


-- ===================
-- == Object Groups ==
-- ===================


pdnDot1dBasePortMaxFdbEntriesGroup  OBJECT-GROUP
   OBJECTS {
      pdnDot1dBasePortMaxFdbEntries
   }
   STATUS      current
   DESCRIPTION "Configures the maximum number of entries allowed in
                a bridge port's forwarding database."
   ::= { pdnBridgeExtObjGroups 1 }

pdnDot1dBasePortRoleGroup  OBJECT-GROUP
   OBJECTS {
      pdnDot1dBasePortRole
   }
   STATUS      current
   DESCRIPTION "Objects related to the role attribute on a bridge 
                port."
   ::= { pdnBridgeExtObjGroups 2 }

pdnDot1dBasePortUnknownMulticastForwardingModeGroup  OBJECT-GROUP
   OBJECTS {
      pdnDot1dBasePortUnknownMulticastForwardingMode
   }
   STATUS      current
   DESCRIPTION "Provides the ability to configure the forwarding
                mode for unknown multicast frames."
   ::= { pdnBridgeExtObjGroups 3 }

pdnDot1dQinQVlanGroup OBJECT-GROUP
   OBJECTS {
      pdnDot1dBasePortOuterTag,
      pdnDot1dBasePortOuterPriority,
      pdnDot1dBasePortOuterEthertype
   }
   STATUS      current
   DESCRIPTION "Objects related to QinQ VLAN (802.1ad"
   ::= { pdnBridgeExtObjGroups 5 }

-- =================================
-- ==                             ==
-- == Traffic Profile Groups      ==
-- ==                             ==
-- == { pdnBridgeExtObjGroups 4 } ==
-- ==                             ==
-- =================================


pdnDot1dTrafficProfileBasicGroup  OBJECT-GROUP
   OBJECTS {
      pdnDot1dTrafficProfileNextIndex,
      pdnDot1dTrafficProfileName,
      pdnDot1dTrafficProfileRowStatus,
      pdnDot1dTrafficProfileNbrRefs,
      pdnDot1dTrafficProfileTrafficClass,
      pdnDot1dTrafficProfileInvIndex,
      pdnDot1dTrafficProfileMappingRowStatus,
      pdnDot1dTrafficProfileMappingIndex
   }
   STATUS      current  
   DESCRIPTION "Objects supporting the `basic' framework for 
                configuring traffic profiles.  Objects supporting
                specific attributes of a profile exist in other
                groups."
   ::= { pdnBridgeExtTPGroups 1 }


pdnDot1dTrafficProfileMaxRateGroup  OBJECT-GROUP
   OBJECTS {
      pdnDot1dTrafficProfileMaxRate
   }
   STATUS      current
   DESCRIPTION "Object to support the configuration of the maximum
                rate traffic profile attribute."
  ::= { pdnBridgeExtTPGroups 2 }


-- =========================================
-- == Accessible for Notifications Groups ==
-- =========================================
-- None defined



-- =========================
-- == Notification Groups ==
-- =========================
-- None defined




-- =========
-- == END ==
-- =========
END

PDN-HEALTHANDSTATUS-MIB DEFINITIONS ::= BEGIN

IMPORTS
	DisplayString, ifIndex
		FROM RFC1213-MIB
	IpAddress
		FROM RFC1155-SMI
	OBJECT-TYPE
		FROM RFC-1212
     	pdn-devStatus
		FROM PDN-HEADER-MIB
        entPhysicalIndex
                FROM ENTITY-MIB
	TRAP-TYPE
		FROM RFC-1215;

-- ===============================================================
--
-- Device Health and Status
--
-- Version 1.8.0
-- Last Updated 11/18/2003

-- History:
-- 1.8.0 - Changed dup name devSelfTestResults
-- 1.7.0 - Updated by Rob Stainberger 05/26/00
-- 	 - moved devFailureStatus to devStatus 7
-- 1.6.0 - Updated by Dragana Gough, 03/08/2000
--	 - added deviceFailureStatus Display string
--	 - object 
-- 1.5.0 - Updated by Dragana Gough , 02/23/2000
--	 - Added deviceFailure, devicelfTestFailure and devStatusTrapEnable
-- 1.4.0 - Updated by Rob Steinberger, 11/10/98
--       - Added devLastTrapString for string Variable binding.
-- 1.3.0 - Added devAuthenicationFailureIpAddress for trap processing
-- 1.2.0 - Updated by Soklei Leong, 6/10/98
--       - Added devSNMPSetStatusTable for retrieving the status of a SNMP
--       - SET command when an error occurs.
-- 1.1.0 - Updated by Rocco Sansone, 8/22/97
--       - Added devAbortStatus object for retrieving the last abort code.
-- 1.0.0 - Created 1994.

devStatus       OBJECT IDENTIFIER ::= { pdn-devStatus 1 }

devHealthAndStatus OBJECT-TYPE
    SYNTAX  DisplayString (SIZE (0..255))
    ACCESS  read-only
    STATUS  mandatory
    DESCRIPTION
        "Health and Status of the device. Health & Status is 
        represented as a concatenation of health and status 
        message strings, where each message string is separated
        by a semi-colon. Refer to device-specific user documentation
        for a complete description of the Health and Status codes."
    ::= { devStatus 1 }

devSelfTestResults OBJECT-TYPE
    SYNTAX  DisplayString (SIZE (0..255))
    ACCESS  read-only
    STATUS  mandatory
    DESCRIPTION
        "Self-test results. Self-test (or power-up test) results
        summarizes the test results of each CCA, where each CCA test
        result is separated by a semi-colon. Refer to device-specific 
        user documentation for a complete description of the self test
        codes and messages."
    ::= { devStatus 2 }

devAbortStatus OBJECT-TYPE
    SYNTAX  DisplayString (SIZE (0..255))
    ACCESS  read-only
    STATUS  mandatory
    DESCRIPTION
        "Abort Status.  The devAbortStatus object is used to retrieve the 
	latest abort status that is stored in the agent.  The agent will 
	need to save the latest abort information in non-volatile memory
	so that it will be available immediately after a fatal reset.  
	How long the latest failure information is remembered after this point 
	is an implementation issue.  Refer to device-specific 
        user documentation for a complete description of the abort
        codes and/or messages."
    ::= { devStatus 3 }

devSNMPSetStatusTable OBJECT-TYPE
     SYNTAX   SEQUENCE OF DevSNMPSetStatusEntry
     ACCESS   not-accessible
     STATUS   mandatory
     DESCRIPTION
         "A table containing SNMP Set command Statuses when an error occurs.
          It contains maximum of 5 entries. Oldest entry is pushed out when
          the table is full and a new entry is added."
     ::= { devStatus 4 } 

devSNMPSetStatusEntry OBJECT-TYPE
         SYNTAX   DevSNMPSetStatusEntry
         ACCESS   not-accessible
         STATUS   mandatory
         DESCRIPTION
             "The information regarding each SNMP Set command Status when
              en error occurs. Each entry is index by a request ID generated
              by the client and attached to the UDP when the Set command is
              sent."
         INDEX { devSNMPSetReqId }
     ::= { devSNMPSetStatusTable 1 }  

DevSNMPSetStatusEntry ::=
    SEQUENCE {
        devSNMPSetReqId
            INTEGER,
        devSNMPSetStatus
            DisplayString
    }

devSNMPSetReqId OBJECT-TYPE
    SYNTAX   INTEGER
    ACCESS   read-only                                          
    STATUS   mandatory                                          
    DESCRIPTION                                                 
        "The Request ID which identifies the SNMP Set command in error."                                            
    ::= { devSNMPSetStatusEntry 1 }                                        

devSNMPSetStatus OBJECT-TYPE
    SYNTAX  DisplayString (SIZE (0..255))
    ACCESS  read-only
    STATUS  mandatory                                            
    DESCRIPTION                                                  
        "Indicates the error message string associated with the Set command 
         of this row in the table."
    ::= { devSNMPSetStatusEntry 2 }     

devAuthenticationFailureIpAddress OBJECT-TYPE
    SYNTAX  IpAddress
    ACCESS  read-only
    STATUS  mandatory
    DESCRIPTION
        "Authentication Failure Ip Address is used when a
         authenticationFailure trap is generated.  The single
         varbind represents the ip address causing the error.
         If the ip address is not known, 0.0.0.0 is used."
    ::= { devStatus 5 }

devLastTrapString OBJECT-TYPE
    SYNTAX  DisplayString (SIZE (0..255))
    ACCESS  read-only
    STATUS  mandatory                                            
    DESCRIPTION                                                  
        "This object contains a textual description of the last trap that
         was processed by the device.  The exact text in the description
         is device specific and should be contained user documentation
         outside of this MIB. It is recommended that the important 
         information is contained within the first 100 characters."
    ::= { devStatus 6 }     

devFailureStatus OBJECT-TYPE
    SYNTAX  DisplayString (SIZE (0..255))
    ACCESS  read-only
    STATUS  mandatory
    DESCRIPTION
	 " Device Failure status. Conditions that cause failure
	   are further described in the device documentation."
    ::= { devStatus 7 }

devStatusTrapEnable OBJECT-TYPE
     SYNTAX  INTEGER
     ACCESS  read-write
     STATUS  mandatory
     DESCRIPTION
	    " This object provides ability to enable or disable
	      individual enterprise traps. The object is bit map
	      represented as a sum. The bit positions are:
			1 deviceSelfTestFailure
			2 deviceFailure"
    ::= { devStatus 8 }

devSelfTestResultTable OBJECT-TYPE
     SYNTAX   SEQUENCE OF DevSelfTestResultEntry
     ACCESS   not-accessible
     STATUS   mandatory
     DESCRIPTION
         "A table containing results of power on selftest for the whole unit."
     ::= { devStatus 9 } 

devSelfTestResultEntry OBJECT-TYPE
         SYNTAX   DevSelfTestResultEntry
         ACCESS   not-accessible
         STATUS   mandatory
         DESCRIPTION
             "The information regarding each SelfTest on each unit."
         INDEX { entPhysicalIndex }
     ::= { devSelfTestResultTable 1 }  

DevSelfTestResultEntry ::=
    SEQUENCE {
        devSelfTestResult
            DisplayString 
    }

devSelfTestResult OBJECT-TYPE
    SYNTAX   DisplayString 
    ACCESS   read-only                                          
    STATUS   mandatory                                          
    DESCRIPTION                                                 
        "Self-test results. Self-test (or power-up test) results
        summarizes the test results of each interface, where each CCA test
        result is separated by a semi-colon. Refer to device-specific 
        user documentation for a complete description of the self test
        codes and messages."
    ::= { devSelfTestResultEntry 1 }                                        

devSelfTestFailure TRAP-TYPE
     ENTERPRISE  devStatus  
     VARIABLES { ifIndex, devSelfTestResults }
     DESCRIPTION
       "This trap signifies that the sending protocol's
        device has failed self test.
        The variable binding for this trap would be the selfTest
        devSelfTestResults object of the Health and Status MIB. The
        exact format of this display string will be well-documented
        in the Operational Specifications of the device."
    ::= 1 

deviceFailure TRAP-TYPE
     ENTERPRISE  devStatus  
     VARIABLES { ifIndex, devFailureStatus }
     DESCRIPTION
	" This trap signifies that the sending protocol's
	  device has failed and the failure was not a result
	  of a device test."
     ::= 2 
END

-- ======================================================================
-- ==                                                                  ==
-- ==        Copyright (C) 2005 Paradyne Networks, Inc.                ==
-- ==                                                                  ==
-- ======================================================================



PDN-DSL-ATM-BOND-MIB DEFINITIONS ::= BEGIN

IMPORTS
   MODULE-IDENTITY, OBJECT-TYPE, Integer32, Counter32, Unsigned32, 
   NOTIFICATION-TYPE
      FROM SNMPv2-SMI
   OBJECT-GROUP, MODULE-COMPLIANCE, NOTIFICATION-GROUP
      FROM SNMPv2-CONF
   TEXTUAL-CONVENTION, RowStatus, DateAndTime, TestAndIncr, TruthValue
      FROM SNMPv2-TC
   SnmpAdminString
      FROM SNMP-FRAMEWORK-MIB
   InterfaceIndex
      FROM IF-MIB
   pdn-interfaces
      FROM PDN-HEADER-MIB;
        
pdnDslAtmBondMIB MODULE-IDENTITY
   LAST-UPDATED "200508030000Z"  -- August 3, 2005
   ORGANIZATION "Paradyne Networks, Inc.
                 MIB Working Group"
   CONTACT-INFO "Paradyne Networks, Inc.
                 8545 126th Avenue North
                 Largo, FL 33733
                 www.paradyne.com
        
                 General Comments to: mibwg_team@paradyne.com

                 Editor(s)
                    Clay Sikes"

   DESCRIPTION
      "This MIB module defines a collection of objects for managing
       the bonding of multiple digital subscriber lines (DSL) to 
       transport ATM streams.  

       At the time this modules was defined, neither the IETF nor the
       ATM Forum had any indication of plans to produce MIB modules
       to support the bonding of multiple digital subscriber lines to 
       transport ATM streams.  As a result, these objects may be a 
       `temporary' solution should a standards body produces a module
       to support this type of bonding.

       The following documents are informational references with
       respect to this MIB module:

       [G.998.1]  ITU-T G.998.1, `ATM-based Multi-Pair Bonding', 
                  January 2005.

       [RFC 2494] Fowler, D., `Definitions of Managed Objects for the
                  DS0 and DS0 Bundle Interface type', January 1999. 

       [T1E1.4]   ANSI T1E1.4/2003-334R6, American National Standards 
                  Institute (ANSI), `Draft proposed American National 
                  Standard, ATM-based multi-pair bonding', October 2004.

       [TR-090]   Abbi, R., DSL Forum Technical Report Technical Report
                  TR-090, `Protocol Independent Object Model for 
                  Managing Next Generation ADSL Technologies', 
                  December 2004. 


       =================================================================
       ==                                                             ==
       ==          Copyright (C) 2005 Paradyne Networks, Inc.         ==
       ==                                                             ==
       ================================================================="



   REVISION    "200508030000Z"  -- August 3, 2005
   DESCRIPTION "Removed `0' as a supported value for 
                PdnDslAtmBondGroupIdentityTC.  The hardware doesn't 
                support a `0' and a `0' is not explicitly called out
                in the ITU or the ANSI specifications."

   REVISION    "200508010000Z"  -- August 1, 2005
   DESCRIPTION "Added the bonding group's ifIndex to the notification
                data for all traps."

   REVISION    "200507260000Z"  -- July 26, 2005
   DESCRIPTION "Replaced the pdnDslAtmBondNotificationsEnable object
                with the pdnDslAtmBondGroupStatusNotifyEnabled
                object to allow notifications for group status change
                to be controlled on a per-bonding-group basis.
                General clean up and clarification of some descriptions."

   REVISION    "200506070000Z"  -- June 7, 2005
   DESCRIPTION "Initial release."

::=  { pdn-interfaces 33 } 


--
-- Define groups for Notifications, MIB Objects, Accessible for 
-- Notifications (AFNs), and Conformance.
-- These may just be place holders.
--
pdnDslAtmBondNotifications OBJECT IDENTIFIER ::= { pdnDslAtmBondMIB 0 }
pdnDslAtmBondObjects       OBJECT IDENTIFIER ::= { pdnDslAtmBondMIB 1 }
pdnDslAtmBondAFNs          OBJECT IDENTIFIER ::= { pdnDslAtmBondMIB 2 } 
pdnDslAtmBondConformance   OBJECT IDENTIFIER ::= { pdnDslAtmBondMIB 3 }



-- ======================================================================
-- ==              Convention Notes                                    ==
-- ======================================================================
-- ==                                                                  ==
-- == In the, "Protocol Independent Object Model for Managing Next     ==
-- == Generation ADSL Technologies" [TR-090], Section 5.5.1, "ATU      ==
-- == Sub-Carrier Status," there is a note that states the following   ==
-- == relationship:                                                    ==
-- ==     1. ATU-C corresponds to downstream.                          ==
-- ==     2. ATU-R corresponds to upstream.                            ==
-- == In addition, "ANSI ATM-based Multi-pair bonding" [T1E1.4] and    == 
-- == "ITU-T ATM-based Multi-pair bonding" [G.998.1], Definitions      ==
-- == section state:                                                   ==
-- ==     1. Downstream is the direction of transmission from the      ==
-- ==        carrier Central Office to the Customer Installation.      ==
-- ==     2. Upstream is the direction of transmission from the        ==
-- ==        Customer Installation to the carrier Central Office.      ==
-- ==                                                                  ==
-- ======================================================================



-- ======================================================================
-- ==              Textual Conventions                                 ==
-- ======================================================================

PdnDslAtmBondGroupIndexTC ::= TEXTUAL-CONVENTION
   DISPLAY-HINT "d"
   STATUS       current
   DESCRIPTION  "An identifier for a bonding group table entry.
                 This syntax was chosen to correspond to the 
                 TestAndIncr TC for pdnDslAtmBondNextGroupIndex."
   SYNTAX       Integer32(0..2147483647)

PdnDslAtmBondGroupIdentityTC ::= TEXTUAL-CONVENTION
   DISPLAY-HINT "d"
   STATUS       current
   DESCRIPTION  "An identifier to uniquely identify a bonding group."
   REFERENCE    "T1E1.4, Section 9.1.4, `Format of the Autonomous Status 
                 Message (ASM)', Table 9-1`ASM Message Format'.
                 G.998.1, Section 9.1.4, `Format of the Autonomous Status 
                 Message (ASM)', Table 9-1`ASM Message Format'."
   SYNTAX       Unsigned32(1..65535)

PdnDslAtmBondGroupBearerNumberTC ::= TEXTUAL-CONVENTION
   DISPLAY-HINT "d"
   STATUS       current
   DESCRIPTION  "Bearer number for the line to bond."
   REFERENCE    "T1E1.4, Section 9.1.4, `Format of the Autonomous Status
                 Message (ASM)', Table 9-1`ASM Message Format'.
                 G.998.1, Section 9.1.4, `Format of the Autonomous Status 
                 Message (ASM)', Table 9-1`ASM Message Format'."
   SYNTAX       Unsigned32(1..4)

PdnDslAtmBondLinkStatusAsmTC ::= TEXTUAL-CONVENTION
   STATUS       current
   DESCRIPTION  "The status of a link within a bonding group relative to 
                 its capability or current state with respect to the
                 transportation of bonded traffic.

                 +------------------------------------------------------+
                 |                                                      |
                 | Rx Link Status                                       |
                 |    1.  Not provisioned.                              |
                 |        The link is indicated as not provisioned, and |
                 |        will never be part of a bonded group.         |
                 |    2.  Should not be used.                           |
                 |        The transmitter should not use this link for  |
                 |        bonding, but this link is provisioned as a    |
                 |        candidate link member (i.e. a temporary       |
                 |        outage).                                      |
                 |    3.  Acceptable to carry bonded traffic.           |
                 |        This status is used to request that the       |
                 |        transmitter consider this provisioned link    |
                 |        for bonding.                                  |
                 |    4.  Selected to carry bonded traffic.             |
                 |        Bonded traffic is expected on this link.      |
                 |                                                      |
                 +------------------------------------------------------+
                 |                                                      |
                 | Tx Link Status                                       |
                 |    1.  Not provisioned.                              |
                 |        The link is indicated as not provisioned, and |
                 |        will never be part of a bonded group.         |
                 |    2.  Should not be used.                           |
                 |        The receiver should not consider this link    |
                 |        for bonding, but this link is provisioned as  |
                 |        a candidate link member.                      |
                 |    3.  Acceptable to carry bonded traffic.           |
                 |        This status is used to indicate that the      |
                 |        receiver should consider it for carrying      |
                 |        bonded traffic.                               |
                 |    4.  Selected to carry bonded traffic.             |
                 |        The transmitter is using or will use this     |
                 |        link to carry bonded traffic.                 |
                 |                                                      |
                 +------------------------------------------------------+"                
   REFERENCE    "T1E1.4, Section 9.1.4, `Format of the Autonomous Status 
                 Message (ASM)', Table 9-1`ASM Message Format'.
                 G.998.1, Section 9.1.4, `Format of the Autonomous Status 
                 Message (ASM)', Table 9-1`ASM Message Format'."
   SYNTAX       INTEGER {
                   notProvisioned(1),
                   shouldNotBeUsed(2),
                   acceptableToCarryBondedTraffic(3),
                   selectedToCarryBondedTraffic(4)
                }

PdnDslAtmBondAsmRxStatusTC ::= TEXTUAL-CONVENTION
   STATUS       current
   DESCRIPTION  "The status of Autonomous Status Message (ASM) received
                 on a link in the past one second.  The bonding entity 
                 is required to send ASM status messages at no less a
                 frequency than once per second per link."
   REFERENCE    "T1E1.4, Section 9.1.3, `Frequency of Autonomous Status
                 Messages'.
                 G.998.1, Section 9.1.3, `Frequency of Autonomous Status
                 Messages'.
                 T1E1.4, Section 9.1.4, `Format of the Autonomous Status 
                 Message (ASM)', Table 9-1`ASM Message Format'.
                 G.998.1, Section 9.1.4, `Format of the Autonomous Status 
                 Message (ASM)', Table 9-1`ASM Message Format'."
   SYNTAX       INTEGER {
                   receivedASM(1),
                   notReceivedASM(2)
                }

PdnDslAtmBondGroupDataRateTC ::= TEXTUAL-CONVENTION
   DISPLAY-HINT "d"
   STATUS       current
   DESCRIPTION  "A data rate, in bits/s, for a bonding group.  The
                 value, -1 represents infinity, and indicates that the 
                 parameter is to be ignored."
   REFERENCE    "T1E1.4,  Section 11.4.1, `Group Provisioning'.
                 G.998.1, Section 11.4.1, `Group Provisioning'."
   SYNTAX       Integer32(-1 | 0..2147483647)

PdnDslAtmBondGroupDiffDelayTolTC ::= TEXTUAL-CONVENTION
   DISPLAY-HINT "d"
   STATUS       current
   DESCRIPTION  "The maximum differential delay tolerance, in 
                 milliseconds, among member links in a bonding group."
   REFERENCE    "T1E1.4,  Section 11.4.1, `Group Provisioning'.
                 G.998.1, Section 11.4.1, `Group Provisioning'."
   SYNTAX       Unsigned32(0..2147483647)

PdnDslAtmBondGroupStatusTC ::= TEXTUAL-CONVENTION
   STATUS       current
   DESCRIPTION  "The status of a group.  A group is considered 
                 `unavailable' when it does not satisfy the
                 parameters provisioned for the group."
   REFERENCE    "T1E1.4,  Section 11.4.2, `Group Performance'.
                 G.998.1, Section 11.4.2, `Group Performance'."
   SYNTAX       INTEGER {
                   operational(1),
                   unavailable(2)
                }

PdnDslAtmBondGroupFailReasonTC ::= TEXTUAL-CONVENTION
   STATUS       current
   DESCRIPTION  "The reason the operational status for a bonding group
                 is not `operational'."
   REFERENCE    "T1E1.4,  Section 11.4.3, `Group Failures'.
                 G.998.1, Section 11.4.3, `Group Failures'."
   SYNTAX       INTEGER {
                   notApplicable(1),          -- In an `operational` 
                                              -- state, so a reason is
                                              -- not applicable.
                   unknown(2),                -- Could not match a reason
                                              -- in this list.
                   atucMinDataRateNotMet(3),  -- Couldn't achieve the 
                                              -- minimum data rate 
                                              -- specified for the group
                                              -- for the downstream 
                                              -- direction.
                   aturMinDataRateNotMet(4),  -- Couldn't achieve the 
                                              -- minimum data rate 
                                              -- specified for the group
                                              -- for the upstream 
                                              -- direction.
                   atucDiffDelayExceeded(5),  -- Couldn't achieve the 
                                              -- differential delay 
                                              -- tolerance in the 
                                              -- downstream direction.
                   aturDiffDelayExceeded(6)   -- Couldn't achieve the 
                                              -- differential delay 
                                              -- tolerance in the 
                                              -- upstream direction.
                }

                  


-- ======================================================================
-- ==                  MIB Objects                                     ==
-- ======================================================================

pdnDslAtmBondNextGroupIndex OBJECT-TYPE
   SYNTAX      TestAndIncr
   MAX-ACCESS  read-write
   STATUS      current
   DESCRIPTION "This object is used to establish the next unused group
                index (pdnDslAtmBondGroupIndex).

                This object is used to assist the manager in
                selecting a value for pdnDslAtmBondGroupIndex.  Because
                this object is of syntax TestAndIncr (see the
                SNMPv2-TC document, RFC 2579) it can also be used
                to avoid race conditions with multiple managers
                trying to create rows in the table.

                If the result of the SET for pdnDslAtmBondNextGroupIndex
                is not success, this means the value has been
                changed from index (i.e. another manager used the
                value), so a new value is required.

                The algorithm is:
                done = false
                while done == false
                   index = GET (pdnDslAtmBondNextGroupIndex.0)
                   SET (pdnDslAtmBondNextGroupIndex.0=index)
                   if (set failed)
                      done = false
                   else
                      SET(pdnDslAtmBondGroupRowStatus.index=createAndGo)
                      if (set failed)
                         done = false
                      else
                         done = true
                         other error handling

                This description was modeled from RFC2494, 
                DS0BUNDLE-MIB."
   ::= { pdnDslAtmBondObjects 1 }

pdnDslAtmBondNbrOfGroups OBJECT-TYPE
   SYNTAX      Unsigned32(0..2147483647)
   MAX-ACCESS  read-only
   STATUS      current
   DESCRIPTION "The number of bonding groups configured on this system."
   ::= { pdnDslAtmBondObjects 2 }


-- =================================================
-- == DSL ATM Bond Group Table
-- =================================================
pdnDslAtmBondGroupTable OBJECT-TYPE
   SYNTAX      SEQUENCE OF PdnDslAtmBondGroupEntry
   MAX-ACCESS  not-accessible
   STATUS      current
   DESCRIPTION "The DSL ATM Bond Group Table.  
                Contains configuration and operational information 
                relative to a particular bonding group."
   REFERENCE   "T1E1.4,  Section 11.4.1, `Group Provisioning'.
                G.998.1, Section 11.4.1, `Group Provisioning'."
   ::= { pdnDslAtmBondObjects 3 }

pdnDslAtmBondGroupEntry OBJECT-TYPE
   SYNTAX      PdnDslAtmBondGroupEntry
   MAX-ACCESS  not-accessible
   STATUS      current
   DESCRIPTION "An entry in the DSL ATM Bond Group Table.
                Each entry represents a particular bonding group."
   INDEX       { pdnDslAtmBondGroupIndex }
   ::= { pdnDslAtmBondGroupTable 1 }

PdnDslAtmBondGroupEntry ::=
   SEQUENCE {
      pdnDslAtmBondGroupIndex              PdnDslAtmBondGroupIndexTC,
      pdnDslAtmBondGroupRowStatus          RowStatus,
      pdnDslAtmBondGroupNbrRefs            Unsigned32,
      pdnDslAtmBondGroupIfIndex            InterfaceIndex,
      pdnDslAtmBondGroupID                 PdnDslAtmBondGroupIdentityTC,
      pdnDslAtmBondGroupAlarmConfProfileName SnmpAdminString,
      pdnDslAtmBondGroupAtucMaxNetDataRate PdnDslAtmBondGroupDataRateTC,
      pdnDslAtmBondGroupAturMaxNetDataRate PdnDslAtmBondGroupDataRateTC,
      pdnDslAtmBondGroupAtucMinNetDataRate PdnDslAtmBondGroupDataRateTC,
      pdnDslAtmBondGroupAturMinNetDataRate PdnDslAtmBondGroupDataRateTC,
      pdnDslAtmBondGroupAtucDiffDelay  PdnDslAtmBondGroupDiffDelayTolTC,
      pdnDslAtmBondGroupAturDiffDelay  PdnDslAtmBondGroupDiffDelayTolTC,
      pdnDslAtmBondGroupStatusNotifyEnabled  TruthValue
   }

pdnDslAtmBondGroupIndex OBJECT-TYPE
   SYNTAX      PdnDslAtmBondGroupIndexTC
   MAX-ACCESS  not-accessible
   STATUS      current
   DESCRIPTION "A unique identifier for a bonding group.  This is not
                the same value as an ifIndex for the group.  The
                pdnDslAtmBondGroupIfIndex object contains the bonding
                group's ifIndex."
   ::= { pdnDslAtmBondGroupEntry 1 }

pdnDslAtmBondGroupRowStatus OBJECT-TYPE
   SYNTAX      RowStatus
   MAX-ACCESS  read-create
   STATUS      current
   DESCRIPTION "This object allows create, change, and delete operations 
                on the table.  The delete operation can only occur when
                the pdnDslAtmBondGroupNbrRefs is 0 meaning that there
                are no DSL interfaces and bearers that are bonded to 
                this group."
   ::= { pdnDslAtmBondGroupEntry 2 }

pdnDslAtmBondGroupNbrRefs OBJECT-TYPE
   SYNTAX      Unsigned32(0..2147483647)
   MAX-ACCESS  read-only
   STATUS      current
   DESCRIPTION "The number of DSL interface / bearer combinations that
                are members of this group.  This is the number of 
                entries in the pdnDslAtmBondMappingTable that have
                their pdnDslAtmBondMappingGroupIndex assigned to this
                value of pdnDslAtmBondGroupIndex."
   ::= { pdnDslAtmBondGroupEntry 3 }

pdnDslAtmBondGroupIfIndex OBJECT-TYPE
   SYNTAX      InterfaceIndex
   MAX-ACCESS  read-only
   STATUS      current
   DESCRIPTION "Identifies the interface number assigned to this bonding
                group and is used to identify corresponding rows in the 
                interfaces MIB."
   ::= { pdnDslAtmBondGroupEntry 4 }

pdnDslAtmBondGroupID OBJECT-TYPE
   SYNTAX      PdnDslAtmBondGroupIdentityTC
   MAX-ACCESS  read-create
   STATUS      current
   DESCRIPTION "An identifier to uniquely identify the bonding group.
                This ID one of the fields of the Autonomous Status 
                Message and may be useful in some debugging situations."
   REFERENCE   "T1E1.4, Section 9.1.4, `Format of the Autonomous Status 
                Message (ASM)', Table 9-1`ASM Message Format'.
                G.998.1, Section 9.1.4, `Format of the Autonomous Status 
                Message (ASM)', Table 9-1`ASM Message Format'."
   ::= { pdnDslAtmBondGroupEntry 5 }

pdnDslAtmBondGroupAlarmConfProfileName OBJECT-TYPE
   SYNTAX      SnmpAdminString(SIZE(0 | 1..32))
   MAX-ACCESS  read-create
   STATUS      current
   DESCRIPTION "Identifies the Alarm Profile this group is associated
                with which is an entry in the 
                pdnDslAtmBondAlarmConfProfileTable.  If this object 
                is not a zero-length string, it should default to the
                default profile whose name is `DEFVAL'."
   ::= { pdnDslAtmBondGroupEntry 6 }

pdnDslAtmBondGroupAtucMaxNetDataRate OBJECT-TYPE
   SYNTAX      PdnDslAtmBondGroupDataRateTC 
   UNITS       "bps"
   MAX-ACCESS  read-create
   STATUS      current
   DESCRIPTION "The maximum net data rate this bonding group is allowed
                to achieve in the downstream direction."
   ::= { pdnDslAtmBondGroupEntry 7 }

pdnDslAtmBondGroupAturMaxNetDataRate OBJECT-TYPE
   SYNTAX      PdnDslAtmBondGroupDataRateTC  
   UNITS       "bps"  
   MAX-ACCESS  read-create
   STATUS      current
   DESCRIPTION "The maximum net data rate this bonding group is allowed
                to achieve in the upstream direction."
   ::= { pdnDslAtmBondGroupEntry 8 }

pdnDslAtmBondGroupAtucMinNetDataRate OBJECT-TYPE
   SYNTAX      PdnDslAtmBondGroupDataRateTC
   UNITS       "bps"
   MAX-ACCESS  read-create
   STATUS      current
   DESCRIPTION "The minimum net data rate this bonding group is allowed
                to achieve in the downstream direction."
   ::= { pdnDslAtmBondGroupEntry 9 }

pdnDslAtmBondGroupAturMinNetDataRate OBJECT-TYPE
   SYNTAX      PdnDslAtmBondGroupDataRateTC 
   UNITS       "bps"
   MAX-ACCESS  read-create
   STATUS      current
   DESCRIPTION "The minimum net data rate this bonding group is allowed
                to achieve in the upstream direction."
   ::= { pdnDslAtmBondGroupEntry 10 }

pdnDslAtmBondGroupAtucDiffDelay OBJECT-TYPE
   SYNTAX      PdnDslAtmBondGroupDiffDelayTolTC
   UNITS       "milliseconds"
   MAX-ACCESS  read-create
   STATUS      current
   DESCRIPTION "The maximum differential delay tolerance among member 
                links in this bonding group in the downstream 
                direction."
   ::= { pdnDslAtmBondGroupEntry 11 }

pdnDslAtmBondGroupAturDiffDelay OBJECT-TYPE
   SYNTAX      PdnDslAtmBondGroupDiffDelayTolTC
   UNITS       "milliseconds"
   MAX-ACCESS  read-create
   STATUS      current
   DESCRIPTION "The maximum differential delay tolerance among member 
                links in this bonding group in the upstream 
                direction."
   ::= { pdnDslAtmBondGroupEntry 12 }

pdnDslAtmBondGroupStatusNotifyEnabled OBJECT-TYPE
   SYNTAX      TruthValue
   MAX-ACCESS  read-create
   STATUS      current
   DESCRIPTION "Specifies whether or not the 
                pdnDslAtmBondGroupStatusChange notification will be
                generated.  When set to true(1), the notification will
                be generated when the pdnDslAtmBondPerfGroupStatus 
                changes.  When set to false(2), the notification will
                not be generated with the pdnDslAtmBondPerfGroupStatus
                changes."
   ::= { pdnDslAtmBondGroupEntry 13 }


-- =================================================
-- == DSL ATM Bond Mapping Table
-- =================================================
pdnDslAtmBondMappingTable OBJECT-TYPE
   SYNTAX      SEQUENCE OF PdnDslAtmBondMappingEntry
   MAX-ACCESS  not-accessible
   STATUS      current
   DESCRIPTION "The DSL ATM Bond Mapping Table. 
                This table is used to map a DSL port and a bearer 
                number to a bonding group."
   REFERENCE   "T1E1.4,  Section 11.4.1, `Group Provisioning'.
                G.998.1, Section 11.4.1, `Group Provisioning'."
   ::= { pdnDslAtmBondObjects 4 }

pdnDslAtmBondMappingEntry OBJECT-TYPE
   SYNTAX      PdnDslAtmBondMappingEntry
   MAX-ACCESS  not-accessible
   STATUS      current
   DESCRIPTION "An entry in the DSL ATM Bond Mapping Table.
                Each entry represents a DSL interface and a a
                bearer number."
   INDEX       { pdnDslAtmBondDslIfIndex, 
                 pdnDslAtmBondBearerNbr } 
   ::= { pdnDslAtmBondMappingTable 1 }

PdnDslAtmBondMappingEntry ::=
   SEQUENCE {
      pdnDslAtmBondDslIfIndex          InterfaceIndex,
      pdnDslAtmBondBearerNbr           PdnDslAtmBondGroupBearerNumberTC,
      pdnDslAtmBondMappingRowStatus    RowStatus,
      pdnDslAtmBondMappingGroupIndex   PdnDslAtmBondGroupIndexTC
   }

pdnDslAtmBondDslIfIndex OBJECT-TYPE
   SYNTAX      InterfaceIndex
   MAX-ACCESS  not-accessible
   STATUS      current
   DESCRIPTION "Identifies the DSL interface of a link that is to be
                bonded to the group."
   ::= { pdnDslAtmBondMappingEntry 1 }

pdnDslAtmBondBearerNbr OBJECT-TYPE
   SYNTAX      PdnDslAtmBondGroupBearerNumberTC
   MAX-ACCESS  not-accessible
   STATUS      current
   DESCRIPTION "Identifies the bearer number of a link for the DSL line 
                to be bonded to the group."
   ::= { pdnDslAtmBondMappingEntry 2 }

pdnDslAtmBondMappingRowStatus OBJECT-TYPE
   SYNTAX      RowStatus
   MAX-ACCESS  read-create
   STATUS      current
   DESCRIPTION "This object allows create, change, and delete operations 
                on the table."
   ::= { pdnDslAtmBondMappingEntry 3 }

pdnDslAtmBondMappingGroupIndex OBJECT-TYPE
   SYNTAX      PdnDslAtmBondGroupIndexTC
   MAX-ACCESS  read-create
   STATUS      current
   DESCRIPTION "The pdnDslAtmBondGroupIndex which identifies the
                group to which the DSL line and bearer number, which 
                form a link, are to be bound to."
   ::= { pdnDslAtmBondMappingEntry 4 }


-- =================================================
-- == DSL ATM Bond Group Index Mapping Table
-- =================================================
pdnDslAtmBondGroupIndexMappingTable OBJECT-TYPE
   SYNTAX      SEQUENCE OF PdnDslAtmBondGroupIndexMappingEntry
   MAX-ACCESS  not-accessible
   STATUS      current
   DESCRIPTION "The DSL ATM Bond Group Index Mapping Table.
                This table identifies the mapping from the bonding
                group's ifIndex to the bonding group's index."
   ::= { pdnDslAtmBondObjects 5 }

pdnDslAtmBondGroupIndexMappingEntry OBJECT-TYPE
   SYNTAX      PdnDslAtmBondGroupIndexMappingEntry
   MAX-ACCESS  not-accessible
   STATUS      current
   DESCRIPTION "An entry in the DSL ATM Bond Group Index Mapping Table.
                Each entry represents an ifIndex for a bonding group."
   INDEX       { pdnDslAtmBondGroupIfIndex }
   ::= { pdnDslAtmBondGroupIndexMappingTable 1 }

PdnDslAtmBondGroupIndexMappingEntry ::=
   SEQUENCE {
      pdnDslAtmBondGroupIndexMappingIndex    PdnDslAtmBondGroupIndexTC
   }

pdnDslAtmBondGroupIndexMappingIndex OBJECT-TYPE
   SYNTAX      PdnDslAtmBondGroupIndexTC
   MAX-ACCESS  read-only
   STATUS      current
   DESCRIPTION "The pdnDslAtmBondGroupIndex this group ifIndex entry
                maps to."
   ::= { pdnDslAtmBondGroupIndexMappingEntry 1 }


-- =================================================
-- == DSL ATM Bond Group Inverse Mapping Table
-- =================================================
pdnDslAtmBondGroupInvMappingTable OBJECT-TYPE
   SYNTAX      SEQUENCE OF PdnDslAtmBondGroupInvMappingEntry
   MAX-ACCESS  not-accessible
   STATUS      current
   DESCRIPTION "The DSL ATM Bond Group Inverse Mapping Table.
                This table identifies the mapping from a bonding
                group's index and a DSL interface to a bearer.
                This object provides a a mechanism to list bonding
                groups from a group's index."
   REFERENCE   "T1E1.4,  Section 11.4.1, `Group Provisioning'.
                G.998.1, Section 11.4.1, `Group Provisioning'."
   ::= { pdnDslAtmBondObjects 6 }

pdnDslAtmBondGroupInvMappingEntry OBJECT-TYPE
   SYNTAX      PdnDslAtmBondGroupInvMappingEntry
   MAX-ACCESS  not-accessible
   STATUS      current
   DESCRIPTION "An entry in the DSL ATM Bond Inverse Mapping Table.
                Each entry represents a particular bonding group and a
                particular DSL interface."
   INDEX       { pdnDslAtmBondGroupIndex, pdnDslAtmBondDslIfIndex }
   ::= { pdnDslAtmBondGroupInvMappingTable 1 }

PdnDslAtmBondGroupInvMappingEntry ::=
   SEQUENCE {
      pdnDslAtmBondInvMappingBearerNbr  PdnDslAtmBondGroupBearerNumberTC
   }

pdnDslAtmBondInvMappingBearerNbr OBJECT-TYPE
   SYNTAX      PdnDslAtmBondGroupBearerNumberTC
   MAX-ACCESS  read-only
   STATUS      current
   DESCRIPTION "The bearer on a particular DSL interface that is  a
                member of the bonding group."
   ::= { pdnDslAtmBondGroupInvMappingEntry 1 }


-- =================================================
-- == DSL ATM Bond Performance Table
-- =================================================
pdnDslAtmBondPerfTable OBJECT-TYPE
   SYNTAX      SEQUENCE OF PdnDslAtmBondPerfEntry
   MAX-ACCESS  not-accessible
   STATUS      current
   DESCRIPTION "The DSL ATM Bond Current Table.
                This table contains the status and performance 
                information for bonding groups."
   REFERENCE   "T1E1.4,  Section 11.4.2, `Group Performance'.
                G.998.1, Section 11.4.2, `Group Performance'.
                T1E1.4,  Section 11.4.3, `Group Failures'.
                G.998.1, Section 11.4.3, `Group Failures'."
   ::= { pdnDslAtmBondObjects 7 }

pdnDslAtmBondPerfEntry OBJECT-TYPE
   SYNTAX      PdnDslAtmBondPerfEntry
   MAX-ACCESS  not-accessible
   STATUS      current
   DESCRIPTION "An entry in the DSL ATM Bond Performance Table.
                Each entry represents a particular bonding group."
   INDEX       { pdnDslAtmBondGroupIndex }
   ::= { pdnDslAtmBondPerfTable 1 }

PdnDslAtmBondPerfEntry ::=
   SEQUENCE {
      pdnDslAtmBondPerfCurrAtucNetDataRate PdnDslAtmBondGroupDataRateTC,
      pdnDslAtmBondPerfCurrAturNetDataRate PdnDslAtmBondGroupDataRateTC,
      pdnDslAtmBondPerfPrevAtucNetDataRate PdnDslAtmBondGroupDataRateTC,
      pdnDslAtmBondPerfPrevAturNetDataRate PdnDslAtmBondGroupDataRateTC,
      pdnDslAtmBondPerfGroupStatus         PdnDslAtmBondGroupStatusTC,
      pdnDslAtmBondPerfFailReason        PdnDslAtmBondGroupFailReasonTC,
      pdnDslAtmBondPerfFailCount         Counter32,
      pdnDslAtmBondPerfRunTime           Counter32,
      pdnDslAtmBondPerfUAS               Counter32,
      pdnDslAtmBondPerfAtucRxCellLoss    Counter32,
      pdnDslAtmBondPerfAturRxCellLoss    Counter32      
   }

pdnDslAtmBondPerfCurrAtucNetDataRate OBJECT-TYPE
   SYNTAX      PdnDslAtmBondGroupDataRateTC
   UNITS       "bps"  
   MAX-ACCESS  read-only
   STATUS      current
   DESCRIPTION "The current net data rate the bonding group has achieved
                for the downstream direction."
   ::= { pdnDslAtmBondPerfEntry 1 }

pdnDslAtmBondPerfCurrAturNetDataRate OBJECT-TYPE
   SYNTAX      PdnDslAtmBondGroupDataRateTC
   UNITS       "bps"  
   MAX-ACCESS  read-only
   STATUS      current
   DESCRIPTION "The current net data rate the bonding group has achieved
                for the upstream direction."
   ::= { pdnDslAtmBondPerfEntry 2 }

pdnDslAtmBondPerfPrevAtucNetDataRate OBJECT-TYPE
   SYNTAX      PdnDslAtmBondGroupDataRateTC
   UNITS       "bps"  
   MAX-ACCESS  read-only
   STATUS      current
   DESCRIPTION "The previous net data rate the bonding group had 
                achieved for the downstream direction.  This value is 
                set at initialization to prevent a notification from
                being sent."
   ::= { pdnDslAtmBondPerfEntry 3 }

pdnDslAtmBondPerfPrevAturNetDataRate OBJECT-TYPE
   SYNTAX      PdnDslAtmBondGroupDataRateTC
   UNITS       "bps"  
   MAX-ACCESS  read-only
   STATUS      current
   DESCRIPTION "The previous net data rate the bonding group had 
                achieved for the upstream direction.  This value is 
                set at initialization to prevent a notification from
                being sent."
   ::= { pdnDslAtmBondPerfEntry 4 }

pdnDslAtmBondPerfGroupStatus OBJECT-TYPE
   SYNTAX      PdnDslAtmBondGroupStatusTC
   MAX-ACCESS  read-only
   STATUS      current
   DESCRIPTION "The status of the bonding group."
   ::= { pdnDslAtmBondPerfEntry 5 }

pdnDslAtmBondPerfFailReason OBJECT-TYPE
   SYNTAX      PdnDslAtmBondGroupFailReasonTC
   MAX-ACCESS  read-only
   STATUS      current
   DESCRIPTION "The reason the operational status of the bonding group
                is not `operational'."
   ::= { pdnDslAtmBondPerfEntry 6 }

pdnDslAtmBondPerfFailCount OBJECT-TYPE
   SYNTAX      Counter32
   MAX-ACCESS  read-only
   STATUS      current
   DESCRIPTION "A count of the number of times the group was declared
                `unavailable` since last restart."
   ::= { pdnDslAtmBondPerfEntry 7 }

pdnDslAtmBondPerfRunTime OBJECT-TYPE
   SYNTAX      Counter32
   UNITS       "seconds"  
   MAX-ACCESS  read-only
   STATUS      current
   DESCRIPTION "The total accumulated time the bonding group was in 
                the `normal' operational status since last restart."
   ::= { pdnDslAtmBondPerfEntry 8 }

pdnDslAtmBondPerfUAS OBJECT-TYPE
   SYNTAX      Counter32
   UNITS       "seconds"
   MAX-ACCESS  read-only
   STATUS      current
   DESCRIPTION "The total accumulated time the bonding group was 
                unavailable since last restart."
   ::= { pdnDslAtmBondPerfEntry 9 }

pdnDslAtmBondPerfAtucRxCellLoss OBJECT-TYPE
   SYNTAX      Counter32
   MAX-ACCESS  read-only
   STATUS      current
   DESCRIPTION "The total number of cells that are lost at the 
                aggregation output in the upstream direction from the
                bonding group since last restart."
   ::= { pdnDslAtmBondPerfEntry 10 }

pdnDslAtmBondPerfAturRxCellLoss OBJECT-TYPE
   SYNTAX      Counter32
   MAX-ACCESS  read-only
   STATUS      current
   DESCRIPTION "The total number of cells that are lost at the 
                aggregation output in the downstream direction from a 
                bonding group since last restart."
   ::= { pdnDslAtmBondPerfEntry 11 }


-- =================================================
-- == DSL ATM Bond 15-Minute Interval Table
-- =================================================
pdnDslAtmBond15MinIntervalTable OBJECT-TYPE
   SYNTAX      SEQUENCE OF PdnDslAtmBond15MinIntervalEntry
   MAX-ACCESS  not-accessible
   STATUS      current
   DESCRIPTION "The DSL ATM Bond 15-Minute Interval Table.
                This table contains the status and performance 
                information for bonding groups collected in
                 15-minute intervals."
   REFERENCE   "T1E1.4,  Section 11.4.2, `Group Performance'.
                G.998.1, Section 11.4.2, `Group Performance'.
                T1E1.4,  Section 11.4.3, `Group Failures'.
                G.998.1, Section 11.4.3, `Group Failures'."
   ::= { pdnDslAtmBondObjects 8 }

pdnDslAtmBond15MinIntervalEntry OBJECT-TYPE
   SYNTAX      PdnDslAtmBond15MinIntervalEntry
   MAX-ACCESS  not-accessible
   STATUS      current
   DESCRIPTION "An entry in the DSL ATM Bond 15-Minute Interval Table.
                Each entry represents a particular bonding group and a
                particular 15-minute interval."
   INDEX       { pdnDslAtmBondGroupIndex, 
                 pdnDslAtmBond15MinIntervalNumber }
   ::= { pdnDslAtmBond15MinIntervalTable 1 }

PdnDslAtmBond15MinIntervalEntry ::=
   SEQUENCE {
      pdnDslAtmBond15MinIntervalNumber                        Unsigned32,
      pdnDslAtmBond15MinIntervalStartDateAndTime              DateAndTime,
      pdnDslAtmBond15MinIntervalFailCount                     Counter32,
      pdnDslAtmBond15MinIntervalRunTime                       Counter32,
      pdnDslAtmBond15MinIntervalUAS                           Counter32,
      pdnDslAtmBond15MinIntervalAtucRxCellLoss                Counter32,
      pdnDslAtmBond15MinIntervalAturRxCellLoss                Counter32
   }

pdnDslAtmBond15MinIntervalNumber OBJECT-TYPE
   SYNTAX      Unsigned32(1..96)
   MAX-ACCESS  not-accessible
   STATUS      current
   DESCRIPTION "Performance Data Interval number.  Interval 1 is the 
                most recent previous 15-minute interval; interval 96 is
                24 hours ago.  Intervals 2..96 are optional."
   ::= { pdnDslAtmBond15MinIntervalEntry 1 }

pdnDslAtmBond15MinIntervalStartDateAndTime OBJECT-TYPE
   SYNTAX      DateAndTime
   MAX-ACCESS  read-only
   STATUS      current
   DESCRIPTION "Provides a date-time indication of when the interval 
                started."
   ::= { pdnDslAtmBond15MinIntervalEntry 2 }

pdnDslAtmBond15MinIntervalFailCount OBJECT-TYPE
   SYNTAX      Counter32
   MAX-ACCESS  read-only
   STATUS      current
   DESCRIPTION "A count of the number of times the group was declared
                `unavailable` during the interval."
   ::= { pdnDslAtmBond15MinIntervalEntry 3 }

pdnDslAtmBond15MinIntervalRunTime OBJECT-TYPE
   SYNTAX      Counter32
   MAX-ACCESS  read-only
   STATUS      current
   DESCRIPTION "The accumulated time the bonding group was in the
                `normal' operational status during the interval."
   ::= { pdnDslAtmBond15MinIntervalEntry 4 }

pdnDslAtmBond15MinIntervalUAS OBJECT-TYPE
   SYNTAX      Counter32
   MAX-ACCESS  read-only
   STATUS      current
   DESCRIPTION "The accumulated time the bonding group was unavailable
                during the interval,"
   ::= { pdnDslAtmBond15MinIntervalEntry 5 }

pdnDslAtmBond15MinIntervalAtucRxCellLoss OBJECT-TYPE
   SYNTAX      Counter32
   MAX-ACCESS  read-only
   STATUS      current
   DESCRIPTION "The number of cells that are lost at the aggregation
                output in the upstream direction from the bonding group
                during the interval."
   ::= { pdnDslAtmBond15MinIntervalEntry 6 }

pdnDslAtmBond15MinIntervalAturRxCellLoss OBJECT-TYPE
   SYNTAX      Counter32
   MAX-ACCESS  read-only
   STATUS      current
   DESCRIPTION "The number of cells that are lost at the aggregation 
                output in the downstream direction from the bonding 
                group during the interval."
   ::= { pdnDslAtmBond15MinIntervalEntry 7 }


-- =================================================
-- == DSL ATM Bond 1-Day Interval Table
-- =================================================
pdnDslAtmBond1DayIntervalTable OBJECT-TYPE
   SYNTAX      SEQUENCE OF PdnDslAtmBond1DayIntervalEntry
   MAX-ACCESS  not-accessible
   STATUS      current
   DESCRIPTION "The DSL ATM Bond 1-Day Interval Table.
                This table contains the status and performance 
                information for bonding groups collected in
                 1-Day intervals."
   REFERENCE   "T1E1.4,  Section 11.4.2, `Group Performance'.
                G.998.1, Section 11.4.2, `Group Performance'.
                T1E1.4,  Section 11.4.3, `Group Failures'.
                G.998.1, Section 11.4.3, `Group Failures'."
   ::= { pdnDslAtmBondObjects 9 }

pdnDslAtmBond1DayIntervalEntry OBJECT-TYPE
   SYNTAX      PdnDslAtmBond1DayIntervalEntry
   MAX-ACCESS  not-accessible
   STATUS      current
   DESCRIPTION "An entry in the DSL ATM Bond 1-Day Interval Table.
                Each entry represents a particular bonding group and a
                particular 1-day interval."
   INDEX       { pdnDslAtmBondGroupIndex, 
                 pdnDslAtmBond1DayIntervalNumber }
   ::= { pdnDslAtmBond1DayIntervalTable 1 }

PdnDslAtmBond1DayIntervalEntry ::=
   SEQUENCE {
      pdnDslAtmBond1DayIntervalNumber                         Unsigned32,
      pdnDslAtmBond1DayIntervalStartDateAndTime               DateAndTime,
      pdnDslAtmBond1DayIntervalFailCount                      Counter32,
      pdnDslAtmBond1DayIntervalRunTime                        Counter32,
      pdnDslAtmBond1DayIntervalUAS                            Counter32,
      pdnDslAtmBond1DayIntervalAtucRxCellLoss                 Counter32,
      pdnDslAtmBond1DayIntervalAturRxCellLoss                 Counter32
   }

pdnDslAtmBond1DayIntervalNumber OBJECT-TYPE
   SYNTAX      Unsigned32(1..30)
   MAX-ACCESS  not-accessible
   STATUS      current
   DESCRIPTION "Performance Data Interval number.  Interval 1 is the 
                most recent previous 1-day interval; interval 30 is 30
                days ago.  Intervals 2..30 are optional."
   ::= { pdnDslAtmBond1DayIntervalEntry 1 }

pdnDslAtmBond1DayIntervalStartDateAndTime OBJECT-TYPE
   SYNTAX      DateAndTime
   MAX-ACCESS  read-only
   STATUS      current
   DESCRIPTION "Provides a date-time indication of when the interval
                started."
   ::= { pdnDslAtmBond1DayIntervalEntry 2 }

pdnDslAtmBond1DayIntervalFailCount OBJECT-TYPE
   SYNTAX      Counter32
   MAX-ACCESS  read-only
   STATUS      current
   DESCRIPTION "A count of the number of times the group was declared
                `unavailable` during the interval."
   ::= { pdnDslAtmBond1DayIntervalEntry 3 }

pdnDslAtmBond1DayIntervalRunTime OBJECT-TYPE
   SYNTAX      Counter32
   MAX-ACCESS  read-only
   STATUS      current
   DESCRIPTION "The accumulated time the bonding group was in the
                `normal' operational status during the interval."
   ::= { pdnDslAtmBond1DayIntervalEntry 4 }

pdnDslAtmBond1DayIntervalUAS OBJECT-TYPE
   SYNTAX      Counter32
   MAX-ACCESS  read-only
   STATUS      current
   DESCRIPTION "The accumulated time the bonding group was unavailable
                during the interval,"
   ::= { pdnDslAtmBond1DayIntervalEntry 5 }

pdnDslAtmBond1DayIntervalAtucRxCellLoss OBJECT-TYPE
   SYNTAX      Counter32
   MAX-ACCESS  read-only
   STATUS      current
   DESCRIPTION "The number of cells that are lost at the aggregation
                output in the upstream direction from a bonding group
                during the interval."
   ::= { pdnDslAtmBond1DayIntervalEntry 6 }

pdnDslAtmBond1DayIntervalAturRxCellLoss OBJECT-TYPE
   SYNTAX      Counter32
   MAX-ACCESS  read-only
   STATUS      current
   DESCRIPTION "The number of cells that are lost at the aggregation 
                output in the downstream direction from the bonding 
                group during the interval."
   ::= { pdnDslAtmBond1DayIntervalEntry 7 }


-- =================================================
-- == DSL ATM Bond Link Table
-- =================================================
pdnDslAtmBondLinkTable OBJECT-TYPE
   SYNTAX      SEQUENCE OF PdnDslAtmBondLinkEntry
   MAX-ACCESS  not-accessible
   STATUS      current
   DESCRIPTION "The DSL ATM Bond Link Table.
                This table contains the current status information for
                a link in a bonding group."
   REFERENCE   "T1E1.4, Section 9.1.3, `Frequency of Autonomous Status
                Messages'.
                G.998.1, Section 9.1.3, `Frequency of Autonomous Status
                Messages'.
                T1E1.4, Section 9.1.4, `Format of the Autonomous Status 
                Message (ASM)', Table 9-1`ASM Message Format'.
                G.998.1, Section 9.1.4, `Format of the Autonomous Status 
                Message (ASM)', Table 9-1`ASM Message Format'."
   ::= { pdnDslAtmBondObjects 10 }

pdnDslAtmBondLinkEntry OBJECT-TYPE
   SYNTAX      PdnDslAtmBondLinkEntry
   MAX-ACCESS  not-accessible
   STATUS      current
   DESCRIPTION "An entry in the DSL ATM Bond Link Table.
                each entry represents a DSL interface on a particular 
                bonding group."
   INDEX       { pdnDslAtmBondGroupIndex,
                 pdnDslAtmBondDslIfIndex }
   ::= { pdnDslAtmBondLinkTable 1 }

PdnDslAtmBondLinkEntry ::=
   SEQUENCE {
      pdnDslAtmBondLinkAtucRxLinkStatus    PdnDslAtmBondLinkStatusAsmTC,
      pdnDslAtmBondLinkAturRxLinkStatus    PdnDslAtmBondLinkStatusAsmTC,
      pdnDslAtmBondLinkAtucTxLinkStatus    PdnDslAtmBondLinkStatusAsmTC,
      pdnDslAtmBondLinkAturTxLinkStatus    PdnDslAtmBondLinkStatusAsmTC,
      pdnDslAtmBondLinkAtucAsmRxStatus     PdnDslAtmBondAsmRxStatusTC,
      pdnDslAtmBondLinkAturAsmRxStatus     PdnDslAtmBondAsmRxStatusTC
   }

pdnDslAtmBondLinkAtucRxLinkStatus OBJECT-TYPE
   SYNTAX      PdnDslAtmBondLinkStatusAsmTC
   MAX-ACCESS  read-only
   STATUS      current
   DESCRIPTION "The status of the Rx link in a bonded group in the 
                upstream direction."
   ::= { pdnDslAtmBondLinkEntry 1 }

pdnDslAtmBondLinkAturRxLinkStatus OBJECT-TYPE
   SYNTAX      PdnDslAtmBondLinkStatusAsmTC
   MAX-ACCESS  read-only
   STATUS      current
   DESCRIPTION "The status of the Rx link in a bonded group in the 
                downstream direction."
   ::= { pdnDslAtmBondLinkEntry 2 }

pdnDslAtmBondLinkAtucTxLinkStatus OBJECT-TYPE
   SYNTAX      PdnDslAtmBondLinkStatusAsmTC
   MAX-ACCESS  read-only
   STATUS      current
   DESCRIPTION "The status of the Tx link in a bonded group in the 
                downstream direction."
   ::= { pdnDslAtmBondLinkEntry 3 }

pdnDslAtmBondLinkAturTxLinkStatus OBJECT-TYPE
   SYNTAX      PdnDslAtmBondLinkStatusAsmTC
   MAX-ACCESS  read-only
   STATUS      current
   DESCRIPTION "The status of the Rx link in a bonded group in the 
                upstream direction."
   ::= { pdnDslAtmBondLinkEntry 4 }

pdnDslAtmBondLinkAtucAsmRxStatus OBJECT-TYPE
   SYNTAX      PdnDslAtmBondAsmRxStatusTC
   MAX-ACCESS  read-only
   STATUS      current
   DESCRIPTION "The status of ASMs received for the link in a bonded 
                in the upstream direction."
   ::= { pdnDslAtmBondLinkEntry 5 }

pdnDslAtmBondLinkAturAsmRxStatus OBJECT-TYPE
   SYNTAX      PdnDslAtmBondAsmRxStatusTC
   MAX-ACCESS  read-only
   STATUS      current
   DESCRIPTION "The status of ASMs received for the link in a bonded 
                in the downstream direction."
   ::= { pdnDslAtmBondLinkEntry 6 }


-- ===================================================
-- == DSL ATM Bond Alarm Configuration Profile Table
-- ===================================================
pdnDslAtmBondAlarmConfProfileTable OBJECT-TYPE
   SYNTAX      SEQUENCE OF PdnDslAtmBondAlarmConfProfileEntry
   MAX-ACCESS  not-accessible
   STATUS      current
   DESCRIPTION "The DSL ATM Bond Alarm Configuration Profile Table.
                This table contains the alarm configuration profiles
                for DSL ATM Bonding."
   ::= { pdnDslAtmBondObjects 11 }

pdnDslAtmBondAlarmConfProfileEntry OBJECT-TYPE
   SYNTAX      PdnDslAtmBondAlarmConfProfileEntry
   MAX-ACCESS  not-accessible
   STATUS      current
   DESCRIPTION "An entry in the DSL ATM Bond Alarm Configuration 
                Profile Table.  Each entry represents a single alarm 
                configuration profile.  Profiles may be created/deleted
                using the RowStatus mechanism not including the default
                profile.  A default profile with
                an index of `DEFVAL' will always exist and its 
                parameters will be set to implementation-specific 
                values."
   INDEX       { IMPLIED pdnDslAtmBondAlarmConfProfileName }
   ::= { pdnDslAtmBondAlarmConfProfileTable 1 }

PdnDslAtmBondAlarmConfProfileEntry ::=
   SEQUENCE {
      pdnDslAtmBondAlarmConfProfileName            SnmpAdminString,
      pdnDslAtmBondAlarmConfRowStatus              RowStatus,
      pdnDslAtmBondAlarmConfNbrRefs                Unsigned32,
      pdnDslAtmBondAlarmConfAtucThreshRateUp       Integer32,
      pdnDslAtmBondAlarmConfAturThreshRateUp       Integer32,
      pdnDslAtmBondAlarmConfAtucThreshRateDown     Integer32,
      pdnDslAtmBondAlarmConfAturThreshRateDown     Integer32
   }

pdnDslAtmBondAlarmConfProfileName OBJECT-TYPE
   SYNTAX      SnmpAdminString(SIZE(1..32))
   MAX-ACCESS  not-accessible
   STATUS      current
   DESCRIPTION "This object is the index for the table and identifies
                a unique row in the table.  A default profile with an 
                index of `DEFVAL' will always exist and its parameters
                will be set to implementation-specific values."
   ::= { pdnDslAtmBondAlarmConfProfileEntry 1 }

pdnDslAtmBondAlarmConfRowStatus OBJECT-TYPE
   SYNTAX      RowStatus
   MAX-ACCESS  read-create
   STATUS      current
   DESCRIPTION "This object allows profiles to be created to deleted.
                The delete operation can only occur when the 
                pdnDslAtmBondAlarmConfNbrRefs is 0 meaning that there
                are no entries in the pdnDslAtmBondGroupTable that
                reference this group."
   ::= { pdnDslAtmBondAlarmConfProfileEntry 2 }

pdnDslAtmBondAlarmConfNbrRefs OBJECT-TYPE
   SYNTAX      Unsigned32(0..2147483647)
   MAX-ACCESS  read-only
   STATUS      current
   DESCRIPTION "The number of entries in the pdnDslAtmBondGroupTable
                that reference this profile."
   ::= { pdnDslAtmBondAlarmConfProfileEntry 3 }

pdnDslAtmBondAlarmConfAtucThreshRateUp OBJECT-TYPE
   SYNTAX      Integer32(0..2147483647)
   UNITS       "bps"  
   MAX-ACCESS  read-create
   STATUS      current
   DESCRIPTION "Configured change in rate, in bps, causing a 
                pdnDslAtmBondAtucRateChange notification.  The 
                notification is produced when 
                current rate >= previous rate plus the value of this
                object.  A value of `0' will disable the trap."
   ::= { pdnDslAtmBondAlarmConfProfileEntry 4 }

pdnDslAtmBondAlarmConfAturThreshRateUp OBJECT-TYPE
   SYNTAX      Integer32(0..2147483647)
   UNITS       "bps"  
   MAX-ACCESS  read-create
   STATUS      current
   DESCRIPTION "Configured change in rate, in bps, causing a 
                pdnDslAtmBondAturRateChange notification.  The 
                notification is produced when 
                current rate >= previous rate plus the value of this
                object.  A value of `0' will disable the trap."
   ::= { pdnDslAtmBondAlarmConfProfileEntry 5 }

pdnDslAtmBondAlarmConfAtucThreshRateDown OBJECT-TYPE
   SYNTAX      Integer32(0..2147483647)
   UNITS       "bps"  
   MAX-ACCESS  read-create
   STATUS      current
   DESCRIPTION "Configured change in rate, in bps, causing a 
                pdnDslAtmBondAtucRateChange notification.  The 
                notification is produced when 
                current rate <= previous rate minus the value of this
                object.  A value of `0' will disable the trap."
   ::= { pdnDslAtmBondAlarmConfProfileEntry 6 }

pdnDslAtmBondAlarmConfAturThreshRateDown OBJECT-TYPE
   SYNTAX      Integer32(0..2147483647)
   UNITS       "bps"  
   MAX-ACCESS  read-create
   STATUS      current
   DESCRIPTION "Configured change in rate, in bps, causing a 
                pdnDslAtmBondAturRateChange notification.  The 
                notification is produced when 
                current rate <= previous rate minus the value of this
                object.  A value of `0' will disable the trap."
   ::= { pdnDslAtmBondAlarmConfProfileEntry 7 }




-- ======================================================================
-- ==              Accessible for Notifications (AFNs)                 ==
-- ======================================================================
-- None defined



-- ======================================================================
-- ==                  Traps/Notifications                             ==
-- ======================================================================

pdnDslAtmBondAtucRateChange NOTIFICATION-TYPE
   OBJECTS {
      pdnDslAtmBondGroupIfIndex,
      pdnDslAtmBondPerfCurrAtucNetDataRate,
      pdnDslAtmBondPerfPrevAtucNetDataRate
   }
   STATUS current
   DESCRIPTION "The downstream transmit rate has changed."
   ::= { pdnDslAtmBondNotifications 1 }
   
pdnDslAtmBondAturRateChange NOTIFICATION-TYPE
   OBJECTS {
      pdnDslAtmBondGroupIfIndex,
      pdnDslAtmBondPerfCurrAturNetDataRate,
      pdnDslAtmBondPerfPrevAturNetDataRate
   }
   STATUS current
   DESCRIPTION "The upstream transmit rate has changed."
   ::= { pdnDslAtmBondNotifications 2 }

pdnDslAtmBondGroupStatusChange NOTIFICATION-TYPE
   OBJECTS {
      pdnDslAtmBondGroupIfIndex,
      pdnDslAtmBondPerfGroupStatus,
      pdnDslAtmBondPerfFailReason
   }
   STATUS      current
   DESCRIPTION "The operational status of the group has changed."
   ::= { pdnDslAtmBondNotifications 3 }



-- ======================================================================
-- ==                  Conformance Information                         ==
-- ======================================================================

pdnDslAtmBondCompliances  OBJECT IDENTIFIER ::= 
   { pdnDslAtmBondConformance 1 }
pdnDslAtmBondGroups       OBJECT IDENTIFIER ::= 
   { pdnDslAtmBondConformance 2 }


-- ===========================
-- == Compliance Statements ==
-- ===========================


pdnDslAtmBondMIBCompliance MODULE-COMPLIANCE
   STATUS      current
   DESCRIPTION "The compliance statement for the entities which
                implement the pdnDslAtmBondMIB."
   MODULE      -- this module

   MANDATORY-GROUPS {
         pdnDslAtmBondGroup,
         pdnDslAtmBondMappingGroup,
         pdnDslAtmBondPerfAggDataRateGroup,
         pdnDslAtmBondPerfBondGroupStatusGroup,
         pdnDslAtmBondNotificationsGroup
      }

   --
   -- Optional Groups
   --

   GROUP       pdnDslAtmBondMaxRateGroup
   DESCRIPTION "This group is only required for implementations that
                need to be able to configure the maximum net data rate
                a bonding group is allowed to achieve."

   GROUP       pdnDslAtmBondMinRateGroup
   DESCRIPTION "This group is only required for implementations that
                need to be able to configure the minimum net data rate
                a bonding group is allowed to achieve."

   GROUP       pdnDslAtmBondDiffDelayGroup
   DESCRIPTION "This group is only required for implementations that
                need to be able to configure the maximum differential
                delay tolerance among member links in a bonding group."

   GROUP       pdnDslAtmBondGroupStatusNotifyEnabledGroup
   DESCRIPTION "This group is only required for implementations that
                need to be able to configure whether or not 
                notifications will be generated when the status of
                a particular bonding group changes."

   GROUP       pdnDslAtmBondIndexMappingGroup
   DESCRIPTION "This group is only required for implementations that
                require mapping from a group's ifIndex to the 
                group's index."

   GROUP       pdnDslAtmBondInvMappingGroup
   DESCRIPTION "This group is only required for implementations that
                require inverse mapping support."

   GROUP       pdnDslAtmBondDateAndTimeGroup
   DESCRIPTION "This group is only required for implementations that
                require a date-time stamp for a particular entry in
                an interval table."

   GROUP       pdnDslAtmBondRunTimeGroup
   DESCRIPTION "This group is only required for implementations that
                require tracking of the time a bonding group is 
                `operational'."

   GROUP       pdnDslAtmBondRxCellLossGroup
   DESCRIPTION "This group is only required for implementations that
                require tracking of the number of cells that are lost
                at the aggregation output from a bonding group."

   GROUP       pdnDslAtmBondPerfFailReasonGroup
   DESCRIPTION "This group is only required for implementations that
                require tracking of the reason a bonding group is 
                failing to become `operational'."

   GROUP       pdnDslAtmBondFailCountGroup
   DESCRIPTION "This group is only required for implementations that
                require tracking of the number of times a bonding group
                was declared `unavailable'."

   GROUP       pdnDslAtmBondUASGroup
   DESCRIPTION "This group is only required for implementations that
                require tracking of the time the bonding group was
                unavailable."

   GROUP       pdnDslAtmBondTrafficCapGroup
   DESCRIPTION "This group is only required for implementations that
                require tracking of the current status of a link
                in a bonded group with respect to carrying bonded
                traffic."

   GROUP       pdnDslATmBondAsmRxStatusGroup
   DESCRIPTION "This group is only required for implementations that
                require the tracking of the status of reception of ASMs
                for a link in a bonded group."

   GROUP       pdnDslAtmBondAlarmConfProfileGroup
   DESCRIPTION "This group is only required for implementations that
                require the support for alarm profiles."

   GROUP       pdnDslAtmBondAlarmConfAtucThreshRateGroup
   DESCRIPTION "This group is only required for implementations that
                require thresholds for rate changes in the downstream
                direction."

   GROUP       pdnDslAtmBondAlarmConfAturThreshRateGroup
   DESCRIPTION "This group is only required for implementations that
                require thresholds for rate changes in the upstream
                direction."



   OBJECT pdnDslAtmBondInvMappingBearerNbr
   SYNTAX      Integer32(1)
   DESCRIPTION "An implementation only has to support 1 bearer."


   ::= { pdnDslAtmBondCompliances 1 }


-- ==========================
-- == Units of Conformance ==
-- ==========================

pdnDslAtmBondObjGroups   OBJECT IDENTIFIER ::= { pdnDslAtmBondGroups 1 }
pdnDslAtmBondAfnGroups   OBJECT IDENTIFIER ::= { pdnDslAtmBondGroups 2 }
pdnDslAtmBondNtfyGroups  OBJECT IDENTIFIER ::= { pdnDslAtmBondGroups 3 }

-- ===================
-- == Object Groups ==
-- ===================

pdnDslAtmBondGroup OBJECT-GROUP
   OBJECTS {
      pdnDslAtmBondNextGroupIndex,
      pdnDslAtmBondNbrOfGroups,
      pdnDslAtmBondGroupRowStatus,
      pdnDslAtmBondGroupNbrRefs,
      pdnDslAtmBondGroupIfIndex,
      pdnDslAtmBondGroupID
    }
    STATUS      current
    DESCRIPTION "General configuration/definition of a bonding group."
    ::= { pdnDslAtmBondObjGroups 1 }

pdnDslAtmBondMaxRateGroup OBJECT-GROUP
   OBJECTS {
      pdnDslAtmBondGroupAtucMaxNetDataRate,
      pdnDslAtmBondGroupAturMaxNetDataRate
    }
    STATUS      current
    DESCRIPTION "Configuration of the maximum net data rate a bonding
                 group is allowed to achieve."
    ::= { pdnDslAtmBondObjGroups 2 }

pdnDslAtmBondMinRateGroup OBJECT-GROUP
   OBJECTS {
      pdnDslAtmBondGroupAtucMinNetDataRate,
      pdnDslAtmBondGroupAturMinNetDataRate
    }
    STATUS      current
    DESCRIPTION "Configuration of the minimum net data rate a bonding
                 group is allowed to achieve."
    ::= { pdnDslAtmBondObjGroups 3 }

pdnDslAtmBondDiffDelayGroup OBJECT-GROUP
   OBJECTS {
      pdnDslAtmBondGroupAtucDiffDelay,
      pdnDslAtmBondGroupAturDiffDelay

    }
    STATUS      current
    DESCRIPTION "Configuration of maximum differential delay among 
                 member links in a bonding group."
    ::= { pdnDslAtmBondObjGroups 4 }

pdnDslAtmBondGroupStatusNotifyEnabledGroup OBJECT-GROUP
   OBJECTS {
      pdnDslAtmBondGroupStatusNotifyEnabled
   }
   STATUS      current
   DESCRIPTION "Configuration of notifications for changes to the
                status of a bonding group."
   ::= { pdnDslAtmBondObjGroups 5 }

pdnDslAtmBondMappingGroup OBJECT-GROUP
   OBJECTS {
      pdnDslAtmBondMappingRowStatus,
      pdnDslAtmBondMappingGroupIndex
   }
   STATUS      current
   DESCRIPTION "Map a DSL interface and a bearer to a bonding group."
   ::= { pdnDslAtmBondObjGroups 6 }

pdnDslAtmBondIndexMappingGroup OBJECT-GROUP
   OBJECTS {
      pdnDslAtmBondGroupIndexMappingIndex
   }
   STATUS       current
   DESCRIPTION "Map from a bonding group's ifIndex to the bonding
                group's index."
   ::= { pdnDslAtmBondObjGroups 7 }

pdnDslAtmBondInvMappingGroup OBJECT-GROUP
   OBJECTS {
      pdnDslAtmBondInvMappingBearerNbr
   }
   STATUS       current
   DESCRIPTION "Map from a bonding group and a DSL interface to a 
                bearer."
   ::= { pdnDslAtmBondObjGroups 8 }

pdnDslAtmBondPerfAggDataRateGroup OBJECT-GROUP
   OBJECTS {
      pdnDslAtmBondPerfCurrAtucNetDataRate,
      pdnDslAtmBondPerfCurrAturNetDataRate,
      pdnDslAtmBondPerfPrevAtucNetDataRate,
      pdnDslAtmBondPerfPrevAturNetDataRate
   }
   STATUS      current
   DESCRIPTION "Status of the net data rate the bonding group has 
                currently or had previously achieved."
   ::= { pdnDslAtmBondObjGroups 9 }

pdnDslAtmBondPerfBondGroupStatusGroup OBJECT-GROUP
   OBJECTS {
      pdnDslAtmBondPerfGroupStatus
   }
   STATUS      current
   DESCRIPTION "Current status of the bonding group."
   ::= { pdnDslAtmBondObjGroups 10 }

pdnDslAtmBondDateAndTimeGroup OBJECT-GROUP
   OBJECTS {
      pdnDslAtmBond15MinIntervalStartDateAndTime,
      pdnDslAtmBond1DayIntervalStartDateAndTime
   }
   STATUS      current
   DESCRIPTION "Date-time stamp of when an interval started."
   ::= { pdnDslAtmBondObjGroups 11 }

pdnDslAtmBondRunTimeGroup OBJECT-GROUP
   OBJECTS {
      pdnDslAtmBondPerfRunTime,
      pdnDslAtmBond15MinIntervalRunTime,
      pdnDslAtmBond1DayIntervalRunTime
   }
   STATUS      current
   DESCRIPTION "The tracking of time a bonding group is `operational'."
   ::= { pdnDslAtmBondObjGroups 12 }

pdnDslAtmBondRxCellLossGroup OBJECT-GROUP
   OBJECTS {
      pdnDslAtmBondPerfAtucRxCellLoss,
      pdnDslAtmBondPerfAturRxCellLoss,
      pdnDslAtmBond15MinIntervalAtucRxCellLoss,
      pdnDslAtmBond15MinIntervalAturRxCellLoss,
      pdnDslAtmBond1DayIntervalAtucRxCellLoss,
      pdnDslAtmBond1DayIntervalAturRxCellLoss
   }
   STATUS      current
   DESCRIPTION "The tracking the total number of cells that are lost
                at the aggregation output from a bonding group."
   ::= { pdnDslAtmBondObjGroups 13 }

pdnDslAtmBondPerfFailReasonGroup OBJECT-GROUP
   OBJECTS {
      pdnDslAtmBondPerfFailReason
   }
   STATUS      current
   DESCRIPTION "The reason the operational status of the bonding group 
                is not `operational'."
   ::= { pdnDslAtmBondObjGroups 14 }

pdnDslAtmBondFailCountGroup OBJECT-GROUP
   OBJECTS {
      pdnDslAtmBondPerfFailCount,
      pdnDslAtmBond15MinIntervalFailCount,
      pdnDslAtmBond1DayIntervalFailCount
   }
   STATUS      current
   DESCRIPTION "The number of times a bonding group was declared 
                `unavailable'."
   ::= { pdnDslAtmBondObjGroups 15 }

pdnDslAtmBondUASGroup OBJECT-GROUP
   OBJECTS {
      pdnDslAtmBondPerfUAS,
      pdnDslAtmBond15MinIntervalUAS,
      pdnDslAtmBond1DayIntervalUAS
   }
   STATUS      current
   DESCRIPTION "The time a bonding group was unavailable."
   ::= { pdnDslAtmBondObjGroups 16 }

pdnDslAtmBondTrafficCapGroup OBJECT-GROUP
   OBJECTS {
      pdnDslAtmBondLinkAtucRxLinkStatus,
      pdnDslAtmBondLinkAturRxLinkStatus,
      pdnDslAtmBondLinkAtucTxLinkStatus,
      pdnDslAtmBondLinkAturTxLinkStatus
   }
   STATUS      current
   DESCRIPTION "Current status of the link in a bonded group with
                respect to carrying bonded traffic."
   ::= { pdnDslAtmBondObjGroups 17 }

pdnDslATmBondAsmRxStatusGroup OBJECT-GROUP
   OBJECTS {
      pdnDslAtmBondLinkAtucAsmRxStatus,
      pdnDslAtmBondLinkAturAsmRxStatus
   }
   STATUS      current
   DESCRIPTION "Status of the reception of ASMs for a link in a bonded
                group."
   ::= { pdnDslAtmBondObjGroups 18 }

pdnDslAtmBondAlarmConfProfileGroup OBJECT-GROUP
   OBJECTS {
       pdnDslAtmBondGroupAlarmConfProfileName,
       pdnDslAtmBondAlarmConfRowStatus,
       pdnDslAtmBondAlarmConfNbrRefs
   }
   STATUS      current
   DESCRIPTION "Provides the ability to create or delete alarm 
                profiles."
   ::= { pdnDslAtmBondObjGroups 19 }

pdnDslAtmBondAlarmConfAtucThreshRateGroup OBJECT-GROUP
   OBJECTS {
      pdnDslAtmBondAlarmConfAtucThreshRateUp,
      pdnDslAtmBondAlarmConfAtucThreshRateDown
   }
   STATUS      current
   DESCRIPTION "Provides the ability to configure thresholds for
                rate changes in the downstream direction."
   ::=  { pdnDslAtmBondObjGroups 20 }

pdnDslAtmBondAlarmConfAturThreshRateGroup OBJECT-GROUP
   OBJECTS {
      pdnDslAtmBondAlarmConfAturThreshRateUp,
      pdnDslAtmBondAlarmConfAturThreshRateDown
   }
   STATUS      current
   DESCRIPTION "Provides the ability to configure thresholds for
                rate changes in the upstream direction."
   ::=  { pdnDslAtmBondObjGroups 21 }




-- ==================================
-- == Accessible for Notify Groups ==
-- ==================================
-- None.



-- =========================
-- == Notification Groups ==
-- =========================

pdnDslAtmBondNotificationsGroup NOTIFICATION-GROUP
   NOTIFICATIONS {
      pdnDslAtmBondAtucRateChange,
      pdnDslAtmBondAturRateChange,
      pdnDslAtmBondGroupStatusChange
   }
   STATUS      current
   DESCRIPTION "The collection of notifications for the MIB module."
   ::= { pdnDslAtmBondNtfyGroups 1 }


-- =========
-- == END ==
-- =========
END
