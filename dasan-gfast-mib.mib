--
-- DASAN-GFAST-MIB.my
-- MIB generated by MG-SOFT Visual MIB Builder Version 6.0  Build 88
-- Tuesday, January 17, 2017 at 14:38:18
--

	DASAN-GFAST-MIB DEFINITIONS ::= BEGIN
 
		IMPORTS
			dasanEvents, dasanMgmt			
				FROM DASAN-SMI			
			ifIndex			
				FROM IF-MIB			
			IpAddress, Integer32, Counter32, Counter64, OBJECT-TYPE, 
			MODULE-IDENTITY			
				FROM SNMPv2-SMI			
			TEXTUAL-CONVENTION			
				FROM SNMPv2-TC;
	
	
--  March 26, 2014 at 00:00 GMT
		-- 1.3.6.1.4.1.6296.9.102
		gFastMIB MODULE-IDENTITY 
			LAST-UPDATED "201507210000Z"		-- July 21, 2015 at 00:00 GMT
			ORGANIZATION 
				"Dasan Co., Ltd."
			CONTACT-INFO 
				"Dasan Co., Ltd."
			DESCRIPTION 
				"The MIB module to describe G-FAST."
			::= { dasanMgmt 102 }

		
	
--
-- Type definitions
--
	
		DisplayString ::= OCTET STRING

	
--
-- Textual conventions
--
	
		EntryStatus ::= TEXTUAL-CONVENTION
			STATUS current
			DESCRIPTION 
				"The status of a table entry.
				
				Setting this object to the value invalid(4) has the
				effect of invalidating the corresponding entry.
				That is, it effectively disassociates the mapping
				identified with said entry.
				It is an implementation-specific matter as to whether
				the.wmdser removes an invalidated entry from the table.
				Accordingly, management stations must be prepared to
				receive tabular information from.wmdsers nthat corresponds
				to entries currently not in use.  Proper
				interpretation of such entries requires examination
				of the relevant EntryStatus object.
				
				An existing instance of this object cannot be set to
				createRequest(2).  This object may only be set to
				createRequest(2) when this instance is created.  When
				this object is created, the.wmdser may wish to create
				supplemental object instances with default values
				to complete a conceptual row in this table.  Because the
				
				creation of these default objects is entirely at the option
				of the.wmdser, the manager must not assume that any will be
				created, but may make use of any that are created.
				Immediately after completing the create operation, the.wmdser
				must set this object to underCreation(3).
				
				When in the underCreation(3) state, an entry is allowed to
				exist in a possibly incomplete, possibly inconsistent state,
				usually to allow it to be modified in multiple PDUs.  When in
				this state, an entry is not fully active.
				Entries shall exist in the underCreation(3) state until
				the management station is finished configuring the entry
				and sets this object to valid(1) or aborts, setting this
				object to invalid(4).  If the.wmdser determines that an
				entry has been in the underCreation(3) state for an
				abnormally long time, it may decide that the management
				station has crashed.  If the.wmdser makes this decision,
				it may set this object to invalid(4) to reclaim the
				entry.  A prudent.wmdser will understand that the
				management station may need to wait for human input
				and will allow for that possibility in its
				determination of this abnormally long period.
				
				An entry in the valid(1) state is fully configured and
				consistent and fully represents the configuration or
				operation such a row is intended to represent.  For
				example, it could be a statistical function that is
				configured and active, or a filter that is available
				in the list of filters processed by the packet capture
				process.
				
				A manager is restricted to changing the state of an entry in
				the following ways:
				
				     To:       valid  createRequest  underCreation  invalid
				From:
				valid             OK             NO             OK       OK
				createRequest    N/A            N/A            N/A      N/A
				underCreation     OK             NO             OK       OK
				invalid           NO             NO             NO       OK
				nonExistent       NO             OK             NO       OK
				
				In the table above, it is not applicable to move the state
				from the createRequest state to any other state because the
				manager will never find the variable in that state.  The
				nonExistent state is not a value of the enumeration, rather
				it means that the entryStatus variable does not exist at all.
				
				An.wmdser may allow an entryStatus variable to change state in
				additional ways, so long as the semantics of the states are
				followed.  This allowance is made to ease the implementation of
				the.wmdser and is made despite the fact that managers should
				never exercise these additional state transitions."
			SYNTAX INTEGER
				{
				valid(1),
				createRequest(2),
				underCreation(3),
				invalid(4)
				}

	
--
-- Node definitions
--
	
		-- 1.3.6.1.4.1.6296.9.102.1
		gfastGroup OBJECT IDENTIFIER ::= { gFastMIB 1 }

		
--  ********************************************************************
-- * Define Group Object Identifier
-- ********************************************************************
		-- 1.3.6.1.4.1.6296.9.102.1.0
		gfastNotifPrefix OBJECT IDENTIFIER ::= { gfastGroup 0 }

		
		-- 1.3.6.1.4.1.6296.9.102.1.1
		gfastDeviceGroup OBJECT IDENTIFIER ::= { gfastGroup 1 }

		
--  *********************************************************************
-- * gfastDeviceGroup :
-- *********************************************************************
		-- 1.3.6.1.4.1.6296.9.102.1.1.1
		gfastDevTddMf OBJECT-TYPE
			SYNTAX INTEGER
			MAX-ACCESS read-only
			STATUS current
			DESCRIPTION
				"Specifies the gfast number of symbols in a TDD frame."
			::= { gfastDeviceGroup 1 }

		
		-- 1.3.6.1.4.1.6296.9.102.1.1.2
		gfastDevTddMds OBJECT-TYPE
			SYNTAX INTEGER (10..32)
			MAX-ACCESS read-write
			STATUS current
			DESCRIPTION
				"Specifies the gfast number of DS symbols in a TDD frame."
			::= { gfastDeviceGroup 2 }

		
		-- 1.3.6.1.4.1.6296.9.102.1.1.3
		gfastDevReboot OBJECT-TYPE
			SYNTAX INTEGER
				{
				noaction(0),
				reboot(1)
				}
			MAX-ACCESS read-write
			STATUS current
			DESCRIPTION
				" Controls the Gfast DSP to reboot."
			::= { gfastDeviceGroup 3 }

		
		-- 1.3.6.1.4.1.6296.9.102.1.1.4
		gfastDevLineMode OBJECT-TYPE
			SYNTAX INTEGER
				{
				gfast-only(0),
				vdsl-compatible(1)
				}
			MAX-ACCESS read-write
			STATUS current
			DESCRIPTION
				" Controls the Gfast Line Mode."
			::= { gfastDeviceGroup 4 }

		
		-- 1.3.6.1.4.1.6296.9.102.1.1.5
		gfastDevSyslogRateChange OBJECT-TYPE
			SYNTAX INTEGER (1..100000)
			MAX-ACCESS read-write
			STATUS current
			DESCRIPTION
				"Specifies the gfast syslog rate-change bps. unit is Kbps."
			::= { gfastDeviceGroup 5 }

		
		-- 1.3.6.1.4.1.6296.9.102.1.1.6
		gfastDevAutoRateLimit OBJECT-TYPE
			SYNTAX INTEGER
				{
				disable(0),
				enable(1)
				}
			MAX-ACCESS read-write
			STATUS current
			DESCRIPTION
				"Specifies the gFastMIB System Port Auto Rate-Limit."
			::= { gfastDeviceGroup 6 }

		
		-- 1.3.6.1.4.1.6296.9.102.1.2
		gfastPortGroup OBJECT IDENTIFIER ::= { gfastGroup 2 }

		
--  *********************************************************************
-- * gfastPortGroup
-- *********************************************************************
-- *********************************************************************
-- * Port Table Group
-- *********************************************************************
		-- 1.3.6.1.4.1.6296.9.102.1.2.1
		gfastPortTable OBJECT-TYPE
			SYNTAX SEQUENCE OF GfastPortEntry
			MAX-ACCESS not-accessible
			STATUS current
			DESCRIPTION
				"This table includes common attributes describing gFastMIB
				System Port Information."
			::= { gfastPortGroup 1 }

		
		-- 1.3.6.1.4.1.6296.9.102.1.2.1.1
		gfastPortEntry OBJECT-TYPE
			SYNTAX GfastPortEntry
			MAX-ACCESS not-accessible
			STATUS current
			DESCRIPTION
				"An entry in gfastPortTable."
			INDEX { gfastPortIndex }
			::= { gfastPortTable 1 }

		
		GfastPortEntry ::=
			SEQUENCE { 
				gfastPortIndex
					INTEGER,
				gfastPortProfileID
					INTEGER,
				gfastPortProfileName
					DisplayString,
				gfastPortAdminCommand
					INTEGER,
				gfastPortRestartCommand
					INTEGER
			 }

		-- 1.3.6.1.4.1.6296.9.102.1.2.1.1.1
		gfastPortIndex OBJECT-TYPE
			SYNTAX INTEGER (1..16)
			MAX-ACCESS read-only
			STATUS current
			DESCRIPTION
				"Specifies the gFastMIB System Port index."
			::= { gfastPortEntry 1 }

		
		-- 1.3.6.1.4.1.6296.9.102.1.2.1.1.2
		gfastPortProfileID OBJECT-TYPE
			SYNTAX INTEGER
			MAX-ACCESS read-only
			STATUS current
			DESCRIPTION
				"Specifies the gFastMIB Profile ID."
			::= { gfastPortEntry 2 }

		
		-- 1.3.6.1.4.1.6296.9.102.1.2.1.1.3
		gfastPortProfileName OBJECT-TYPE
			SYNTAX DisplayString
			MAX-ACCESS read-only
			STATUS current
			DESCRIPTION
				"Defines the Profile Name."
			::= { gfastPortEntry 3 }

		
		-- 1.3.6.1.4.1.6296.9.102.1.2.1.1.4
		gfastPortAdminCommand OBJECT-TYPE
			SYNTAX INTEGER
				{
				disable(0),
				enable(1)
				}
			MAX-ACCESS read-write
			STATUS current
			DESCRIPTION
				" Controls the Gfast Port admin mode."
			::= { gfastPortEntry 4 }

		
		-- 1.3.6.1.4.1.6296.9.102.1.2.1.1.5
		gfastPortRestartCommand OBJECT-TYPE
			SYNTAX INTEGER
				{
				noaction(0),
				restart(1)
				}
			MAX-ACCESS read-write
			STATUS current
			DESCRIPTION
				" Controls the Gfast Port to restart."
			::= { gfastPortEntry 5 }

		
--  *******************************************************************
-- * Port Status Table Group
-- *******************************************************************
		-- 1.3.6.1.4.1.6296.9.102.1.2.2
		gfastPortStatusTable OBJECT-TYPE
			SYNTAX SEQUENCE OF GfastPortStatusEntry
			MAX-ACCESS not-accessible
			STATUS current
			DESCRIPTION
				"The gfast port status table"
			::= { gfastPortGroup 2 }

		
		-- 1.3.6.1.4.1.6296.9.102.1.2.2.1
		gfastPortStatusEntry OBJECT-TYPE
			SYNTAX GfastPortStatusEntry
			MAX-ACCESS not-accessible
			STATUS current
			DESCRIPTION
				"an entry of the gfast port status table"
			INDEX { gfastPortIndex }
			::= { gfastPortStatusTable 1 }

		
		GfastPortStatusEntry ::=
			SEQUENCE { 
				gfastPortStatusState
					DisplayString,
				gfastPortStatusUsLineBitRate
					INTEGER,
				gfastPortStatusDsLineBitRate
					INTEGER,
				gfastPortStatusAggregateDataBitRate
					INTEGER,
				gfastPortStatusUsDataBitRate
					INTEGER,
				gfastPortStatusDsDataBitRate
					INTEGER,
				gfastPortStatusUsSnrm
					DisplayString,
				gfastPortStatusDsSnrm
					DisplayString,
				gfastPortStatusUsOutputPower
					DisplayString,
				gfastPortStatusDsOutputPower
					DisplayString,
				gfastPortStatusUsActualInp
					DisplayString,
				gfastPortStatusDsActualInp
					DisplayString,
				gfastPortStatusUsActualInpRein
					DisplayString,
				gfastPortStatusDsActualInpRein
					DisplayString,
				gfastPortStatusLoopLength
					DisplayString,
				gfastPortStatusUpTime
					Counter32,
				gfastPortStatusLPR
					INTEGER,
				gfastPortStatusUsAutoBitRate
					INTEGER,
				gfastPortStatusDsAutoBitRate
					INTEGER,
				gfastPortStatusProfileName
					DisplayString
			 }

-- 		gfastPortStatusProfile			DisplayString,
-- gfastPortStatusUsAttainableDataBitRate	INTEGER,
-- gfastPortStatusDsAttainableDataBitRate	INTEGER,	
-- gfastPortStatusUsRaMode			DisplayString,
-- gfastPortStatusDsRaMode			DisplayString,
-- gfastPortStatusUsRtxMode		DisplayString,
-- gfastPortStatusDsRtxMode		DisplayString,
		-- 1.3.6.1.4.1.6296.9.102.1.2.2.1.1
		gfastPortStatusState OBJECT-TYPE
			SYNTAX DisplayString
			MAX-ACCESS read-only
			STATUS current
			DESCRIPTION
				"Specifies the gfast Port's Status."
			::= { gfastPortStatusEntry 1 }

		
-- gfastPortStatusProfile	OBJECT-TYPE
-- SYNTAX      	DisplayString
-- MAX-ACCESS  	read-only
-- STATUS      	current
-- DESCRIPTION 	"Specifies the gfast Port's Association Proile."
-- ::= { gfastPortStatusEntry 2 }
		-- 1.3.6.1.4.1.6296.9.102.1.2.2.1.2
		gfastPortStatusUsLineBitRate OBJECT-TYPE
			SYNTAX INTEGER
			MAX-ACCESS read-only
			STATUS current
			DESCRIPTION
				"Specifies the gfast Port's Up Stream Line Bit Rate. Unit is 1Kbps"
			::= { gfastPortStatusEntry 2 }

		
		-- 1.3.6.1.4.1.6296.9.102.1.2.2.1.3
		gfastPortStatusDsLineBitRate OBJECT-TYPE
			SYNTAX INTEGER
			MAX-ACCESS read-only
			STATUS current
			DESCRIPTION
				"Specifies the gfast Port's Down Stream Line Bit Rate. Unit is 1Kbps"
			::= { gfastPortStatusEntry 3 }

		
		-- 1.3.6.1.4.1.6296.9.102.1.2.2.1.4
		gfastPortStatusAggregateDataBitRate OBJECT-TYPE
			SYNTAX INTEGER
			MAX-ACCESS read-only
			STATUS current
			DESCRIPTION
				"Specifies the gfast Port's Aggregate Data Bit Rate. Unit is 1Kbps"
			::= { gfastPortStatusEntry 4 }

		
		-- 1.3.6.1.4.1.6296.9.102.1.2.2.1.5
		gfastPortStatusUsDataBitRate OBJECT-TYPE
			SYNTAX INTEGER
			MAX-ACCESS read-only
			STATUS current
			DESCRIPTION
				"Specifies the gfast Port's Up Stream Data Bit Rate. Unit is 1Kbps"
			::= { gfastPortStatusEntry 5 }

		
		-- 1.3.6.1.4.1.6296.9.102.1.2.2.1.6
		gfastPortStatusDsDataBitRate OBJECT-TYPE
			SYNTAX INTEGER
			MAX-ACCESS read-only
			STATUS current
			DESCRIPTION
				"Specifies the gfast Port's Down Stream Data Bit Rate. Unit is 1Kbps"
			::= { gfastPortStatusEntry 6 }

		
-- gfastPortStatusUsAttainableDataBitRate OBJECT-TYPE
-- SYNTAX      INTEGER
-- MAX-ACCESS  read-only
-- STATUS      current
-- DESCRIPTION
-- "Specifies the gfast Port's Up Stream Attainable Data Bit Rate. Unit is 1Kbps"
-- ::= { gfastPortStatusEntry 8 }
-- gfastPortStatusDsAttainableDataBitRate OBJECT-TYPE
-- SYNTAX      INTEGER
-- MAX-ACCESS  read-only
-- STATUS      current
-- DESCRIPTION
-- "Specifies the gfast Port's Down Stream Attainable Data Bit Rate. Unit is 1Kbps"
-- ::= { gfastPortStatusEntry 9 }
		-- 1.3.6.1.4.1.6296.9.102.1.2.2.1.7
		gfastPortStatusUsSnrm OBJECT-TYPE
			SYNTAX DisplayString
			MAX-ACCESS read-only
			STATUS current
			DESCRIPTION
				"Specifies the gfast Port's Up Stream Signal to Noise Ratio Margin. Expressed in tenth of dB's"
			::= { gfastPortStatusEntry 7 }

		
		-- 1.3.6.1.4.1.6296.9.102.1.2.2.1.8
		gfastPortStatusDsSnrm OBJECT-TYPE
			SYNTAX DisplayString
			MAX-ACCESS read-only
			STATUS current
			DESCRIPTION
				"Specifies the gfast Port's Down Stream Signal to Noise Ratio Margin. Expressed in tenth of dB's"
			::= { gfastPortStatusEntry 8 }

		
		-- 1.3.6.1.4.1.6296.9.102.1.2.2.1.9
		gfastPortStatusUsOutputPower OBJECT-TYPE
			SYNTAX DisplayString
			MAX-ACCESS read-only
			STATUS current
			DESCRIPTION
				"Specifies the gfast Port's Up Stream Transmit Power. Expressed in tenth of dBm's"
			::= { gfastPortStatusEntry 9 }

		
		-- 1.3.6.1.4.1.6296.9.102.1.2.2.1.10
		gfastPortStatusDsOutputPower OBJECT-TYPE
			SYNTAX DisplayString
			MAX-ACCESS read-only
			STATUS current
			DESCRIPTION
				"Specifies the gfast Port's Down Stream Transmit Power. Expressed in tenth of dBm's"
			::= { gfastPortStatusEntry 10 }

		
-- gfastPortStatusUsRaMode	OBJECT-TYPE
-- SYNTAX      DisplayString
-- MAX-ACCESS  read-only
-- STATUS      current
-- DESCRIPTION
-- "Specifies the gfast Port's Up Stream Rate Adaptation Status."
-- ::= { gfastPortStatusEntry 14 }
-- gfastPortStatusDsRaMode	OBJECT-TYPE
-- SYNTAX      DisplayString
-- MAX-ACCESS  read-only
-- STATUS      current
-- DESCRIPTION
-- "Specifies the gfast Port's Down Stream Rate Adaptation Status."
-- ::= { gfastPortStatusEntry 15 }
-- gfastPortStatusUsRtxMode	OBJECT-TYPE
-- SYNTAX      DisplayString
-- MAX-ACCESS  read-only
-- STATUS      current
-- DESCRIPTION
-- "Specifies the gfast Port's Up Stream Retransmission Status."
-- ::= { gfastPortStatusEntry 16 }
-- gfastPortStatusDsRtxMode	OBJECT-TYPE
-- SYNTAX      DisplayString
-- MAX-ACCESS  read-only
-- STATUS      current
-- DESCRIPTION
-- "Specifies the gfast Port's Down Stream Retransmission Status."
-- ::= { gfastPortStatusEntry 17 }
		-- 1.3.6.1.4.1.6296.9.102.1.2.2.1.11
		gfastPortStatusUsActualInp OBJECT-TYPE
			SYNTAX DisplayString
			MAX-ACCESS read-only
			STATUS current
			DESCRIPTION
				"Specifies the gfast Port's Up Stream Actual INP aginst SHINE."
			::= { gfastPortStatusEntry 11 }

		
		-- 1.3.6.1.4.1.6296.9.102.1.2.2.1.12
		gfastPortStatusDsActualInp OBJECT-TYPE
			SYNTAX DisplayString
			MAX-ACCESS read-only
			STATUS current
			DESCRIPTION
				"Specifies the gfast Port's Down Stream Actual INP aginst SHINE."
			::= { gfastPortStatusEntry 12 }

		
		-- 1.3.6.1.4.1.6296.9.102.1.2.2.1.13
		gfastPortStatusUsActualInpRein OBJECT-TYPE
			SYNTAX DisplayString
			MAX-ACCESS read-only
			STATUS current
			DESCRIPTION
				"Specifies the gfast Port's Up Stream Actual INP aginst REIN."
			::= { gfastPortStatusEntry 13 }

		
		-- 1.3.6.1.4.1.6296.9.102.1.2.2.1.14
		gfastPortStatusDsActualInpRein OBJECT-TYPE
			SYNTAX DisplayString
			MAX-ACCESS read-only
			STATUS current
			DESCRIPTION
				"Specifies the gfast Port's Down Stream Actual INP aginst REIN."
			::= { gfastPortStatusEntry 14 }

		
		-- 1.3.6.1.4.1.6296.9.102.1.2.2.1.15
		gfastPortStatusLoopLength OBJECT-TYPE
			SYNTAX DisplayString
			MAX-ACCESS read-only
			STATUS current
			DESCRIPTION
				"Specifies the gfast Port's Estimated Loop Length."
			::= { gfastPortStatusEntry 15 }

		
		-- 1.3.6.1.4.1.6296.9.102.1.2.2.1.16
		gfastPortStatusUpTime OBJECT-TYPE
			SYNTAX Counter32
			MAX-ACCESS read-only
			STATUS current
			DESCRIPTION
				" Specifies the gfast Port's Showtime Up Time (sec)."
			::= { gfastPortStatusEntry 16 }

		
		-- 1.3.6.1.4.1.6296.9.102.1.2.2.1.17
		gfastPortStatusLPR OBJECT-TYPE
			SYNTAX INTEGER
				{
				false(0),
				true(1)
				}
			MAX-ACCESS read-only
			STATUS current
			DESCRIPTION
				"Specifies the gfast Port's LPR status."
			::= { gfastPortStatusEntry 17 }

		
		-- 1.3.6.1.4.1.6296.9.102.1.2.2.1.18
		gfastPortStatusUsAutoBitRate OBJECT-TYPE
			SYNTAX INTEGER
			MAX-ACCESS read-only
			STATUS current
			DESCRIPTION
				"Specifies the gfast Port's Up Stream Auto Bit Rate. Unit is 1Kbps"
			::= { gfastPortStatusEntry 18 }

		
		-- 1.3.6.1.4.1.6296.9.102.1.2.2.1.19
		gfastPortStatusDsAutoBitRate OBJECT-TYPE
			SYNTAX INTEGER
			MAX-ACCESS read-only
			STATUS current
			DESCRIPTION
				"Specifies the gfast Port's Down Stream Auto Bit Rate. Unit is 1Kbps"
			::= { gfastPortStatusEntry 19 }

		
		-- 1.3.6.1.4.1.6296.9.102.1.2.2.1.20
		gfastPortStatusProfileName OBJECT-TYPE
			SYNTAX DisplayString (SIZE (0..32))
			MAX-ACCESS read-only
			STATUS current
			DESCRIPTION
				"Defines the Profile Name."
			::= { gfastPortStatusEntry 20 }

		
--  *********************************************************************
-- * gfastPortCounterTable : Port Counter Group
-- *********************************************************************
		-- 1.3.6.1.4.1.6296.9.102.1.2.3
		gfastPortCounterTable OBJECT-TYPE
			SYNTAX SEQUENCE OF GfastPortCounterEntry
			MAX-ACCESS not-accessible
			STATUS current
			DESCRIPTION
				"The G.fast port running counter table"
			::= { gfastPortGroup 3 }

		
		-- 1.3.6.1.4.1.6296.9.102.1.2.3.1
		gfastPortCounterEntry OBJECT-TYPE
			SYNTAX GfastPortCounterEntry
			MAX-ACCESS not-accessible
			STATUS current
			DESCRIPTION
				"An entry in gfastPortCounterTable."
			INDEX { gfastPortIndex }
			::= { gfastPortCounterTable 1 }

		
		GfastPortCounterEntry ::=
			SEQUENCE { 
				gfastPortCounterUsMinEftr
					Counter32,
				gfastPortCounterDsMinEftr
					Counter32,
				gfastPortCounterUsFecs
					Counter32,
				gfastPortCounterDsFecs
					Counter32,
				gfastPortCounterUsLoss
					Counter32,
				gfastPortCounterDsLoss
					Counter32,
				gfastPortCounterUsEs
					Counter32,
				gfastPortCounterDsEs
					Counter32,
				gfastPortCounterUsSes
					Counter32,
				gfastPortCounterDsSes
					Counter32,
				gfastPortCounterUsUas
					Counter32,
				gfastPortCounterDsUas
					Counter32,
				gfastPortCounterUsCv
					Counter32,
				gfastPortCounterDsCv
					Counter32,
				gfastPortCounterUsLols
					Counter32,
				gfastPortCounterDsLprs
					Counter32,
				gfastPortCounterUncorrectedCw
					Counter32,
				gfastPortCounterUsRtxCw
					Counter32,
				gfastPortCounterDsRtxCw
					Counter32,
				gfastPortCounterRtxCorrectedCw
					Counter32,
				gfastPortCounterRtxUncorrectedCw
					Counter32,
				gfastPortCounterFullInitCount
					Counter32,
				gfastPortCounterFastInitCount
					Counter32
			 }

-- 		gfastPortCounterUsErrFreeBits		Counter32,
-- gfastPortCounterDsErrFreeBits		Counter32,
-- gfastPortCounterDsUncorrectedCw		Counter32,
-- gfastPortCounterDsRtxCorrectedCw	Counter32,
-- gfastPortCounterDsRtxUncorrectedCw	Counter32,
		-- 1.3.6.1.4.1.6296.9.102.1.2.3.1.1
		gfastPortCounterUsMinEftr OBJECT-TYPE
			SYNTAX Counter32
			MAX-ACCESS read-only
			STATUS current
			DESCRIPTION
				" Specifies the gfast Port's Up Stream Minimum Error Free Throughput."
			::= { gfastPortCounterEntry 1 }

		
		-- 1.3.6.1.4.1.6296.9.102.1.2.3.1.2
		gfastPortCounterDsMinEftr OBJECT-TYPE
			SYNTAX Counter32
			MAX-ACCESS read-only
			STATUS current
			DESCRIPTION
				" Specifies the gfast Port's Down Stream Minimum Error Free Throughput."
			::= { gfastPortCounterEntry 2 }

		
-- gfastPortCounterUsErrFreeBits OBJECT-TYPE
-- SYNTAX      Counter32
-- MAX-ACCESS  read-only
-- STATUS      current
-- DESCRIPTION
-- " Specifies the gfast Port's Up Stream Error Free Bits."
-- ::= { gfastPortCounterEntry 3 }
-- gfastPortCounterDsErrFreeBits OBJECT-TYPE
-- SYNTAX      Counter32
-- MAX-ACCESS  read-only
-- STATUS      current
-- DESCRIPTION
-- " Specifies the gfast Port's Down Stream Error Free Bits."
-- ::= { gfastPortCounterEntry 4 }
		-- 1.3.6.1.4.1.6296.9.102.1.2.3.1.3
		gfastPortCounterUsFecs OBJECT-TYPE
			SYNTAX Counter32
			MAX-ACCESS read-only
			STATUS current
			DESCRIPTION
				" Specifies the gfast Port's Up Stream Forward Error Collection Seconds."
			::= { gfastPortCounterEntry 3 }

		
		-- 1.3.6.1.4.1.6296.9.102.1.2.3.1.4
		gfastPortCounterDsFecs OBJECT-TYPE
			SYNTAX Counter32
			MAX-ACCESS read-only
			STATUS current
			DESCRIPTION
				" Specifies the gfast Port's Down Stream Forward Error Collection Seconds."
			::= { gfastPortCounterEntry 4 }

		
		-- 1.3.6.1.4.1.6296.9.102.1.2.3.1.5
		gfastPortCounterUsLoss OBJECT-TYPE
			SYNTAX Counter32
			MAX-ACCESS read-only
			STATUS current
			DESCRIPTION
				" Specifies the gfast Port's Up Stream Loss of signal Seconds."
			::= { gfastPortCounterEntry 5 }

		
		-- 1.3.6.1.4.1.6296.9.102.1.2.3.1.6
		gfastPortCounterDsLoss OBJECT-TYPE
			SYNTAX Counter32
			MAX-ACCESS read-only
			STATUS current
			DESCRIPTION
				" Specifies the gfast Port's Down Stream Loss of signal Seconds."
			::= { gfastPortCounterEntry 6 }

		
		-- 1.3.6.1.4.1.6296.9.102.1.2.3.1.7
		gfastPortCounterUsEs OBJECT-TYPE
			SYNTAX Counter32
			MAX-ACCESS read-only
			STATUS current
			DESCRIPTION
				" Specifies the gfast Port's Up Stream Errored Seconds."
			::= { gfastPortCounterEntry 7 }

		
		-- 1.3.6.1.4.1.6296.9.102.1.2.3.1.8
		gfastPortCounterDsEs OBJECT-TYPE
			SYNTAX Counter32
			MAX-ACCESS read-only
			STATUS current
			DESCRIPTION
				" Specifies the gfast Port's Down Stream Errored Seconds."
			::= { gfastPortCounterEntry 8 }

		
		-- 1.3.6.1.4.1.6296.9.102.1.2.3.1.9
		gfastPortCounterUsSes OBJECT-TYPE
			SYNTAX Counter32
			MAX-ACCESS read-only
			STATUS current
			DESCRIPTION
				" Specifies the gfast Port's Up Stream Severely Errored Seconds."
			::= { gfastPortCounterEntry 9 }

		
		-- 1.3.6.1.4.1.6296.9.102.1.2.3.1.10
		gfastPortCounterDsSes OBJECT-TYPE
			SYNTAX Counter32
			MAX-ACCESS read-only
			STATUS current
			DESCRIPTION
				" Specifies the gfast Port's Down Stream Severely Errored Seconds."
			::= { gfastPortCounterEntry 10 }

		
		-- 1.3.6.1.4.1.6296.9.102.1.2.3.1.11
		gfastPortCounterUsUas OBJECT-TYPE
			SYNTAX Counter32
			MAX-ACCESS read-only
			STATUS current
			DESCRIPTION
				" Specifies the gfast Port's Up Stream Unavailable Seconds."
			::= { gfastPortCounterEntry 11 }

		
		-- 1.3.6.1.4.1.6296.9.102.1.2.3.1.12
		gfastPortCounterDsUas OBJECT-TYPE
			SYNTAX Counter32
			MAX-ACCESS read-only
			STATUS current
			DESCRIPTION
				" Specifies the gfast Port's Down Stream Unavailable Seconds."
			::= { gfastPortCounterEntry 12 }

		
		-- 1.3.6.1.4.1.6296.9.102.1.2.3.1.13
		gfastPortCounterUsCv OBJECT-TYPE
			SYNTAX Counter32
			MAX-ACCESS read-only
			STATUS current
			DESCRIPTION
				" Specifies the gfast Port's Up Stream CRC Violations."
			::= { gfastPortCounterEntry 13 }

		
		-- 1.3.6.1.4.1.6296.9.102.1.2.3.1.14
		gfastPortCounterDsCv OBJECT-TYPE
			SYNTAX Counter32
			MAX-ACCESS read-only
			STATUS current
			DESCRIPTION
				" Specifies the gfast Port's Down Stream CRC Violations."
			::= { gfastPortCounterEntry 14 }

		
		-- 1.3.6.1.4.1.6296.9.102.1.2.3.1.15
		gfastPortCounterUsLols OBJECT-TYPE
			SYNTAX Counter32
			MAX-ACCESS read-only
			STATUS current
			DESCRIPTION
				" Specifies the gfast Port's Up Stream Loss of Link Seconds."
			::= { gfastPortCounterEntry 15 }

		
		-- 1.3.6.1.4.1.6296.9.102.1.2.3.1.16
		gfastPortCounterDsLprs OBJECT-TYPE
			SYNTAX Counter32
			MAX-ACCESS read-only
			STATUS current
			DESCRIPTION
				" Specifies the gfast Port's Down Stream Loss of Power Seconds."
			::= { gfastPortCounterEntry 16 }

		
		-- 1.3.6.1.4.1.6296.9.102.1.2.3.1.17
		gfastPortCounterUncorrectedCw OBJECT-TYPE
			SYNTAX Counter32
			MAX-ACCESS read-only
			STATUS current
			DESCRIPTION
				" Specifies the gfast Port's Up Stream Codeword that could not be correced."
			::= { gfastPortCounterEntry 17 }

		
-- gfastPortCounterDsUncorrectedCw OBJECT-TYPE
-- SYNTAX      Counter32
-- MAX-ACCESS  read-only
-- STATUS      current
-- DESCRIPTION
-- " Specifies the gfast Port's Down Stream Codeword that could not be correced."
-- ::= { gfastPortCounterEntry 18 }
		-- 1.3.6.1.4.1.6296.9.102.1.2.3.1.18
		gfastPortCounterUsRtxCw OBJECT-TYPE
			SYNTAX Counter32
			MAX-ACCESS read-only
			STATUS current
			DESCRIPTION
				" Specifies the gfast Port's Up Stream Number of Codewords retransmitted."
			::= { gfastPortCounterEntry 18 }

		
		-- 1.3.6.1.4.1.6296.9.102.1.2.3.1.19
		gfastPortCounterDsRtxCw OBJECT-TYPE
			SYNTAX Counter32
			MAX-ACCESS read-only
			STATUS current
			DESCRIPTION
				" Specifies the gfast Port's Down Stream Number of Codewords retransmitted."
			::= { gfastPortCounterEntry 19 }

		
		-- 1.3.6.1.4.1.6296.9.102.1.2.3.1.20
		gfastPortCounterRtxCorrectedCw OBJECT-TYPE
			SYNTAX Counter32
			MAX-ACCESS read-only
			STATUS current
			DESCRIPTION
				" Specifies the gfast Port's Up Stream Number of Codewords corrected through retransmission."
			::= { gfastPortCounterEntry 20 }

		
-- gfastPortCounterDsRtxCorrectedCw OBJECT-TYPE
-- SYNTAX      Counter32
-- MAX-ACCESS  read-only
-- STATUS      current
-- DESCRIPTION
-- " Specifies the gfast Port's Down Stream Number of Codewords corrected through retransmission."
-- ::= { gfastPortCounterEntry 22 }
		-- 1.3.6.1.4.1.6296.9.102.1.2.3.1.21
		gfastPortCounterRtxUncorrectedCw OBJECT-TYPE
			SYNTAX Counter32
			MAX-ACCESS read-only
			STATUS current
			DESCRIPTION
				" Specifies the gfast Port's Up Stream Number of Codewords left uncorrected after retransmission."
			::= { gfastPortCounterEntry 21 }

		
-- gfastPortCounterDsRtxUncorrectedCw OBJECT-TYPE
-- SYNTAX      Counter32
-- MAX-ACCESS  read-only
-- STATUS      current
-- DESCRIPTION
-- " Specifies the gfast Port's Down Stream Number of Codewords left uncorrected after retransmission."
-- ::= { gfastPortCounterEntry 24 }
		-- 1.3.6.1.4.1.6296.9.102.1.2.3.1.22
		gfastPortCounterFullInitCount OBJECT-TYPE
			SYNTAX Counter32
			MAX-ACCESS read-only
			STATUS current
			DESCRIPTION
				" Specifies the gfast Port's Full Init Count."
			::= { gfastPortCounterEntry 22 }

		
		-- 1.3.6.1.4.1.6296.9.102.1.2.3.1.23
		gfastPortCounterFastInitCount OBJECT-TYPE
			SYNTAX Counter32
			MAX-ACCESS read-only
			STATUS current
			DESCRIPTION
				" Specifies the gfast Port's Fast Init Count."
			::= { gfastPortCounterEntry 23 }

		
--  *********************************************************************
-- * gfastPortCounterTable : Port Current 15min Counter Group
-- *********************************************************************
		-- 1.3.6.1.4.1.6296.9.102.1.2.4
		gfastPortCurrent15MCounterTable OBJECT-TYPE
			SYNTAX SEQUENCE OF GfastPortCurrent15MCounterEntry
			MAX-ACCESS not-accessible
			STATUS current
			DESCRIPTION
				"The G.fast port Current 15min Counter table"
			::= { gfastPortGroup 4 }

		
		-- 1.3.6.1.4.1.6296.9.102.1.2.4.1
		gfastPortCurrent15MCounterEntry OBJECT-TYPE
			SYNTAX GfastPortCurrent15MCounterEntry
			MAX-ACCESS not-accessible
			STATUS current
			DESCRIPTION
				"An entry in gfastPortCurrent15MCounterTable."
			INDEX { gfastPortIndex }
			::= { gfastPortCurrent15MCounterTable 1 }

		
		GfastPortCurrent15MCounterEntry ::=
			SEQUENCE { 
				gfastPortCurrent15MCounterUsMinEftr
					Counter32,
				gfastPortCurrent15MCounterDsMinEftr
					Counter32,
				gfastPortCurrent15MCounterUsFecs
					Counter32,
				gfastPortCurrent15MCounterDsFecs
					Counter32,
				gfastPortCurrent15MCounterUsLoss
					Counter32,
				gfastPortCurrent15MCounterDsLoss
					Counter32,
				gfastPortCurrent15MCounterUsEs
					Counter32,
				gfastPortCurrent15MCounterDsEs
					Counter32,
				gfastPortCurrent15MCounterUsSes
					Counter32,
				gfastPortCurrent15MCounterDsSes
					Counter32,
				gfastPortCurrent15MCounterUsUas
					Counter32,
				gfastPortCurrent15MCounterDsUas
					Counter32,
				gfastPortCurrent15MCounterUsCv
					Counter32,
				gfastPortCurrent15MCounterDsCv
					Counter32,
				gfastPortCurrent15MCounterUsLols
					Counter32,
				gfastPortCurrent15MCounterDsLprs
					Counter32,
				gfastPortCurrent15MCounterUncorrectedCw
					Counter32,
				gfastPortCurrent15MCounterUsRtxCw
					Counter32,
				gfastPortCurrent15MCounterDsRtxCw
					Counter32,
				gfastPortCurrent15MCounterRtxCorrectedCw
					Counter32,
				gfastPortCurrent15MCounterRtxUncorrectedCw
					Counter32,
				gfastPortCurrent15MCounterFullInitCount
					Counter32,
				gfastPortCurrent15MCounterFastInitCount
					Counter32
			 }

-- 		gfastPortCurrent15MCounterUsErrFreeBits		Counter32,
-- gfastPortCurrent15MCounterDsErrFreeBits		Counter32,
-- gfastPortCurrent15MCounterDsUncorrectedCw	Counter32,
-- gfastPortCurrent15MCounterDsRtxCorrectedCw	Counter32,
-- gfastPortCurrent15MCounterDsRtxUncorrectedCw	Counter32,
		-- 1.3.6.1.4.1.6296.9.102.1.2.4.1.1
		gfastPortCurrent15MCounterUsMinEftr OBJECT-TYPE
			SYNTAX Counter32
			MAX-ACCESS read-only
			STATUS current
			DESCRIPTION
				" Specifies the gfast Port's Current15Min Up Stream Minimum Error Free Throughput."
			::= { gfastPortCurrent15MCounterEntry 1 }

		
		-- 1.3.6.1.4.1.6296.9.102.1.2.4.1.2
		gfastPortCurrent15MCounterDsMinEftr OBJECT-TYPE
			SYNTAX Counter32
			MAX-ACCESS read-only
			STATUS current
			DESCRIPTION
				" Specifies the gfast Port's Current15Min Down Stream Minimum Error Free Throughput."
			::= { gfastPortCurrent15MCounterEntry 2 }

		
-- gfastPortCurrent15MCounterUsErrFreeBits OBJECT-TYPE
-- SYNTAX      Counter32
-- MAX-ACCESS  read-only
-- STATUS      current
-- DESCRIPTION
-- " Specifies the gfast Port's Current15Min Up Stream Error Free Bits."
-- ::= { gfastPortCurrent15MCounterEntry 3 }
-- gfastPortCurrent15MCounterDsErrFreeBits OBJECT-TYPE
-- SYNTAX      Counter32
-- MAX-ACCESS  read-only
-- STATUS      current
-- DESCRIPTION
-- " Specifies the gfast Port's Current15Min Down Stream Error Free Bits."
-- ::= { gfastPortCurrent15MCounterEntry 4 }
		-- 1.3.6.1.4.1.6296.9.102.1.2.4.1.3
		gfastPortCurrent15MCounterUsFecs OBJECT-TYPE
			SYNTAX Counter32
			MAX-ACCESS read-only
			STATUS current
			DESCRIPTION
				" Specifies the gfast Port's Current15Min Up Stream Forward Error Collection Seconds."
			::= { gfastPortCurrent15MCounterEntry 3 }

		
		-- 1.3.6.1.4.1.6296.9.102.1.2.4.1.4
		gfastPortCurrent15MCounterDsFecs OBJECT-TYPE
			SYNTAX Counter32
			MAX-ACCESS read-only
			STATUS current
			DESCRIPTION
				" Specifies the gfast Port's Current15Min Down Stream Current15Min Forward Error Collection Seconds."
			::= { gfastPortCurrent15MCounterEntry 4 }

		
		-- 1.3.6.1.4.1.6296.9.102.1.2.4.1.5
		gfastPortCurrent15MCounterUsLoss OBJECT-TYPE
			SYNTAX Counter32
			MAX-ACCESS read-only
			STATUS current
			DESCRIPTION
				" Specifies the gfast Port's Current15Min Up Stream Loss of signal Seconds."
			::= { gfastPortCurrent15MCounterEntry 5 }

		
		-- 1.3.6.1.4.1.6296.9.102.1.2.4.1.6
		gfastPortCurrent15MCounterDsLoss OBJECT-TYPE
			SYNTAX Counter32
			MAX-ACCESS read-only
			STATUS current
			DESCRIPTION
				" Specifies the gfast Port's Current15Min Down Stream Loss of signal Seconds."
			::= { gfastPortCurrent15MCounterEntry 6 }

		
		-- 1.3.6.1.4.1.6296.9.102.1.2.4.1.7
		gfastPortCurrent15MCounterUsEs OBJECT-TYPE
			SYNTAX Counter32
			MAX-ACCESS read-only
			STATUS current
			DESCRIPTION
				" Specifies the gfast Port's Current15Min Up Stream Errored Seconds."
			::= { gfastPortCurrent15MCounterEntry 7 }

		
		-- 1.3.6.1.4.1.6296.9.102.1.2.4.1.8
		gfastPortCurrent15MCounterDsEs OBJECT-TYPE
			SYNTAX Counter32
			MAX-ACCESS read-only
			STATUS current
			DESCRIPTION
				" Specifies the gfast Port's Current15Min Down Stream Errored Seconds."
			::= { gfastPortCurrent15MCounterEntry 8 }

		
		-- 1.3.6.1.4.1.6296.9.102.1.2.4.1.9
		gfastPortCurrent15MCounterUsSes OBJECT-TYPE
			SYNTAX Counter32
			MAX-ACCESS read-only
			STATUS current
			DESCRIPTION
				" Specifies the gfast Port's Current15Min Up Stream Severely Errored Seconds."
			::= { gfastPortCurrent15MCounterEntry 9 }

		
		-- 1.3.6.1.4.1.6296.9.102.1.2.4.1.10
		gfastPortCurrent15MCounterDsSes OBJECT-TYPE
			SYNTAX Counter32
			MAX-ACCESS read-only
			STATUS current
			DESCRIPTION
				" Specifies the gfast Port's Current15Min Down Stream Severely Errored Seconds."
			::= { gfastPortCurrent15MCounterEntry 10 }

		
		-- 1.3.6.1.4.1.6296.9.102.1.2.4.1.11
		gfastPortCurrent15MCounterUsUas OBJECT-TYPE
			SYNTAX Counter32
			MAX-ACCESS read-only
			STATUS current
			DESCRIPTION
				" Specifies the gfast Port's Current15Min Up Stream Unavailable Seconds."
			::= { gfastPortCurrent15MCounterEntry 11 }

		
		-- 1.3.6.1.4.1.6296.9.102.1.2.4.1.12
		gfastPortCurrent15MCounterDsUas OBJECT-TYPE
			SYNTAX Counter32
			MAX-ACCESS read-only
			STATUS current
			DESCRIPTION
				" Specifies the gfast Port's Current15Min Down Stream Unavailable Seconds."
			::= { gfastPortCurrent15MCounterEntry 12 }

		
		-- 1.3.6.1.4.1.6296.9.102.1.2.4.1.13
		gfastPortCurrent15MCounterUsCv OBJECT-TYPE
			SYNTAX Counter32
			MAX-ACCESS read-only
			STATUS current
			DESCRIPTION
				" Specifies the gfast Port's Current15Min Up Stream CRC Violations."
			::= { gfastPortCurrent15MCounterEntry 13 }

		
		-- 1.3.6.1.4.1.6296.9.102.1.2.4.1.14
		gfastPortCurrent15MCounterDsCv OBJECT-TYPE
			SYNTAX Counter32
			MAX-ACCESS read-only
			STATUS current
			DESCRIPTION
				" Specifies the gfast Port's Current15Min Down Stream CRC Violations."
			::= { gfastPortCurrent15MCounterEntry 14 }

		
		-- 1.3.6.1.4.1.6296.9.102.1.2.4.1.15
		gfastPortCurrent15MCounterUsLols OBJECT-TYPE
			SYNTAX Counter32
			MAX-ACCESS read-only
			STATUS current
			DESCRIPTION
				" Specifies the gfast Port's Current15Min Up Stream Loss of Link Seconds."
			::= { gfastPortCurrent15MCounterEntry 15 }

		
		-- 1.3.6.1.4.1.6296.9.102.1.2.4.1.16
		gfastPortCurrent15MCounterDsLprs OBJECT-TYPE
			SYNTAX Counter32
			MAX-ACCESS read-only
			STATUS current
			DESCRIPTION
				" Specifies the gfast Port's Current15Min Down Stream Loss of Power Seconds."
			::= { gfastPortCurrent15MCounterEntry 16 }

		
		-- 1.3.6.1.4.1.6296.9.102.1.2.4.1.17
		gfastPortCurrent15MCounterUncorrectedCw OBJECT-TYPE
			SYNTAX Counter32
			MAX-ACCESS read-only
			STATUS current
			DESCRIPTION
				" Specifies the gfast Port's Current15Min Up Stream Codeword that could not be correced."
			::= { gfastPortCurrent15MCounterEntry 17 }

		
-- gfastPortCurrent15MCounterDsUncorrectedCw OBJECT-TYPE
-- SYNTAX      Counter32
-- MAX-ACCESS  read-only
-- STATUS      current
-- DESCRIPTION
-- " Specifies the gfast Port's Current15Min Down Stream Codeword that could not be correced."
-- ::= { gfastPortCurrent15MCounterEntry 18 }
		-- 1.3.6.1.4.1.6296.9.102.1.2.4.1.18
		gfastPortCurrent15MCounterUsRtxCw OBJECT-TYPE
			SYNTAX Counter32
			MAX-ACCESS read-only
			STATUS current
			DESCRIPTION
				" Specifies the gfast Port's Current15Min Up Stream Number of Codewords retransmitted."
			::= { gfastPortCurrent15MCounterEntry 18 }

		
		-- 1.3.6.1.4.1.6296.9.102.1.2.4.1.19
		gfastPortCurrent15MCounterDsRtxCw OBJECT-TYPE
			SYNTAX Counter32
			MAX-ACCESS read-only
			STATUS current
			DESCRIPTION
				" Specifies the gfast Port's Current15Min Down Stream Number of Codewords retransmitted."
			::= { gfastPortCurrent15MCounterEntry 19 }

		
		-- 1.3.6.1.4.1.6296.9.102.1.2.4.1.20
		gfastPortCurrent15MCounterRtxCorrectedCw OBJECT-TYPE
			SYNTAX Counter32
			MAX-ACCESS read-only
			STATUS current
			DESCRIPTION
				" Specifies the gfast Port's Current15Min Up Stream Number of Codewords corrected through retransmission."
			::= { gfastPortCurrent15MCounterEntry 20 }

		
-- gfastPortCurrent15MCounterDsRtxCorrectedCw OBJECT-TYPE
-- SYNTAX      Counter32
-- MAX-ACCESS  read-only
-- STATUS      current
-- DESCRIPTION
-- " Specifies the gfast Port's Current15Min Down Stream Number of Codewords corrected through retransmission."
-- ::= { gfastPortCurrent15MCounterEntry 22 }
		-- 1.3.6.1.4.1.6296.9.102.1.2.4.1.21
		gfastPortCurrent15MCounterRtxUncorrectedCw OBJECT-TYPE
			SYNTAX Counter32
			MAX-ACCESS read-only
			STATUS current
			DESCRIPTION
				" Specifies the gfast Port's Current15Min Up Stream Number of Codewords left uncorrected after retransmission."
			::= { gfastPortCurrent15MCounterEntry 21 }

		
-- gfastPortCurrent15MCounterDsRtxUncorrectedCw OBJECT-TYPE
-- SYNTAX      Counter32
-- MAX-ACCESS  read-only
-- STATUS      current
-- DESCRIPTION
-- " Specifies the gfast Port's Current15Min Down Stream Number of Codewords left uncorrected after retransmission."
-- ::= { gfastPortCurrent15MCounterEntry 24 }
		-- 1.3.6.1.4.1.6296.9.102.1.2.4.1.22
		gfastPortCurrent15MCounterFullInitCount OBJECT-TYPE
			SYNTAX Counter32
			MAX-ACCESS read-only
			STATUS current
			DESCRIPTION
				" Specifies the gfast Port's Current15Min Full Init Count."
			::= { gfastPortCurrent15MCounterEntry 22 }

		
		-- 1.3.6.1.4.1.6296.9.102.1.2.4.1.23
		gfastPortCurrent15MCounterFastInitCount OBJECT-TYPE
			SYNTAX Counter32
			MAX-ACCESS read-only
			STATUS current
			DESCRIPTION
				" Specifies the gfast Port's Current15Min Fast Init Count."
			::= { gfastPortCurrent15MCounterEntry 23 }

		
--  *********************************************************************
-- * gfastPortCounterTable : Port Previos 15min Counter Group
-- - *********************************************************************
		-- 1.3.6.1.4.1.6296.9.102.1.2.5
		gfastPortPrevious15MCounterTable OBJECT-TYPE
			SYNTAX SEQUENCE OF GfastPortPrevious15MCounterEntry
			MAX-ACCESS not-accessible
			STATUS current
			DESCRIPTION
				"The G.fast port Previos 15min Counter table"
			::= { gfastPortGroup 5 }

		
		-- 1.3.6.1.4.1.6296.9.102.1.2.5.1
		gfastPortPrevious15MCounterEntry OBJECT-TYPE
			SYNTAX GfastPortPrevious15MCounterEntry
			MAX-ACCESS not-accessible
			STATUS current
			DESCRIPTION
				"An entry in gfastPortPrevious15MCounterTable."
			INDEX { gfastPortIndex }
			::= { gfastPortPrevious15MCounterTable 1 }

		
		GfastPortPrevious15MCounterEntry ::=
			SEQUENCE { 
				gfastPortPrevious15MCounterUsMinEftr
					Counter32,
				gfastPortPrevious15MCounterDsMinEftr
					Counter32,
				gfastPortPrevious15MCounterUsFecs
					Counter32,
				gfastPortPrevious15MCounterDsFecs
					Counter32,
				gfastPortPrevious15MCounterUsLoss
					Counter32,
				gfastPortPrevious15MCounterDsLoss
					Counter32,
				gfastPortPrevious15MCounterUsEs
					Counter32,
				gfastPortPrevious15MCounterDsEs
					Counter32,
				gfastPortPrevious15MCounterUsSes
					Counter32,
				gfastPortPrevious15MCounterDsSes
					Counter32,
				gfastPortPrevious15MCounterUsUas
					Counter32,
				gfastPortPrevious15MCounterDsUas
					Counter32,
				gfastPortPrevious15MCounterUsCv
					Counter32,
				gfastPortPrevious15MCounterDsCv
					Counter32,
				gfastPortPrevious15MCounterUsLols
					Counter32,
				gfastPortPrevious15MCounterDsLprs
					Counter32,
				gfastPortPrevious15MCounterUncorrectedCw
					Counter32,
				gfastPortPrevious15MCounterUsRtxCw
					Counter32,
				gfastPortPrevious15MCounterDsRtxCw
					Counter32,
				gfastPortPrevious15MCounterRtxCorrectedCw
					Counter32,
				gfastPortPrevious15MCounterRtxUncorrectedCw
					Counter32,
				gfastPortPrevious15MCounterFullInitCount
					Counter32,
				gfastPortPrevious15MCounterFastInitCount
					Counter32
			 }

-- 		gfastPortPrevious15MCounterUsErrFreeBits	Counter32,
-- gfastPortPrevious15MCounterDsErrFreeBits	Counter32,
-- gfastPortPrevious15MCounterDsUncorrectedCw	Counter32,
-- gfastPortPrevious15MCounterDsRtxCorrectedCw	Counter32,
-- gfastPortPrevious15MCounterDsRtxUncorrectedCw	Counter32,
		-- 1.3.6.1.4.1.6296.9.102.1.2.5.1.1
		gfastPortPrevious15MCounterUsMinEftr OBJECT-TYPE
			SYNTAX Counter32
			MAX-ACCESS read-only
			STATUS current
			DESCRIPTION
				" Specifies the gfast Port's Previous15Min Up Stream Minimum Error Free Throughput."
			::= { gfastPortPrevious15MCounterEntry 1 }

		
		-- 1.3.6.1.4.1.6296.9.102.1.2.5.1.2
		gfastPortPrevious15MCounterDsMinEftr OBJECT-TYPE
			SYNTAX Counter32
			MAX-ACCESS read-only
			STATUS current
			DESCRIPTION
				" Specifies the gfast Port's Previous15Min Down Stream Minimum Error Free Throughput."
			::= { gfastPortPrevious15MCounterEntry 2 }

		
-- gfastPortPrevious15MCounterUsErrFreeBits OBJECT-TYPE
-- SYNTAX      Counter32
-- MAX-ACCESS  read-only
-- STATUS      current
-- DESCRIPTION
-- " Specifies the gfast Port's Previous15Min Up Stream Error Free Bits."
-- ::= { gfastPortPrevious15MCounterEntry 3 }
-- gfastPortPrevious15MCounterDsErrFreeBits OBJECT-TYPE
-- SYNTAX      Counter32
-- MAX-ACCESS  read-only
-- STATUS      current
-- DESCRIPTION
-- " Specifies the gfast Port's Previous15Min Down Stream Error Free Bits."
-- ::= { gfastPortPrevious15MCounterEntry 4 }
		-- 1.3.6.1.4.1.6296.9.102.1.2.5.1.3
		gfastPortPrevious15MCounterUsFecs OBJECT-TYPE
			SYNTAX Counter32
			MAX-ACCESS read-only
			STATUS current
			DESCRIPTION
				" Specifies the gfast Port's Previous15Min Up Stream Forward Error Collection Seconds."
			::= { gfastPortPrevious15MCounterEntry 3 }

		
		-- 1.3.6.1.4.1.6296.9.102.1.2.5.1.4
		gfastPortPrevious15MCounterDsFecs OBJECT-TYPE
			SYNTAX Counter32
			MAX-ACCESS read-only
			STATUS current
			DESCRIPTION
				" Specifies the gfast Port's Previous15Min Down Stream Previous15Min Forward Error Collection Seconds."
			::= { gfastPortPrevious15MCounterEntry 4 }

		
		-- 1.3.6.1.4.1.6296.9.102.1.2.5.1.5
		gfastPortPrevious15MCounterUsLoss OBJECT-TYPE
			SYNTAX Counter32
			MAX-ACCESS read-only
			STATUS current
			DESCRIPTION
				" Specifies the gfast Port's Previous15Min Up Stream Loss of signal Seconds."
			::= { gfastPortPrevious15MCounterEntry 5 }

		
		-- 1.3.6.1.4.1.6296.9.102.1.2.5.1.6
		gfastPortPrevious15MCounterDsLoss OBJECT-TYPE
			SYNTAX Counter32
			MAX-ACCESS read-only
			STATUS current
			DESCRIPTION
				" Specifies the gfast Port's Previous15Min Down Stream Loss of signal Seconds."
			::= { gfastPortPrevious15MCounterEntry 6 }

		
		-- 1.3.6.1.4.1.6296.9.102.1.2.5.1.7
		gfastPortPrevious15MCounterUsEs OBJECT-TYPE
			SYNTAX Counter32
			MAX-ACCESS read-only
			STATUS current
			DESCRIPTION
				" Specifies the gfast Port's Previous15Min Up Stream Errored Seconds."
			::= { gfastPortPrevious15MCounterEntry 7 }

		
		-- 1.3.6.1.4.1.6296.9.102.1.2.5.1.8
		gfastPortPrevious15MCounterDsEs OBJECT-TYPE
			SYNTAX Counter32
			MAX-ACCESS read-only
			STATUS current
			DESCRIPTION
				" Specifies the gfast Port's Previous15Min Down Stream Errored Seconds."
			::= { gfastPortPrevious15MCounterEntry 8 }

		
		-- 1.3.6.1.4.1.6296.9.102.1.2.5.1.9
		gfastPortPrevious15MCounterUsSes OBJECT-TYPE
			SYNTAX Counter32
			MAX-ACCESS read-only
			STATUS current
			DESCRIPTION
				" Specifies the gfast Port's Previous15Min Up Stream Severely Errored Seconds."
			::= { gfastPortPrevious15MCounterEntry 9 }

		
		-- 1.3.6.1.4.1.6296.9.102.1.2.5.1.10
		gfastPortPrevious15MCounterDsSes OBJECT-TYPE
			SYNTAX Counter32
			MAX-ACCESS read-only
			STATUS current
			DESCRIPTION
				" Specifies the gfast Port's Previous15Min Down Stream Severely Errored Seconds."
			::= { gfastPortPrevious15MCounterEntry 10 }

		
		-- 1.3.6.1.4.1.6296.9.102.1.2.5.1.11
		gfastPortPrevious15MCounterUsUas OBJECT-TYPE
			SYNTAX Counter32
			MAX-ACCESS read-only
			STATUS current
			DESCRIPTION
				" Specifies the gfast Port's Previous15Min Up Stream Unavailable Seconds."
			::= { gfastPortPrevious15MCounterEntry 11 }

		
		-- 1.3.6.1.4.1.6296.9.102.1.2.5.1.12
		gfastPortPrevious15MCounterDsUas OBJECT-TYPE
			SYNTAX Counter32
			MAX-ACCESS read-only
			STATUS current
			DESCRIPTION
				" Specifies the gfast Port's Previous15Min Down Stream Unavailable Seconds."
			::= { gfastPortPrevious15MCounterEntry 12 }

		
		-- 1.3.6.1.4.1.6296.9.102.1.2.5.1.13
		gfastPortPrevious15MCounterUsCv OBJECT-TYPE
			SYNTAX Counter32
			MAX-ACCESS read-only
			STATUS current
			DESCRIPTION
				" Specifies the gfast Port's Previous15Min Up Stream CRC Violations."
			::= { gfastPortPrevious15MCounterEntry 13 }

		
		-- 1.3.6.1.4.1.6296.9.102.1.2.5.1.14
		gfastPortPrevious15MCounterDsCv OBJECT-TYPE
			SYNTAX Counter32
			MAX-ACCESS read-only
			STATUS current
			DESCRIPTION
				" Specifies the gfast Port's Previous15Min Down Stream CRC Violations."
			::= { gfastPortPrevious15MCounterEntry 14 }

		
		-- 1.3.6.1.4.1.6296.9.102.1.2.5.1.15
		gfastPortPrevious15MCounterUsLols OBJECT-TYPE
			SYNTAX Counter32
			MAX-ACCESS read-only
			STATUS current
			DESCRIPTION
				" Specifies the gfast Port's Previous15Min Up Stream Loss of Link Seconds."
			::= { gfastPortPrevious15MCounterEntry 15 }

		
		-- 1.3.6.1.4.1.6296.9.102.1.2.5.1.16
		gfastPortPrevious15MCounterDsLprs OBJECT-TYPE
			SYNTAX Counter32
			MAX-ACCESS read-only
			STATUS current
			DESCRIPTION
				" Specifies the gfast Port's Previous15Min Down Stream Loss of Power Seconds."
			::= { gfastPortPrevious15MCounterEntry 16 }

		
		-- 1.3.6.1.4.1.6296.9.102.1.2.5.1.17
		gfastPortPrevious15MCounterUncorrectedCw OBJECT-TYPE
			SYNTAX Counter32
			MAX-ACCESS read-only
			STATUS current
			DESCRIPTION
				" Specifies the gfast Port's Previous15Min Up Stream Codeword that could not be correced."
			::= { gfastPortPrevious15MCounterEntry 17 }

		
-- gfastPortPrevious15MCounterDsUncorrectedCw OBJECT-TYPE
-- SYNTAX      Counter32
-- MAX-ACCESS  read-only
-- STATUS      current
-- DESCRIPTION
-- " Specifies the gfast Port's Previous15Min Down Stream Codeword that could not be correced."
-- ::= { gfastPortPrevious15MCounterEntry 18 }
		-- 1.3.6.1.4.1.6296.9.102.1.2.5.1.18
		gfastPortPrevious15MCounterUsRtxCw OBJECT-TYPE
			SYNTAX Counter32
			MAX-ACCESS read-only
			STATUS current
			DESCRIPTION
				" Specifies the gfast Port's Previous15Min Up Stream Number of Codewords retransmitted."
			::= { gfastPortPrevious15MCounterEntry 18 }

		
		-- 1.3.6.1.4.1.6296.9.102.1.2.5.1.19
		gfastPortPrevious15MCounterDsRtxCw OBJECT-TYPE
			SYNTAX Counter32
			MAX-ACCESS read-only
			STATUS current
			DESCRIPTION
				" Specifies the gfast Port's Previous15Min Down Stream Number of Codewords retransmitted."
			::= { gfastPortPrevious15MCounterEntry 19 }

		
		-- 1.3.6.1.4.1.6296.9.102.1.2.5.1.20
		gfastPortPrevious15MCounterRtxCorrectedCw OBJECT-TYPE
			SYNTAX Counter32
			MAX-ACCESS read-only
			STATUS current
			DESCRIPTION
				" Specifies the gfast Port's Previous15Min Up Stream Number of Codewords corrected through retransmission."
			::= { gfastPortPrevious15MCounterEntry 20 }

		
-- gfastPortPrevious15MCounterDsRtxCorrectedCw OBJECT-TYPE
-- SYNTAX      Counter32
-- MAX-ACCESS  read-only
-- STATUS      current
-- DESCRIPTION
-- " Specifies the gfast Port's Previous15Min Down Stream Number of Codewords corrected through retransmission."
-- ::= { gfastPortPrevious15MCounterEntry 22 }
		-- 1.3.6.1.4.1.6296.9.102.1.2.5.1.21
		gfastPortPrevious15MCounterRtxUncorrectedCw OBJECT-TYPE
			SYNTAX Counter32
			MAX-ACCESS read-only
			STATUS current
			DESCRIPTION
				" Specifies the gfast Port's Previous15Min Up Stream Number of Codewords left uncorrected after retransmission."
			::= { gfastPortPrevious15MCounterEntry 21 }

		
-- gfastPortPrevious15MCounterDsRtxUncorrectedCw OBJECT-TYPE
-- SYNTAX      Counter32
-- MAX-ACCESS  read-only
-- STATUS      current
-- DESCRIPTION
-- " Specifies the gfast Port's Previous15Min Down Stream Number of Codewords left uncorrected after retransmission."
-- ::= { gfastPortPrevious15MCounterEntry 24 } 
		-- 1.3.6.1.4.1.6296.9.102.1.2.5.1.22
		gfastPortPrevious15MCounterFullInitCount OBJECT-TYPE
			SYNTAX Counter32
			MAX-ACCESS read-only
			STATUS current
			DESCRIPTION
				" Specifies the gfast Port's Previous15Min Full Init Count."
			::= { gfastPortPrevious15MCounterEntry 22 }

		
		-- 1.3.6.1.4.1.6296.9.102.1.2.5.1.23
		gfastPortPrevious15MCounterFastInitCount OBJECT-TYPE
			SYNTAX Counter32
			MAX-ACCESS read-only
			STATUS current
			DESCRIPTION
				" Specifies the gfast Port's Previous15Min Fast Init Count."
			::= { gfastPortPrevious15MCounterEntry 23 }

		
--  *********************************************************************
-- * gfastPortCounterTable : Port Current 1day Counter Group
-- *********************************************************************
		-- 1.3.6.1.4.1.6296.9.102.1.2.6
		gfastPortCurrent1DayCounterTable OBJECT-TYPE
			SYNTAX SEQUENCE OF GfastPortCurrent1DayCounterEntry
			MAX-ACCESS not-accessible
			STATUS current
			DESCRIPTION
				"The G.fast port Current 1day Counter table"
			::= { gfastPortGroup 6 }

		
		-- 1.3.6.1.4.1.6296.9.102.1.2.6.1
		gfastPortCurrent1DayCounterEntry OBJECT-TYPE
			SYNTAX GfastPortCurrent1DayCounterEntry
			MAX-ACCESS not-accessible
			STATUS current
			DESCRIPTION
				"An entry in gfastPortCurrent1DayCounterTable."
			INDEX { gfastPortIndex }
			::= { gfastPortCurrent1DayCounterTable 1 }

		
		GfastPortCurrent1DayCounterEntry ::=
			SEQUENCE { 
				gfastPortCurrent1DayCounterUsMinEftr
					Counter32,
				gfastPortCurrent1DayCounterDsMinEftr
					Counter32,
				gfastPortCurrent1DayCounterUsFecs
					Counter32,
				gfastPortCurrent1DayCounterDsFecs
					Counter32,
				gfastPortCurrent1DayCounterUsLoss
					Counter32,
				gfastPortCurrent1DayCounterDsLoss
					Counter32,
				gfastPortCurrent1DayCounterUsEs
					Counter32,
				gfastPortCurrent1DayCounterDsEs
					Counter32,
				gfastPortCurrent1DayCounterUsSes
					Counter32,
				gfastPortCurrent1DayCounterDsSes
					Counter32,
				gfastPortCurrent1DayCounterUsUas
					Counter32,
				gfastPortCurrent1DayCounterDsUas
					Counter32,
				gfastPortCurrent1DayCounterUsCv
					Counter32,
				gfastPortCurrent1DayCounterDsCv
					Counter32,
				gfastPortCurrent1DayCounterUsLols
					Counter32,
				gfastPortCurrent1DayCounterDsLprs
					Counter32,
				gfastPortCurrent1DayCounterUncorrectedCw
					Counter32,
				gfastPortCurrent1DayCounterUsRtxCw
					Counter32,
				gfastPortCurrent1DayCounterDsRtxCw
					Counter32,
				gfastPortCurrent1DayCounterRtxCorrectedCw
					Counter32,
				gfastPortCurrent1DayCounterRtxUncorrectedCw
					Counter32,
				gfastPortCurrent1DayCounterFullInitCount
					Counter32,
				gfastPortCurrent1DayCounterFastInitCount
					Counter32
			 }

-- 		gfastPortCurrent1DayCounterUsErrFreeBits	Counter32,
-- gfastPortCurrent1DayCounterDsErrFreeBits	Counter32,
-- gfastPortCurrent1DayCounterDsUncorrectedCw	Counter32,
-- gfastPortCurrent1DayCounterDsRtxCorrectedCw	Counter32,
-- gfastPortCurrent1DayCounterDsRtxUncorrectedCw	Counter32,  
		-- 1.3.6.1.4.1.6296.9.102.1.2.6.1.1
		gfastPortCurrent1DayCounterUsMinEftr OBJECT-TYPE
			SYNTAX Counter32
			MAX-ACCESS read-only
			STATUS current
			DESCRIPTION
				" Specifies the gfast Port's Current1day Up Stream Minimum Error Free Throughput."
			::= { gfastPortCurrent1DayCounterEntry 1 }

		
		-- 1.3.6.1.4.1.6296.9.102.1.2.6.1.2
		gfastPortCurrent1DayCounterDsMinEftr OBJECT-TYPE
			SYNTAX Counter32
			MAX-ACCESS read-only
			STATUS current
			DESCRIPTION
				" Specifies the gfast Port's Current1day Down Stream Minimum Error Free Throughput."
			::= { gfastPortCurrent1DayCounterEntry 2 }

		
-- gfastPortCurrent1DayCounterUsErrFreeBits OBJECT-TYPE
-- SYNTAX      Counter32
-- MAX-ACCESS  read-only
-- STATUS      current
-- DESCRIPTION
-- " Specifies the gfast Port's Current1day Up Stream Error Free Bits."
-- ::= { gfastPortCurrent1DayCounterEntry 3 }
-- gfastPortCurrent1DayCounterDsErrFreeBits OBJECT-TYPE
-- SYNTAX      Counter32
-- MAX-ACCESS  read-only
-- STATUS      current
-- DESCRIPTION
-- " Specifies the gfast Port's Current1day Down Stream Error Free Bits."
-- ::= { gfastPortCurrent1DayCounterEntry 4 }
		-- 1.3.6.1.4.1.6296.9.102.1.2.6.1.3
		gfastPortCurrent1DayCounterUsFecs OBJECT-TYPE
			SYNTAX Counter32
			MAX-ACCESS read-only
			STATUS current
			DESCRIPTION
				" Specifies the gfast Port's Current1day Up Stream Forward Error Collection Seconds."
			::= { gfastPortCurrent1DayCounterEntry 3 }

		
		-- 1.3.6.1.4.1.6296.9.102.1.2.6.1.4
		gfastPortCurrent1DayCounterDsFecs OBJECT-TYPE
			SYNTAX Counter32
			MAX-ACCESS read-only
			STATUS current
			DESCRIPTION
				" Specifies the gfast Port's Current1day Down Stream Current1day Forward Error Collection Seconds."
			::= { gfastPortCurrent1DayCounterEntry 4 }

		
		-- 1.3.6.1.4.1.6296.9.102.1.2.6.1.5
		gfastPortCurrent1DayCounterUsLoss OBJECT-TYPE
			SYNTAX Counter32
			MAX-ACCESS read-only
			STATUS current
			DESCRIPTION
				" Specifies the gfast Port's Current1day Up Stream Loss of signal Seconds."
			::= { gfastPortCurrent1DayCounterEntry 5 }

		
		-- 1.3.6.1.4.1.6296.9.102.1.2.6.1.6
		gfastPortCurrent1DayCounterDsLoss OBJECT-TYPE
			SYNTAX Counter32
			MAX-ACCESS read-only
			STATUS current
			DESCRIPTION
				" Specifies the gfast Port's Current1day Down Stream Loss of signal Seconds."
			::= { gfastPortCurrent1DayCounterEntry 6 }

		
		-- 1.3.6.1.4.1.6296.9.102.1.2.6.1.7
		gfastPortCurrent1DayCounterUsEs OBJECT-TYPE
			SYNTAX Counter32
			MAX-ACCESS read-only
			STATUS current
			DESCRIPTION
				" Specifies the gfast Port's Current1day Up Stream Errored Seconds."
			::= { gfastPortCurrent1DayCounterEntry 7 }

		
		-- 1.3.6.1.4.1.6296.9.102.1.2.6.1.8
		gfastPortCurrent1DayCounterDsEs OBJECT-TYPE
			SYNTAX Counter32
			MAX-ACCESS read-only
			STATUS current
			DESCRIPTION
				" Specifies the gfast Port's Current1day Down Stream Errored Seconds."
			::= { gfastPortCurrent1DayCounterEntry 8 }

		
		-- 1.3.6.1.4.1.6296.9.102.1.2.6.1.9
		gfastPortCurrent1DayCounterUsSes OBJECT-TYPE
			SYNTAX Counter32
			MAX-ACCESS read-only
			STATUS current
			DESCRIPTION
				" Specifies the gfast Port's Current1day Up Stream Severely Errored Seconds."
			::= { gfastPortCurrent1DayCounterEntry 9 }

		
		-- 1.3.6.1.4.1.6296.9.102.1.2.6.1.10
		gfastPortCurrent1DayCounterDsSes OBJECT-TYPE
			SYNTAX Counter32
			MAX-ACCESS read-only
			STATUS current
			DESCRIPTION
				" Specifies the gfast Port's Current1day Down Stream Severely Errored Seconds."
			::= { gfastPortCurrent1DayCounterEntry 10 }

		
		-- 1.3.6.1.4.1.6296.9.102.1.2.6.1.11
		gfastPortCurrent1DayCounterUsUas OBJECT-TYPE
			SYNTAX Counter32
			MAX-ACCESS read-only
			STATUS current
			DESCRIPTION
				" Specifies the gfast Port's Current1day Up Stream Unavailable Seconds."
			::= { gfastPortCurrent1DayCounterEntry 11 }

		
		-- 1.3.6.1.4.1.6296.9.102.1.2.6.1.12
		gfastPortCurrent1DayCounterDsUas OBJECT-TYPE
			SYNTAX Counter32
			MAX-ACCESS read-only
			STATUS current
			DESCRIPTION
				" Specifies the gfast Port's Current1day Down Stream Unavailable Seconds."
			::= { gfastPortCurrent1DayCounterEntry 12 }

		
		-- 1.3.6.1.4.1.6296.9.102.1.2.6.1.13
		gfastPortCurrent1DayCounterUsCv OBJECT-TYPE
			SYNTAX Counter32
			MAX-ACCESS read-only
			STATUS current
			DESCRIPTION
				" Specifies the gfast Port's Current1day Up Stream CRC Violations."
			::= { gfastPortCurrent1DayCounterEntry 13 }

		
		-- 1.3.6.1.4.1.6296.9.102.1.2.6.1.14
		gfastPortCurrent1DayCounterDsCv OBJECT-TYPE
			SYNTAX Counter32
			MAX-ACCESS read-only
			STATUS current
			DESCRIPTION
				" Specifies the gfast Port's Current1day Down Stream CRC Violations."
			::= { gfastPortCurrent1DayCounterEntry 14 }

		
		-- 1.3.6.1.4.1.6296.9.102.1.2.6.1.15
		gfastPortCurrent1DayCounterUsLols OBJECT-TYPE
			SYNTAX Counter32
			MAX-ACCESS read-only
			STATUS current
			DESCRIPTION
				" Specifies the gfast Port's Current1day Up Stream Loss of Link Seconds."
			::= { gfastPortCurrent1DayCounterEntry 15 }

		
		-- 1.3.6.1.4.1.6296.9.102.1.2.6.1.16
		gfastPortCurrent1DayCounterDsLprs OBJECT-TYPE
			SYNTAX Counter32
			MAX-ACCESS read-only
			STATUS current
			DESCRIPTION
				" Specifies the gfast Port's Current1day Down Stream Loss of Power Seconds."
			::= { gfastPortCurrent1DayCounterEntry 16 }

		
		-- 1.3.6.1.4.1.6296.9.102.1.2.6.1.17
		gfastPortCurrent1DayCounterUncorrectedCw OBJECT-TYPE
			SYNTAX Counter32
			MAX-ACCESS read-only
			STATUS current
			DESCRIPTION
				" Specifies the gfast Port's Current1day Up Stream Codeword that could not be correced."
			::= { gfastPortCurrent1DayCounterEntry 17 }

		
-- gfastPortCurrent1DayCounterDsUncorrectedCw OBJECT-TYPE
-- SYNTAX      Counter32
-- MAX-ACCESS  read-only
-- STATUS      current
-- DESCRIPTION
-- " Specifies the gfast Port's Current1day Down Stream Codeword that could not be correced."
-- ::= { gfastPortCurrent1DayCounterEntry 18 }
		-- 1.3.6.1.4.1.6296.9.102.1.2.6.1.18
		gfastPortCurrent1DayCounterUsRtxCw OBJECT-TYPE
			SYNTAX Counter32
			MAX-ACCESS read-only
			STATUS current
			DESCRIPTION
				" Specifies the gfast Port's Current1day Up Stream Number of Codewords retransmitted."
			::= { gfastPortCurrent1DayCounterEntry 18 }

		
		-- 1.3.6.1.4.1.6296.9.102.1.2.6.1.19
		gfastPortCurrent1DayCounterDsRtxCw OBJECT-TYPE
			SYNTAX Counter32
			MAX-ACCESS read-only
			STATUS current
			DESCRIPTION
				" Specifies the gfast Port's Current1day Down Stream Number of Codewords retransmitted."
			::= { gfastPortCurrent1DayCounterEntry 19 }

		
		-- 1.3.6.1.4.1.6296.9.102.1.2.6.1.20
		gfastPortCurrent1DayCounterRtxCorrectedCw OBJECT-TYPE
			SYNTAX Counter32
			MAX-ACCESS read-only
			STATUS current
			DESCRIPTION
				" Specifies the gfast Port's Current1day Up Stream Number of Codewords corrected through retransmission."
			::= { gfastPortCurrent1DayCounterEntry 20 }

		
-- gfastPortCurrent1DayCounterDsRtxCorrectedCw OBJECT-TYPE
-- SYNTAX      Counter32
-- MAX-ACCESS  read-only
-- STATUS      current
-- DESCRIPTION
-- " Specifies the gfast Port's Current1day Down Stream Number of Codewords corrected through retransmission."
-- ::= { gfastPortCurrent1DayCounterEntry 22 }
		-- 1.3.6.1.4.1.6296.9.102.1.2.6.1.21
		gfastPortCurrent1DayCounterRtxUncorrectedCw OBJECT-TYPE
			SYNTAX Counter32
			MAX-ACCESS read-only
			STATUS current
			DESCRIPTION
				" Specifies the gfast Port's Current1day Up Stream Number of Codewords left uncorrected after retransmission."
			::= { gfastPortCurrent1DayCounterEntry 21 }

		
-- gfastPortCurrent1DayCounterDsRtxUncorrectedCw OBJECT-TYPE
-- SYNTAX      Counter32
-- MAX-ACCESS  read-only
-- STATUS      current
-- DESCRIPTION
-- " Specifies the gfast Port's Current1day Down Stream Number of Codewords left uncorrected after retransmission."
-- ::= { gfastPortCurrent1DayCounterEntry 24 }
		-- 1.3.6.1.4.1.6296.9.102.1.2.6.1.22
		gfastPortCurrent1DayCounterFullInitCount OBJECT-TYPE
			SYNTAX Counter32
			MAX-ACCESS read-only
			STATUS current
			DESCRIPTION
				" Specifies the gfast Port's Current1day Full Init Count."
			::= { gfastPortCurrent1DayCounterEntry 22 }

		
		-- 1.3.6.1.4.1.6296.9.102.1.2.6.1.23
		gfastPortCurrent1DayCounterFastInitCount OBJECT-TYPE
			SYNTAX Counter32
			MAX-ACCESS read-only
			STATUS current
			DESCRIPTION
				" Specifies the gfast Port's Current1day Fast Init Count."
			::= { gfastPortCurrent1DayCounterEntry 23 }

		
--  *********************************************************************
-- * gfastPortCounterTable : Port Previous 1day Counter Group
-- *********************************************************************
		-- 1.3.6.1.4.1.6296.9.102.1.2.7
		gfastPortPrevious1DayCounterTable OBJECT-TYPE
			SYNTAX SEQUENCE OF GfastPortPrevious1DayCounterEntry
			MAX-ACCESS not-accessible
			STATUS current
			DESCRIPTION
				"The G.fast port Previous 1day Counter table"
			::= { gfastPortGroup 7 }

		
		-- 1.3.6.1.4.1.6296.9.102.1.2.7.1
		gfastPortPrevious1DayCounterEntry OBJECT-TYPE
			SYNTAX GfastPortPrevious1DayCounterEntry
			MAX-ACCESS not-accessible
			STATUS current
			DESCRIPTION
				"An entry in gfastPortPrevious1DayCounterTable."
			INDEX { gfastPortIndex }
			::= { gfastPortPrevious1DayCounterTable 1 }

		
		GfastPortPrevious1DayCounterEntry ::=
			SEQUENCE { 
				gfastPortPrevious1DayCounterUsMinEftr
					Counter32,
				gfastPortPrevious1DayCounterDsMinEftr
					Counter32,
				gfastPortPrevious1DayCounterUsFecs
					Counter32,
				gfastPortPrevious1DayCounterDsFecs
					Counter32,
				gfastPortPrevious1DayCounterUsLoss
					Counter32,
				gfastPortPrevious1DayCounterDsLoss
					Counter32,
				gfastPortPrevious1DayCounterUsEs
					Counter32,
				gfastPortPrevious1DayCounterDsEs
					Counter32,
				gfastPortPrevious1DayCounterUsSes
					Counter32,
				gfastPortPrevious1DayCounterDsSes
					Counter32,
				gfastPortPrevious1DayCounterUsUas
					Counter32,
				gfastPortPrevious1DayCounterDsUas
					Counter32,
				gfastPortPrevious1DayCounterUsCv
					Counter32,
				gfastPortPrevious1DayCounterDsCv
					Counter32,
				gfastPortPrevious1DayCounterUsLols
					Counter32,
				gfastPortPrevious1DayCounterDsLprs
					Counter32,
				gfastPortPrevious1DayCounterUncorrectedCw
					Counter32,
				gfastPortPrevious1DayCounterUsRtxCw
					Counter32,
				gfastPortPrevious1DayCounterDsRtxCw
					Counter32,
				gfastPortPrevious1DayCounterRtxCorrectedCw
					Counter32,
				gfastPortPrevious1DayCounterRtxUncorrectedCw
					Counter32,
				gfastPortPrevious1DayCounterFullInitCount
					Counter32,
				gfastPortPrevious1DayCounterFastInitCount
					Counter32
			 }

-- 		gfastPortPrevious1DayCounterUsErrFreeBits	Counter32,
-- gfastPortPrevious1DayCounterDsErrFreeBits	Counter32,
-- gfastPortPrevious1DayCounterDsUncorrectedCw	Counter32,
-- gfastPortPrevious1DayCounterDsRtxCorrectedCw	Counter32,
-- gfastPortPrevious1DayCounterDsRtxUncorrectedCw	Counter32,
		-- 1.3.6.1.4.1.6296.9.102.1.2.7.1.1
		gfastPortPrevious1DayCounterUsMinEftr OBJECT-TYPE
			SYNTAX Counter32
			MAX-ACCESS read-only
			STATUS current
			DESCRIPTION
				" Specifies the gfast Port's Previous1Day Up Stream Minimum Error Free Throughput."
			::= { gfastPortPrevious1DayCounterEntry 1 }

		
		-- 1.3.6.1.4.1.6296.9.102.1.2.7.1.2
		gfastPortPrevious1DayCounterDsMinEftr OBJECT-TYPE
			SYNTAX Counter32
			MAX-ACCESS read-only
			STATUS current
			DESCRIPTION
				" Specifies the gfast Port's Previous1Day Down Stream Minimum Error Free Throughput."
			::= { gfastPortPrevious1DayCounterEntry 2 }

		
-- gfastPortPrevious1DayCounterUsErrFreeBits OBJECT-TYPE
-- SYNTAX      Counter32
-- MAX-ACCESS  read-only
-- STATUS      current
-- DESCRIPTION
-- " Specifies the gfast Port's Previous1Day Up Stream Error Free Bits."
-- ::= { gfastPortPrevious1DayCounterEntry 3 }
-- gfastPortPrevious1DayCounterDsErrFreeBits OBJECT-TYPE
-- SYNTAX      Counter32
-- MAX-ACCESS  read-only
-- STATUS      current
-- DESCRIPTION
-- " Specifies the gfast Port's Previous1Day Down Stream Error Free Bits."
-- ::= { gfastPortPrevious1DayCounterEntry 4 }
		-- 1.3.6.1.4.1.6296.9.102.1.2.7.1.3
		gfastPortPrevious1DayCounterUsFecs OBJECT-TYPE
			SYNTAX Counter32
			MAX-ACCESS read-only
			STATUS current
			DESCRIPTION
				" Specifies the gfast Port's Previous1Day Up Stream Forward Error Collection Seconds."
			::= { gfastPortPrevious1DayCounterEntry 3 }

		
		-- 1.3.6.1.4.1.6296.9.102.1.2.7.1.4
		gfastPortPrevious1DayCounterDsFecs OBJECT-TYPE
			SYNTAX Counter32
			MAX-ACCESS read-only
			STATUS current
			DESCRIPTION
				" Specifies the gfast Port's Previous1Day Down Stream Previous1Day Forward Error Collection Seconds."
			::= { gfastPortPrevious1DayCounterEntry 4 }

		
		-- 1.3.6.1.4.1.6296.9.102.1.2.7.1.5
		gfastPortPrevious1DayCounterUsLoss OBJECT-TYPE
			SYNTAX Counter32
			MAX-ACCESS read-only
			STATUS current
			DESCRIPTION
				" Specifies the gfast Port's Previous1Day Up Stream Loss of signal Seconds."
			::= { gfastPortPrevious1DayCounterEntry 5 }

		
		-- 1.3.6.1.4.1.6296.9.102.1.2.7.1.6
		gfastPortPrevious1DayCounterDsLoss OBJECT-TYPE
			SYNTAX Counter32
			MAX-ACCESS read-only
			STATUS current
			DESCRIPTION
				" Specifies the gfast Port's Previous1Day Down Stream Loss of signal Seconds."
			::= { gfastPortPrevious1DayCounterEntry 6 }

		
		-- 1.3.6.1.4.1.6296.9.102.1.2.7.1.7
		gfastPortPrevious1DayCounterUsEs OBJECT-TYPE
			SYNTAX Counter32
			MAX-ACCESS read-only
			STATUS current
			DESCRIPTION
				" Specifies the gfast Port's Previous1Day Up Stream Errored Seconds."
			::= { gfastPortPrevious1DayCounterEntry 7 }

		
		-- 1.3.6.1.4.1.6296.9.102.1.2.7.1.8
		gfastPortPrevious1DayCounterDsEs OBJECT-TYPE
			SYNTAX Counter32
			MAX-ACCESS read-only
			STATUS current
			DESCRIPTION
				" Specifies the gfast Port's Previous1Day Down Stream Errored Seconds."
			::= { gfastPortPrevious1DayCounterEntry 8 }

		
		-- 1.3.6.1.4.1.6296.9.102.1.2.7.1.9
		gfastPortPrevious1DayCounterUsSes OBJECT-TYPE
			SYNTAX Counter32
			MAX-ACCESS read-only
			STATUS current
			DESCRIPTION
				" Specifies the gfast Port's Previous1Day Up Stream Severely Errored Seconds."
			::= { gfastPortPrevious1DayCounterEntry 9 }

		
		-- 1.3.6.1.4.1.6296.9.102.1.2.7.1.10
		gfastPortPrevious1DayCounterDsSes OBJECT-TYPE
			SYNTAX Counter32
			MAX-ACCESS read-only
			STATUS current
			DESCRIPTION
				" Specifies the gfast Port's Previous1Day Down Stream Severely Errored Seconds."
			::= { gfastPortPrevious1DayCounterEntry 10 }

		
		-- 1.3.6.1.4.1.6296.9.102.1.2.7.1.11
		gfastPortPrevious1DayCounterUsUas OBJECT-TYPE
			SYNTAX Counter32
			MAX-ACCESS read-only
			STATUS current
			DESCRIPTION
				" Specifies the gfast Port's Previous1Day Up Stream Unavailable Seconds."
			::= { gfastPortPrevious1DayCounterEntry 11 }

		
		-- 1.3.6.1.4.1.6296.9.102.1.2.7.1.12
		gfastPortPrevious1DayCounterDsUas OBJECT-TYPE
			SYNTAX Counter32
			MAX-ACCESS read-only
			STATUS current
			DESCRIPTION
				" Specifies the gfast Port's Previous1Day Down Stream Unavailable Seconds."
			::= { gfastPortPrevious1DayCounterEntry 12 }

		
		-- 1.3.6.1.4.1.6296.9.102.1.2.7.1.13
		gfastPortPrevious1DayCounterUsCv OBJECT-TYPE
			SYNTAX Counter32
			MAX-ACCESS read-only
			STATUS current
			DESCRIPTION
				" Specifies the gfast Port's Previous1Day Up Stream CRC Violations."
			::= { gfastPortPrevious1DayCounterEntry 13 }

		
		-- 1.3.6.1.4.1.6296.9.102.1.2.7.1.14
		gfastPortPrevious1DayCounterDsCv OBJECT-TYPE
			SYNTAX Counter32
			MAX-ACCESS read-only
			STATUS current
			DESCRIPTION
				" Specifies the gfast Port's Previous1Day Down Stream CRC Violations."
			::= { gfastPortPrevious1DayCounterEntry 14 }

		
		-- 1.3.6.1.4.1.6296.9.102.1.2.7.1.15
		gfastPortPrevious1DayCounterUsLols OBJECT-TYPE
			SYNTAX Counter32
			MAX-ACCESS read-only
			STATUS current
			DESCRIPTION
				" Specifies the gfast Port's Previous1Day Up Stream Loss of Link Seconds."
			::= { gfastPortPrevious1DayCounterEntry 15 }

		
		-- 1.3.6.1.4.1.6296.9.102.1.2.7.1.16
		gfastPortPrevious1DayCounterDsLprs OBJECT-TYPE
			SYNTAX Counter32
			MAX-ACCESS read-only
			STATUS current
			DESCRIPTION
				" Specifies the gfast Port's Previous1Day Down Stream Loss of Power Seconds."
			::= { gfastPortPrevious1DayCounterEntry 16 }

		
		-- 1.3.6.1.4.1.6296.9.102.1.2.7.1.17
		gfastPortPrevious1DayCounterUncorrectedCw OBJECT-TYPE
			SYNTAX Counter32
			MAX-ACCESS read-only
			STATUS current
			DESCRIPTION
				" Specifies the gfast Port's Previous1Day Up Stream Codeword that could not be correced."
			::= { gfastPortPrevious1DayCounterEntry 17 }

		
-- gfastPortPrevious1DayCounterDsUncorrectedCw OBJECT-TYPE
-- SYNTAX      Counter32
-- MAX-ACCESS  read-only
-- STATUS      current
-- DESCRIPTION
-- " Specifies the gfast Port's Previous1Day Down Stream Codeword that could not be correced."
-- ::= { gfastPortPrevious1DayCounterEntry 18 }
		-- 1.3.6.1.4.1.6296.9.102.1.2.7.1.18
		gfastPortPrevious1DayCounterUsRtxCw OBJECT-TYPE
			SYNTAX Counter32
			MAX-ACCESS read-only
			STATUS current
			DESCRIPTION
				" Specifies the gfast Port's Previous1Day Up Stream Number of Codewords retransmitted."
			::= { gfastPortPrevious1DayCounterEntry 18 }

		
		-- 1.3.6.1.4.1.6296.9.102.1.2.7.1.19
		gfastPortPrevious1DayCounterDsRtxCw OBJECT-TYPE
			SYNTAX Counter32
			MAX-ACCESS read-only
			STATUS current
			DESCRIPTION
				" Specifies the gfast Port's Previous1Day Down Stream Number of Codewords retransmitted."
			::= { gfastPortPrevious1DayCounterEntry 19 }

		
		-- 1.3.6.1.4.1.6296.9.102.1.2.7.1.20
		gfastPortPrevious1DayCounterRtxCorrectedCw OBJECT-TYPE
			SYNTAX Counter32
			MAX-ACCESS read-only
			STATUS current
			DESCRIPTION
				" Specifies the gfast Port's Previous1Day Up Stream Number of Codewords corrected through retransmission."
			::= { gfastPortPrevious1DayCounterEntry 20 }

		
-- gfastPortPrevious1DayCounterDsRtxCorrectedCw OBJECT-TYPE
-- SYNTAX      Counter32
-- MAX-ACCESS  read-only
-- STATUS      current
-- DESCRIPTION
-- " Specifies the gfast Port's Previous1Day Down Stream Number of Codewords corrected through retransmission."
-- ::= { gfastPortPrevious1DayCounterEntry 22 }
		-- 1.3.6.1.4.1.6296.9.102.1.2.7.1.21
		gfastPortPrevious1DayCounterRtxUncorrectedCw OBJECT-TYPE
			SYNTAX Counter32
			MAX-ACCESS read-only
			STATUS current
			DESCRIPTION
				" Specifies the gfast Port's Previous1Day Up Stream Number of Codewords left uncorrected after retransmission."
			::= { gfastPortPrevious1DayCounterEntry 21 }

		
-- gfastPortPrevious1DayCounterDsRtxUncorrectedCw OBJECT-TYPE
-- SYNTAX      Counter32
-- MAX-ACCESS  read-only
-- STATUS      current
-- DESCRIPTION
-- " Specifies the gfast Port's Previous1Day Down Stream Number of Codewords left uncorrected after retransmission."
-- ::= { gfastPortPrevious1DayCounterEntry 24 }
		-- 1.3.6.1.4.1.6296.9.102.1.2.7.1.22
		gfastPortPrevious1DayCounterFullInitCount OBJECT-TYPE
			SYNTAX Counter32
			MAX-ACCESS read-only
			STATUS current
			DESCRIPTION
				" Specifies the gfast Port's Previous1Day Full Init Count."
			::= { gfastPortPrevious1DayCounterEntry 22 }

		
		-- 1.3.6.1.4.1.6296.9.102.1.2.7.1.23
		gfastPortPrevious1DayCounterFastInitCount OBJECT-TYPE
			SYNTAX Counter32
			MAX-ACCESS read-only
			STATUS current
			DESCRIPTION
				" Specifies the gfast Port's Previous1Day Fast Init Count."
			::= { gfastPortPrevious1DayCounterEntry 23 }

		
--  *********************************************************************
-- * gfastPortEventTable : Port Event Group
-- *********************************************************************
		-- 1.3.6.1.4.1.6296.9.102.1.2.8
		gfastPortEventTable OBJECT-TYPE
			SYNTAX SEQUENCE OF GfastPortEventEntry
			MAX-ACCESS not-accessible
			STATUS current
			DESCRIPTION
				"The G.fast port running event counter table"
			::= { gfastPortGroup 8 }

		
		-- 1.3.6.1.4.1.6296.9.102.1.2.8.1
		gfastPortEventEntry OBJECT-TYPE
			SYNTAX GfastPortEventEntry
			MAX-ACCESS not-accessible
			STATUS current
			DESCRIPTION
				"An entry in gfastPortEventTable."
			INDEX { gfastPortIndex }
			::= { gfastPortEventTable 1 }

		
		GfastPortEventEntry ::=
			SEQUENCE { 
				gfastPortEventUsLos
					Counter32,
				gfastPortEventDsLos
					Counter32,
				gfastPortEventUsLom
					Counter32,
				gfastPortEventDsLom
					Counter32,
				gfastPortEventUsLor
					Counter32,
				gfastPortEventDsLor
					Counter32,
				gfastPortEventLpr
					Counter32,
				gfastPortEventLol
					Counter32,
				gfastPortEventUsBs
					Counter32,
				gfastPortEventDsBs
					Counter32,
				gfastPortEventUsRau
					Counter32,
				gfastPortEventDsRau
					Counter32,
				gfastPortEventUsRad
					Counter32,
				gfastPortEventDsRad
					Counter32,
				gfastPortEventUsFra
					Counter32,
				gfastPortEventDsFra
					Counter32,
				gfastPortEventUsRpa
					Counter32,
				gfastPortEventDsRpa
					Counter32,
				gfastPortEventTiga
					Counter32
			 }

-- 		gfastPortEventHostReinit		Counter32,
-- gfastPortEventSpontaneousReinit		Counter32,
		-- 1.3.6.1.4.1.6296.9.102.1.2.8.1.1
		gfastPortEventUsLos OBJECT-TYPE
			SYNTAX Counter32
			MAX-ACCESS read-only
			STATUS current
			DESCRIPTION
				" Specifies the gfast Port's Up Stream Loss Of Signal."
			::= { gfastPortEventEntry 1 }

		
		-- 1.3.6.1.4.1.6296.9.102.1.2.8.1.2
		gfastPortEventDsLos OBJECT-TYPE
			SYNTAX Counter32
			MAX-ACCESS read-only
			STATUS current
			DESCRIPTION
				" Specifies the gfast Port's Down Stream Loss Of Signal."
			::= { gfastPortEventEntry 2 }

		
		-- 1.3.6.1.4.1.6296.9.102.1.2.8.1.3
		gfastPortEventUsLom OBJECT-TYPE
			SYNTAX Counter32
			MAX-ACCESS read-only
			STATUS current
			DESCRIPTION
				" Specifies the gfast Port's Up Stream Loss Of Margin."
			::= { gfastPortEventEntry 3 }

		
		-- 1.3.6.1.4.1.6296.9.102.1.2.8.1.4
		gfastPortEventDsLom OBJECT-TYPE
			SYNTAX Counter32
			MAX-ACCESS read-only
			STATUS current
			DESCRIPTION
				" Specifies the gfast Port's Down Stream Loss Of Margin."
			::= { gfastPortEventEntry 4 }

		
		-- 1.3.6.1.4.1.6296.9.102.1.2.8.1.5
		gfastPortEventUsLor OBJECT-TYPE
			SYNTAX Counter32
			MAX-ACCESS read-only
			STATUS current
			DESCRIPTION
				" Specifies the gfast Port's Up Stream Loss of RMC."
			::= { gfastPortEventEntry 5 }

		
		-- 1.3.6.1.4.1.6296.9.102.1.2.8.1.6
		gfastPortEventDsLor OBJECT-TYPE
			SYNTAX Counter32
			MAX-ACCESS read-only
			STATUS current
			DESCRIPTION
				" Specifies the gfast Port's Down Stream Loss of RMC."
			::= { gfastPortEventEntry 6 }

		
		-- 1.3.6.1.4.1.6296.9.102.1.2.8.1.7
		gfastPortEventLpr OBJECT-TYPE
			SYNTAX Counter32
			MAX-ACCESS read-only
			STATUS current
			DESCRIPTION
				" Specifies the gfast Port's Loss of Power."
			::= { gfastPortEventEntry 7 }

		
		-- 1.3.6.1.4.1.6296.9.102.1.2.8.1.8
		gfastPortEventLol OBJECT-TYPE
			SYNTAX Counter32
			MAX-ACCESS read-only
			STATUS current
			DESCRIPTION
				" Specifies the gfast Port's LOL."
			::= { gfastPortEventEntry 8 }

		
		-- 1.3.6.1.4.1.6296.9.102.1.2.8.1.9
		gfastPortEventUsBs OBJECT-TYPE
			SYNTAX Counter32
			MAX-ACCESS read-only
			STATUS current
			DESCRIPTION
				" Specifies the gfast Port's Up Stream Bit-Swap."
			::= { gfastPortEventEntry 9 }

		
		-- 1.3.6.1.4.1.6296.9.102.1.2.8.1.10
		gfastPortEventDsBs OBJECT-TYPE
			SYNTAX Counter32
			MAX-ACCESS read-only
			STATUS current
			DESCRIPTION
				" Specifies the gfast Port's Down Stream Bit-Swap."
			::= { gfastPortEventEntry 10 }

		
		-- 1.3.6.1.4.1.6296.9.102.1.2.8.1.11
		gfastPortEventUsRau OBJECT-TYPE
			SYNTAX Counter32
			MAX-ACCESS read-only
			STATUS current
			DESCRIPTION
				" Specifies the gfast Port's Up Stream Rate Adaptation Upwards."
			::= { gfastPortEventEntry 11 }

		
		-- 1.3.6.1.4.1.6296.9.102.1.2.8.1.12
		gfastPortEventDsRau OBJECT-TYPE
			SYNTAX Counter32
			MAX-ACCESS read-only
			STATUS current
			DESCRIPTION
				" Specifies the gfast Port's Down Stream Rate Adaptation Upwards."
			::= { gfastPortEventEntry 12 }

		
		-- 1.3.6.1.4.1.6296.9.102.1.2.8.1.13
		gfastPortEventUsRad OBJECT-TYPE
			SYNTAX Counter32
			MAX-ACCESS read-only
			STATUS current
			DESCRIPTION
				" Specifies the gfast Port's Up Stream Rate Adaptation Downwards."
			::= { gfastPortEventEntry 13 }

		
		-- 1.3.6.1.4.1.6296.9.102.1.2.8.1.14
		gfastPortEventDsRad OBJECT-TYPE
			SYNTAX Counter32
			MAX-ACCESS read-only
			STATUS current
			DESCRIPTION
				" Specifies the gfast Port's Down Stream Rate Adaptation Downwards."
			::= { gfastPortEventEntry 14 }

		
		-- 1.3.6.1.4.1.6296.9.102.1.2.8.1.15
		gfastPortEventUsFra OBJECT-TYPE
			SYNTAX Counter32
			MAX-ACCESS read-only
			STATUS current
			DESCRIPTION
				" Specifies the gfast Port's Up Stream FRA."
			::= { gfastPortEventEntry 15 }

		
		-- 1.3.6.1.4.1.6296.9.102.1.2.8.1.16
		gfastPortEventDsFra OBJECT-TYPE
			SYNTAX Counter32
			MAX-ACCESS read-only
			STATUS current
			DESCRIPTION
				" Specifies the gfast Port's Down Stream FRA."
			::= { gfastPortEventEntry 16 }

		
		-- 1.3.6.1.4.1.6296.9.102.1.2.8.1.17
		gfastPortEventUsRpa OBJECT-TYPE
			SYNTAX Counter32
			MAX-ACCESS read-only
			STATUS current
			DESCRIPTION
				" Specifies the gfast Port's Up Stream RMC Parameter Adjustment."
			::= { gfastPortEventEntry 17 }

		
		-- 1.3.6.1.4.1.6296.9.102.1.2.8.1.18
		gfastPortEventDsRpa OBJECT-TYPE
			SYNTAX Counter32
			MAX-ACCESS read-only
			STATUS current
			DESCRIPTION
				" Specifies the gfast Port's Down Stream RMC Parameter Adjustment."
			::= { gfastPortEventEntry 18 }

		
		-- 1.3.6.1.4.1.6296.9.102.1.2.8.1.19
		gfastPortEventTiga OBJECT-TYPE
			SYNTAX Counter32
			MAX-ACCESS read-only
			STATUS current
			DESCRIPTION
				" Specifies the gfast Port's Transmitter Initiated Gain Adjustment."
			::= { gfastPortEventEntry 19 }

		
-- gfastPortEventHostReinit OBJECT-TYPE
-- SYNTAX      Counter32
-- MAX-ACCESS  read-only
-- STATUS      current
-- DESCRIPTION
-- " Specifies the gfast Port's Host ReInit event."
-- ::= { gfastPortEventEntry 20 }
-- gfastPortEventSpontaneousReinit OBJECT-TYPE
-- SYNTAX      Counter32
-- MAX-ACCESS  read-only
-- STATUS      current
-- DESCRIPTION
-- " Specifies the gfast Port's Spontaneous ReInit event."
-- ::= { gfastPortEventEntry 21 }
-- *********************************************************************
-- * gfastPortCurr15MinEventTable : Port Event Group
-- *********************************************************************
		-- 1.3.6.1.4.1.6296.9.102.1.2.9
		gfastPortCurr15MinEventTable OBJECT-TYPE
			SYNTAX SEQUENCE OF GfastPortCurr15MinEventEntry
			MAX-ACCESS not-accessible
			STATUS current
			DESCRIPTION
				"The G.fast port Current 15Minutes Event counter table"
			::= { gfastPortGroup 9 }

		
		-- 1.3.6.1.4.1.6296.9.102.1.2.9.1
		gfastPortCurr15MinEventEntry OBJECT-TYPE
			SYNTAX GfastPortCurr15MinEventEntry
			MAX-ACCESS not-accessible
			STATUS current
			DESCRIPTION
				"An entry in gfastPortCurr15MinEventTable."
			INDEX { gfastPortIndex }
			::= { gfastPortCurr15MinEventTable 1 }

		
		GfastPortCurr15MinEventEntry ::=
			SEQUENCE { 
				gfastPortCurr15MinEventUsLos
					Counter32,
				gfastPortCurr15MinEventDsLos
					Counter32,
				gfastPortCurr15MinEventUsLom
					Counter32,
				gfastPortCurr15MinEventDsLom
					Counter32,
				gfastPortCurr15MinEventUsLor
					Counter32,
				gfastPortCurr15MinEventDsLor
					Counter32,
				gfastPortCurr15MinEventLpr
					Counter32,
				gfastPortCurr15MinEventLol
					Counter32,
				gfastPortCurr15MinEventUsBs
					Counter32,
				gfastPortCurr15MinEventDsBs
					Counter32,
				gfastPortCurr15MinEventUsRau
					Counter32,
				gfastPortCurr15MinEventDsRau
					Counter32,
				gfastPortCurr15MinEventUsRad
					Counter32,
				gfastPortCurr15MinEventDsRad
					Counter32,
				gfastPortCurr15MinEventUsFra
					Counter32,
				gfastPortCurr15MinEventDsFra
					Counter32,
				gfastPortCurr15MinEventUsRpa
					Counter32,
				gfastPortCurr15MinEventDsRpa
					Counter32,
				gfastPortCurr15MinEventTiga
					Counter32
			 }

-- 		gfastPortCurr15MinEventHostReinit		Counter32,
-- gfastPortCurr15MinEventSpontaneousReinit		Counter32,
		-- 1.3.6.1.4.1.6296.9.102.1.2.9.1.1
		gfastPortCurr15MinEventUsLos OBJECT-TYPE
			SYNTAX Counter32
			MAX-ACCESS read-only
			STATUS current
			DESCRIPTION
				" Specifies the gfast Port's Current 15Minutes Up Stream Loss Of Signal."
			::= { gfastPortCurr15MinEventEntry 1 }

		
		-- 1.3.6.1.4.1.6296.9.102.1.2.9.1.2
		gfastPortCurr15MinEventDsLos OBJECT-TYPE
			SYNTAX Counter32
			MAX-ACCESS read-only
			STATUS current
			DESCRIPTION
				" Specifies the gfast Port's Current 15Minutes Down Stream Loss Of Signal."
			::= { gfastPortCurr15MinEventEntry 2 }

		
		-- 1.3.6.1.4.1.6296.9.102.1.2.9.1.3
		gfastPortCurr15MinEventUsLom OBJECT-TYPE
			SYNTAX Counter32
			MAX-ACCESS read-only
			STATUS current
			DESCRIPTION
				" Specifies the gfast Port's Current 15Minutes Up Stream Loss Of Margin."
			::= { gfastPortCurr15MinEventEntry 3 }

		
		-- 1.3.6.1.4.1.6296.9.102.1.2.9.1.4
		gfastPortCurr15MinEventDsLom OBJECT-TYPE
			SYNTAX Counter32
			MAX-ACCESS read-only
			STATUS current
			DESCRIPTION
				" Specifies the gfast Port's Current 15Minutes Down Stream Loss Of Margin."
			::= { gfastPortCurr15MinEventEntry 4 }

		
		-- 1.3.6.1.4.1.6296.9.102.1.2.9.1.5
		gfastPortCurr15MinEventUsLor OBJECT-TYPE
			SYNTAX Counter32
			MAX-ACCESS read-only
			STATUS current
			DESCRIPTION
				" Specifies the gfast Port's Current 15Minutes Up Stream Loss of RMC."
			::= { gfastPortCurr15MinEventEntry 5 }

		
		-- 1.3.6.1.4.1.6296.9.102.1.2.9.1.6
		gfastPortCurr15MinEventDsLor OBJECT-TYPE
			SYNTAX Counter32
			MAX-ACCESS read-only
			STATUS current
			DESCRIPTION
				" Specifies the gfast Port's Current 15Minutes Down Stream Loss of RMC."
			::= { gfastPortCurr15MinEventEntry 6 }

		
		-- 1.3.6.1.4.1.6296.9.102.1.2.9.1.7
		gfastPortCurr15MinEventLpr OBJECT-TYPE
			SYNTAX Counter32
			MAX-ACCESS read-only
			STATUS current
			DESCRIPTION
				" Specifies the gfast Port's Current 15Minutes Loss of Power."
			::= { gfastPortCurr15MinEventEntry 7 }

		
		-- 1.3.6.1.4.1.6296.9.102.1.2.9.1.8
		gfastPortCurr15MinEventLol OBJECT-TYPE
			SYNTAX Counter32
			MAX-ACCESS read-only
			STATUS current
			DESCRIPTION
				" Specifies the gfast Port's Current 15Minutes LOL."
			::= { gfastPortCurr15MinEventEntry 8 }

		
		-- 1.3.6.1.4.1.6296.9.102.1.2.9.1.9
		gfastPortCurr15MinEventUsBs OBJECT-TYPE
			SYNTAX Counter32
			MAX-ACCESS read-only
			STATUS current
			DESCRIPTION
				" Specifies the gfast Port's Current 15Minutes Up Stream Bit-Swap."
			::= { gfastPortCurr15MinEventEntry 9 }

		
		-- 1.3.6.1.4.1.6296.9.102.1.2.9.1.10
		gfastPortCurr15MinEventDsBs OBJECT-TYPE
			SYNTAX Counter32
			MAX-ACCESS read-only
			STATUS current
			DESCRIPTION
				" Specifies the gfast Port's Current 15Minutes Down Stream Bit-Swap."
			::= { gfastPortCurr15MinEventEntry 10 }

		
		-- 1.3.6.1.4.1.6296.9.102.1.2.9.1.11
		gfastPortCurr15MinEventUsRau OBJECT-TYPE
			SYNTAX Counter32
			MAX-ACCESS read-only
			STATUS current
			DESCRIPTION
				" Specifies the gfast Port's Current 15Minutes Up Stream Rate Adaptation Upwards."
			::= { gfastPortCurr15MinEventEntry 11 }

		
		-- 1.3.6.1.4.1.6296.9.102.1.2.9.1.12
		gfastPortCurr15MinEventDsRau OBJECT-TYPE
			SYNTAX Counter32
			MAX-ACCESS read-only
			STATUS current
			DESCRIPTION
				" Specifies the gfast Port's Current 15Minutes Down Stream Rate Adaptation Upwards."
			::= { gfastPortCurr15MinEventEntry 12 }

		
		-- 1.3.6.1.4.1.6296.9.102.1.2.9.1.13
		gfastPortCurr15MinEventUsRad OBJECT-TYPE
			SYNTAX Counter32
			MAX-ACCESS read-only
			STATUS current
			DESCRIPTION
				" Specifies the gfast Port's Current 15Minutes Up Stream Rate Adaptation Downwards."
			::= { gfastPortCurr15MinEventEntry 13 }

		
		-- 1.3.6.1.4.1.6296.9.102.1.2.9.1.14
		gfastPortCurr15MinEventDsRad OBJECT-TYPE
			SYNTAX Counter32
			MAX-ACCESS read-only
			STATUS current
			DESCRIPTION
				" Specifies the gfast Port's Current 15Minutes Down Stream Rate Adaptation Downwards."
			::= { gfastPortCurr15MinEventEntry 14 }

		
		-- 1.3.6.1.4.1.6296.9.102.1.2.9.1.15
		gfastPortCurr15MinEventUsFra OBJECT-TYPE
			SYNTAX Counter32
			MAX-ACCESS read-only
			STATUS current
			DESCRIPTION
				" Specifies the gfast Port's Current 15Minutes Up Stream FRA."
			::= { gfastPortCurr15MinEventEntry 15 }

		
		-- 1.3.6.1.4.1.6296.9.102.1.2.9.1.16
		gfastPortCurr15MinEventDsFra OBJECT-TYPE
			SYNTAX Counter32
			MAX-ACCESS read-only
			STATUS current
			DESCRIPTION
				" Specifies the gfast Port's Current 15Minutes Down Stream FRA."
			::= { gfastPortCurr15MinEventEntry 16 }

		
		-- 1.3.6.1.4.1.6296.9.102.1.2.9.1.17
		gfastPortCurr15MinEventUsRpa OBJECT-TYPE
			SYNTAX Counter32
			MAX-ACCESS read-only
			STATUS current
			DESCRIPTION
				" Specifies the gfast Port's Current 15Minutes Up Stream RMC Parameter Adjustment."
			::= { gfastPortCurr15MinEventEntry 17 }

		
		-- 1.3.6.1.4.1.6296.9.102.1.2.9.1.18
		gfastPortCurr15MinEventDsRpa OBJECT-TYPE
			SYNTAX Counter32
			MAX-ACCESS read-only
			STATUS current
			DESCRIPTION
				" Specifies the gfast Port's Current 15Minutes Down Stream RMC Parameter Adjustment."
			::= { gfastPortCurr15MinEventEntry 18 }

		
		-- 1.3.6.1.4.1.6296.9.102.1.2.9.1.19
		gfastPortCurr15MinEventTiga OBJECT-TYPE
			SYNTAX Counter32
			MAX-ACCESS read-only
			STATUS current
			DESCRIPTION
				" Specifies the gfast Port's Current 15Minutes Transmitter Initiated Gain Adjustment."
			::= { gfastPortCurr15MinEventEntry 19 }

		
-- gfastPortCurr15MinEventHostReinit OBJECT-TYPE
-- SYNTAX      Counter32
-- MAX-ACCESS  read-only
-- STATUS      current
-- DESCRIPTION
-- " Specifies the gfast Port's Current 15Minutes Host ReInit event."
-- ::= { gfastPortCurr15MinEventEntry 20 }
-- gfastPortCurr15MinEventSpontaneousReinit OBJECT-TYPE
-- SYNTAX      Counter32
-- MAX-ACCESS  read-only
-- STATUS      current
-- DESCRIPTION
-- " Specifies the gfast Port's Current 15Minutes Spontaneous ReInit event."
-- ::= { gfastPortCurr15MinEventEntry 21 }
-- *********************************************************************
-- * gfastPortPrev15MinEventTable : Port Event Group
-- *********************************************************************
		-- 1.3.6.1.4.1.6296.9.102.1.2.10
		gfastPortPrev15MinEventTable OBJECT-TYPE
			SYNTAX SEQUENCE OF GfastPortPrev15MinEventEntry
			MAX-ACCESS not-accessible
			STATUS current
			DESCRIPTION
				"The G.fast port previous 15Minutes event counter table"
			::= { gfastPortGroup 10 }

		
		-- 1.3.6.1.4.1.6296.9.102.1.2.10.1
		gfastPortPrev15MinEventEntry OBJECT-TYPE
			SYNTAX GfastPortPrev15MinEventEntry
			MAX-ACCESS not-accessible
			STATUS current
			DESCRIPTION
				"An entry in gfastPortPrev15MinEventTable."
			INDEX { gfastPortIndex }
			::= { gfastPortPrev15MinEventTable 1 }

		
		GfastPortPrev15MinEventEntry ::=
			SEQUENCE { 
				gfastPortPrev15MinEventUsLos
					Counter32,
				gfastPortPrev15MinEventDsLos
					Counter32,
				gfastPortPrev15MinEventUsLom
					Counter32,
				gfastPortPrev15MinEventDsLom
					Counter32,
				gfastPortPrev15MinEventUsLor
					Counter32,
				gfastPortPrev15MinEventDsLor
					Counter32,
				gfastPortPrev15MinEventLpr
					Counter32,
				gfastPortPrev15MinEventLol
					Counter32,
				gfastPortPrev15MinEventUsBs
					Counter32,
				gfastPortPrev15MinEventDsBs
					Counter32,
				gfastPortPrev15MinEventUsRau
					Counter32,
				gfastPortPrev15MinEventDsRau
					Counter32,
				gfastPortPrev15MinEventUsRad
					Counter32,
				gfastPortPrev15MinEventDsRad
					Counter32,
				gfastPortPrev15MinEventUsFra
					Counter32,
				gfastPortPrev15MinEventDsFra
					Counter32,
				gfastPortPrev15MinEventUsRpa
					Counter32,
				gfastPortPrev15MinEventDsRpa
					Counter32,
				gfastPortPrev15MinEventTiga
					Counter32
			 }

-- 		gfastPortPrev15MinEventHostReinit		Counter32,
-- gfastPortPrev15MinEventSpontaneousReinit		Counter32,
		-- 1.3.6.1.4.1.6296.9.102.1.2.10.1.1
		gfastPortPrev15MinEventUsLos OBJECT-TYPE
			SYNTAX Counter32
			MAX-ACCESS read-only
			STATUS current
			DESCRIPTION
				" Specifies the gfast Port's Previous 15Minutes Up Stream Loss Of Signal."
			::= { gfastPortPrev15MinEventEntry 1 }

		
		-- 1.3.6.1.4.1.6296.9.102.1.2.10.1.2
		gfastPortPrev15MinEventDsLos OBJECT-TYPE
			SYNTAX Counter32
			MAX-ACCESS read-only
			STATUS current
			DESCRIPTION
				" Specifies the gfast Port's Previous 15Minutes Down Stream Loss Of Signal."
			::= { gfastPortPrev15MinEventEntry 2 }

		
		-- 1.3.6.1.4.1.6296.9.102.1.2.10.1.3
		gfastPortPrev15MinEventUsLom OBJECT-TYPE
			SYNTAX Counter32
			MAX-ACCESS read-only
			STATUS current
			DESCRIPTION
				" Specifies the gfast Port's Previous 15Minutes Up Stream Loss Of Margin."
			::= { gfastPortPrev15MinEventEntry 3 }

		
		-- 1.3.6.1.4.1.6296.9.102.1.2.10.1.4
		gfastPortPrev15MinEventDsLom OBJECT-TYPE
			SYNTAX Counter32
			MAX-ACCESS read-only
			STATUS current
			DESCRIPTION
				" Specifies the gfast Port's Previous 15Minutes Down Stream Loss Of Margin."
			::= { gfastPortPrev15MinEventEntry 4 }

		
		-- 1.3.6.1.4.1.6296.9.102.1.2.10.1.5
		gfastPortPrev15MinEventUsLor OBJECT-TYPE
			SYNTAX Counter32
			MAX-ACCESS read-only
			STATUS current
			DESCRIPTION
				" Specifies the gfast Port's Previous 15Minutes Up Stream Loss of RMC."
			::= { gfastPortPrev15MinEventEntry 5 }

		
		-- 1.3.6.1.4.1.6296.9.102.1.2.10.1.6
		gfastPortPrev15MinEventDsLor OBJECT-TYPE
			SYNTAX Counter32
			MAX-ACCESS read-only
			STATUS current
			DESCRIPTION
				" Specifies the gfast Port's Previous 15Minutes Down Stream Loss of RMC."
			::= { gfastPortPrev15MinEventEntry 6 }

		
		-- 1.3.6.1.4.1.6296.9.102.1.2.10.1.7
		gfastPortPrev15MinEventLpr OBJECT-TYPE
			SYNTAX Counter32
			MAX-ACCESS read-only
			STATUS current
			DESCRIPTION
				" Specifies the gfast Port's Previous 15Minutes Loss of Power."
			::= { gfastPortPrev15MinEventEntry 7 }

		
		-- 1.3.6.1.4.1.6296.9.102.1.2.10.1.8
		gfastPortPrev15MinEventLol OBJECT-TYPE
			SYNTAX Counter32
			MAX-ACCESS read-only
			STATUS current
			DESCRIPTION
				" Specifies the gfast Port's Previous 15Minutes LOL."
			::= { gfastPortPrev15MinEventEntry 8 }

		
		-- 1.3.6.1.4.1.6296.9.102.1.2.10.1.9
		gfastPortPrev15MinEventUsBs OBJECT-TYPE
			SYNTAX Counter32
			MAX-ACCESS read-only
			STATUS current
			DESCRIPTION
				" Specifies the gfast Port's Previous 15Minutes Up Stream Bit-Swap."
			::= { gfastPortPrev15MinEventEntry 9 }

		
		-- 1.3.6.1.4.1.6296.9.102.1.2.10.1.10
		gfastPortPrev15MinEventDsBs OBJECT-TYPE
			SYNTAX Counter32
			MAX-ACCESS read-only
			STATUS current
			DESCRIPTION
				" Specifies the gfast Port's Previous 15Minutes Down Stream Bit-Swap."
			::= { gfastPortPrev15MinEventEntry 10 }

		
		-- 1.3.6.1.4.1.6296.9.102.1.2.10.1.11
		gfastPortPrev15MinEventUsRau OBJECT-TYPE
			SYNTAX Counter32
			MAX-ACCESS read-only
			STATUS current
			DESCRIPTION
				" Specifies the gfast Port's Previous 15Minutes Up Stream Rate Adaptation Upwards."
			::= { gfastPortPrev15MinEventEntry 11 }

		
		-- 1.3.6.1.4.1.6296.9.102.1.2.10.1.12
		gfastPortPrev15MinEventDsRau OBJECT-TYPE
			SYNTAX Counter32
			MAX-ACCESS read-only
			STATUS current
			DESCRIPTION
				" Specifies the gfast Port's Previous 15Minutes Down Stream Rate Adaptation Upwards."
			::= { gfastPortPrev15MinEventEntry 12 }

		
		-- 1.3.6.1.4.1.6296.9.102.1.2.10.1.13
		gfastPortPrev15MinEventUsRad OBJECT-TYPE
			SYNTAX Counter32
			MAX-ACCESS read-only
			STATUS current
			DESCRIPTION
				" Specifies the gfast Port's Previous 15Minutes Up Stream Rate Adaptation Downwards."
			::= { gfastPortPrev15MinEventEntry 13 }

		
		-- 1.3.6.1.4.1.6296.9.102.1.2.10.1.14
		gfastPortPrev15MinEventDsRad OBJECT-TYPE
			SYNTAX Counter32
			MAX-ACCESS read-only
			STATUS current
			DESCRIPTION
				" Specifies the gfast Port's Previous 15Minutes Down Stream Rate Adaptation Downwards."
			::= { gfastPortPrev15MinEventEntry 14 }

		
		-- 1.3.6.1.4.1.6296.9.102.1.2.10.1.15
		gfastPortPrev15MinEventUsFra OBJECT-TYPE
			SYNTAX Counter32
			MAX-ACCESS read-only
			STATUS current
			DESCRIPTION
				" Specifies the gfast Port's Previous 15Minutes Up Stream FRA."
			::= { gfastPortPrev15MinEventEntry 15 }

		
		-- 1.3.6.1.4.1.6296.9.102.1.2.10.1.16
		gfastPortPrev15MinEventDsFra OBJECT-TYPE
			SYNTAX Counter32
			MAX-ACCESS read-only
			STATUS current
			DESCRIPTION
				" Specifies the gfast Port's Previous 15Minutes Down Stream FRA."
			::= { gfastPortPrev15MinEventEntry 16 }

		
		-- 1.3.6.1.4.1.6296.9.102.1.2.10.1.17
		gfastPortPrev15MinEventUsRpa OBJECT-TYPE
			SYNTAX Counter32
			MAX-ACCESS read-only
			STATUS current
			DESCRIPTION
				" Specifies the gfast Port's Previous 15Minutes Up Stream RMC Parameter Adjustment."
			::= { gfastPortPrev15MinEventEntry 17 }

		
		-- 1.3.6.1.4.1.6296.9.102.1.2.10.1.18
		gfastPortPrev15MinEventDsRpa OBJECT-TYPE
			SYNTAX Counter32
			MAX-ACCESS read-only
			STATUS current
			DESCRIPTION
				" Specifies the gfast Port's Previous 15Minutes Down Stream RMC Parameter Adjustment."
			::= { gfastPortPrev15MinEventEntry 18 }

		
		-- 1.3.6.1.4.1.6296.9.102.1.2.10.1.19
		gfastPortPrev15MinEventTiga OBJECT-TYPE
			SYNTAX Counter32
			MAX-ACCESS read-only
			STATUS current
			DESCRIPTION
				" Specifies the gfast Port's Previous 15Minutes Transmitter Initiated Gain Adjustment."
			::= { gfastPortPrev15MinEventEntry 19 }

		
-- gfastPortPrev15MinEventHostReinit OBJECT-TYPE
-- SYNTAX      Counter32
-- MAX-ACCESS  read-only
-- STATUS      current
-- DESCRIPTION
-- " Specifies the gfast Port's Previous 15Minutes Host ReInit event."
-- ::= { gfastPortPrev15MinEventEntry 20 }
-- gfastPortPrev15MinEventSpontaneousReinit OBJECT-TYPE
-- SYNTAX      Counter32
-- MAX-ACCESS  read-only
-- STATUS      current
-- DESCRIPTION
-- " Specifies the gfast Port's Previous 15Minutes Spontaneous ReInit event."
-- ::= { gfastPortPrev15MinEventEntry 21 }
-- *********************************************************************
-- * gfastPortCurr1DayEventTable : Port Event Group
-- *********************************************************************
		-- 1.3.6.1.4.1.6296.9.102.1.2.11
		gfastPortCurr1DayEventTable OBJECT-TYPE
			SYNTAX SEQUENCE OF GfastPortCurr1DayEventEntry
			MAX-ACCESS not-accessible
			STATUS current
			DESCRIPTION
				"The G.fast port Current 1Day event counter table"
			::= { gfastPortGroup 11 }

		
		-- 1.3.6.1.4.1.6296.9.102.1.2.11.1
		gfastPortCurr1DayEventEntry OBJECT-TYPE
			SYNTAX GfastPortCurr1DayEventEntry
			MAX-ACCESS not-accessible
			STATUS current
			DESCRIPTION
				"An entry in gfastPortCurr1DayEventTable."
			INDEX { gfastPortIndex }
			::= { gfastPortCurr1DayEventTable 1 }

		
		GfastPortCurr1DayEventEntry ::=
			SEQUENCE { 
				gfastPortCurr1DayEventUsLos
					Counter32,
				gfastPortCurr1DayEventDsLos
					Counter32,
				gfastPortCurr1DayEventUsLom
					Counter32,
				gfastPortCurr1DayEventDsLom
					Counter32,
				gfastPortCurr1DayEventUsLor
					Counter32,
				gfastPortCurr1DayEventDsLor
					Counter32,
				gfastPortCurr1DayEventLpr
					Counter32,
				gfastPortCurr1DayEventLol
					Counter32,
				gfastPortCurr1DayEventUsBs
					Counter32,
				gfastPortCurr1DayEventDsBs
					Counter32,
				gfastPortCurr1DayEventUsRau
					Counter32,
				gfastPortCurr1DayEventDsRau
					Counter32,
				gfastPortCurr1DayEventUsRad
					Counter32,
				gfastPortCurr1DayEventDsRad
					Counter32,
				gfastPortCurr1DayEventUsFra
					Counter32,
				gfastPortCurr1DayEventDsFra
					Counter32,
				gfastPortCurr1DayEventUsRpa
					Counter32,
				gfastPortCurr1DayEventDsRpa
					Counter32,
				gfastPortCurr1DayEventTiga
					Counter32
			 }

-- 		gfastPortCurr1DayEventHostReinit		Counter32,
-- gfastPortCurr1DayEventSpontaneousReinit		Counter32,
		-- 1.3.6.1.4.1.6296.9.102.1.2.11.1.1
		gfastPortCurr1DayEventUsLos OBJECT-TYPE
			SYNTAX Counter32
			MAX-ACCESS read-only
			STATUS current
			DESCRIPTION
				" Specifies the gfast Port's Current 1Day Up Stream Loss Of Signal."
			::= { gfastPortCurr1DayEventEntry 1 }

		
		-- 1.3.6.1.4.1.6296.9.102.1.2.11.1.2
		gfastPortCurr1DayEventDsLos OBJECT-TYPE
			SYNTAX Counter32
			MAX-ACCESS read-only
			STATUS current
			DESCRIPTION
				" Specifies the gfast Port's Current 1Day Down Stream Loss Of Signal."
			::= { gfastPortCurr1DayEventEntry 2 }

		
		-- 1.3.6.1.4.1.6296.9.102.1.2.11.1.3
		gfastPortCurr1DayEventUsLom OBJECT-TYPE
			SYNTAX Counter32
			MAX-ACCESS read-only
			STATUS current
			DESCRIPTION
				" Specifies the gfast Port's Current 1Day Up Stream Loss Of Margin."
			::= { gfastPortCurr1DayEventEntry 3 }

		
		-- 1.3.6.1.4.1.6296.9.102.1.2.11.1.4
		gfastPortCurr1DayEventDsLom OBJECT-TYPE
			SYNTAX Counter32
			MAX-ACCESS read-only
			STATUS current
			DESCRIPTION
				" Specifies the gfast Port's Current 1Day Down Stream Loss Of Margin."
			::= { gfastPortCurr1DayEventEntry 4 }

		
		-- 1.3.6.1.4.1.6296.9.102.1.2.11.1.5
		gfastPortCurr1DayEventUsLor OBJECT-TYPE
			SYNTAX Counter32
			MAX-ACCESS read-only
			STATUS current
			DESCRIPTION
				" Specifies the gfast Port's Current 1Day Up Stream Loss of RMC."
			::= { gfastPortCurr1DayEventEntry 5 }

		
		-- 1.3.6.1.4.1.6296.9.102.1.2.11.1.6
		gfastPortCurr1DayEventDsLor OBJECT-TYPE
			SYNTAX Counter32
			MAX-ACCESS read-only
			STATUS current
			DESCRIPTION
				" Specifies the gfast Port's Current 1Day Down Stream Loss of RMC."
			::= { gfastPortCurr1DayEventEntry 6 }

		
		-- 1.3.6.1.4.1.6296.9.102.1.2.11.1.7
		gfastPortCurr1DayEventLpr OBJECT-TYPE
			SYNTAX Counter32
			MAX-ACCESS read-only
			STATUS current
			DESCRIPTION
				" Specifies the gfast Port's Current 1Day Loss of Power."
			::= { gfastPortCurr1DayEventEntry 7 }

		
		-- 1.3.6.1.4.1.6296.9.102.1.2.11.1.8
		gfastPortCurr1DayEventLol OBJECT-TYPE
			SYNTAX Counter32
			MAX-ACCESS read-only
			STATUS current
			DESCRIPTION
				" Specifies the gfast Port's Current 1Day LOL."
			::= { gfastPortCurr1DayEventEntry 8 }

		
		-- 1.3.6.1.4.1.6296.9.102.1.2.11.1.9
		gfastPortCurr1DayEventUsBs OBJECT-TYPE
			SYNTAX Counter32
			MAX-ACCESS read-only
			STATUS current
			DESCRIPTION
				" Specifies the gfast Port's Current 1Day Up Stream Bit-Swap."
			::= { gfastPortCurr1DayEventEntry 9 }

		
		-- 1.3.6.1.4.1.6296.9.102.1.2.11.1.10
		gfastPortCurr1DayEventDsBs OBJECT-TYPE
			SYNTAX Counter32
			MAX-ACCESS read-only
			STATUS current
			DESCRIPTION
				" Specifies the gfast Port's Current 1Day Down Stream Bit-Swap."
			::= { gfastPortCurr1DayEventEntry 10 }

		
		-- 1.3.6.1.4.1.6296.9.102.1.2.11.1.11
		gfastPortCurr1DayEventUsRau OBJECT-TYPE
			SYNTAX Counter32
			MAX-ACCESS read-only
			STATUS current
			DESCRIPTION
				" Specifies the gfast Port's Current 1Day Up Stream Rate Adaptation Upwards."
			::= { gfastPortCurr1DayEventEntry 11 }

		
		-- 1.3.6.1.4.1.6296.9.102.1.2.11.1.12
		gfastPortCurr1DayEventDsRau OBJECT-TYPE
			SYNTAX Counter32
			MAX-ACCESS read-only
			STATUS current
			DESCRIPTION
				" Specifies the gfast Port's Current 1Day Down Stream Rate Adaptation Upwards."
			::= { gfastPortCurr1DayEventEntry 12 }

		
		-- 1.3.6.1.4.1.6296.9.102.1.2.11.1.13
		gfastPortCurr1DayEventUsRad OBJECT-TYPE
			SYNTAX Counter32
			MAX-ACCESS read-only
			STATUS current
			DESCRIPTION
				" Specifies the gfast Port's Current 1Day Up Stream Rate Adaptation Downwards."
			::= { gfastPortCurr1DayEventEntry 13 }

		
		-- 1.3.6.1.4.1.6296.9.102.1.2.11.1.14
		gfastPortCurr1DayEventDsRad OBJECT-TYPE
			SYNTAX Counter32
			MAX-ACCESS read-only
			STATUS current
			DESCRIPTION
				" Specifies the gfast Port's Current 1Day Down Stream Rate Adaptation Downwards."
			::= { gfastPortCurr1DayEventEntry 14 }

		
		-- 1.3.6.1.4.1.6296.9.102.1.2.11.1.15
		gfastPortCurr1DayEventUsFra OBJECT-TYPE
			SYNTAX Counter32
			MAX-ACCESS read-only
			STATUS current
			DESCRIPTION
				" Specifies the gfast Port's Current 1Day Up Stream FRA."
			::= { gfastPortCurr1DayEventEntry 15 }

		
		-- 1.3.6.1.4.1.6296.9.102.1.2.11.1.16
		gfastPortCurr1DayEventDsFra OBJECT-TYPE
			SYNTAX Counter32
			MAX-ACCESS read-only
			STATUS current
			DESCRIPTION
				" Specifies the gfast Port's Current 1Day Down Stream FRA."
			::= { gfastPortCurr1DayEventEntry 16 }

		
		-- 1.3.6.1.4.1.6296.9.102.1.2.11.1.17
		gfastPortCurr1DayEventUsRpa OBJECT-TYPE
			SYNTAX Counter32
			MAX-ACCESS read-only
			STATUS current
			DESCRIPTION
				" Specifies the gfast Port's Current 1Day Up Stream RMC Parameter Adjustment."
			::= { gfastPortCurr1DayEventEntry 17 }

		
		-- 1.3.6.1.4.1.6296.9.102.1.2.11.1.18
		gfastPortCurr1DayEventDsRpa OBJECT-TYPE
			SYNTAX Counter32
			MAX-ACCESS read-only
			STATUS current
			DESCRIPTION
				" Specifies the gfast Port's Current 1Day Down Stream RMC Parameter Adjustment."
			::= { gfastPortCurr1DayEventEntry 18 }

		
		-- 1.3.6.1.4.1.6296.9.102.1.2.11.1.19
		gfastPortCurr1DayEventTiga OBJECT-TYPE
			SYNTAX Counter32
			MAX-ACCESS read-only
			STATUS current
			DESCRIPTION
				" Specifies the gfast Port's Current 1Day Transmitter Initiated Gain Adjustment."
			::= { gfastPortCurr1DayEventEntry 19 }

		
-- gfastPortCurr1DayEventHostReinit OBJECT-TYPE
-- SYNTAX      Counter32
-- MAX-ACCESS  read-only
-- STATUS      current
-- DESCRIPTION
-- " Specifies the gfast Port's Current 1Day Host ReInit event."
-- ::= { gfastPortCurr1DayEventEntry 20 }
-- gfastPortCurr1DayEventSpontaneousReinit OBJECT-TYPE
-- SYNTAX      Counter32
-- MAX-ACCESS  read-only
-- STATUS      current
-- DESCRIPTION
-- " Specifies the gfast Port's Current 1Day Spontaneous ReInit event."
-- ::= { gfastPortCurr1DayEventEntry 21 }
-- *********************************************************************
-- * gfastPortPrev1DayEventTable : Port Event Group
-- *********************************************************************
		-- 1.3.6.1.4.1.6296.9.102.1.2.12
		gfastPortPrev1DayEventTable OBJECT-TYPE
			SYNTAX SEQUENCE OF GfastPortPrev1DayEventEntry
			MAX-ACCESS not-accessible
			STATUS current
			DESCRIPTION
				"The G.fast port Previous 1Day event counter table"
			::= { gfastPortGroup 12 }

		
		-- 1.3.6.1.4.1.6296.9.102.1.2.12.1
		gfastPortPrev1DayEventEntry OBJECT-TYPE
			SYNTAX GfastPortPrev1DayEventEntry
			MAX-ACCESS not-accessible
			STATUS current
			DESCRIPTION
				"An entry in gfastPortPrev1DayEventTable."
			INDEX { gfastPortIndex }
			::= { gfastPortPrev1DayEventTable 1 }

		
		GfastPortPrev1DayEventEntry ::=
			SEQUENCE { 
				gfastPortPrev1DayEventUsLos
					Counter32,
				gfastPortPrev1DayEventDsLos
					Counter32,
				gfastPortPrev1DayEventUsLom
					Counter32,
				gfastPortPrev1DayEventDsLom
					Counter32,
				gfastPortPrev1DayEventUsLor
					Counter32,
				gfastPortPrev1DayEventDsLor
					Counter32,
				gfastPortPrev1DayEventLpr
					Counter32,
				gfastPortPrev1DayEventLol
					Counter32,
				gfastPortPrev1DayEventUsBs
					Counter32,
				gfastPortPrev1DayEventDsBs
					Counter32,
				gfastPortPrev1DayEventUsRau
					Counter32,
				gfastPortPrev1DayEventDsRau
					Counter32,
				gfastPortPrev1DayEventUsRad
					Counter32,
				gfastPortPrev1DayEventDsRad
					Counter32,
				gfastPortPrev1DayEventUsFra
					Counter32,
				gfastPortPrev1DayEventDsFra
					Counter32,
				gfastPortPrev1DayEventUsRpa
					Counter32,
				gfastPortPrev1DayEventDsRpa
					Counter32,
				gfastPortPrev1DayEventTiga
					Counter32
			 }

-- 		gfastPortPrev1DayEventHostReinit		Counter32,
-- gfastPortPrev1DayEventSpontaneousReinit		Counter32,
		-- 1.3.6.1.4.1.6296.9.102.1.2.12.1.1
		gfastPortPrev1DayEventUsLos OBJECT-TYPE
			SYNTAX Counter32
			MAX-ACCESS read-only
			STATUS current
			DESCRIPTION
				" Specifies the gfast Port's Previous 1Day Up Stream Loss Of Signal."
			::= { gfastPortPrev1DayEventEntry 1 }

		
		-- 1.3.6.1.4.1.6296.9.102.1.2.12.1.2
		gfastPortPrev1DayEventDsLos OBJECT-TYPE
			SYNTAX Counter32
			MAX-ACCESS read-only
			STATUS current
			DESCRIPTION
				" Specifies the gfast Port's Previous 1Day Down Stream Loss Of Signal."
			::= { gfastPortPrev1DayEventEntry 2 }

		
		-- 1.3.6.1.4.1.6296.9.102.1.2.12.1.3
		gfastPortPrev1DayEventUsLom OBJECT-TYPE
			SYNTAX Counter32
			MAX-ACCESS read-only
			STATUS current
			DESCRIPTION
				" Specifies the gfast Port's Previous 1Day Up Stream Loss Of Margin."
			::= { gfastPortPrev1DayEventEntry 3 }

		
		-- 1.3.6.1.4.1.6296.9.102.1.2.12.1.4
		gfastPortPrev1DayEventDsLom OBJECT-TYPE
			SYNTAX Counter32
			MAX-ACCESS read-only
			STATUS current
			DESCRIPTION
				" Specifies the gfast Port's Previous 1Day Down Stream Loss Of Margin."
			::= { gfastPortPrev1DayEventEntry 4 }

		
		-- 1.3.6.1.4.1.6296.9.102.1.2.12.1.5
		gfastPortPrev1DayEventUsLor OBJECT-TYPE
			SYNTAX Counter32
			MAX-ACCESS read-only
			STATUS current
			DESCRIPTION
				" Specifies the gfast Port's Previous 1Day Up Stream Loss of RMC."
			::= { gfastPortPrev1DayEventEntry 5 }

		
		-- 1.3.6.1.4.1.6296.9.102.1.2.12.1.6
		gfastPortPrev1DayEventDsLor OBJECT-TYPE
			SYNTAX Counter32
			MAX-ACCESS read-only
			STATUS current
			DESCRIPTION
				" Specifies the gfast Port's Previous 1Day Down Stream Loss of RMC."
			::= { gfastPortPrev1DayEventEntry 6 }

		
		-- 1.3.6.1.4.1.6296.9.102.1.2.12.1.7
		gfastPortPrev1DayEventLpr OBJECT-TYPE
			SYNTAX Counter32
			MAX-ACCESS read-only
			STATUS current
			DESCRIPTION
				" Specifies the gfast Port's Previous 1Day Loss of Power."
			::= { gfastPortPrev1DayEventEntry 7 }

		
		-- 1.3.6.1.4.1.6296.9.102.1.2.12.1.8
		gfastPortPrev1DayEventLol OBJECT-TYPE
			SYNTAX Counter32
			MAX-ACCESS read-only
			STATUS current
			DESCRIPTION
				" Specifies the gfast Port's Previous 1Day LOL."
			::= { gfastPortPrev1DayEventEntry 8 }

		
		-- 1.3.6.1.4.1.6296.9.102.1.2.12.1.9
		gfastPortPrev1DayEventUsBs OBJECT-TYPE
			SYNTAX Counter32
			MAX-ACCESS read-only
			STATUS current
			DESCRIPTION
				" Specifies the gfast Port's Previous 1Day Up Stream Bit-Swap."
			::= { gfastPortPrev1DayEventEntry 9 }

		
		-- 1.3.6.1.4.1.6296.9.102.1.2.12.1.10
		gfastPortPrev1DayEventDsBs OBJECT-TYPE
			SYNTAX Counter32
			MAX-ACCESS read-only
			STATUS current
			DESCRIPTION
				" Specifies the gfast Port's Previous 1Day Down Stream Bit-Swap."
			::= { gfastPortPrev1DayEventEntry 10 }

		
		-- 1.3.6.1.4.1.6296.9.102.1.2.12.1.11
		gfastPortPrev1DayEventUsRau OBJECT-TYPE
			SYNTAX Counter32
			MAX-ACCESS read-only
			STATUS current
			DESCRIPTION
				" Specifies the gfast Port's Previous 1Day Up Stream Rate Adaptation Upwards."
			::= { gfastPortPrev1DayEventEntry 11 }

		
		-- 1.3.6.1.4.1.6296.9.102.1.2.12.1.12
		gfastPortPrev1DayEventDsRau OBJECT-TYPE
			SYNTAX Counter32
			MAX-ACCESS read-only
			STATUS current
			DESCRIPTION
				" Specifies the gfast Port's Previous 1Day Down Stream Rate Adaptation Upwards."
			::= { gfastPortPrev1DayEventEntry 12 }

		
		-- 1.3.6.1.4.1.6296.9.102.1.2.12.1.13
		gfastPortPrev1DayEventUsRad OBJECT-TYPE
			SYNTAX Counter32
			MAX-ACCESS read-only
			STATUS current
			DESCRIPTION
				" Specifies the gfast Port's Previous 1Day Up Stream Rate Adaptation Downwards."
			::= { gfastPortPrev1DayEventEntry 13 }

		
		-- 1.3.6.1.4.1.6296.9.102.1.2.12.1.14
		gfastPortPrev1DayEventDsRad OBJECT-TYPE
			SYNTAX Counter32
			MAX-ACCESS read-only
			STATUS current
			DESCRIPTION
				" Specifies the gfast Port's Previous 1Day Down Stream Rate Adaptation Downwards."
			::= { gfastPortPrev1DayEventEntry 14 }

		
		-- 1.3.6.1.4.1.6296.9.102.1.2.12.1.15
		gfastPortPrev1DayEventUsFra OBJECT-TYPE
			SYNTAX Counter32
			MAX-ACCESS read-only
			STATUS current
			DESCRIPTION
				" Specifies the gfast Port's Previous 1Day Up Stream FRA."
			::= { gfastPortPrev1DayEventEntry 15 }

		
		-- 1.3.6.1.4.1.6296.9.102.1.2.12.1.16
		gfastPortPrev1DayEventDsFra OBJECT-TYPE
			SYNTAX Counter32
			MAX-ACCESS read-only
			STATUS current
			DESCRIPTION
				" Specifies the gfast Port's Previous 1Day Down Stream FRA."
			::= { gfastPortPrev1DayEventEntry 16 }

		
		-- 1.3.6.1.4.1.6296.9.102.1.2.12.1.17
		gfastPortPrev1DayEventUsRpa OBJECT-TYPE
			SYNTAX Counter32
			MAX-ACCESS read-only
			STATUS current
			DESCRIPTION
				" Specifies the gfast Port's Previous 1Day Up Stream RMC Parameter Adjustment."
			::= { gfastPortPrev1DayEventEntry 17 }

		
		-- 1.3.6.1.4.1.6296.9.102.1.2.12.1.18
		gfastPortPrev1DayEventDsRpa OBJECT-TYPE
			SYNTAX Counter32
			MAX-ACCESS read-only
			STATUS current
			DESCRIPTION
				" Specifies the gfast Port's Previous 1Day Down Stream RMC Parameter Adjustment."
			::= { gfastPortPrev1DayEventEntry 18 }

		
		-- 1.3.6.1.4.1.6296.9.102.1.2.12.1.19
		gfastPortPrev1DayEventTiga OBJECT-TYPE
			SYNTAX Counter32
			MAX-ACCESS read-only
			STATUS current
			DESCRIPTION
				" Specifies the gfast Port's Previous 1Day Transmitter Initiated Gain Adjustment."
			::= { gfastPortPrev1DayEventEntry 19 }

		
-- gfastPortPrev1DayEventHostReinit OBJECT-TYPE
-- SYNTAX      Counter32
-- MAX-ACCESS  read-only
-- STATUS      current
-- DESCRIPTION
-- " Specifies the gfast Port's Previous 1Day Host ReInit event."
-- ::= { gfastPortPrev1DayEventEntry 20 }
-- gfastPortPrev1DayEventSpontaneousReinit OBJECT-TYPE
-- SYNTAX      Counter32
-- MAX-ACCESS  read-only
-- STATUS      current
-- DESCRIPTION
-- " Specifies the gfast Port's Previous 1Day Spontaneous ReInit event."
-- ::= { gfastPortPrev1DayEventEntry 21 }
-- *********************************************************************
-- * gfastPortCounterClearTable
-- *********************************************************************
		-- 1.3.6.1.4.1.6296.9.102.1.2.13
		gfastPortCounterClearTable OBJECT-TYPE
			SYNTAX SEQUENCE OF GfastPortCounterClearEntry
			MAX-ACCESS not-accessible
			STATUS current
			DESCRIPTION
				"This table includes G.fast Port's Counter Clear Table."
			::= { gfastPortGroup 13 }

		
		-- 1.3.6.1.4.1.6296.9.102.1.2.13.1
		gfastPortCounterClearEntry OBJECT-TYPE
			SYNTAX GfastPortCounterClearEntry
			MAX-ACCESS not-accessible
			STATUS current
			DESCRIPTION
				"An entry in the G.fast Port's Counter Clear Table."
			INDEX { gfastPortIndex }
			::= { gfastPortCounterClearTable 1 }

		
		GfastPortCounterClearEntry ::=
			SEQUENCE { 
				gfastPortCounterClearCommand
					INTEGER
			 }

		-- 1.3.6.1.4.1.6296.9.102.1.2.13.1.1
		gfastPortCounterClearCommand OBJECT-TYPE
			SYNTAX INTEGER
				{
				noAction(0),
				clear-Counter(1)
				}
			MAX-ACCESS read-write
			STATUS current
			DESCRIPTION
				"Clear G.FAST Port's Counter."
			::= { gfastPortCounterClearEntry 1 }

		
		-- 1.3.6.1.4.1.6296.9.102.1.3
		gfastPortSubcarrierGroup OBJECT IDENTIFIER ::= { gfastGroup 3 }

		
-- gfastAutoRateLimitPercentageGroup		OBJECT IDENTIFIER ::= { gfastGroup 7 }
		-- 1.3.6.1.4.1.6296.9.102.1.3.1
		gfastBitAllocPerScGroup OBJECT IDENTIFIER ::= { gfastPortSubcarrierGroup 1 }

		
--  *********************************************************************
-- * gfastDisplayLineScInfoGroup
-- *********************************************************************
-- *********************************************************************
-- * gfastBitAllocationPerScGroup
-- *********************************************************************
-- gfastBitAllocPerScGroup	OBJECT IDENTIFIER ::= { gfastPortSubcarrierGroup 1}
		-- 1.3.6.1.4.1.6296.9.102.1.3.1.1
		gfastBitAllocPortNumber OBJECT-TYPE
			SYNTAX INTEGER (1..16)
			MAX-ACCESS read-write
			STATUS current
			DESCRIPTION
				"Specifies the gFastMIB System Port index."
			::= { gfastBitAllocPerScGroup 1 }

		
		-- 1.3.6.1.4.1.6296.9.102.1.3.1.2
		gfastBitAllocGetCommand OBJECT-TYPE
			SYNTAX INTEGER
				{
				noAction(0),
				getUs(1),
				getDs(2)
				}
			MAX-ACCESS read-write
			STATUS current
			DESCRIPTION
				"Specifies the Bit Alloc per sub carrier request command"
			::= { gfastBitAllocPerScGroup 2 }

		
		-- 1.3.6.1.4.1.6296.9.102.1.3.1.3
		gfastBitAllocTable OBJECT-TYPE
			SYNTAX SEQUENCE OF GfastBitAllocEntry
			MAX-ACCESS not-accessible
			STATUS current
			DESCRIPTION
				"This table includes G.fast Bit Allocation Per Sub-carrier Table."
			::= { gfastBitAllocPerScGroup 3 }

		
		-- 1.3.6.1.4.1.6296.9.102.1.3.1.3.1
		gfastBitAllocEntry OBJECT-TYPE
			SYNTAX GfastBitAllocEntry
			MAX-ACCESS not-accessible
			STATUS current
			DESCRIPTION
				"An entry in the gfast BitAllocation Table."
			INDEX { gfastBitAllocToneIndex }
			::= { gfastBitAllocTable 1 }

		
		GfastBitAllocEntry ::=
			SEQUENCE { 
				gfastBitAllocToneIndex
					Integer32,
				gfastBitAlloc
					DisplayString
			 }

		-- 1.3.6.1.4.1.6296.9.102.1.3.1.3.1.1
		gfastBitAllocToneIndex OBJECT-TYPE
			SYNTAX Integer32
			MAX-ACCESS read-only
			STATUS current
			DESCRIPTION
				"Specifies the G.Fast bit allocation Tone Index."
			::= { gfastBitAllocEntry 1 }

		
		-- 1.3.6.1.4.1.6296.9.102.1.3.1.3.1.2
		gfastBitAlloc OBJECT-TYPE
			SYNTAX DisplayString
			MAX-ACCESS read-only
			STATUS current
			DESCRIPTION
				"Specifies the G.Fast US/DS bit allocation value."
			::= { gfastBitAllocEntry 2 }

		
		-- 1.3.6.1.4.1.6296.9.102.1.3.2
		gfastSnrPerScGroup OBJECT IDENTIFIER ::= { gfastPortSubcarrierGroup 2 }

		
--  *********************************************************************
-- * gfastSNRPerScGroup
-- *********************************************************************
-- gfastSnrPerScGroup		OBJECT IDENTIFIER ::= { gfastPortSubcarrierGroup 2}
		-- 1.3.6.1.4.1.6296.9.102.1.3.2.1
		gfastSnrPortNumber OBJECT-TYPE
			SYNTAX INTEGER (1..16)
			MAX-ACCESS read-write
			STATUS current
			DESCRIPTION
				"Specifies the gFastMIB System Port index."
			::= { gfastSnrPerScGroup 1 }

		
		-- 1.3.6.1.4.1.6296.9.102.1.3.2.2
		gfastSnrGetCommand OBJECT-TYPE
			SYNTAX INTEGER
				{
				noAction(0),
				getUs(1),
				getDs(2)
				}
			MAX-ACCESS read-write
			STATUS current
			DESCRIPTION
				"Specifies the SNR per sub carrier request command"
			::= { gfastSnrPerScGroup 2 }

		
		-- 1.3.6.1.4.1.6296.9.102.1.3.2.3
		gfastSnrTable OBJECT-TYPE
			SYNTAX SEQUENCE OF GfastSnrEntry
			MAX-ACCESS not-accessible
			STATUS current
			DESCRIPTION
				"This table includes G.fast Snr Per Sub-carrier Table."
			::= { gfastSnrPerScGroup 3 }

		
		-- 1.3.6.1.4.1.6296.9.102.1.3.2.3.1
		gfastSnrEntry OBJECT-TYPE
			SYNTAX GfastSnrEntry
			MAX-ACCESS not-accessible
			STATUS current
			DESCRIPTION
				"An entry in the gfast SNR Table."
			INDEX { gfastSnrToneIndex }
			::= { gfastSnrTable 1 }

		
		GfastSnrEntry ::=
			SEQUENCE { 
				gfastSnrToneIndex
					Integer32,
				gfastSnr
					DisplayString
			 }

		-- 1.3.6.1.4.1.6296.9.102.1.3.2.3.1.1
		gfastSnrToneIndex OBJECT-TYPE
			SYNTAX Integer32
			MAX-ACCESS read-only
			STATUS current
			DESCRIPTION
				"Specifies the G.Fast SNR Tone Index."
			::= { gfastSnrEntry 1 }

		
		-- 1.3.6.1.4.1.6296.9.102.1.3.2.3.1.2
		gfastSnr OBJECT-TYPE
			SYNTAX DisplayString
			MAX-ACCESS read-only
			STATUS current
			DESCRIPTION
				"Specifies the G.Fast US/DS SNR value."
			::= { gfastSnrEntry 2 }

		
		-- 1.3.6.1.4.1.6296.9.102.1.3.3
		gfastHlogPerSgGroup OBJECT IDENTIFIER ::= { gfastPortSubcarrierGroup 3 }

		
--  *********************************************************************
-- * gfastHLOGPerSgGroup
-- *********************************************************************
-- gfastHlogPerSgGroup		OBJECT IDENTIFIER ::= { gfastPortSubcarrierGroup 3}
		-- 1.3.6.1.4.1.6296.9.102.1.3.3.1
		gfastHlogPortNumber OBJECT-TYPE
			SYNTAX INTEGER (1..16)
			MAX-ACCESS read-write
			STATUS current
			DESCRIPTION
				"Specifies the gFastMIB System Port index."
			::= { gfastHlogPerSgGroup 1 }

		
		-- 1.3.6.1.4.1.6296.9.102.1.3.3.2
		gfastHlogGetCommand OBJECT-TYPE
			SYNTAX INTEGER
				{
				noAction(0),
				getUs(1),
				getDs(2)
				}
			MAX-ACCESS read-write
			STATUS current
			DESCRIPTION
				"Specifies the HLOG per sub carrier request command"
			::= { gfastHlogPerSgGroup 2 }

		
		-- 1.3.6.1.4.1.6296.9.102.1.3.3.3
		gfastHlogTable OBJECT-TYPE
			SYNTAX SEQUENCE OF GfastHlogEntry
			MAX-ACCESS not-accessible
			STATUS current
			DESCRIPTION
				"This table includes G.fast HLOG Per Sub-carrier group Table."
			::= { gfastHlogPerSgGroup 3 }

		
		-- 1.3.6.1.4.1.6296.9.102.1.3.3.3.1
		gfastHlogEntry OBJECT-TYPE
			SYNTAX GfastHlogEntry
			MAX-ACCESS not-accessible
			STATUS current
			DESCRIPTION
				"An entry in the gfast HLOG Table."
			INDEX { gfastHlogToneIndex }
			::= { gfastHlogTable 1 }

		
		GfastHlogEntry ::=
			SEQUENCE { 
				gfastHlogToneIndex
					Integer32,
				gfastHlog
					DisplayString
			 }

		-- 1.3.6.1.4.1.6296.9.102.1.3.3.3.1.1
		gfastHlogToneIndex OBJECT-TYPE
			SYNTAX Integer32
			MAX-ACCESS read-only
			STATUS current
			DESCRIPTION
				"Specifies the G.Fast HLOG Tone Index."
			::= { gfastHlogEntry 1 }

		
		-- 1.3.6.1.4.1.6296.9.102.1.3.3.3.1.2
		gfastHlog OBJECT-TYPE
			SYNTAX DisplayString
			MAX-ACCESS read-only
			STATUS current
			DESCRIPTION
				"Specifies the G.Fast US/DS HLOG value."
			::= { gfastHlogEntry 2 }

		
		-- 1.3.6.1.4.1.6296.9.102.1.3.4
		gfastQlnPerSgGroup OBJECT IDENTIFIER ::= { gfastPortSubcarrierGroup 4 }

		
--  *********************************************************************
-- * gfastQLNPerScGroup
-- *********************************************************************
-- gfastQlnPerSgGroup		OBJECT IDENTIFIER ::= { gfastPortSubcarrierGroup 4}
		-- 1.3.6.1.4.1.6296.9.102.1.3.4.1
		gfastQlnPortNumber OBJECT-TYPE
			SYNTAX INTEGER (1..16)
			MAX-ACCESS read-write
			STATUS current
			DESCRIPTION
				"Specifies the gFastMIB System Port index."
			::= { gfastQlnPerSgGroup 1 }

		
		-- 1.3.6.1.4.1.6296.9.102.1.3.4.2
		gfastQlnGetCommand OBJECT-TYPE
			SYNTAX INTEGER
				{
				noAction(0),
				getUs(1),
				getDs(2)
				}
			MAX-ACCESS read-write
			STATUS current
			DESCRIPTION
				"Specifies the Qln per sub carrier request command"
			::= { gfastQlnPerSgGroup 2 }

		
		-- 1.3.6.1.4.1.6296.9.102.1.3.4.3
		gfastQlnTable OBJECT-TYPE
			SYNTAX SEQUENCE OF GfastQlnEntry
			MAX-ACCESS not-accessible
			STATUS current
			DESCRIPTION
				"This table includes G.fast QLN Per Sub-carrier group Table."
			::= { gfastQlnPerSgGroup 3 }

		
		-- 1.3.6.1.4.1.6296.9.102.1.3.4.3.1
		gfastQlnEntry OBJECT-TYPE
			SYNTAX GfastQlnEntry
			MAX-ACCESS not-accessible
			STATUS current
			DESCRIPTION
				"An entry in the gfast Qln Table."
			INDEX { gfastQlnToneIndex }
			::= { gfastQlnTable 1 }

		
		GfastQlnEntry ::=
			SEQUENCE { 
				gfastQlnToneIndex
					Integer32,
				gfastQln
					DisplayString
			 }

		-- 1.3.6.1.4.1.6296.9.102.1.3.4.3.1.1
		gfastQlnToneIndex OBJECT-TYPE
			SYNTAX Integer32
			MAX-ACCESS read-only
			STATUS current
			DESCRIPTION
				"Specifies the G.Fast Qln Tone Index."
			::= { gfastQlnEntry 1 }

		
		-- 1.3.6.1.4.1.6296.9.102.1.3.4.3.1.2
		gfastQln OBJECT-TYPE
			SYNTAX DisplayString
			MAX-ACCESS read-only
			STATUS current
			DESCRIPTION
				"Specifies the G.Fast US/DS Qln value."
			::= { gfastQlnEntry 2 }

		
		-- 1.3.6.1.4.1.6296.9.102.1.3.5
		gfastAlnPerSgGroup OBJECT IDENTIFIER ::= { gfastPortSubcarrierGroup 5 }

		
--  *********************************************************************
-- * gfastALNPerScGroup
-- *********************************************************************
-- gfastAlnPerSgGroup		OBJECT IDENTIFIER ::= { gfastPortSubcarrierGroup 5}
		-- 1.3.6.1.4.1.6296.9.102.1.3.5.1
		gfastAlnPortNumber OBJECT-TYPE
			SYNTAX INTEGER (1..16)
			MAX-ACCESS read-write
			STATUS current
			DESCRIPTION
				"Specifies the gFastMIB System Port index."
			::= { gfastAlnPerSgGroup 1 }

		
		-- 1.3.6.1.4.1.6296.9.102.1.3.5.2
		gfastAlnGetCommand OBJECT-TYPE
			SYNTAX INTEGER
				{
				noAction(0),
				getDs(1)
				}
			MAX-ACCESS read-write
			STATUS current
			DESCRIPTION
				"Specifies the Aln per sub carrier request command"
			::= { gfastAlnPerSgGroup 2 }

		
		-- 1.3.6.1.4.1.6296.9.102.1.3.5.3
		gfastAlnTable OBJECT-TYPE
			SYNTAX SEQUENCE OF GfastAlnEntry
			MAX-ACCESS not-accessible
			STATUS current
			DESCRIPTION
				"This table includes G.fast ALN Per Sub-carrier group Table."
			::= { gfastAlnPerSgGroup 3 }

		
		-- 1.3.6.1.4.1.6296.9.102.1.3.5.3.1
		gfastAlnEntry OBJECT-TYPE
			SYNTAX GfastAlnEntry
			MAX-ACCESS not-accessible
			STATUS current
			DESCRIPTION
				"An entry in the gfast Aln Table."
			INDEX { gfastAlnToneIndex }
			::= { gfastAlnTable 1 }

		
		GfastAlnEntry ::=
			SEQUENCE { 
				gfastAlnToneIndex
					Integer32,
				gfastAln
					DisplayString
			 }

		-- 1.3.6.1.4.1.6296.9.102.1.3.5.3.1.1
		gfastAlnToneIndex OBJECT-TYPE
			SYNTAX Integer32
			MAX-ACCESS read-only
			STATUS current
			DESCRIPTION
				"Specifies the G.Fast Aln Tone Index."
			::= { gfastAlnEntry 1 }

		
		-- 1.3.6.1.4.1.6296.9.102.1.3.5.3.1.2
		gfastAln OBJECT-TYPE
			SYNTAX DisplayString
			MAX-ACCESS read-only
			STATUS current
			DESCRIPTION
				"Specifies the G.Fast DS Aln value."
			::= { gfastAlnEntry 2 }

		
		-- 1.3.6.1.4.1.6296.9.102.1.4
		gfastProfileGroup OBJECT IDENTIFIER ::= { gfastGroup 4 }

		
--  *********************************************************************
-- * gfastProfileGroup
-- *********************************************************************
		-- 1.3.6.1.4.1.6296.9.102.1.4.1
		gfastProfileCreate OBJECT-TYPE
			SYNTAX DisplayString
			MAX-ACCESS read-write
			STATUS current
			DESCRIPTION
				"Create a Gfast profile. Input Profile name."
			::= { gfastProfileGroup 1 }

		
		-- 1.3.6.1.4.1.6296.9.102.1.4.2
		gfastProfileDelete OBJECT-TYPE
			SYNTAX DisplayString
			MAX-ACCESS read-write
			STATUS current
			DESCRIPTION
				"Delete a Gfast profile. Input Profile name."
			::= { gfastProfileGroup 2 }

		
--  *********************************************************************
-- * Profile Table Group
-- *********************************************************************
		-- 1.3.6.1.4.1.6296.9.102.1.4.5
		gfastProfileTable OBJECT-TYPE
			SYNTAX SEQUENCE OF GfastProfileEntry
			MAX-ACCESS not-accessible
			STATUS current
			DESCRIPTION
				"This table includes Gfast Profile Configuration Table."
			::= { gfastProfileGroup 5 }

		
		-- 1.3.6.1.4.1.6296.9.102.1.4.5.1
		gfastProfileEntry OBJECT-TYPE
			SYNTAX GfastProfileEntry
			MAX-ACCESS not-accessible
			STATUS current
			DESCRIPTION
				"An entry in the gfastProfileTable."
			INDEX { gfastProfileIndex }
			::= { gfastProfileTable 1 }

		
		GfastProfileEntry ::=
			SEQUENCE { 
				gfastProfileIndex
					INTEGER,
				gfastProfileName
					DisplayString,
				gfastProfileAddPort
					DisplayString,
				gfastProfileDelPort
					DisplayString,
				gfastProfileActive
					INTEGER,
				gfastProfileUsBandPlanLower
					INTEGER,
				gfastProfileUsBandPlanUpper
					INTEGER,
				gfastProfileDsBandPlanLower
					INTEGER,
				gfastProfileDsBandPlanUpper
					INTEGER,
				gfastProfileUsMaxNDR
					INTEGER,
				gfastProfileDsMaxNDR
					INTEGER,
				gfastProfileUsTargetMargin
					INTEGER,
				gfastProfileDsTargetMargin
					INTEGER,
				gfastProfileUsMaxMargin
					INTEGER,
				gfastProfileDsMaxMargin
					INTEGER,
				gfastProfileUsMinMargin
					INTEGER,
				gfastProfileDsMinMargin
					INTEGER,
				gfastProfileUsMaxTxPower
					INTEGER,
				gfastProfileDsMaxTxPower
					INTEGER,
				gfastProfileUsSraMode
					INTEGER,
				gfastProfileDsSraMode
					INTEGER,
				gfastProfileUsUpShiftMargin
					INTEGER,
				gfastProfileUsDownShiftMargin
					INTEGER,
				gfastProfileDsUpShiftMargin
					INTEGER,
				gfastProfileDsDownShiftMargin
					INTEGER,
				gfastProfileUsUpShiftInterval
					INTEGER,
				gfastProfileUsDownShiftInterval
					INTEGER,
				gfastProfileDsUpShiftInterval
					INTEGER,
				gfastProfileDsDownShiftInterval
					INTEGER,
				gfastProfileUsRpaMode
					INTEGER,
				gfastProfileDsRpaMode
					INTEGER,
				gfastProfileUsTargetMarginRmc
					INTEGER,
				gfastProfileDsTargetMarginRmc
					INTEGER,
				gfastProfileUsMinMarginRmc
					INTEGER,
				gfastProfileDsMinMarginRmc
					INTEGER,
				gfastProfileUsMaxBitloadingRmc
					INTEGER,
				gfastProfileDsMaxBitloadingRmc
					INTEGER,
				gfastProfileUsFraMode
					INTEGER,
				gfastProfileDsFraMode
					INTEGER,
				gfastProfileUsFraTime
					INTEGER,
				gfastProfileDsFraTime
					INTEGER,
				gfastProfileUsFraNtones
					INTEGER,
				gfastProfileDsFraNtones
					INTEGER,
				gfastProfileUsFraRtxUc
					INTEGER,
				gfastProfileDsFraRtxUc
					INTEGER,
				gfastProfileUsFraVendisc
					INTEGER,
				gfastProfileDsFraVendisc
					INTEGER,
				gfastProfileRtxUsETRmin
					INTEGER,
				gfastProfileRtxDsETRmin
					INTEGER,
				gfastProfileRtxUsMaxDelay
					INTEGER,
				gfastProfileRtxDsMaxDelay
					INTEGER,
				gfastProfileRtxUsInpMinShine
					INTEGER,
				gfastProfileRtxDsInpMinShine
					INTEGER,
				gfastProfileRtxUsShineRatio
					INTEGER,
				gfastProfileRtxDsShineRatio
					INTEGER,
				gfastProfileRtxUsInpMinRein
					INTEGER,
				gfastProfileRtxDsInpMinRein
					INTEGER,
				gfastProfileRtxUsIatReinFlag
					INTEGER,
				gfastProfileRtxDsIatReinFlag
					INTEGER,
				gfastProfileRtxUsRNratio
					INTEGER,
				gfastProfileRtxDsRNratio
					INTEGER,
				gfastProfileUpboAdmin
					INTEGER,
				gfastProfileUpboAValue
					INTEGER,
				gfastProfileUpboBValue
					INTEGER,
				gfastProfileUpboKl0
					INTEGER,
				gfastProfileUsLosPersistency
					INTEGER,
				gfastProfileDsLosPersistency
					INTEGER,
				gfastProfileUsLorPersistency
					INTEGER,
				gfastProfileDsLorPersistency
					INTEGER,
				gfastProfileMaxBitloading
					INTEGER,
				gfastProfileUsLomPersistency
					INTEGER,
				gfastProfileDsLomPersistency
					INTEGER,
				gfastProfileUsTpsTcTestMode
					INTEGER,
				gfastProfileDsTpsTcTestMode
					INTEGER,
				gfastProfileUsIdleSymbolMode
					INTEGER,
				gfastProfileDsIdleSymbolMode
					INTEGER
			 }

-- gfastProfileDisableBitSwap		INTEGER,
-- gfastProfileRtxUsMode			INTEGER,
-- gfastProfileRtxDsMode			INTEGER,
		-- 1.3.6.1.4.1.6296.9.102.1.4.5.1.1
		gfastProfileIndex OBJECT-TYPE
			SYNTAX INTEGER (1..20)
			MAX-ACCESS read-only
			STATUS current
			DESCRIPTION
				"Specifies the Gfast System's Profile index."
			::= { gfastProfileEntry 1 }

		
		-- 1.3.6.1.4.1.6296.9.102.1.4.5.1.2
		gfastProfileName OBJECT-TYPE
			SYNTAX DisplayString (SIZE (0..16))
			MAX-ACCESS read-only
			STATUS current
			DESCRIPTION
				"Defines the Profile Name.
				It ranges from 1 to 16"
			::= { gfastProfileEntry 2 }

		
		-- 1.3.6.1.4.1.6296.9.102.1.4.5.1.3
		gfastProfileAddPort OBJECT-TYPE
			SYNTAX DisplayString (SIZE (0..16))
			MAX-ACCESS read-write
			STATUS current
			DESCRIPTION
				"To apply a profile to a port. Enter the port number. ex) 1 | 1,4 | 1-4"
			::= { gfastProfileEntry 3 }

		
		-- 1.3.6.1.4.1.6296.9.102.1.4.5.1.4
		gfastProfileDelPort OBJECT-TYPE
			SYNTAX DisplayString (SIZE (0..16))
			MAX-ACCESS read-write
			STATUS current
			DESCRIPTION
				"Remove the port profile is applied. Enter the port number. ex) 1 | 1,4 | 1-4"
			::= { gfastProfileEntry 4 }

		
		-- 1.3.6.1.4.1.6296.9.102.1.4.5.1.5
		gfastProfileActive OBJECT-TYPE
			SYNTAX INTEGER
				{
				no_action(0),
				active(1)
				}
			MAX-ACCESS read-write
			STATUS current
			DESCRIPTION
				"Activate the profile."
			::= { gfastProfileEntry 5 }

		
		-- 1.3.6.1.4.1.6296.9.102.1.4.5.1.6
		gfastProfileUsBandPlanLower OBJECT-TYPE
			SYNTAX INTEGER (43..2042)
			MAX-ACCESS read-write
			STATUS current
			DESCRIPTION
				"Specifies the gfast Port's Up stream Lower Band plan. 
				It range from 43 to 2042 units is 1 sub-carrier (frequency = sub-carier * 51.75kHz) "
			::= { gfastProfileEntry 6 }

		
		-- 1.3.6.1.4.1.6296.9.102.1.4.5.1.7
		gfastProfileUsBandPlanUpper OBJECT-TYPE
			SYNTAX INTEGER (43..2042)
			MAX-ACCESS read-write
			STATUS current
			DESCRIPTION
				"Specifies the gfast Port's Up stream Upper Band plan. 
				It range from 43 to 2042 units is 1 sub-carrier (frequency = sub-carier * 51.75kHz) "
			::= { gfastProfileEntry 7 }

		
		-- 1.3.6.1.4.1.6296.9.102.1.4.5.1.8
		gfastProfileDsBandPlanLower OBJECT-TYPE
			SYNTAX INTEGER (43..2042)
			MAX-ACCESS read-write
			STATUS current
			DESCRIPTION
				"Specifies the gfast Port's Down stream Lower Band plan. 
				It range from 43 to 2042 units is 1 sub-carrier (frequency = sub-carier * 51.75kHz) "
			::= { gfastProfileEntry 8 }

		
		-- 1.3.6.1.4.1.6296.9.102.1.4.5.1.9
		gfastProfileDsBandPlanUpper OBJECT-TYPE
			SYNTAX INTEGER (43..2042)
			MAX-ACCESS read-write
			STATUS current
			DESCRIPTION
				"Specifies the gfast Port's Down stream Upper Band plan. 
				It range from 43 to 2042 units is 1 sub-carrier (frequency = sub-carier * 51.75kHz) "
			::= { gfastProfileEntry 9 }

		
		-- 1.3.6.1.4.1.6296.9.102.1.4.5.1.10
		gfastProfileUsMaxNDR OBJECT-TYPE
			SYNTAX INTEGER (64..6291360)
			MAX-ACCESS read-write
			STATUS current
			DESCRIPTION
				"Specifies the gfast Port's Up stream Maximum Data Rate. 
				It range from 64 to 6291360 units is 1 kbps "
			::= { gfastProfileEntry 10 }

		
		-- 1.3.6.1.4.1.6296.9.102.1.4.5.1.11
		gfastProfileDsMaxNDR OBJECT-TYPE
			SYNTAX INTEGER (64..6291360)
			MAX-ACCESS read-write
			STATUS current
			DESCRIPTION
				"Specifies the gfast Port's Down stream Maximum Data Rate. 
				It range from 64 to 6291360 units is 1 kbps "
			::= { gfastProfileEntry 11 }

		
		-- 1.3.6.1.4.1.6296.9.102.1.4.5.1.12
		gfastProfileUsTargetMargin OBJECT-TYPE
			SYNTAX INTEGER (0..310)
			MAX-ACCESS read-write
			STATUS current
			DESCRIPTION
				"Specifies the gfast Port's Up stream Target noise margin. 
				It range from 0 to 310 units is 0.1 dB "
			::= { gfastProfileEntry 12 }

		
		-- 1.3.6.1.4.1.6296.9.102.1.4.5.1.13
		gfastProfileDsTargetMargin OBJECT-TYPE
			SYNTAX INTEGER (0..310)
			MAX-ACCESS read-write
			STATUS current
			DESCRIPTION
				"Specifies the gfast Port's Down stream Target noise margin. 
				It range from 0 to 310 units is 0.1 dB "
			::= { gfastProfileEntry 13 }

		
		-- 1.3.6.1.4.1.6296.9.102.1.4.5.1.14
		gfastProfileUsMaxMargin OBJECT-TYPE
			SYNTAX INTEGER (0..310)
			MAX-ACCESS read-write
			STATUS current
			DESCRIPTION
				"Specifies the gfast Port's Up stream Max noise margin. 
				It range from 0 to 310 units is 0.1 dB "
			::= { gfastProfileEntry 14 }

		
		-- 1.3.6.1.4.1.6296.9.102.1.4.5.1.15
		gfastProfileDsMaxMargin OBJECT-TYPE
			SYNTAX INTEGER (0..310)
			MAX-ACCESS read-write
			STATUS current
			DESCRIPTION
				"Specifies the gfast Port's Down stream Max noise margin. 
				It range from 0 to 310 units is 0.1 dB "
			::= { gfastProfileEntry 15 }

		
		-- 1.3.6.1.4.1.6296.9.102.1.4.5.1.16
		gfastProfileUsMinMargin OBJECT-TYPE
			SYNTAX INTEGER (0..310)
			MAX-ACCESS read-write
			STATUS current
			DESCRIPTION
				"Specifies the gfast Port's Up stream Min noise margin. 
				It range from 0 to 310 units is 0.1 dB "
			::= { gfastProfileEntry 16 }

		
		-- 1.3.6.1.4.1.6296.9.102.1.4.5.1.17
		gfastProfileDsMinMargin OBJECT-TYPE
			SYNTAX INTEGER (0..310)
			MAX-ACCESS read-write
			STATUS current
			DESCRIPTION
				"Specifies the gfast Port's Down stream Min noise margin. 
				It range from 0 to 310 units is 0.1 dB "
			::= { gfastProfileEntry 17 }

		
		-- 1.3.6.1.4.1.6296.9.102.1.4.5.1.18
		gfastProfileUsMaxTxPower OBJECT-TYPE
			SYNTAX INTEGER (-130..200)
			MAX-ACCESS read-write
			STATUS current
			DESCRIPTION
				"Specifies the gfast Port's Up stream Maximum allowed transmit power. 
				It range from -130 to 200 units is 0.1 dBm"
			::= { gfastProfileEntry 18 }

		
		-- 1.3.6.1.4.1.6296.9.102.1.4.5.1.19
		gfastProfileDsMaxTxPower OBJECT-TYPE
			SYNTAX INTEGER (-50..200)
			MAX-ACCESS read-write
			STATUS current
			DESCRIPTION
				"Specifies the gfast Port's Down stream Maximum allowed transmit power. 
				It range from -50 to 200 units is 0.1 dBm"
			::= { gfastProfileEntry 19 }

		
-- gfastProfileDisableBitSwap OBJECT-TYPE
-- SYNTAX      INTEGER { us-On-ds-On(0), us-Off-ds-On(1), us-On-ds-Off(2), us-Off-ds-Off(3) }
-- MAX-ACCESS  read-write
-- STATUS      current
-- DESCRIPTION
-- "Specifies the gfast Port's Bit swap admin. "
-- ::= { gfastProfileEntry 17 }
		-- 1.3.6.1.4.1.6296.9.102.1.4.5.1.20
		gfastProfileUsSraMode OBJECT-TYPE
			SYNTAX INTEGER
				{
				disable(0),
				enable(1)
				}
			MAX-ACCESS read-write
			STATUS current
			DESCRIPTION
				"Specifies the gfast Port's Up stream Rate Adaption admin. "
			::= { gfastProfileEntry 20 }

		
		-- 1.3.6.1.4.1.6296.9.102.1.4.5.1.21
		gfastProfileDsSraMode OBJECT-TYPE
			SYNTAX INTEGER
				{
				disable(0),
				enable(1)
				}
			MAX-ACCESS read-write
			STATUS current
			DESCRIPTION
				"Specifies the gfast Port's Down stream Rate Adaption admin. "
			::= { gfastProfileEntry 21 }

		
		-- 1.3.6.1.4.1.6296.9.102.1.4.5.1.22
		gfastProfileUsUpShiftMargin OBJECT-TYPE
			SYNTAX INTEGER (0..310)
			MAX-ACCESS read-write
			STATUS current
			DESCRIPTION
				"Specifies the gfast Port's Up stream up-shift noise margin. 
				It range from 0 to 310 units is 0.1 dB"
			::= { gfastProfileEntry 22 }

		
		-- 1.3.6.1.4.1.6296.9.102.1.4.5.1.23
		gfastProfileUsDownShiftMargin OBJECT-TYPE
			SYNTAX INTEGER (0..310)
			MAX-ACCESS read-write
			STATUS current
			DESCRIPTION
				"Specifies the gfast Port's Up stream down-shift noise margin. 
				It range from 0 to 310 units is 0.1 dB"
			::= { gfastProfileEntry 23 }

		
		-- 1.3.6.1.4.1.6296.9.102.1.4.5.1.24
		gfastProfileDsUpShiftMargin OBJECT-TYPE
			SYNTAX INTEGER (0..310)
			MAX-ACCESS read-write
			STATUS current
			DESCRIPTION
				"Specifies the gfast Port's Down stream up-shift noise margin. 
				It range from 0 to 310 units is 0.1 dB"
			::= { gfastProfileEntry 24 }

		
		-- 1.3.6.1.4.1.6296.9.102.1.4.5.1.25
		gfastProfileDsDownShiftMargin OBJECT-TYPE
			SYNTAX INTEGER (0..310)
			MAX-ACCESS read-write
			STATUS current
			DESCRIPTION
				"Specifies the gfast Port's Down stream down-shift noise margin. 
				It range from 0 to 310 units is 0.1 dB"
			::= { gfastProfileEntry 25 }

		
		-- 1.3.6.1.4.1.6296.9.102.1.4.5.1.26
		gfastProfileUsUpShiftInterval OBJECT-TYPE
			SYNTAX INTEGER (0..16383)
			MAX-ACCESS read-write
			STATUS current
			DESCRIPTION
				"Specifies the gfast Port's Up stream up-shift time interval. 
				It range from 0 to 16383 units is 1sec"
			::= { gfastProfileEntry 26 }

		
		-- 1.3.6.1.4.1.6296.9.102.1.4.5.1.27
		gfastProfileUsDownShiftInterval OBJECT-TYPE
			SYNTAX INTEGER (0..16383)
			MAX-ACCESS read-write
			STATUS current
			DESCRIPTION
				"Specifies the gfast Port's Up stream down-shift time interval. 
				It range from 0 to 16383 units is 1sec"
			::= { gfastProfileEntry 27 }

		
		-- 1.3.6.1.4.1.6296.9.102.1.4.5.1.28
		gfastProfileDsUpShiftInterval OBJECT-TYPE
			SYNTAX INTEGER (0..16383)
			MAX-ACCESS read-write
			STATUS current
			DESCRIPTION
				"Specifies the gfast Port's Down stream up-shift time interval. 
				It range from 0 to 16383 units is 1sec"
			::= { gfastProfileEntry 28 }

		
		-- 1.3.6.1.4.1.6296.9.102.1.4.5.1.29
		gfastProfileDsDownShiftInterval OBJECT-TYPE
			SYNTAX INTEGER (0..16383)
			MAX-ACCESS read-write
			STATUS current
			DESCRIPTION
				"Specifies the gfast Port's Down stream down-shift time interval. 
				It range from 0 to 16383 units is 1sec"
			::= { gfastProfileEntry 29 }

		
		-- 1.3.6.1.4.1.6296.9.102.1.4.5.1.30
		gfastProfileUsRpaMode OBJECT-TYPE
			SYNTAX INTEGER
				{
				disable(0),
				enable(1)
				}
			MAX-ACCESS read-write
			STATUS current
			DESCRIPTION
				"Specifies the gfast Port's Up stream RMC parameter adjustment admin."
			::= { gfastProfileEntry 30 }

		
		-- 1.3.6.1.4.1.6296.9.102.1.4.5.1.31
		gfastProfileDsRpaMode OBJECT-TYPE
			SYNTAX INTEGER
				{
				disable(0),
				enable(1)
				}
			MAX-ACCESS read-write
			STATUS current
			DESCRIPTION
				"Specifies the gfast Port's Down stream RMC parameter adjustment admin."
			::= { gfastProfileEntry 31 }

		
		-- 1.3.6.1.4.1.6296.9.102.1.4.5.1.32
		gfastProfileUsTargetMarginRmc OBJECT-TYPE
			SYNTAX INTEGER (0..310)
			MAX-ACCESS read-write
			STATUS current
			DESCRIPTION
				"Specifies the gfast Port's Up stream target SNR margin of the RMC. 
				It range from 0 to 310 units is 0.1 dB"
			::= { gfastProfileEntry 32 }

		
		-- 1.3.6.1.4.1.6296.9.102.1.4.5.1.33
		gfastProfileDsTargetMarginRmc OBJECT-TYPE
			SYNTAX INTEGER (0..310)
			MAX-ACCESS read-write
			STATUS current
			DESCRIPTION
				"Specifies the gfast Port's Down stream target SNR margin of the RMC. 
				It range from 0 to 310 units is 0.1 dB"
			::= { gfastProfileEntry 33 }

		
		-- 1.3.6.1.4.1.6296.9.102.1.4.5.1.34
		gfastProfileUsMinMarginRmc OBJECT-TYPE
			SYNTAX INTEGER (0..310)
			MAX-ACCESS read-write
			STATUS current
			DESCRIPTION
				"Specifies the gfast Port's Up stream minimum SNR margin of the RMC. 
				It range from 0 to 310 units is 0.1 dB"
			::= { gfastProfileEntry 34 }

		
		-- 1.3.6.1.4.1.6296.9.102.1.4.5.1.35
		gfastProfileDsMinMarginRmc OBJECT-TYPE
			SYNTAX INTEGER (0..310)
			MAX-ACCESS read-write
			STATUS current
			DESCRIPTION
				"Specifies the gfast Port's Down stream minimum SNR margin of the RMC. 
				It range from 0 to 310 units is 0.1 dB"
			::= { gfastProfileEntry 35 }

		
		-- 1.3.6.1.4.1.6296.9.102.1.4.5.1.36
		gfastProfileUsMaxBitloadingRmc OBJECT-TYPE
			SYNTAX INTEGER (2..6)
			MAX-ACCESS read-write
			STATUS current
			DESCRIPTION
				"Specifies the gfast Port's Up stream maximum bit loading allowed for RMC sub-carrier. 
				It range from 2 to 6"
			::= { gfastProfileEntry 36 }

		
		-- 1.3.6.1.4.1.6296.9.102.1.4.5.1.37
		gfastProfileDsMaxBitloadingRmc OBJECT-TYPE
			SYNTAX INTEGER (2..6)
			MAX-ACCESS read-write
			STATUS current
			DESCRIPTION
				"Specifies the gfast Port's Down stream maximum bit loading allowed for RMC sub-carrier. 
				It range from 2 to 6"
			::= { gfastProfileEntry 37 }

		
		-- 1.3.6.1.4.1.6296.9.102.1.4.5.1.38
		gfastProfileUsFraMode OBJECT-TYPE
			SYNTAX INTEGER
				{
				disable(0),
				enable(1)
				}
			MAX-ACCESS read-write
			STATUS current
			DESCRIPTION
				"Specifies the gfast Port's Up stream Fast Rate Adaptation admin."
			::= { gfastProfileEntry 38 }

		
		-- 1.3.6.1.4.1.6296.9.102.1.4.5.1.39
		gfastProfileDsFraMode OBJECT-TYPE
			SYNTAX INTEGER
				{
				disable(0),
				enable(1)
				}
			MAX-ACCESS read-write
			STATUS current
			DESCRIPTION
				"Specifies the gfast Port's Down stream Fast Rate Adaptation admin."
			::= { gfastProfileEntry 39 }

		
		-- 1.3.6.1.4.1.6296.9.102.1.4.5.1.40
		gfastProfileUsFraTime OBJECT-TYPE
			SYNTAX INTEGER (0..8)
			MAX-ACCESS read-write
			STATUS current
			DESCRIPTION
				"Specifies the gfast Port's Up stream duration of the FRA time window
				used in the standard FRA triggering criteria. 
				It range from 0 to 8"
			::= { gfastProfileEntry 40 }

		
		-- 1.3.6.1.4.1.6296.9.102.1.4.5.1.41
		gfastProfileDsFraTime OBJECT-TYPE
			SYNTAX INTEGER (0..8)
			MAX-ACCESS read-write
			STATUS current
			DESCRIPTION
				"Specifies the gfast Port's Down stream duration of the FRA time window
				used in the standard FRA triggering criteria. 
				It range from 0 to 8"
			::= { gfastProfileEntry 41 }

		
		-- 1.3.6.1.4.1.6296.9.102.1.4.5.1.42
		gfastProfileUsFraNtones OBJECT-TYPE
			SYNTAX INTEGER (0..100)
			MAX-ACCESS read-write
			STATUS current
			DESCRIPTION
				"Specifies the gfast Port's Up stream minimum percentage of
				degraded loaded sub-carriers during FRA-TIME in order to
				arm the first FRA triggering criteria. 
				It range from 0 to 100"
			::= { gfastProfileEntry 42 }

		
		-- 1.3.6.1.4.1.6296.9.102.1.4.5.1.43
		gfastProfileDsFraNtones OBJECT-TYPE
			SYNTAX INTEGER (0..100)
			MAX-ACCESS read-write
			STATUS current
			DESCRIPTION
				"Specifies the gfast Port's Down stream minimum percentage of
				degraded loaded sub-carriers during FRA-TIME in order to
				arm the first FRA triggering criteria. 
				It range from 0 to 100"
			::= { gfastProfileEntry 43 }

		
		-- 1.3.6.1.4.1.6296.9.102.1.4.5.1.44
		gfastProfileUsFraRtxUc OBJECT-TYPE
			SYNTAX INTEGER (0..1023)
			MAX-ACCESS read-write
			STATUS current
			DESCRIPTION
				"Specifies the gfast Port's Up stream minimum number of
				rtx-uc anomalies received during FRA-TIME in order to
				arm the second FRA triggering criteria. 
				It range from 0 to 1023"
			::= { gfastProfileEntry 44 }

		
		-- 1.3.6.1.4.1.6296.9.102.1.4.5.1.45
		gfastProfileDsFraRtxUc OBJECT-TYPE
			SYNTAX INTEGER (0..1023)
			MAX-ACCESS read-write
			STATUS current
			DESCRIPTION
				"Specifies the gfast Port's Down stream minimum number of
				rtx-uc anomalies received during FRA-TIME in order to
				arm the second FRA triggering criteria. 
				It range from 0 to 1023"
			::= { gfastProfileEntry 45 }

		
		-- 1.3.6.1.4.1.6296.9.102.1.4.5.1.46
		gfastProfileUsFraVendisc OBJECT-TYPE
			SYNTAX INTEGER
				{
				disable(0),
				enable(1)
				}
			MAX-ACCESS read-write
			STATUS current
			DESCRIPTION
				"Specifies the gfast Port's Up stream whether vendor
				discretionary FRA triggering criteria may be used."
			::= { gfastProfileEntry 46 }

		
		-- 1.3.6.1.4.1.6296.9.102.1.4.5.1.47
		gfastProfileDsFraVendisc OBJECT-TYPE
			SYNTAX INTEGER
				{
				disable(0),
				enable(1)
				}
			MAX-ACCESS read-write
			STATUS current
			DESCRIPTION
				"Specifies the gfast Port's Down stream whether vendor
				discretionary FRA triggering criteria may be used."
			::= { gfastProfileEntry 47 }

		
-- gfastProfileRtxUsMode OBJECT-TYPE
-- SYNTAX      INTEGER { forbidden(0), preferred(1), forced(2), test(3) }
-- MAX-ACCESS  read-write
-- STATUS      current
-- DESCRIPTION
-- "Specifies the gfast Port's Up stream Retransmission mode." 
-- ::= { gfastProfileEntry 45 }
-- gfastProfileRtxDsMode OBJECT-TYPE
-- SYNTAX      INTEGER { forbidden(0), preferred(1), forced(2), test(3) }
-- MAX-ACCESS  read-write
-- STATUS      current
-- DESCRIPTION
-- "Specifies the gfast Port's Down stream Retransmission mode." 
-- ::= { gfastProfileEntry 46 }
		-- 1.3.6.1.4.1.6296.9.102.1.4.5.1.48
		gfastProfileRtxUsETRmin OBJECT-TYPE
			SYNTAX INTEGER (0..6291360)
			MAX-ACCESS read-write
			STATUS current
			DESCRIPTION
				"Specifies the gfast Port's Up stream minimum Expected Throughput Rate. 
				It range from 0 to Max-NDR units is 1kbps."
			::= { gfastProfileEntry 48 }

		
		-- 1.3.6.1.4.1.6296.9.102.1.4.5.1.49
		gfastProfileRtxDsETRmin OBJECT-TYPE
			SYNTAX INTEGER (0..6291360)
			MAX-ACCESS read-write
			STATUS current
			DESCRIPTION
				"Specifies the gfast Port's Down stream minimum Expected Throughput Rate. 
				It range from 0 to Max-NDR units is 1kbps"
			::= { gfastProfileEntry 49 }

		
		-- 1.3.6.1.4.1.6296.9.102.1.4.5.1.50
		gfastProfileRtxUsMaxDelay OBJECT-TYPE
			SYNTAX INTEGER (0..63000)
			MAX-ACCESS read-write
			STATUS current
			DESCRIPTION
				"Specifies the gfast Port's Up stream maximum allowed delay for retransmission. 
				It range from 0 to 63000 units is 1 micro sec"
			::= { gfastProfileEntry 50 }

		
		-- 1.3.6.1.4.1.6296.9.102.1.4.5.1.51
		gfastProfileRtxDsMaxDelay OBJECT-TYPE
			SYNTAX INTEGER (0..63000)
			MAX-ACCESS read-write
			STATUS current
			DESCRIPTION
				"Specifies the gfast Port's Down stream maximum allowed delay for retransmission. 
				It range from 0 to 63000 units is 1 micro sec"
			::= { gfastProfileEntry 51 }

		
		-- 1.3.6.1.4.1.6296.9.102.1.4.5.1.52
		gfastProfileRtxUsInpMinShine OBJECT-TYPE
			SYNTAX INTEGER (0..1040)
			MAX-ACCESS read-write
			STATUS current
			DESCRIPTION
				"Specifies the gfast Port's Up stream minimum impulse noise protection against SHINE. 
				It range from 0 to 1040 units is 0.5symbol"
			::= { gfastProfileEntry 52 }

		
		-- 1.3.6.1.4.1.6296.9.102.1.4.5.1.53
		gfastProfileRtxDsInpMinShine OBJECT-TYPE
			SYNTAX INTEGER (0..1040)
			MAX-ACCESS read-write
			STATUS current
			DESCRIPTION
				"Specifies the gfast Port's Down stream minimum impulse noise protection against SHINE. 
				It range from 0 to 1040 units is 0.5symbol"
			::= { gfastProfileEntry 53 }

		
		-- 1.3.6.1.4.1.6296.9.102.1.4.5.1.54
		gfastProfileRtxUsShineRatio OBJECT-TYPE
			SYNTAX INTEGER (0..100)
			MAX-ACCESS read-write
			STATUS current
			DESCRIPTION
				"Specifies the gfast Port's Up stream SHINE ratio. 
				It range from 0 to 100 units is 0.001"
			::= { gfastProfileEntry 54 }

		
		-- 1.3.6.1.4.1.6296.9.102.1.4.5.1.55
		gfastProfileRtxDsShineRatio OBJECT-TYPE
			SYNTAX INTEGER (0..100)
			MAX-ACCESS read-write
			STATUS current
			DESCRIPTION
				"Specifies the gfast Port's Down stream SHINE ratio. 
				It range from 0 to 100 units is 0.001"
			::= { gfastProfileEntry 55 }

		
		-- 1.3.6.1.4.1.6296.9.102.1.4.5.1.56
		gfastProfileRtxUsInpMinRein OBJECT-TYPE
			SYNTAX INTEGER (0..126)
			MAX-ACCESS read-write
			STATUS current
			DESCRIPTION
				"Specifies the gfast Port's Up stream minimum impulse noise protection against REIN. 
				It range from 0 to 126 units is 0.5symbol"
			::= { gfastProfileEntry 56 }

		
		-- 1.3.6.1.4.1.6296.9.102.1.4.5.1.57
		gfastProfileRtxDsInpMinRein OBJECT-TYPE
			SYNTAX INTEGER (0..126)
			MAX-ACCESS read-write
			STATUS current
			DESCRIPTION
				"Specifies the gfast Port's Down stream minimum impulse noise protection against REIN. 
				It range from 0 to 126 units is 0.5symbol"
			::= { gfastProfileEntry 57 }

		
		-- 1.3.6.1.4.1.6296.9.102.1.4.5.1.58
		gfastProfileRtxUsIatReinFlag OBJECT-TYPE
			SYNTAX INTEGER
				{
				hz100(0),
				hz120(1),
				hz300(2),
				hz360(3)
				}
			MAX-ACCESS read-write
			STATUS current
			DESCRIPTION
				"Specifies the gfast Port's Up stream inter arrival time of REIN. "
			::= { gfastProfileEntry 58 }

		
		-- 1.3.6.1.4.1.6296.9.102.1.4.5.1.59
		gfastProfileRtxDsIatReinFlag OBJECT-TYPE
			SYNTAX INTEGER
				{
				hz100(0),
				hz120(1),
				hz300(2),
				hz360(3)
				}
			MAX-ACCESS read-write
			STATUS current
			DESCRIPTION
				"Specifies the gfast Port's Down stream inter arrival time of REIN. "
			::= { gfastProfileEntry 59 }

		
		-- 1.3.6.1.4.1.6296.9.102.1.4.5.1.60
		gfastProfileRtxUsRNratio OBJECT-TYPE
			SYNTAX INTEGER (0..8)
			MAX-ACCESS read-write
			STATUS current
			DESCRIPTION
				"Specifies the gfast Port's Up stream minimum ratio R/N.
				It range from 0 to 8 unit is 1/32"
			::= { gfastProfileEntry 60 }

		
		-- 1.3.6.1.4.1.6296.9.102.1.4.5.1.61
		gfastProfileRtxDsRNratio OBJECT-TYPE
			SYNTAX INTEGER (0..8)
			MAX-ACCESS read-write
			STATUS current
			DESCRIPTION
				"Specifies the gfast Port's Down stream minimum ratio R/N.
				It range from 0 to 8 unit is 1/32"
			::= { gfastProfileEntry 61 }

		
		-- 1.3.6.1.4.1.6296.9.102.1.4.5.1.62
		gfastProfileUpboAdmin OBJECT-TYPE
			SYNTAX INTEGER
				{
				disable(0),
				enable(1)
				}
			MAX-ACCESS read-create
			STATUS current
			DESCRIPTION
				"The identifier for G.FAST UPBO"
			::= { gfastProfileEntry 62 }

		
		-- 1.3.6.1.4.1.6296.9.102.1.4.5.1.63
		gfastProfileUpboAValue OBJECT-TYPE
			SYNTAX INTEGER (10240..20725)
			MAX-ACCESS read-create
			STATUS current
			DESCRIPTION
				"Specifies the gfast Port's UPBO a value.
				Unit is -1/256"
			::= { gfastProfileEntry 63 }

		
		-- 1.3.6.1.4.1.6296.9.102.1.4.5.1.64
		gfastProfileUpboBValue OBJECT-TYPE
			SYNTAX INTEGER (0..10485)
			MAX-ACCESS read-create
			STATUS current
			DESCRIPTION
				"Specifies the gfast Port's UPBO b value.
				Unit is -1/256"
			::= { gfastProfileEntry 64 }

		
		-- 1.3.6.1.4.1.6296.9.102.1.4.5.1.65
		gfastProfileUpboKl0 OBJECT-TYPE
			SYNTAX INTEGER (0..635)
			MAX-ACCESS read-create
			STATUS current
			DESCRIPTION
				"Specifies the gfast Port's UPBO Electrical length estimation.
				value is 0 or 18 ~ 635. Unit is 0.1db"
			::= { gfastProfileEntry 65 }

		
		-- 1.3.6.1.4.1.6296.9.102.1.4.5.1.66
		gfastProfileUsLosPersistency OBJECT-TYPE
			SYNTAX INTEGER (1..20)
			MAX-ACCESS read-write
			STATUS current
			DESCRIPTION
				"Specifies the gfast Port's Up stream LOS Persistency.
				It range from 1 to 20. unit is 100ms."
			::= { gfastProfileEntry 66 }

		
		-- 1.3.6.1.4.1.6296.9.102.1.4.5.1.67
		gfastProfileDsLosPersistency OBJECT-TYPE
			SYNTAX INTEGER (1..20)
			MAX-ACCESS read-write
			STATUS current
			DESCRIPTION
				"Specifies the gfast Port's Down stream LOS Persistency.
				It range from 1 to 20. unit is 100ms."
			::= { gfastProfileEntry 67 }

		
		-- 1.3.6.1.4.1.6296.9.102.1.4.5.1.68
		gfastProfileUsLorPersistency OBJECT-TYPE
			SYNTAX INTEGER (1..20)
			MAX-ACCESS read-write
			STATUS current
			DESCRIPTION
				"Specifies the gfast Port's Up stream LOR Persistency.
				It range from 1 to 20. unit is 100ms."
			::= { gfastProfileEntry 68 }

		
		-- 1.3.6.1.4.1.6296.9.102.1.4.5.1.69
		gfastProfileDsLorPersistency OBJECT-TYPE
			SYNTAX INTEGER (1..20)
			MAX-ACCESS read-write
			STATUS current
			DESCRIPTION
				"Specifies the gfast Port's Down stream LOR Persistency.
				It range from 1 to 20. unit is 100ms."
			::= { gfastProfileEntry 69 }

		
		-- 1.3.6.1.4.1.6296.9.102.1.4.5.1.70
		gfastProfileMaxBitloading OBJECT-TYPE
			SYNTAX INTEGER
				{
				bit_12(1),
				bit_14(2)
				}
			MAX-ACCESS read-write
			STATUS current
			DESCRIPTION
				"Specifies the gfast Port's Max Bitloading per tone."
			::= { gfastProfileEntry 70 }

		
		-- 1.3.6.1.4.1.6296.9.102.1.4.5.1.71
		gfastProfileUsLomPersistency OBJECT-TYPE
			SYNTAX INTEGER (1..20)
			MAX-ACCESS read-write
			STATUS current
			DESCRIPTION
				"Specifies the gfast Port's Up stream LOM Persistency.
				It range from 1 to 20. unit is 100ms."
			::= { gfastProfileEntry 71 }

		
		-- 1.3.6.1.4.1.6296.9.102.1.4.5.1.72
		gfastProfileDsLomPersistency OBJECT-TYPE
			SYNTAX INTEGER (1..20)
			MAX-ACCESS read-write
			STATUS current
			DESCRIPTION
				"Specifies the gfast Port's Down stream LOM Persistency.
				It range from 1 to 20. unit is 100ms."
			::= { gfastProfileEntry 72 }

		
		-- 1.3.6.1.4.1.6296.9.102.1.4.5.1.73
		gfastProfileUsTpsTcTestMode OBJECT-TYPE
			SYNTAX INTEGER
				{
				disable(0),
				enable(1)
				}
			MAX-ACCESS read-write
			STATUS current
			DESCRIPTION
				"Specifies the gfast Up Stream TPS-TC test mode."
			::= { gfastProfileEntry 73 }

		
		-- 1.3.6.1.4.1.6296.9.102.1.4.5.1.74
		gfastProfileDsTpsTcTestMode OBJECT-TYPE
			SYNTAX INTEGER
				{
				disable(0),
				enable(1)
				}
			MAX-ACCESS read-write
			STATUS current
			DESCRIPTION
				"Specifies the gfast Down Stream TPS-TC test mode."
			::= { gfastProfileEntry 74 }

		
		-- 1.3.6.1.4.1.6296.9.102.1.4.5.1.75
		gfastProfileUsIdleSymbolMode OBJECT-TYPE
			SYNTAX INTEGER
				{
				disable(0),
				enable(1)
				}
			MAX-ACCESS read-write
			STATUS current
			DESCRIPTION
				"Specifies the gfast Up Stream Idle Symbol mode."
			::= { gfastProfileEntry 75 }

		
		-- 1.3.6.1.4.1.6296.9.102.1.4.5.1.76
		gfastProfileDsIdleSymbolMode OBJECT-TYPE
			SYNTAX INTEGER
				{
				disable(0),
				enable(1)
				}
			MAX-ACCESS read-write
			STATUS current
			DESCRIPTION
				"Specifies the gfast Down Stream Idle Symbol mode."
			::= { gfastProfileEntry 76 }

		
--  *********************************************************************
-- * Profile Upstream PSD Mask Table
-- *********************************************************************	
		-- 1.3.6.1.4.1.6296.9.102.1.4.6
		gfastProfileUsPsdMaskTable OBJECT-TYPE
			SYNTAX SEQUENCE OF GfastProfileUsPsdMaskEntry
			MAX-ACCESS not-accessible
			STATUS current
			DESCRIPTION
				"This table includes Gfast Profile Upstream PSD Mask Configuration Table."
			::= { gfastProfileGroup 6 }

		
		-- 1.3.6.1.4.1.6296.9.102.1.4.6.1
		gfastProfileUsPsdMaskEntry OBJECT-TYPE
			SYNTAX GfastProfileUsPsdMaskEntry
			MAX-ACCESS not-accessible
			STATUS current
			DESCRIPTION
				"An entry in the gfastProfileUsPsdMaskTable."
			INDEX { gfastProfileIndex, gfastProfileUsPsdMaskIndex }
			::= { gfastProfileUsPsdMaskTable 1 }

		
		GfastProfileUsPsdMaskEntry ::=
			SEQUENCE { 
				gfastProfileUsPsdMaskIndex
					INTEGER,
				gfastProfileUsPsdMaskTone
					INTEGER,
				gfastProfileUsPsdMaskPSD
					INTEGER,
				gfastProfileUsPsdMaskRowStatus
					EntryStatus
			 }

		-- 1.3.6.1.4.1.6296.9.102.1.4.6.1.1
		gfastProfileUsPsdMaskIndex OBJECT-TYPE
			SYNTAX INTEGER
			MAX-ACCESS not-accessible
			STATUS current
			DESCRIPTION
				"The identifier for G.FAST PSD Mask"
			::= { gfastProfileUsPsdMaskEntry 1 }

		
		-- 1.3.6.1.4.1.6296.9.102.1.4.6.1.2
		gfastProfileUsPsdMaskTone OBJECT-TYPE
			SYNTAX INTEGER (0..4095)
			MAX-ACCESS read-create
			STATUS current
			DESCRIPTION
				"Specifies the gfast Port's Up stream PSD mask Sub-carrier index.
				Unit is 1 sub-carrier (frequency = sub-carier * 51.75kHz)"
			::= { gfastProfileUsPsdMaskEntry 2 }

		
		-- 1.3.6.1.4.1.6296.9.102.1.4.6.1.3
		gfastProfileUsPsdMaskPSD OBJECT-TYPE
			SYNTAX INTEGER (0..1400)
			MAX-ACCESS read-create
			STATUS current
			DESCRIPTION
				"Specifies the gfast Port's Up stream PSD mask value.
				Unit is -0.1dB"
			::= { gfastProfileUsPsdMaskEntry 3 }

		
		-- 1.3.6.1.4.1.6296.9.102.1.4.6.1.4
		gfastProfileUsPsdMaskRowStatus OBJECT-TYPE
			SYNTAX EntryStatus
			MAX-ACCESS read-create
			STATUS current
			DESCRIPTION
				"The status of this conceptual row."
			::= { gfastProfileUsPsdMaskEntry 4 }

		
--  *********************************************************************
-- * Profile Downstream PSD Mask Table
-- *********************************************************************	
		-- 1.3.6.1.4.1.6296.9.102.1.4.7
		gfastProfileDsPsdMaskTable OBJECT-TYPE
			SYNTAX SEQUENCE OF GfastProfileDsPsdMaskEntry
			MAX-ACCESS not-accessible
			STATUS current
			DESCRIPTION
				"This table includes Gfast Profile Downstream PSD Mask Configuration Table."
			::= { gfastProfileGroup 7 }

		
		-- 1.3.6.1.4.1.6296.9.102.1.4.7.1
		gfastProfileDsPsdMaskEntry OBJECT-TYPE
			SYNTAX GfastProfileDsPsdMaskEntry
			MAX-ACCESS not-accessible
			STATUS current
			DESCRIPTION
				"An entry in the gfastProfileDsPsdMaskTable."
			INDEX { gfastProfileIndex, gfastProfileDsPsdMaskIndex }
			::= { gfastProfileDsPsdMaskTable 1 }

		
		GfastProfileDsPsdMaskEntry ::=
			SEQUENCE { 
				gfastProfileDsPsdMaskIndex
					INTEGER,
				gfastProfileDsPsdMaskTone
					INTEGER,
				gfastProfileDsPsdMaskPSD
					INTEGER,
				gfastProfileDsPsdMaskRowStatus
					EntryStatus
			 }

		-- 1.3.6.1.4.1.6296.9.102.1.4.7.1.1
		gfastProfileDsPsdMaskIndex OBJECT-TYPE
			SYNTAX INTEGER
			MAX-ACCESS not-accessible
			STATUS current
			DESCRIPTION
				"The identifier for G.FAST PSD Mask"
			::= { gfastProfileDsPsdMaskEntry 1 }

		
		-- 1.3.6.1.4.1.6296.9.102.1.4.7.1.2
		gfastProfileDsPsdMaskTone OBJECT-TYPE
			SYNTAX INTEGER (0..4095)
			MAX-ACCESS read-create
			STATUS current
			DESCRIPTION
				"Specifies the gfast Port's Down stream PSD mask Sub-carrier index.
				Unit is 1 sub-carrier (frequency = sub-carier * 51.75kHz"
			::= { gfastProfileDsPsdMaskEntry 2 }

		
		-- 1.3.6.1.4.1.6296.9.102.1.4.7.1.3
		gfastProfileDsPsdMaskPSD OBJECT-TYPE
			SYNTAX INTEGER (0..1400)
			MAX-ACCESS read-create
			STATUS current
			DESCRIPTION
				"Specifies the gfast Port's Down stream PSD mask value.
				Unit is -0.1dB"
			::= { gfastProfileDsPsdMaskEntry 3 }

		
		-- 1.3.6.1.4.1.6296.9.102.1.4.7.1.4
		gfastProfileDsPsdMaskRowStatus OBJECT-TYPE
			SYNTAX EntryStatus
			MAX-ACCESS read-create
			STATUS current
			DESCRIPTION
				"The status of this conceptual row."
			::= { gfastProfileDsPsdMaskEntry 4 }

		
--  *********************************************************************
-- * Profile Upstream Subcarrier Mask Table
-- *********************************************************************
		-- 1.3.6.1.4.1.6296.9.102.1.4.8
		gfastProfileUsCarrierMaskTable OBJECT-TYPE
			SYNTAX SEQUENCE OF GfastProfileUsCarrierMaskEntry
			MAX-ACCESS not-accessible
			STATUS current
			DESCRIPTION
				"This table includes Gfast Profile Upstream Carrier Mask Configuration Table."
			::= { gfastProfileGroup 8 }

		
		-- 1.3.6.1.4.1.6296.9.102.1.4.8.1
		gfastProfileUsCarrierMaskEntry OBJECT-TYPE
			SYNTAX GfastProfileUsCarrierMaskEntry
			MAX-ACCESS not-accessible
			STATUS current
			DESCRIPTION
				"An entry in the gfastProfileUsCarrierMaskTable."
			INDEX { gfastProfileIndex, gfastProfileUsCarrierMaskIndex }
			::= { gfastProfileUsCarrierMaskTable 1 }

		
		GfastProfileUsCarrierMaskEntry ::=
			SEQUENCE { 
				gfastProfileUsCarrierMaskIndex
					INTEGER,
				gfastProfileUsCarrierMaskStartTone
					INTEGER,
				gfastProfileUsCarrierMaskEndTone
					INTEGER,
				gfastProfileUsCarrierMaskRowStatus
					EntryStatus
			 }

		-- 1.3.6.1.4.1.6296.9.102.1.4.8.1.1
		gfastProfileUsCarrierMaskIndex OBJECT-TYPE
			SYNTAX INTEGER
			MAX-ACCESS not-accessible
			STATUS current
			DESCRIPTION
				"The identifier for G.FAST Carrier Mask"
			::= { gfastProfileUsCarrierMaskEntry 1 }

		
		-- 1.3.6.1.4.1.6296.9.102.1.4.8.1.2
		gfastProfileUsCarrierMaskStartTone OBJECT-TYPE
			SYNTAX INTEGER (0..4095)
			MAX-ACCESS read-create
			STATUS current
			DESCRIPTION
				"Specifies the gfast Port's Up stream Carrier mask Sub-carrier start index.
				Unit is 1 sub-carrier (frequency = sub-carier * 51.75kHz"
			::= { gfastProfileUsCarrierMaskEntry 2 }

		
		-- 1.3.6.1.4.1.6296.9.102.1.4.8.1.3
		gfastProfileUsCarrierMaskEndTone OBJECT-TYPE
			SYNTAX INTEGER (0..4095)
			MAX-ACCESS read-create
			STATUS current
			DESCRIPTION
				"Specifies the gfast Port's Up stream Carrier mask Sub-carrier end index.
				Unit is 1 sub-carrier (frequency = sub-carier * 51.75kHz"
			::= { gfastProfileUsCarrierMaskEntry 3 }

		
		-- 1.3.6.1.4.1.6296.9.102.1.4.8.1.4
		gfastProfileUsCarrierMaskRowStatus OBJECT-TYPE
			SYNTAX EntryStatus
			MAX-ACCESS read-create
			STATUS current
			DESCRIPTION
				"The status of this conceptual row."
			::= { gfastProfileUsCarrierMaskEntry 4 }

		
--  *********************************************************************
-- * Profile Downstream Subcarrier Mask Table
-- *********************************************************************
		-- 1.3.6.1.4.1.6296.9.102.1.4.9
		gfastProfileDsCarrierMaskTable OBJECT-TYPE
			SYNTAX SEQUENCE OF GfastProfileDsCarrierMaskEntry
			MAX-ACCESS not-accessible
			STATUS current
			DESCRIPTION
				"This table includes Gfast Profile Downstream Carrier Mask Configuration Table."
			::= { gfastProfileGroup 9 }

		
		-- 1.3.6.1.4.1.6296.9.102.1.4.9.1
		gfastProfileDsCarrierMaskEntry OBJECT-TYPE
			SYNTAX GfastProfileDsCarrierMaskEntry
			MAX-ACCESS not-accessible
			STATUS current
			DESCRIPTION
				"An entry in the gfastProfileDsCarrierMaskTable."
			INDEX { gfastProfileIndex, gfastProfileDsCarrierMaskIndex }
			::= { gfastProfileDsCarrierMaskTable 1 }

		
		GfastProfileDsCarrierMaskEntry ::=
			SEQUENCE { 
				gfastProfileDsCarrierMaskIndex
					INTEGER,
				gfastProfileDsCarrierMaskStartTone
					INTEGER,
				gfastProfileDsCarrierMaskEndTone
					INTEGER,
				gfastProfileDsCarrierMaskRowStatus
					EntryStatus
			 }

		-- 1.3.6.1.4.1.6296.9.102.1.4.9.1.1
		gfastProfileDsCarrierMaskIndex OBJECT-TYPE
			SYNTAX INTEGER
			MAX-ACCESS not-accessible
			STATUS current
			DESCRIPTION
				"The identifier for G.FAST Carrier Mask"
			::= { gfastProfileDsCarrierMaskEntry 1 }

		
		-- 1.3.6.1.4.1.6296.9.102.1.4.9.1.2
		gfastProfileDsCarrierMaskStartTone OBJECT-TYPE
			SYNTAX INTEGER (0..4095)
			MAX-ACCESS read-create
			STATUS current
			DESCRIPTION
				"Specifies the gfast Port's Down stream Carrier mask Sub-carrier start index.
				Unit is 1 sub-carrier (frequency = sub-carier * 51.75kHz"
			::= { gfastProfileDsCarrierMaskEntry 2 }

		
		-- 1.3.6.1.4.1.6296.9.102.1.4.9.1.3
		gfastProfileDsCarrierMaskEndTone OBJECT-TYPE
			SYNTAX INTEGER (0..4095)
			MAX-ACCESS read-create
			STATUS current
			DESCRIPTION
				"Specifies the gfast Port's Down stream Carrier mask Sub-carrier end index.
				Unit is 1 sub-carrier (frequency = sub-carier * 51.75kHz"
			::= { gfastProfileDsCarrierMaskEntry 3 }

		
		-- 1.3.6.1.4.1.6296.9.102.1.4.9.1.4
		gfastProfileDsCarrierMaskRowStatus OBJECT-TYPE
			SYNTAX EntryStatus
			MAX-ACCESS read-create
			STATUS current
			DESCRIPTION
				"The status of this conceptual row."
			::= { gfastProfileDsCarrierMaskEntry 4 }

		
--  *********************************************************************
-- * Profile RFI Notching Table
-- *********************************************************************
		-- 1.3.6.1.4.1.6296.9.102.1.4.10
		gfastProfileRfiNotchTable OBJECT-TYPE
			SYNTAX SEQUENCE OF GfastProfileRfiNotchEntry
			MAX-ACCESS not-accessible
			STATUS current
			DESCRIPTION
				"This table includes Gfast Profile RFI notching Configuration Table."
			::= { gfastProfileGroup 10 }

		
		-- 1.3.6.1.4.1.6296.9.102.1.4.10.1
		gfastProfileRfiNotchEntry OBJECT-TYPE
			SYNTAX GfastProfileRfiNotchEntry
			MAX-ACCESS not-accessible
			STATUS current
			DESCRIPTION
				"An entry in the gfastProfileRfiNotchTable."
			INDEX { gfastProfileIndex, gfastProfileRfiNotchIndex }
			::= { gfastProfileRfiNotchTable 1 }

		
		GfastProfileRfiNotchEntry ::=
			SEQUENCE { 
				gfastProfileRfiNotchIndex
					INTEGER,
				gfastProfileRfiNotchStartTone
					INTEGER,
				gfastProfileRfiNotchEndTone
					INTEGER,
				gfastProfileRfiNotchRowStatus
					EntryStatus
			 }

		-- 1.3.6.1.4.1.6296.9.102.1.4.10.1.1
		gfastProfileRfiNotchIndex OBJECT-TYPE
			SYNTAX INTEGER
			MAX-ACCESS not-accessible
			STATUS current
			DESCRIPTION
				"The identifier for G.FAST RFI notching"
			::= { gfastProfileRfiNotchEntry 1 }

		
		-- 1.3.6.1.4.1.6296.9.102.1.4.10.1.2
		gfastProfileRfiNotchStartTone OBJECT-TYPE
			SYNTAX INTEGER (0..4095)
			MAX-ACCESS read-create
			STATUS current
			DESCRIPTION
				"Specifies the gfast Port's Notching Sub-carrier start index.
				Unit is 1 sub-carrier (frequency = sub-carier * 51.75kHz"
			::= { gfastProfileRfiNotchEntry 2 }

		
		-- 1.3.6.1.4.1.6296.9.102.1.4.10.1.3
		gfastProfileRfiNotchEndTone OBJECT-TYPE
			SYNTAX INTEGER (0..4095)
			MAX-ACCESS read-create
			STATUS current
			DESCRIPTION
				"Specifies the gfast Port's Notching Sub-carrier end index.
				Unit is 1 sub-carrier (frequency = sub-carier * 51.75kHz"
			::= { gfastProfileRfiNotchEntry 3 }

		
		-- 1.3.6.1.4.1.6296.9.102.1.4.10.1.4
		gfastProfileRfiNotchRowStatus OBJECT-TYPE
			SYNTAX EntryStatus
			MAX-ACCESS read-create
			STATUS current
			DESCRIPTION
				"The status of this conceptual row."
			::= { gfastProfileRfiNotchEntry 4 }

		
		-- 1.3.6.1.4.1.6296.9.102.1.5
		vdslProfileGroup OBJECT IDENTIFIER ::= { gfastGroup 5 }

		
--  *********************************************************************
-- * vdslProfileGroup
-- *********************************************************************
-- *********************************************************************
-- * Profile Table Group
-- *********************************************************************
		-- 1.3.6.1.4.1.6296.9.102.1.5.1
		vdslProfileTable OBJECT-TYPE
			SYNTAX SEQUENCE OF VdslProfileEntry
			MAX-ACCESS not-accessible
			STATUS current
			DESCRIPTION
				"This table includes Vdsl Profile Configuration Table."
			::= { vdslProfileGroup 1 }

		
		-- 1.3.6.1.4.1.6296.9.102.1.5.1.1
		vdslProfileEntry OBJECT-TYPE
			SYNTAX VdslProfileEntry
			MAX-ACCESS not-accessible
			STATUS current
			DESCRIPTION
				"An entry in the vdslProfileTable."
			INDEX { vdslProfileIndex }
			::= { vdslProfileTable 1 }

		
		VdslProfileEntry ::=
			SEQUENCE { 
				vdslProfileIndex
					INTEGER,
				vdslProfileName
					DisplayString,
				vdslProfileShape
					INTEGER,
				vdslProfileBitmap8a
					INTEGER,
				vdslProfileBitmap8b
					INTEGER,
				vdslProfileBitmap8c
					INTEGER,
				vdslProfileBitmap8d
					INTEGER,
				vdslProfileBitmap12a
					INTEGER,
				vdslProfileBitmap12b
					INTEGER,
				vdslProfileBitmap17a
					INTEGER,
				vdslProfileBitmap30a
					INTEGER,
				vdslProfileMaxTxPower
					INTEGER,
				vdslProfileMaxRxPower
					INTEGER,
				vdslProfileUsTargetMargin
					INTEGER,
				vdslProfileDsTargetMargin
					INTEGER,
				vdslProfileUsMaxMargin
					INTEGER,
				vdslProfileDsMaxMargin
					INTEGER,
				vdslProfileUsMinMargin
					INTEGER,
				vdslProfileDsMinMargin
					INTEGER,
				vdslProfileUsSraMode
					INTEGER,
				vdslProfileDsSraMode
					INTEGER,
				vdslProfileUsUpShiftMargin
					INTEGER,
				vdslProfileUsDownShiftMargin
					INTEGER,
				vdslProfileDsUpShiftMargin
					INTEGER,
				vdslProfileDsDownShiftMargin
					INTEGER,
				vdslProfileUsUpShiftInterval
					INTEGER,
				vdslProfileUsDownShiftInterval
					INTEGER,
				vdslProfileDsUpShiftInterval
					INTEGER,
				vdslProfileDsDownShiftInterval
					INTEGER,
				vdslProfileUsRtxEtrMin
					INTEGER,
				vdslProfileDsRtxEtrMin
					INTEGER,
				vdslProfileUsRtxEtrMax
					INTEGER,
				vdslProfileDsRtxEtrMax
					INTEGER,
				vdslProfileUsRtxMaxNdr
					INTEGER,
				vdslProfileDsRtxMaxNdr
					INTEGER,
				vdslProfileUsRtxMaxDelay
					INTEGER,
				vdslProfileDsRtxMaxDelay
					INTEGER,
				vdslProfileUsRtxMinDelay
					INTEGER,
				vdslProfileDsRtxMinDelay
					INTEGER,
				vdslProfileUsRtxInpMinShine
					INTEGER,
				vdslProfileDsRtxInpMinShine
					INTEGER,
				vdslProfileUsRtxShineRatio
					INTEGER,
				vdslProfileDsRtxShineRatio
					INTEGER,
				vdslProfileUsRtxInpMinRein
					INTEGER,
				vdslProfileDsRtxInpMinRein
					INTEGER,
				vdslProfileUsRtxReinFrequency
					INTEGER,
				vdslProfileDsRtxReinFrequency
					INTEGER,
				vdslProfileUsRtxIatRnRatio
					INTEGER,
				vdslProfileDsRtxIatRnRatio
					INTEGER,
				vdslProfileUsSosMode
					INTEGER,
				vdslProfileDsSosMode
					INTEGER,
				vdslProfileUsSosMinRate
					INTEGER,
				vdslProfileDsSosMinRate
					INTEGER,
				vdslProfileUsSosTime
					INTEGER,
				vdslProfileDsSosTime
					INTEGER,
				vdslProfileUsSosCrc
					INTEGER,
				vdslProfileDsSosCrc
					INTEGER,
				vdslProfileUsSosNtone
					INTEGER,
				vdslProfileDsSosNtone
					INTEGER,
				vdslProfileUsSosMax
					INTEGER,
				vdslProfileDsSosMax
					INTEGER,
				vdslProfileUpboMode
					INTEGER,
				vdslProfileUpboAValue1
					INTEGER,
				vdslProfileUpboBValue1
					INTEGER,
				vdslProfileUpboKl01
					INTEGER,
				vdslProfileUpboAValue2
					INTEGER,
				vdslProfileUpboBValue2
					INTEGER,
				vdslProfileUpboKl02
					INTEGER,
				vdslProfileUpboAValue3
					INTEGER,
				vdslProfileUpboBValue3
					INTEGER,
				vdslProfileUpboKl03
					INTEGER,
				vdslProfileUpboAValue4
					INTEGER,
				vdslProfileUpboBValue4
					INTEGER,
				vdslProfileUpboKl04
					INTEGER,
				vdslProfilePtmMode
					INTEGER
			 }

		-- 1.3.6.1.4.1.6296.9.102.1.5.1.1.1
		vdslProfileIndex OBJECT-TYPE
			SYNTAX INTEGER (1..20)
			MAX-ACCESS read-only
			STATUS current
			DESCRIPTION
				"Specifies the VDSL System's Profile index."
			::= { vdslProfileEntry 1 }

		
		-- 1.3.6.1.4.1.6296.9.102.1.5.1.1.2
		vdslProfileName OBJECT-TYPE
			SYNTAX DisplayString (SIZE (0..16))
			MAX-ACCESS read-only
			STATUS current
			DESCRIPTION
				"Defines the Profile Name.
				It ranges from 1 to 16"
			::= { vdslProfileEntry 2 }

		
		-- 1.3.6.1.4.1.6296.9.102.1.5.1.1.3
		vdslProfileShape OBJECT-TYPE
			SYNTAX INTEGER
				{
				shape_30a-138(1),
				shape_30a-276(2),
				shape_17a-138(3),
				shape_17a-276(4),
				shape_30a-TCMISDN(5)
				}
			MAX-ACCESS read-write
			STATUS current
			DESCRIPTION
				"Specifies the vdsl profile shape."
			::= { vdslProfileEntry 3 }

		
		-- 1.3.6.1.4.1.6296.9.102.1.5.1.1.4
		vdslProfileBitmap8a OBJECT-TYPE
			SYNTAX INTEGER
				{
				disable(0),
				enable(1)
				}
			MAX-ACCESS read-write
			STATUS current
			DESCRIPTION
				"Specifies the VDSL profile 8a protocol."
			::= { vdslProfileEntry 4 }

		
		-- 1.3.6.1.4.1.6296.9.102.1.5.1.1.5
		vdslProfileBitmap8b OBJECT-TYPE
			SYNTAX INTEGER
				{
				disable(0),
				enable(1)
				}
			MAX-ACCESS read-write
			STATUS current
			DESCRIPTION
				"Specifies the VDSL profile 8b protocol."
			::= { vdslProfileEntry 5 }

		
		-- 1.3.6.1.4.1.6296.9.102.1.5.1.1.6
		vdslProfileBitmap8c OBJECT-TYPE
			SYNTAX INTEGER
				{
				disable(0),
				enable(1)
				}
			MAX-ACCESS read-write
			STATUS current
			DESCRIPTION
				"Specifies the VDSL profile 8c protocol."
			::= { vdslProfileEntry 6 }

		
		-- 1.3.6.1.4.1.6296.9.102.1.5.1.1.7
		vdslProfileBitmap8d OBJECT-TYPE
			SYNTAX INTEGER
				{
				disable(0),
				enable(1)
				}
			MAX-ACCESS read-write
			STATUS current
			DESCRIPTION
				"Specifies the VDSL profile 8d protocol."
			::= { vdslProfileEntry 7 }

		
		-- 1.3.6.1.4.1.6296.9.102.1.5.1.1.8
		vdslProfileBitmap12a OBJECT-TYPE
			SYNTAX INTEGER
				{
				disable(0),
				enable(1)
				}
			MAX-ACCESS read-write
			STATUS current
			DESCRIPTION
				"Specifies the VDSL profile 12a protocol."
			::= { vdslProfileEntry 8 }

		
		-- 1.3.6.1.4.1.6296.9.102.1.5.1.1.9
		vdslProfileBitmap12b OBJECT-TYPE
			SYNTAX INTEGER
				{
				disable(0),
				enable(1)
				}
			MAX-ACCESS read-write
			STATUS current
			DESCRIPTION
				"Specifies the VDSL profile 12b protocol."
			::= { vdslProfileEntry 9 }

		
		-- 1.3.6.1.4.1.6296.9.102.1.5.1.1.10
		vdslProfileBitmap17a OBJECT-TYPE
			SYNTAX INTEGER
				{
				disable(0),
				enable(1)
				}
			MAX-ACCESS read-write
			STATUS current
			DESCRIPTION
				"Specifies the VDSL profile 17a protocol."
			::= { vdslProfileEntry 10 }

		
		-- 1.3.6.1.4.1.6296.9.102.1.5.1.1.11
		vdslProfileBitmap30a OBJECT-TYPE
			SYNTAX INTEGER
				{
				disable(0),
				enable(1)
				}
			MAX-ACCESS read-write
			STATUS current
			DESCRIPTION
				"Specifies the VDSL profile 30a protocol."
			::= { vdslProfileEntry 11 }

		
		-- 1.3.6.1.4.1.6296.9.102.1.5.1.1.12
		vdslProfileMaxTxPower OBJECT-TYPE
			SYNTAX INTEGER (-256..40)
			MAX-ACCESS read-write
			STATUS current
			DESCRIPTION
				"Specifies the vdsl maximum downstream transmit power. 
				It range from -256 to 40 units is 0.1dBm."
			::= { vdslProfileEntry 12 }

		
		-- 1.3.6.1.4.1.6296.9.102.1.5.1.1.13
		vdslProfileMaxRxPower OBJECT-TYPE
			SYNTAX INTEGER (-256..256)
			MAX-ACCESS read-write
			STATUS current
			DESCRIPTION
				"Specifies the vdsl maximum upstream receive power. 
				It range from -256 to 256 units is 0.1dBm."
			::= { vdslProfileEntry 13 }

		
		-- 1.3.6.1.4.1.6296.9.102.1.5.1.1.14
		vdslProfileUsTargetMargin OBJECT-TYPE
			SYNTAX INTEGER (0..310)
			MAX-ACCESS read-write
			STATUS current
			DESCRIPTION
				"Specifies the vdsl Port's Up stream Target noise margin. 
				It range from 0 to 310 units is 0.1 dB "
			::= { vdslProfileEntry 14 }

		
		-- 1.3.6.1.4.1.6296.9.102.1.5.1.1.15
		vdslProfileDsTargetMargin OBJECT-TYPE
			SYNTAX INTEGER (0..310)
			MAX-ACCESS read-write
			STATUS current
			DESCRIPTION
				"Specifies the vdsl Port's Down stream Target noise margin. 
				It range from 0 to 310 units is 0.1 dB "
			::= { vdslProfileEntry 15 }

		
		-- 1.3.6.1.4.1.6296.9.102.1.5.1.1.16
		vdslProfileUsMaxMargin OBJECT-TYPE
			SYNTAX INTEGER (-1..310)
			MAX-ACCESS read-write
			STATUS current
			DESCRIPTION
				"Specifies the vdsl Port's Up stream Max noise margin. 
				It range from -1 to 310 units is 0.1 dB "
			::= { vdslProfileEntry 16 }

		
		-- 1.3.6.1.4.1.6296.9.102.1.5.1.1.17
		vdslProfileDsMaxMargin OBJECT-TYPE
			SYNTAX INTEGER (-1..310)
			MAX-ACCESS read-write
			STATUS current
			DESCRIPTION
				"Specifies the vdsl Port's Down stream Max noise margin. 
				It range from -1 to 310 units is 0.1 dB "
			::= { vdslProfileEntry 17 }

		
		-- 1.3.6.1.4.1.6296.9.102.1.5.1.1.18
		vdslProfileUsMinMargin OBJECT-TYPE
			SYNTAX INTEGER (0..310)
			MAX-ACCESS read-write
			STATUS current
			DESCRIPTION
				"Specifies the vdsl Port's Up stream Min noise margin. 
				It range from 0 to 310 units is 0.1 dB "
			::= { vdslProfileEntry 18 }

		
		-- 1.3.6.1.4.1.6296.9.102.1.5.1.1.19
		vdslProfileDsMinMargin OBJECT-TYPE
			SYNTAX INTEGER (0..310)
			MAX-ACCESS read-write
			STATUS current
			DESCRIPTION
				"Specifies the vdsl Port's Down stream Min noise margin. 
				It range from 0 to 310 units is 0.1 dB "
			::= { vdslProfileEntry 19 }

		
		-- 1.3.6.1.4.1.6296.9.102.1.5.1.1.20
		vdslProfileUsSraMode OBJECT-TYPE
			SYNTAX INTEGER
				{
				disable(0),
				enable(1)
				}
			MAX-ACCESS read-write
			STATUS current
			DESCRIPTION
				"Specifies to enable vdsl Seamless Rate Adaptation(SRA) in the upstream."
			::= { vdslProfileEntry 20 }

		
		-- 1.3.6.1.4.1.6296.9.102.1.5.1.1.21
		vdslProfileDsSraMode OBJECT-TYPE
			SYNTAX INTEGER
				{
				disable(0),
				enable(1)
				}
			MAX-ACCESS read-write
			STATUS current
			DESCRIPTION
				"Specifies to enable vdsl Seamless Rate Adaptation(SRA) in the downstream."
			::= { vdslProfileEntry 21 }

		
		-- 1.3.6.1.4.1.6296.9.102.1.5.1.1.22
		vdslProfileUsUpShiftMargin OBJECT-TYPE
			SYNTAX INTEGER (0..310)
			MAX-ACCESS read-write
			STATUS current
			DESCRIPTION
				"Specifies the vdsl Port's Up stream up-shift noise margin. 
				It range from 0 to 310 units is 0.1 dB"
			::= { vdslProfileEntry 22 }

		
		-- 1.3.6.1.4.1.6296.9.102.1.5.1.1.23
		vdslProfileUsDownShiftMargin OBJECT-TYPE
			SYNTAX INTEGER (0..310)
			MAX-ACCESS read-write
			STATUS current
			DESCRIPTION
				"Specifies the vdsl Port's Up stream down-shift noise margin. 
				It range from 0 to 310 units is 0.1 dB"
			::= { vdslProfileEntry 23 }

		
		-- 1.3.6.1.4.1.6296.9.102.1.5.1.1.24
		vdslProfileDsUpShiftMargin OBJECT-TYPE
			SYNTAX INTEGER (0..310)
			MAX-ACCESS read-write
			STATUS current
			DESCRIPTION
				"Specifies the vdsl Port's Down stream up-shift noise margin. 
				It range from 0 to 310 units is 0.1 dB"
			::= { vdslProfileEntry 24 }

		
		-- 1.3.6.1.4.1.6296.9.102.1.5.1.1.25
		vdslProfileDsDownShiftMargin OBJECT-TYPE
			SYNTAX INTEGER (0..310)
			MAX-ACCESS read-write
			STATUS current
			DESCRIPTION
				"Specifies the vdsl Port's Down stream down-shift noise margin. 
				It range from 0 to 310 units is 0.1 dB"
			::= { vdslProfileEntry 25 }

		
		-- 1.3.6.1.4.1.6296.9.102.1.5.1.1.26
		vdslProfileUsUpShiftInterval OBJECT-TYPE
			SYNTAX INTEGER (0..16383)
			MAX-ACCESS read-write
			STATUS current
			DESCRIPTION
				"Specifies the vdsl Port's Up stream up-shift time interval. 
				It range from 0 to 16383 units is 1sec"
			::= { vdslProfileEntry 26 }

		
		-- 1.3.6.1.4.1.6296.9.102.1.5.1.1.27
		vdslProfileUsDownShiftInterval OBJECT-TYPE
			SYNTAX INTEGER (0..16383)
			MAX-ACCESS read-write
			STATUS current
			DESCRIPTION
				"Specifies the vdsl Port's Up stream down-shift time interval. 
				It range from 0 to 16383 units is 1sec"
			::= { vdslProfileEntry 27 }

		
		-- 1.3.6.1.4.1.6296.9.102.1.5.1.1.28
		vdslProfileDsUpShiftInterval OBJECT-TYPE
			SYNTAX INTEGER (0..16383)
			MAX-ACCESS read-write
			STATUS current
			DESCRIPTION
				"Specifies the vdsl Port's Down stream up-shift time interval. 
				It range from 0 to 16383 units is 1sec"
			::= { vdslProfileEntry 28 }

		
		-- 1.3.6.1.4.1.6296.9.102.1.5.1.1.29
		vdslProfileDsDownShiftInterval OBJECT-TYPE
			SYNTAX INTEGER (0..16383)
			MAX-ACCESS read-write
			STATUS current
			DESCRIPTION
				"Specifies the vdsl Port's Down stream down-shift time interval. 
				It range from 0 to 16383 units is 1sec"
			::= { vdslProfileEntry 29 }

		
		-- 1.3.6.1.4.1.6296.9.102.1.5.1.1.30
		vdslProfileUsRtxEtrMin OBJECT-TYPE
			SYNTAX INTEGER (64..512000)
			MAX-ACCESS read-write
			STATUS current
			DESCRIPTION
				"Specifies the vdsl Port's upstream minimum value of the ETR.
				It range from 64 to 512000 units is 1Kbps."
			::= { vdslProfileEntry 30 }

		
		-- 1.3.6.1.4.1.6296.9.102.1.5.1.1.31
		vdslProfileDsRtxEtrMin OBJECT-TYPE
			SYNTAX INTEGER (64..512000)
			MAX-ACCESS read-write
			STATUS current
			DESCRIPTION
				"Specifies the vdsl Port's downstream minimum value of the ETR. 
				It range from 64 to 512000 units is 1Kbps."
			::= { vdslProfileEntry 31 }

		
		-- 1.3.6.1.4.1.6296.9.102.1.5.1.1.32
		vdslProfileUsRtxEtrMax OBJECT-TYPE
			SYNTAX INTEGER (64..512000)
			MAX-ACCESS read-write
			STATUS current
			DESCRIPTION
				"Specifies the vdsl Port's upstream maximum value of the ETR. 
				It range from 64 to 512000 units is 1Kbps."
			::= { vdslProfileEntry 32 }

		
		-- 1.3.6.1.4.1.6296.9.102.1.5.1.1.33
		vdslProfileDsRtxEtrMax OBJECT-TYPE
			SYNTAX INTEGER (64..512000)
			MAX-ACCESS read-write
			STATUS current
			DESCRIPTION
				"Specifies the vdsl Port's downstream maximum value of the ETR. 
				It range from 64 to 512000 units is 1Kbps."
			::= { vdslProfileEntry 33 }

		
		-- 1.3.6.1.4.1.6296.9.102.1.5.1.1.34
		vdslProfileUsRtxMaxNdr OBJECT-TYPE
			SYNTAX INTEGER (64..512000)
			MAX-ACCESS read-write
			STATUS current
			DESCRIPTION
				"Specifies the vdsl Port's upstream maximum data rate. 
				It range from 64 to 512000 units is 1Kbps."
			::= { vdslProfileEntry 34 }

		
		-- 1.3.6.1.4.1.6296.9.102.1.5.1.1.35
		vdslProfileDsRtxMaxNdr OBJECT-TYPE
			SYNTAX INTEGER (64..512000)
			MAX-ACCESS read-write
			STATUS current
			DESCRIPTION
				"Specifies the vdsl Port's downstream maximum data rate. 
				It range from 64 to 512000 units is 1Kbps."
			::= { vdslProfileEntry 35 }

		
		-- 1.3.6.1.4.1.6296.9.102.1.5.1.1.36
		vdslProfileUsRtxMaxDelay OBJECT-TYPE
			SYNTAX INTEGER (0..63)
			MAX-ACCESS read-write
			STATUS current
			DESCRIPTION
				"Specifies the vdsl Port's upstream maximum delay. 
				It range from 0 to 64 units is 1msec."
			::= { vdslProfileEntry 36 }

		
		-- 1.3.6.1.4.1.6296.9.102.1.5.1.1.37
		vdslProfileDsRtxMaxDelay OBJECT-TYPE
			SYNTAX INTEGER (0..63)
			MAX-ACCESS read-write
			STATUS current
			DESCRIPTION
				"Specifies the vdsl Port's downstream maximum delay. 
				It range from 0 to 64 units is 1msec."
			::= { vdslProfileEntry 37 }

		
		-- 1.3.6.1.4.1.6296.9.102.1.5.1.1.38
		vdslProfileUsRtxMinDelay OBJECT-TYPE
			SYNTAX INTEGER (0..63)
			MAX-ACCESS read-write
			STATUS current
			DESCRIPTION
				"Specifies the vdsl Port's upstream minimum delay. 
				It range from 0 to 64 units is 1msec."
			::= { vdslProfileEntry 38 }

		
		-- 1.3.6.1.4.1.6296.9.102.1.5.1.1.39
		vdslProfileDsRtxMinDelay OBJECT-TYPE
			SYNTAX INTEGER (0..63)
			MAX-ACCESS read-write
			STATUS current
			DESCRIPTION
				"Specifies the vdsl Port's downstream minimum delay. 
				It range from 0 to 64 units is 1msec."
			::= { vdslProfileEntry 39 }

		
		-- 1.3.6.1.4.1.6296.9.102.1.5.1.1.40
		vdslProfileUsRtxInpMinShine OBJECT-TYPE
			SYNTAX INTEGER (0..126)
			MAX-ACCESS read-write
			STATUS current
			DESCRIPTION
				"Specifies the vdsl Port's Up stream minimum impulse noise protection against SHINE. 
				It range from 0 to 126 units is a half DMT symbol"
			::= { vdslProfileEntry 40 }

		
		-- 1.3.6.1.4.1.6296.9.102.1.5.1.1.41
		vdslProfileDsRtxInpMinShine OBJECT-TYPE
			SYNTAX INTEGER (0..126)
			MAX-ACCESS read-write
			STATUS current
			DESCRIPTION
				"Specifies the vdsl Port's Down stream minimum impulse noise protection against SHINE. 
				It range from 0 to 126 units is a half DMT symbol"
			::= { vdslProfileEntry 41 }

		
		-- 1.3.6.1.4.1.6296.9.102.1.5.1.1.42
		vdslProfileUsRtxShineRatio OBJECT-TYPE
			SYNTAX INTEGER (0..255)
			MAX-ACCESS read-write
			STATUS current
			DESCRIPTION
				"Specifies the vdsl Port's Up stream SHINE ratio. 
				It range from 0 to 255 units is 0.001"
			::= { vdslProfileEntry 42 }

		
		-- 1.3.6.1.4.1.6296.9.102.1.5.1.1.43
		vdslProfileDsRtxShineRatio OBJECT-TYPE
			SYNTAX INTEGER (0..255)
			MAX-ACCESS read-write
			STATUS current
			DESCRIPTION
				"Specifies the vdsl Port's Down stream SHINE ratio. 
				It range from 0 to 255 units is 0.001"
			::= { vdslProfileEntry 43 }

		
		-- 1.3.6.1.4.1.6296.9.102.1.5.1.1.44
		vdslProfileUsRtxInpMinRein OBJECT-TYPE
			SYNTAX INTEGER (0..7)
			MAX-ACCESS read-write
			STATUS current
			DESCRIPTION
				"Specifies the vdsl Port's Up stream minimum impulse noise protection against REIN. 
				It range from 0 to 7 units is 1/2 symbol at 4kHz."
			::= { vdslProfileEntry 44 }

		
		-- 1.3.6.1.4.1.6296.9.102.1.5.1.1.45
		vdslProfileDsRtxInpMinRein OBJECT-TYPE
			SYNTAX INTEGER (0..7)
			MAX-ACCESS read-write
			STATUS current
			DESCRIPTION
				"Specifies the vdsl Port's Down stream minimum impulse noise protection against REIN. 
				It range from 0 to 7 units is 1/2 symbol at 4kHz."
			::= { vdslProfileEntry 45 }

		
		-- 1.3.6.1.4.1.6296.9.102.1.5.1.1.46
		vdslProfileUsRtxReinFrequency OBJECT-TYPE
			SYNTAX INTEGER
				{
				hz100(5),
				hz120(6)
				}
			MAX-ACCESS read-write
			STATUS current
			DESCRIPTION
				"Specifies the vdsl Port's Up stream rein frequency."
			::= { vdslProfileEntry 46 }

		
		-- 1.3.6.1.4.1.6296.9.102.1.5.1.1.47
		vdslProfileDsRtxReinFrequency OBJECT-TYPE
			SYNTAX INTEGER
				{
				hz100(5),
				hz120(6)
				}
			MAX-ACCESS read-write
			STATUS current
			DESCRIPTION
				"Specifies the vdsl Port's Down stream rein frequency."
			::= { vdslProfileEntry 47 }

		
		-- 1.3.6.1.4.1.6296.9.102.1.5.1.1.48
		vdslProfileUsRtxIatRnRatio OBJECT-TYPE
			SYNTAX INTEGER (0..64)
			MAX-ACCESS read-write
			STATUS current
			DESCRIPTION
				"Specifies the vdsl Port's Up stream minimum ratio R/N.
				It range from 0 to 64 unit is 1/256"
			::= { vdslProfileEntry 48 }

		
		-- 1.3.6.1.4.1.6296.9.102.1.5.1.1.49
		vdslProfileDsRtxIatRnRatio OBJECT-TYPE
			SYNTAX INTEGER (0..64)
			MAX-ACCESS read-write
			STATUS current
			DESCRIPTION
				"Specifies the vdsl Port's Down stream minimum ratio R/N.
				It range from 0 to 64 unit is 1/256"
			::= { vdslProfileEntry 49 }

		
		-- 1.3.6.1.4.1.6296.9.102.1.5.1.1.50
		vdslProfileUsSosMode OBJECT-TYPE
			SYNTAX INTEGER
				{
				disable(0),
				enable(1)
				}
			MAX-ACCESS read-write
			STATUS current
			DESCRIPTION
				"Specifies to enable vdsl port's upstream SOS mode."
			::= { vdslProfileEntry 50 }

		
		-- 1.3.6.1.4.1.6296.9.102.1.5.1.1.51
		vdslProfileDsSosMode OBJECT-TYPE
			SYNTAX INTEGER
				{
				disable(0),
				enable(1)
				}
			MAX-ACCESS read-write
			STATUS current
			DESCRIPTION
				"Specifies to enable vdsl port's downstream SOS mode."
			::= { vdslProfileEntry 51 }

		
		-- 1.3.6.1.4.1.6296.9.102.1.5.1.1.52
		vdslProfileUsSosMinRate OBJECT-TYPE
			SYNTAX INTEGER (0..100000)
			MAX-ACCESS read-write
			STATUS current
			DESCRIPTION
				"Specifies the vdsl Port's upstream minimum bearer rate. 
				It range from 0 to 100000 units is 1kbps."
			::= { vdslProfileEntry 52 }

		
		-- 1.3.6.1.4.1.6296.9.102.1.5.1.1.53
		vdslProfileDsSosMinRate OBJECT-TYPE
			SYNTAX INTEGER (0..100000)
			MAX-ACCESS read-write
			STATUS current
			DESCRIPTION
				"Specifies the vdsl Port's downstream minimum bearer rate. 
				It range from 0 to 100000 units is 1kbps."
			::= { vdslProfileEntry 53 }

		
		-- 1.3.6.1.4.1.6296.9.102.1.5.1.1.54
		vdslProfileUsSosTime OBJECT-TYPE
			SYNTAX INTEGER (64..16320)
			MAX-ACCESS read-write
			STATUS current
			DESCRIPTION
				"Specifies the vdsl Port's Up stream SOS monitering time window. 
				It range from 64 to 16320 units is 1ms."
			::= { vdslProfileEntry 54 }

		
		-- 1.3.6.1.4.1.6296.9.102.1.5.1.1.55
		vdslProfileDsSosTime OBJECT-TYPE
			SYNTAX INTEGER (64..16320)
			MAX-ACCESS read-write
			STATUS current
			DESCRIPTION
				"Specifies the vdsl Port's Down stream SOS monitering time window. 
				It range from 64 to 16320 units is 1ms."
			::= { vdslProfileEntry 55 }

		
		-- 1.3.6.1.4.1.6296.9.102.1.5.1.1.56
		vdslProfileUsSosCrc OBJECT-TYPE
			SYNTAX INTEGER (0..65535)
			MAX-ACCESS read-write
			STATUS current
			DESCRIPTION
				"Specifies the vdsl Port's Up stream SOS CRC trigger condition. 
				It range from 0 to 65535 units is 0.02."
			::= { vdslProfileEntry 56 }

		
		-- 1.3.6.1.4.1.6296.9.102.1.5.1.1.57
		vdslProfileDsSosCrc OBJECT-TYPE
			SYNTAX INTEGER (0..65535)
			MAX-ACCESS read-write
			STATUS current
			DESCRIPTION
				"Specifies the vdsl Port's Down stream SOS CRC trigger condition. 
				It range from 0 to 65535 units is 0.02."
			::= { vdslProfileEntry 57 }

		
		-- 1.3.6.1.4.1.6296.9.102.1.5.1.1.58
		vdslProfileUsSosNtone OBJECT-TYPE
			SYNTAX INTEGER (0..100)
			MAX-ACCESS read-write
			STATUS current
			DESCRIPTION
				"Specifies the vdsl Port's Up stream SOS tone degraded condition. 
				It range from 0 to 100 units is percent."
			::= { vdslProfileEntry 58 }

		
		-- 1.3.6.1.4.1.6296.9.102.1.5.1.1.59
		vdslProfileDsSosNtone OBJECT-TYPE
			SYNTAX INTEGER (0..100)
			MAX-ACCESS read-write
			STATUS current
			DESCRIPTION
				"Specifies the vdsl Port's Down stream SOS tone degraded condition. 
				It range from 0 to 100 units is percent."
			::= { vdslProfileEntry 59 }

		
		-- 1.3.6.1.4.1.6296.9.102.1.5.1.1.60
		vdslProfileUsSosMax OBJECT-TYPE
			SYNTAX INTEGER (0..15)
			MAX-ACCESS read-write
			STATUS current
			DESCRIPTION
				"Specifies the vdsl Port's Up stream maximum number of
				successful SOS procedures in 120 seconds interval. 
				It range from 0 to 15."
			::= { vdslProfileEntry 60 }

		
		-- 1.3.6.1.4.1.6296.9.102.1.5.1.1.61
		vdslProfileDsSosMax OBJECT-TYPE
			SYNTAX INTEGER (0..15)
			MAX-ACCESS read-write
			STATUS current
			DESCRIPTION
				"Specifies the vdsl Port's Down stream maximum number of
				successful SOS procedures in 120 seconds interval. 
				It range from 0 to 15."
			::= { vdslProfileEntry 61 }

		
		-- 1.3.6.1.4.1.6296.9.102.1.5.1.1.62
		vdslProfileUpboMode OBJECT-TYPE
			SYNTAX INTEGER
				{
				disable(0),
				enable(1)
				}
			MAX-ACCESS read-write
			STATUS current
			DESCRIPTION
				"The identifier for VDSL UPBO"
			::= { vdslProfileEntry 62 }

		
		-- 1.3.6.1.4.1.6296.9.102.1.5.1.1.63
		vdslProfileUpboAValue1 OBJECT-TYPE
			SYNTAX INTEGER (10240..20725)
			MAX-ACCESS read-write
			STATUS current
			DESCRIPTION
				"Specifies the vdsl Port's UPBO a value.
				Unit is -1/256"
			::= { vdslProfileEntry 63 }

		
		-- 1.3.6.1.4.1.6296.9.102.1.5.1.1.64
		vdslProfileUpboBValue1 OBJECT-TYPE
			SYNTAX INTEGER (0..10485)
			MAX-ACCESS read-write
			STATUS current
			DESCRIPTION
				"Specifies the vdsl Port's UPBO b value.
				Unit is -1/256"
			::= { vdslProfileEntry 64 }

		
		-- 1.3.6.1.4.1.6296.9.102.1.5.1.1.65
		vdslProfileUpboKl01 OBJECT-TYPE
			SYNTAX INTEGER (0..635)
			MAX-ACCESS read-write
			STATUS current
			DESCRIPTION
				"Specifies the vdsl Port's UPBO Electrical length estimation.
				value is 0 or 18 ~ 635. Unit is 0.1db"
			::= { vdslProfileEntry 65 }

		
		-- 1.3.6.1.4.1.6296.9.102.1.5.1.1.66
		vdslProfileUpboAValue2 OBJECT-TYPE
			SYNTAX INTEGER (10240..20725)
			MAX-ACCESS read-write
			STATUS current
			DESCRIPTION
				"Specifies the vdsl Port's UPBO a value.
				Unit is -1/256"
			::= { vdslProfileEntry 66 }

		
		-- 1.3.6.1.4.1.6296.9.102.1.5.1.1.67
		vdslProfileUpboBValue2 OBJECT-TYPE
			SYNTAX INTEGER (0..10485)
			MAX-ACCESS read-write
			STATUS current
			DESCRIPTION
				"Specifies the vdsl Port's UPBO b value.
				Unit is -1/256"
			::= { vdslProfileEntry 67 }

		
		-- 1.3.6.1.4.1.6296.9.102.1.5.1.1.68
		vdslProfileUpboKl02 OBJECT-TYPE
			SYNTAX INTEGER (0..635)
			MAX-ACCESS read-write
			STATUS current
			DESCRIPTION
				"Specifies the vdsl Port's UPBO Electrical length estimation.
				value is 0 or 18 ~ 635. Unit is 0.1db"
			::= { vdslProfileEntry 68 }

		
		-- 1.3.6.1.4.1.6296.9.102.1.5.1.1.69
		vdslProfileUpboAValue3 OBJECT-TYPE
			SYNTAX INTEGER (10240..20725)
			MAX-ACCESS read-write
			STATUS current
			DESCRIPTION
				"Specifies the vdsl Port's UPBO a value.
				Unit is -1/256"
			::= { vdslProfileEntry 69 }

		
		-- 1.3.6.1.4.1.6296.9.102.1.5.1.1.70
		vdslProfileUpboBValue3 OBJECT-TYPE
			SYNTAX INTEGER (0..10485)
			MAX-ACCESS read-write
			STATUS current
			DESCRIPTION
				"Specifies the vdsl Port's UPBO b value.
				Unit is -1/256"
			::= { vdslProfileEntry 70 }

		
		-- 1.3.6.1.4.1.6296.9.102.1.5.1.1.71
		vdslProfileUpboKl03 OBJECT-TYPE
			SYNTAX INTEGER (0..635)
			MAX-ACCESS read-write
			STATUS current
			DESCRIPTION
				"Specifies the vdsl Port's UPBO Electrical length estimation.
				value is 0 or 18 ~ 635. Unit is 0.1db"
			::= { vdslProfileEntry 71 }

		
		-- 1.3.6.1.4.1.6296.9.102.1.5.1.1.72
		vdslProfileUpboAValue4 OBJECT-TYPE
			SYNTAX INTEGER (10240..20725)
			MAX-ACCESS read-write
			STATUS current
			DESCRIPTION
				"Specifies the vdsl Port's UPBO a value.
				Unit is -1/256"
			::= { vdslProfileEntry 72 }

		
		-- 1.3.6.1.4.1.6296.9.102.1.5.1.1.73
		vdslProfileUpboBValue4 OBJECT-TYPE
			SYNTAX INTEGER (0..10485)
			MAX-ACCESS read-write
			STATUS current
			DESCRIPTION
				"Specifies the vdsl Port's UPBO b value.
				Unit is -1/256"
			::= { vdslProfileEntry 73 }

		
		-- 1.3.6.1.4.1.6296.9.102.1.5.1.1.74
		vdslProfileUpboKl04 OBJECT-TYPE
			SYNTAX INTEGER (0..635)
			MAX-ACCESS read-write
			STATUS current
			DESCRIPTION
				"Specifies the vdsl Port's UPBO Electrical length estimation.
				value is 0 or 18 ~ 635. Unit is 0.1db"
			::= { vdslProfileEntry 74 }

		
		-- 1.3.6.1.4.1.6296.9.102.1.5.1.1.75
		vdslProfilePtmMode OBJECT-TYPE
			SYNTAX INTEGER
				{
				standard(0),
				ikanos(1)
				}
			MAX-ACCESS read-write
			STATUS current
			DESCRIPTION
				"Specifies the vdsl Port's Ptm mode."
			::= { vdslProfileEntry 75 }

		
--  *********************************************************************
-- * Profile RFI Bands Table
-- *********************************************************************
		-- 1.3.6.1.4.1.6296.9.102.1.5.2
		vdslProfileRfiBandsTable OBJECT-TYPE
			SYNTAX SEQUENCE OF VdslProfileRfiBandsEntry
			MAX-ACCESS not-accessible
			STATUS current
			DESCRIPTION
				"This table includes VDSL Profile RFI bands Configuration Table."
			::= { vdslProfileGroup 2 }

		
		-- 1.3.6.1.4.1.6296.9.102.1.5.2.1
		vdslProfileRfiBandsEntry OBJECT-TYPE
			SYNTAX VdslProfileRfiBandsEntry
			MAX-ACCESS not-accessible
			STATUS current
			DESCRIPTION
				"An entry in the vdslProfileRfiBandsTable."
			INDEX { vdslProfileIndex, vdslProfileRfiBandsIndex }
			::= { vdslProfileRfiBandsTable 1 }

		
		VdslProfileRfiBandsEntry ::=
			SEQUENCE { 
				vdslProfileRfiBandsIndex
					INTEGER,
				vdslProfileRfiBandsStartTone
					INTEGER,
				vdslProfileRfiBandsEndTone
					INTEGER,
				vdslProfileRfiBandsRowStatus
					EntryStatus
			 }

		-- 1.3.6.1.4.1.6296.9.102.1.5.2.1.1
		vdslProfileRfiBandsIndex OBJECT-TYPE
			SYNTAX INTEGER
			MAX-ACCESS not-accessible
			STATUS current
			DESCRIPTION
				"The identifier for VDSL RFI bands"
			::= { vdslProfileRfiBandsEntry 1 }

		
		-- 1.3.6.1.4.1.6296.9.102.1.5.2.1.2
		vdslProfileRfiBandsStartTone OBJECT-TYPE
			SYNTAX INTEGER (0..8191)
			MAX-ACCESS read-create
			STATUS current
			DESCRIPTION
				"Specifies the vdsl Port's Bands Sub-carrier start index.
				Unit is 1 sub-carrier (frequency = sub-carier * 4.3125kHz"
			::= { vdslProfileRfiBandsEntry 2 }

		
		-- 1.3.6.1.4.1.6296.9.102.1.5.2.1.3
		vdslProfileRfiBandsEndTone OBJECT-TYPE
			SYNTAX INTEGER (0..8191)
			MAX-ACCESS read-create
			STATUS current
			DESCRIPTION
				"Specifies the vdsl Port's Bands Sub-carrier end index.
				Unit is 1 sub-carrier (frequency = sub-carier * 4.3125kHz"
			::= { vdslProfileRfiBandsEntry 3 }

		
		-- 1.3.6.1.4.1.6296.9.102.1.5.2.1.4
		vdslProfileRfiBandsRowStatus OBJECT-TYPE
			SYNTAX EntryStatus
			MAX-ACCESS read-create
			STATUS current
			DESCRIPTION
				"The status of this conceptual row."
			::= { vdslProfileRfiBandsEntry 4 }

		
--  *********************************************************************
-- * Profile RFI Gaps Table
-- *********************************************************************
		-- 1.3.6.1.4.1.6296.9.102.1.5.3
		vdslProfileRfiGapsTable OBJECT-TYPE
			SYNTAX SEQUENCE OF VdslProfileRfiGapsEntry
			MAX-ACCESS not-accessible
			STATUS current
			DESCRIPTION
				"This table includes VDSL Profile RFI Gaps Configuration Table."
			::= { vdslProfileGroup 3 }

		
		-- 1.3.6.1.4.1.6296.9.102.1.5.3.1
		vdslProfileRfiGapsEntry OBJECT-TYPE
			SYNTAX VdslProfileRfiGapsEntry
			MAX-ACCESS not-accessible
			STATUS current
			DESCRIPTION
				"An entry in the vdslProfileRfiGapsTable."
			INDEX { vdslProfileIndex, vdslProfileRfiGapsIndex }
			::= { vdslProfileRfiGapsTable 1 }

		
		VdslProfileRfiGapsEntry ::=
			SEQUENCE { 
				vdslProfileRfiGapsIndex
					INTEGER,
				vdslProfileRfiGapsStartTone
					INTEGER,
				vdslProfileRfiGapsEndTone
					INTEGER,
				vdslProfileRfiGapsRowStatus
					EntryStatus
			 }

		-- 1.3.6.1.4.1.6296.9.102.1.5.3.1.1
		vdslProfileRfiGapsIndex OBJECT-TYPE
			SYNTAX INTEGER
			MAX-ACCESS not-accessible
			STATUS current
			DESCRIPTION
				"The identifier for VDSL RFI gaps"
			::= { vdslProfileRfiGapsEntry 1 }

		
		-- 1.3.6.1.4.1.6296.9.102.1.5.3.1.2
		vdslProfileRfiGapsStartTone OBJECT-TYPE
			SYNTAX INTEGER (0..8191)
			MAX-ACCESS read-create
			STATUS current
			DESCRIPTION
				"Specifies the vdsl Port's Gaps Sub-carrier start index.
				Unit is 1 sub-carrier (frequency = sub-carier * 4.3125kHz"
			::= { vdslProfileRfiGapsEntry 2 }

		
		-- 1.3.6.1.4.1.6296.9.102.1.5.3.1.3
		vdslProfileRfiGapsEndTone OBJECT-TYPE
			SYNTAX INTEGER (0..8191)
			MAX-ACCESS read-create
			STATUS current
			DESCRIPTION
				"Specifies the vdsl Port's Gaps Sub-carrier end index.
				Unit is 1 sub-carrier (frequency = sub-carier * 4.3125kHz"
			::= { vdslProfileRfiGapsEntry 3 }

		
		-- 1.3.6.1.4.1.6296.9.102.1.5.3.1.4
		vdslProfileRfiGapsRowStatus OBJECT-TYPE
			SYNTAX EntryStatus
			MAX-ACCESS read-create
			STATUS current
			DESCRIPTION
				"The status of this conceptual row."
			::= { vdslProfileRfiGapsEntry 4 }

		
		-- 1.3.6.1.4.1.6296.9.102.1.6
		gfastAutoRateLimitGroup OBJECT IDENTIFIER ::= { gfastGroup 6 }

		
--  *********************************************************************
-- * Port Rate-Limit Table Group
-- *********************************************************************
-- gfastPortRateLimitGroup			OBJECT IDENTIFIER ::= { gfastPortGroup 14 }	
-- gfastPortRateLimitAdmin OBJECT-TYPE
-- SYNTAX      INTEGER
-- MAX-ACCESS  read-write
-- STATUS      current
-- DESCRIPTION
-- "Specifies the gFastMIB System Port Rate-Limit Admin."
-- ::= { gfastPortRateLimitGroup 1 }
		-- 1.3.6.1.4.1.6296.9.102.1.6.1
		gfastAutoRateLimitTable OBJECT-TYPE
			SYNTAX SEQUENCE OF GfastAutoRateLimitEntry
			MAX-ACCESS not-accessible
			STATUS current
			DESCRIPTION
				"This table includes common attributes describing gFastMIB
				System Port AutoRateLimit Information."
			::= { gfastAutoRateLimitGroup 1 }

		
		-- 1.3.6.1.4.1.6296.9.102.1.6.1.1
		gfastAutoRateLimitEntry OBJECT-TYPE
			SYNTAX GfastAutoRateLimitEntry
			MAX-ACCESS not-accessible
			STATUS current
			DESCRIPTION
				"An entry in gfastPortTable."
			INDEX { gfastAutoRateLimitIndex }
			::= { gfastAutoRateLimitTable 1 }

		
		GfastAutoRateLimitEntry ::=
			SEQUENCE { 
				gfastAutoRateLimitIndex
					INTEGER,
				gfastAutoRateLimitEgress
					INTEGER,
				gfastAutoRateLimitWhich
					DisplayString
			 }

		-- 1.3.6.1.4.1.6296.9.102.1.6.1.1.1
		gfastAutoRateLimitIndex OBJECT-TYPE
			SYNTAX INTEGER
			MAX-ACCESS read-only
			STATUS current
			DESCRIPTION
				"Specifies the gFastMIB System Port Rate-Limit Index."
			::= { gfastAutoRateLimitEntry 1 }

		
		-- 1.3.6.1.4.1.6296.9.102.1.6.1.1.2
		gfastAutoRateLimitEgress OBJECT-TYPE
			SYNTAX INTEGER
			MAX-ACCESS read-only
			STATUS current
			DESCRIPTION
				"Specifies the gFastMIB System Port Rate-Limit Egress."
			::= { gfastAutoRateLimitEntry 2 }

		
		-- 1.3.6.1.4.1.6296.9.102.1.6.1.1.3
		gfastAutoRateLimitWhich OBJECT-TYPE
			SYNTAX DisplayString
			MAX-ACCESS read-only
			STATUS current
			DESCRIPTION
				"Specifies the gFastMIB System Port Rate-Limit Which."
			::= { gfastAutoRateLimitEntry 3 }

		
--  *********************************************************************
-- * Port Rate-Limit Table Group
-- *********************************************************************	
		-- 1.3.6.1.4.1.6296.9.102.1.6.2
		gfastAutoRateLimitPercentageTable OBJECT-TYPE
			SYNTAX SEQUENCE OF GfastAutoRateLimitPercentageEntry
			MAX-ACCESS not-accessible
			STATUS current
			DESCRIPTION
				"This table includes common attributes describing gFastMIB
				System Port AutoRateLimitPercentage Information."
			::= { gfastAutoRateLimitGroup 2 }

		
		-- 1.3.6.1.4.1.6296.9.102.1.6.2.1
		gfastAutoRateLimitPercentageEntry OBJECT-TYPE
			SYNTAX GfastAutoRateLimitPercentageEntry
			MAX-ACCESS not-accessible
			STATUS current
			DESCRIPTION
				"An entry in gfastAutoRateLimitPercentageTable."
			INDEX { gfastPortIndex }
			::= { gfastAutoRateLimitPercentageTable 1 }

		
		GfastAutoRateLimitPercentageEntry ::=
			SEQUENCE { 
				gfastAutoRateLimitPercentage
					INTEGER
			 }

		-- 1.3.6.1.4.1.6296.9.102.1.6.2.1.1
		gfastAutoRateLimitPercentage OBJECT-TYPE
			SYNTAX INTEGER (1..100)
			MAX-ACCESS read-write
			STATUS current
			DESCRIPTION
				"Specifies the gfast Auto Rate-Limit Percentage."
			::= { gfastAutoRateLimitPercentageEntry 1 }

		
		-- 1.3.6.1.4.1.6296.9.102.2
		gfastCpeGroup OBJECT IDENTIFIER ::= { gFastMIB 2 }

		
		-- 1.3.6.1.4.1.6296.9.102.2.0
		gfastCpeNotifPrefix OBJECT IDENTIFIER ::= { gfastCpeGroup 0 }

		
		-- 1.3.6.1.4.1.6296.9.102.2.1
		gfastCpeInfoGroup OBJECT IDENTIFIER ::= { gfastCpeGroup 1 }

		
--  *********************************************************************
-- * gfastCpeInfoGroup
-- *********************************************************************
-- *********************************************************************
-- * System Table Group
-- *********************************************************************
		-- 1.3.6.1.4.1.6296.9.102.2.1.1
		gfastCpeSystemTable OBJECT-TYPE
			SYNTAX SEQUENCE OF GfastCpeSystemEntry
			MAX-ACCESS not-accessible
			STATUS current
			DESCRIPTION
				"This table includes common attributes describing gFast Cpe
				System Information."
			::= { gfastCpeInfoGroup 1 }

		
		-- 1.3.6.1.4.1.6296.9.102.2.1.1.1
		gfastCpeSystemEntry OBJECT-TYPE
			SYNTAX GfastCpeSystemEntry
			MAX-ACCESS not-accessible
			STATUS current
			DESCRIPTION
				"An entry in gfastCpeSystemTable."
			INDEX { gfastCpeSystemIndex }
			::= { gfastCpeSystemTable 1 }

		
		GfastCpeSystemEntry ::=
			SEQUENCE { 
				gfastCpeSystemIndex
					INTEGER,
				gfastCpeSystemStatus
					INTEGER,
				gfastCpeSystemModel
					DisplayString,
				gfastCpeSystemHwAddr
					DisplayString,
				gfastCpeSystemSerial
					DisplayString,
				gfastCpeSystemHWVersion
					DisplayString,
				gfastCpeSystemOSVersion
					DisplayString,
				gfastCpeSystemUptime
					DisplayString
			 }

-- 		gfastCpeSystemPhyVersion		DisplayString,
		-- 1.3.6.1.4.1.6296.9.102.2.1.1.1.1
		gfastCpeSystemIndex OBJECT-TYPE
			SYNTAX INTEGER (1..16)
			MAX-ACCESS read-only
			STATUS current
			DESCRIPTION
				"The identifier for G.FAST CPE system"
			::= { gfastCpeSystemEntry 1 }

		
		-- 1.3.6.1.4.1.6296.9.102.2.1.1.1.2
		gfastCpeSystemStatus OBJECT-TYPE
			SYNTAX INTEGER
				{
				noaction(0),
				reset(1)
				}
			MAX-ACCESS read-write
			STATUS current
			DESCRIPTION
				"Reboot the G.fast CPE "
			::= { gfastCpeSystemEntry 2 }

		
		-- 1.3.6.1.4.1.6296.9.102.2.1.1.1.3
		gfastCpeSystemModel OBJECT-TYPE
			SYNTAX DisplayString
			MAX-ACCESS read-only
			STATUS current
			DESCRIPTION
				"Display G.fast CPE model name"
			::= { gfastCpeSystemEntry 3 }

		
		-- 1.3.6.1.4.1.6296.9.102.2.1.1.1.4
		gfastCpeSystemHwAddr OBJECT-TYPE
			SYNTAX DisplayString
			MAX-ACCESS read-only
			STATUS current
			DESCRIPTION
				"Display G.fast CPE system mac address"
			::= { gfastCpeSystemEntry 4 }

		
		-- 1.3.6.1.4.1.6296.9.102.2.1.1.1.5
		gfastCpeSystemSerial OBJECT-TYPE
			SYNTAX DisplayString
			MAX-ACCESS read-only
			STATUS current
			DESCRIPTION
				"Display G.fast CPE system serial number"
			::= { gfastCpeSystemEntry 5 }

		
		-- 1.3.6.1.4.1.6296.9.102.2.1.1.1.6
		gfastCpeSystemHWVersion OBJECT-TYPE
			SYNTAX DisplayString
			MAX-ACCESS read-only
			STATUS current
			DESCRIPTION
				"Display activated G.fast CPE system H/W version"
			::= { gfastCpeSystemEntry 6 }

		
		-- 1.3.6.1.4.1.6296.9.102.2.1.1.1.7
		gfastCpeSystemOSVersion OBJECT-TYPE
			SYNTAX DisplayString
			MAX-ACCESS read-only
			STATUS current
			DESCRIPTION
				"Display activated G.fast CPE system Active OS version"
			::= { gfastCpeSystemEntry 7 }

		
-- gfastCpeSystemPhyVersion OBJECT-TYPE
-- SYNTAX      DisplayString
-- MAX-ACCESS  read-only
-- STATUS      current
-- DESCRIPTION
-- "Display G.fast CPE system phy driver version"
-- ::= { gfastCpeSystemEntry 7 }
		-- 1.3.6.1.4.1.6296.9.102.2.1.1.1.8
		gfastCpeSystemUptime OBJECT-TYPE
			SYNTAX DisplayString
			MAX-ACCESS read-only
			STATUS current
			DESCRIPTION
				"Display G.fast CPE system uptime"
			::= { gfastCpeSystemEntry 8 }

		
--  *******************************************************************
-- * Port Status Table Group
-- *******************************************************************
		-- 1.3.6.1.4.1.6296.9.102.2.1.2
		gfastCpeLanStatusTable OBJECT-TYPE
			SYNTAX SEQUENCE OF GfastCpeLanStatusEntry
			MAX-ACCESS not-accessible
			STATUS current
			DESCRIPTION
				"The gfast cpe port status table"
			::= { gfastCpeInfoGroup 2 }

		
		-- 1.3.6.1.4.1.6296.9.102.2.1.2.1
		gfastCpeLanStatusEntry OBJECT-TYPE
			SYNTAX GfastCpeLanStatusEntry
			MAX-ACCESS not-accessible
			STATUS current
			DESCRIPTION
				"an entry of the gfast cpe port status table"
			INDEX { gfastCpeSystemIndex, gfastCpeLanIndex }
			::= { gfastCpeLanStatusTable 1 }

		
		GfastCpeLanStatusEntry ::=
			SEQUENCE { 
				gfastCpeLanIndex
					INTEGER,
				gfastCpeLanName
					DisplayString,
				gfastCpeLanAdmin
					INTEGER,
				gfastCpeLanOper
					INTEGER,
				gfastCpeLanSpeed
					INTEGER
			 }

		-- 1.3.6.1.4.1.6296.9.102.2.1.2.1.1
		gfastCpeLanIndex OBJECT-TYPE
			SYNTAX INTEGER
			MAX-ACCESS read-only
			STATUS current
			DESCRIPTION
				"The identifier for G.FAST CPE Lan port"
			::= { gfastCpeLanStatusEntry 1 }

		
		-- 1.3.6.1.4.1.6296.9.102.2.1.2.1.2
		gfastCpeLanName OBJECT-TYPE
			SYNTAX DisplayString
			MAX-ACCESS read-only
			STATUS current
			DESCRIPTION
				"Dispaly the G.FAST CPE Lan port name"
			::= { gfastCpeLanStatusEntry 2 }

		
		-- 1.3.6.1.4.1.6296.9.102.2.1.2.1.3
		gfastCpeLanAdmin OBJECT-TYPE
			SYNTAX INTEGER
				{
				disable(0),
				enable(1)
				}
			MAX-ACCESS read-only
			STATUS current
			DESCRIPTION
				"Display G.FAST CPE Lan port admin mode"
			::= { gfastCpeLanStatusEntry 3 }

		
		-- 1.3.6.1.4.1.6296.9.102.2.1.2.1.4
		gfastCpeLanOper OBJECT-TYPE
			SYNTAX INTEGER
				{
				link-off(0),
				link-on(1)
				}
			MAX-ACCESS read-only
			STATUS current
			DESCRIPTION
				"Display G.FAST CPE Lan port operation status"
			::= { gfastCpeLanStatusEntry 4 }

		
		-- 1.3.6.1.4.1.6296.9.102.2.1.2.1.5
		gfastCpeLanSpeed OBJECT-TYPE
			SYNTAX INTEGER
				{
				speed-10M(0),
				speed-100M(1),
				speed-1G(2),
				speed-500M(3)
				}
			MAX-ACCESS read-only
			STATUS current
			DESCRIPTION
				"Display G.FAST CPE Lan port speed"
			::= { gfastCpeLanStatusEntry 5 }

		
--  *******************************************************************
-- * LAN Port Packet counter Table Group
-- *******************************************************************
		-- 1.3.6.1.4.1.6296.9.102.2.1.3
		gfastCpeLanCounterTable OBJECT-TYPE
			SYNTAX SEQUENCE OF GfastCpeLanCounterEntry
			MAX-ACCESS not-accessible
			STATUS current
			DESCRIPTION
				"The gfast cpe lan port packet counter table"
			::= { gfastCpeInfoGroup 3 }

		
		-- 1.3.6.1.4.1.6296.9.102.2.1.3.1
		gfastCpeLanCounterEntry OBJECT-TYPE
			SYNTAX GfastCpeLanCounterEntry
			MAX-ACCESS not-accessible
			STATUS current
			DESCRIPTION
				"an entry of the gfast cpe lan port packet counter table"
			INDEX { gfastCpeSystemIndex, gfastCpeLanIndex }
			::= { gfastCpeLanCounterTable 1 }

		
		GfastCpeLanCounterEntry ::=
			SEQUENCE { 
				gfastCpeLanCounterIndex
					INTEGER,
				gfastCpeLanInOctets
					Counter64,
				gfastCpeLantInUnicast
					Counter64,
				gfastCpeLanInMulticast
					Counter64,
				gfastCpeLanInBroadcast
					Counter64,
				gfastCpeLanInDiscard
					Counter64,
				gfastCpeLanInError
					Counter64,
				gfastCpeLanOutOctets
					Counter64,
				gfastCpeLanOutUnicast
					Counter64,
				gfastCpeLanOutMulticast
					Counter64,
				gfastCpeLanOutBroadcast
					Counter64,
				gfastCpeLanOutDiscard
					Counter64,
				gfastCpeLanOutError
					Counter64
			 }

-- gfastCpeLanInNucast			Counter64,
-- gfastCpeLanOutNucast		Counter64,
		-- 1.3.6.1.4.1.6296.9.102.2.1.3.1.1
		gfastCpeLanCounterIndex OBJECT-TYPE
			SYNTAX INTEGER
			MAX-ACCESS read-only
			STATUS current
			DESCRIPTION
				"The identifier for G.FAST CPE Lan port counter"
			::= { gfastCpeLanCounterEntry 1 }

		
		-- 1.3.6.1.4.1.6296.9.102.2.1.3.1.2
		gfastCpeLanInOctets OBJECT-TYPE
			SYNTAX Counter64
			MAX-ACCESS read-only
			STATUS current
			DESCRIPTION
				"Display G.FAST CPE Lan port input octets"
			::= { gfastCpeLanCounterEntry 2 }

		
		-- 1.3.6.1.4.1.6296.9.102.2.1.3.1.3
		gfastCpeLantInUnicast OBJECT-TYPE
			SYNTAX Counter64
			MAX-ACCESS read-only
			STATUS current
			DESCRIPTION
				"Display G.FAST CPE Lan port input unicast packets"
			::= { gfastCpeLanCounterEntry 3 }

		
		-- 1.3.6.1.4.1.6296.9.102.2.1.3.1.4
		gfastCpeLanInMulticast OBJECT-TYPE
			SYNTAX Counter64
			MAX-ACCESS read-only
			STATUS current
			DESCRIPTION
				"Display G.FAST CPE Lan port input multicast packets"
			::= { gfastCpeLanCounterEntry 4 }

		
		-- 1.3.6.1.4.1.6296.9.102.2.1.3.1.5
		gfastCpeLanInBroadcast OBJECT-TYPE
			SYNTAX Counter64
			MAX-ACCESS read-only
			STATUS current
			DESCRIPTION
				"Display G.FAST CPE Lan port input broadcast packets"
			::= { gfastCpeLanCounterEntry 5 }

		
-- gfastCpeLanInNucast OBJECT-TYPE
-- SYNTAX      Counter64
-- MAX-ACCESS  read-only
-- STATUS      current
-- DESCRIPTION
-- "Display G.FAST CPE Lan port input non unicast packets"
-- ::= { gfastCpeLanCounterEntry 6 }
		-- 1.3.6.1.4.1.6296.9.102.2.1.3.1.6
		gfastCpeLanInDiscard OBJECT-TYPE
			SYNTAX Counter64
			MAX-ACCESS read-only
			STATUS current
			DESCRIPTION
				"Display G.FAST CPE Lan port input discard packets"
			::= { gfastCpeLanCounterEntry 6 }

		
		-- 1.3.6.1.4.1.6296.9.102.2.1.3.1.7
		gfastCpeLanInError OBJECT-TYPE
			SYNTAX Counter64
			MAX-ACCESS read-only
			STATUS current
			DESCRIPTION
				"Display G.FAST CPE Lan port input error packets"
			::= { gfastCpeLanCounterEntry 7 }

		
		-- 1.3.6.1.4.1.6296.9.102.2.1.3.1.8
		gfastCpeLanOutOctets OBJECT-TYPE
			SYNTAX Counter64
			MAX-ACCESS read-only
			STATUS current
			DESCRIPTION
				"Display G.FAST CPE Lan port output octets"
			::= { gfastCpeLanCounterEntry 8 }

		
		-- 1.3.6.1.4.1.6296.9.102.2.1.3.1.9
		gfastCpeLanOutUnicast OBJECT-TYPE
			SYNTAX Counter64
			MAX-ACCESS read-only
			STATUS current
			DESCRIPTION
				"Display G.FAST CPE Lan port output unicast packets"
			::= { gfastCpeLanCounterEntry 9 }

		
		-- 1.3.6.1.4.1.6296.9.102.2.1.3.1.10
		gfastCpeLanOutMulticast OBJECT-TYPE
			SYNTAX Counter64
			MAX-ACCESS read-only
			STATUS current
			DESCRIPTION
				"Display G.FAST CPE Lan port output multicast packets"
			::= { gfastCpeLanCounterEntry 10 }

		
		-- 1.3.6.1.4.1.6296.9.102.2.1.3.1.11
		gfastCpeLanOutBroadcast OBJECT-TYPE
			SYNTAX Counter64
			MAX-ACCESS read-only
			STATUS current
			DESCRIPTION
				"Display G.FAST CPE Lan port output broadcast packets"
			::= { gfastCpeLanCounterEntry 11 }

		
-- gfastCpeLanOutNucast	OBJECT-TYPE
-- SYNTAX      Counter64
-- MAX-ACCESS  read-only
-- STATUS      current
-- DESCRIPTION
-- "Display G.FAST CPE Lan port output non unicast packets"
-- ::= { gfastCpeLanCounterEntry 13 }
		-- 1.3.6.1.4.1.6296.9.102.2.1.3.1.12
		gfastCpeLanOutDiscard OBJECT-TYPE
			SYNTAX Counter64
			MAX-ACCESS read-only
			STATUS current
			DESCRIPTION
				"Display G.FAST CPE Lan port output discard packets"
			::= { gfastCpeLanCounterEntry 12 }

		
		-- 1.3.6.1.4.1.6296.9.102.2.1.3.1.13
		gfastCpeLanOutError OBJECT-TYPE
			SYNTAX Counter64
			MAX-ACCESS read-only
			STATUS current
			DESCRIPTION
				"Display G.FAST CPE Lan port input error packets"
			::= { gfastCpeLanCounterEntry 13 }

		
--  *******************************************************************
-- * WAN Port Packet counter Table Group
-- *******************************************************************
		-- 1.3.6.1.4.1.6296.9.102.2.1.4
		gfastCpeWanCounterTable OBJECT-TYPE
			SYNTAX SEQUENCE OF GfastCpeWanCounterEntry
			MAX-ACCESS not-accessible
			STATUS current
			DESCRIPTION
				"The gfast cpe wan port packet counter table"
			::= { gfastCpeInfoGroup 4 }

		
		-- 1.3.6.1.4.1.6296.9.102.2.1.4.1
		gfastCpeWanCounterEntry OBJECT-TYPE
			SYNTAX GfastCpeWanCounterEntry
			MAX-ACCESS not-accessible
			STATUS current
			DESCRIPTION
				"an entry of the gfast cpe wan port packet counter table"
			INDEX { gfastCpeSystemIndex }
			::= { gfastCpeWanCounterTable 1 }

		
		GfastCpeWanCounterEntry ::=
			SEQUENCE { 
				gfastCpeWanCounterIndex
					INTEGER,
				gfastCpeWantInUnicast
					Counter64,
				gfastCpeWanInMulticast
					Counter64,
				gfastCpeWanInBroadcast
					Counter64,
				gfastCpeWanInDiscard
					Counter64,
				gfastCpeWanInError
					Counter64,
				gfastCpeWanOutUnicast
					Counter64,
				gfastCpeWanOutMulticast
					Counter64,
				gfastCpeWanOutBroadcast
					Counter64,
				gfastCpeWanOutDiscard
					Counter64,
				gfastCpeWanOutError
					Counter64
			 }

-- gfastCpeWanInNucast			Counter64,
-- gfastCpeWanOutNucast		Counter64,
		-- 1.3.6.1.4.1.6296.9.102.2.1.4.1.1
		gfastCpeWanCounterIndex OBJECT-TYPE
			SYNTAX INTEGER
			MAX-ACCESS read-only
			STATUS current
			DESCRIPTION
				"The identifier for G.FAST CPE Wan port counter"
			::= { gfastCpeWanCounterEntry 1 }

		
		-- 1.3.6.1.4.1.6296.9.102.2.1.4.1.2
		gfastCpeWantInUnicast OBJECT-TYPE
			SYNTAX Counter64
			MAX-ACCESS read-only
			STATUS current
			DESCRIPTION
				"Display G.FAST CPE Wan port input unicast packets"
			::= { gfastCpeWanCounterEntry 2 }

		
		-- 1.3.6.1.4.1.6296.9.102.2.1.4.1.3
		gfastCpeWanInMulticast OBJECT-TYPE
			SYNTAX Counter64
			MAX-ACCESS read-only
			STATUS current
			DESCRIPTION
				"Display G.FAST CPE Wan port input multicast packets"
			::= { gfastCpeWanCounterEntry 3 }

		
		-- 1.3.6.1.4.1.6296.9.102.2.1.4.1.4
		gfastCpeWanInBroadcast OBJECT-TYPE
			SYNTAX Counter64
			MAX-ACCESS read-only
			STATUS current
			DESCRIPTION
				"Display G.FAST CPE Wan port input broadcast packets"
			::= { gfastCpeWanCounterEntry 4 }

		
-- gfastCpeWanInNucast OBJECT-TYPE
-- SYNTAX      Counter64
-- MAX-ACCESS  read-only
-- STATUS      current
-- DESCRIPTION
-- "Display G.FAST CPE Wan port input non unicast packets"
-- ::= { gfastCpeWanCounterEntry 5 }
		-- 1.3.6.1.4.1.6296.9.102.2.1.4.1.5
		gfastCpeWanInDiscard OBJECT-TYPE
			SYNTAX Counter64
			MAX-ACCESS read-only
			STATUS current
			DESCRIPTION
				"Display G.FAST CPE Wan port input discard packets"
			::= { gfastCpeWanCounterEntry 5 }

		
		-- 1.3.6.1.4.1.6296.9.102.2.1.4.1.6
		gfastCpeWanInError OBJECT-TYPE
			SYNTAX Counter64
			MAX-ACCESS read-only
			STATUS current
			DESCRIPTION
				"Display G.FAST CPE Wan port input error packets"
			::= { gfastCpeWanCounterEntry 6 }

		
		-- 1.3.6.1.4.1.6296.9.102.2.1.4.1.7
		gfastCpeWanOutUnicast OBJECT-TYPE
			SYNTAX Counter64
			MAX-ACCESS read-only
			STATUS current
			DESCRIPTION
				"Display G.FAST CPE Wan port output unicast packets"
			::= { gfastCpeWanCounterEntry 7 }

		
		-- 1.3.6.1.4.1.6296.9.102.2.1.4.1.8
		gfastCpeWanOutMulticast OBJECT-TYPE
			SYNTAX Counter64
			MAX-ACCESS read-only
			STATUS current
			DESCRIPTION
				"Display G.FAST CPE Wan port output multicast packets"
			::= { gfastCpeWanCounterEntry 8 }

		
		-- 1.3.6.1.4.1.6296.9.102.2.1.4.1.9
		gfastCpeWanOutBroadcast OBJECT-TYPE
			SYNTAX Counter64
			MAX-ACCESS read-only
			STATUS current
			DESCRIPTION
				"Display G.FAST CPE Wan port output broadcast packets"
			::= { gfastCpeWanCounterEntry 9 }

		
-- gfastCpeWanOutNucast	OBJECT-TYPE
-- SYNTAX      Counter64
-- MAX-ACCESS  read-only
-- STATUS      current
-- DESCRIPTION
-- "Display G.FAST CPE Wan port output non unicast packets"
-- ::= { gfastCpeWanCounterEntry 11 }
		-- 1.3.6.1.4.1.6296.9.102.2.1.4.1.10
		gfastCpeWanOutDiscard OBJECT-TYPE
			SYNTAX Counter64
			MAX-ACCESS read-only
			STATUS current
			DESCRIPTION
				"Display G.FAST CPE Wan port output discard packets"
			::= { gfastCpeWanCounterEntry 10 }

		
		-- 1.3.6.1.4.1.6296.9.102.2.1.4.1.11
		gfastCpeWanOutError OBJECT-TYPE
			SYNTAX Counter64
			MAX-ACCESS read-only
			STATUS current
			DESCRIPTION
				"Display G.FAST CPE Wan port input error packets"
			::= { gfastCpeWanCounterEntry 11 }

		
--  *******************************************************************
-- * Cpe Ptm packet counter Table Group
-- ******************************************************************* 
		-- 1.3.6.1.4.1.6296.9.102.2.1.5
		gfastCpePtmCounterTable OBJECT-TYPE
			SYNTAX SEQUENCE OF GfastCpePtmCounterEntry
			MAX-ACCESS not-accessible
			STATUS current
			DESCRIPTION
				"This table includes CPE ptm packet counter"
			::= { gfastCpeInfoGroup 5 }

		
		-- 1.3.6.1.4.1.6296.9.102.2.1.5.1
		gfastCpePtmCounterEntry OBJECT-TYPE
			SYNTAX GfastCpePtmCounterEntry
			MAX-ACCESS not-accessible
			STATUS current
			DESCRIPTION
				"An entry in CPE Ptm Counter Table."
			INDEX { gfastCpePtmIndex }
			::= { gfastCpePtmCounterTable 1 }

		
		GfastCpePtmCounterEntry ::=
			SEQUENCE { 
				gfastCpePtmIndex
					INTEGER,
				gfastCpePtmInPacket
					Counter64,
				gfastCpePtmInPktErr
					Counter64,
				gfastCpePtmOutPacket
					Counter64,
				gfastCpePtmOutPktErr
					Counter64,
				gfastCpePtmFrameDrop
					Counter64
			 }

-- gfastCpePtmInOctets				Counter64,
-- gfastCpePtmOutOctets			Counter64,
		-- 1.3.6.1.4.1.6296.9.102.2.1.5.1.1
		gfastCpePtmIndex OBJECT-TYPE
			SYNTAX INTEGER (1..16)
			MAX-ACCESS read-only
			STATUS current
			DESCRIPTION
				"The identifier for G.FAST CPE ptm counter"
			::= { gfastCpePtmCounterEntry 1 }

		
-- gfastCpePtmInOctets	OBJECT-TYPE
-- SYNTAX		Counter64
-- MAX-ACCESS	read-only
-- STATUS		current
-- DESCRIPTION	"Display G.FAST CPE ptm input octets"
-- ::= { gfastCpePtmCounterEntry 2 }
		-- 1.3.6.1.4.1.6296.9.102.2.1.5.1.2
		gfastCpePtmInPacket OBJECT-TYPE
			SYNTAX Counter64
			MAX-ACCESS read-only
			STATUS current
			DESCRIPTION
				"Display G.FAST CPE ptm input packets"
			::= { gfastCpePtmCounterEntry 2 }

		
		-- 1.3.6.1.4.1.6296.9.102.2.1.5.1.3
		gfastCpePtmInPktErr OBJECT-TYPE
			SYNTAX Counter64
			MAX-ACCESS read-only
			STATUS current
			DESCRIPTION
				"Display G.FAST CPE ptm input error packets"
			::= { gfastCpePtmCounterEntry 3 }

		
-- gfastCpePtmOutOctets	OBJECT-TYPE
-- SYNTAX		Counter64
-- MAX-ACCESS  read-only
-- STATUS      current
-- DESCRIPTION
-- "Display G.FAST CPE ptm output octets"
-- ::= { gfastCpePtmCounterEntry 5 }
		-- 1.3.6.1.4.1.6296.9.102.2.1.5.1.4
		gfastCpePtmOutPacket OBJECT-TYPE
			SYNTAX Counter64
			MAX-ACCESS read-only
			STATUS current
			DESCRIPTION
				"Display G.FAST CPE ptm output packets"
			::= { gfastCpePtmCounterEntry 4 }

		
		-- 1.3.6.1.4.1.6296.9.102.2.1.5.1.5
		gfastCpePtmOutPktErr OBJECT-TYPE
			SYNTAX Counter64
			MAX-ACCESS read-only
			STATUS current
			DESCRIPTION
				"Display G.FAST CPE ptm output error packets"
			::= { gfastCpePtmCounterEntry 5 }

		
		-- 1.3.6.1.4.1.6296.9.102.2.1.5.1.6
		gfastCpePtmFrameDrop OBJECT-TYPE
			SYNTAX Counter64
			MAX-ACCESS read-only
			STATUS current
			DESCRIPTION
				"Display G.FAST CPE ptm drop frame"
			::= { gfastCpePtmCounterEntry 6 }

		
--  *******************************************************************
-- * Cpe G.fast Statistics counter Table Group
-- ******************************************************************* 
		-- 1.3.6.1.4.1.6296.9.102.2.1.6
		gfastCpeStatCounterTable OBJECT-TYPE
			SYNTAX SEQUENCE OF GfastCpeStatCounterEntry
			MAX-ACCESS not-accessible
			STATUS current
			DESCRIPTION
				"This table includes CPE G.fast statistics counter."
			::= { gfastCpeInfoGroup 6 }

		
		-- 1.3.6.1.4.1.6296.9.102.2.1.6.1
		gfastCpeStatCounterEntry OBJECT-TYPE
			SYNTAX GfastCpeStatCounterEntry
			MAX-ACCESS not-accessible
			STATUS current
			DESCRIPTION
				"An entry in CPE Statistics Counter Table."
			INDEX { gfastCpeStatIndex }
			::= { gfastCpeStatCounterTable 1 }

		
		GfastCpeStatCounterEntry ::=
			SEQUENCE { 
				gfastCpeStatIndex
					INTEGER,
				gfastCpeStatDsFec
					Counter32,
				gfastCpeStatUsFec
					Counter32,
				gfastCpeStatDsCrc
					Counter32,
				gfastCpeStatUsCrc
					Counter32,
				gfastCpeStatDsEss
					Counter32,
				gfastCpeStatUsEss
					Counter32,
				gfastCpeStatDsSes
					Counter32,
				gfastCpeStatUsSes
					Counter32,
				gfastCpeStatDsUas
					Counter32,
				gfastCpeStatUsUas
					Counter32,
				gfastCpeStatDsLoss
					Counter32,
				gfastCpeStatUsLoss
					Counter32,
				gfastCpeStatDsLofs
					Counter32,
				gfastCpeStatUsLofs
					Counter32,
				gfastCpeStatDsLoms
					Counter32,
				gfastCpeStatUsLoms
					Counter32,
				gfastCpeStatRetrain
					Counter32
			 }

		-- 1.3.6.1.4.1.6296.9.102.2.1.6.1.1
		gfastCpeStatIndex OBJECT-TYPE
			SYNTAX INTEGER (1..16)
			MAX-ACCESS read-only
			STATUS current
			DESCRIPTION
				"The identifier for G.FAST CPE Port's statistics."
			::= { gfastCpeStatCounterEntry 1 }

		
		-- 1.3.6.1.4.1.6296.9.102.2.1.6.1.2
		gfastCpeStatDsFec OBJECT-TYPE
			SYNTAX Counter32
			MAX-ACCESS read-only
			STATUS current
			DESCRIPTION
				"Display G.FAST CPE Port's Down Stream Forward Error Correction Seconds."
			::= { gfastCpeStatCounterEntry 2 }

		
		-- 1.3.6.1.4.1.6296.9.102.2.1.6.1.3
		gfastCpeStatUsFec OBJECT-TYPE
			SYNTAX Counter32
			MAX-ACCESS read-only
			STATUS current
			DESCRIPTION
				"Display G.FAST CPE Port's Up Stream Forward Error Correction Seconds."
			::= { gfastCpeStatCounterEntry 3 }

		
		-- 1.3.6.1.4.1.6296.9.102.2.1.6.1.4
		gfastCpeStatDsCrc OBJECT-TYPE
			SYNTAX Counter32
			MAX-ACCESS read-only
			STATUS current
			DESCRIPTION
				"Display G.FAST CPE Port's Down Stream Cyclic Redundancy Checking."
			::= { gfastCpeStatCounterEntry 4 }

		
		-- 1.3.6.1.4.1.6296.9.102.2.1.6.1.5
		gfastCpeStatUsCrc OBJECT-TYPE
			SYNTAX Counter32
			MAX-ACCESS read-only
			STATUS current
			DESCRIPTION
				"Display G.FAST CPE Port's Up Stream Cyclic Redundancy Checking."
			::= { gfastCpeStatCounterEntry 5 }

		
		-- 1.3.6.1.4.1.6296.9.102.2.1.6.1.6
		gfastCpeStatDsEss OBJECT-TYPE
			SYNTAX Counter32
			MAX-ACCESS read-only
			STATUS current
			DESCRIPTION
				"Display G.FAST CPE Port's Down Stream Errored Seconds."
			::= { gfastCpeStatCounterEntry 6 }

		
		-- 1.3.6.1.4.1.6296.9.102.2.1.6.1.7
		gfastCpeStatUsEss OBJECT-TYPE
			SYNTAX Counter32
			MAX-ACCESS read-only
			STATUS current
			DESCRIPTION
				"Display G.FAST CPE Port's Up Stream Errored Seconds."
			::= { gfastCpeStatCounterEntry 7 }

		
		-- 1.3.6.1.4.1.6296.9.102.2.1.6.1.8
		gfastCpeStatDsSes OBJECT-TYPE
			SYNTAX Counter32
			MAX-ACCESS read-only
			STATUS current
			DESCRIPTION
				"Display G.FAST CPE Port's Down Stream Severely Errored Seconds."
			::= { gfastCpeStatCounterEntry 8 }

		
		-- 1.3.6.1.4.1.6296.9.102.2.1.6.1.9
		gfastCpeStatUsSes OBJECT-TYPE
			SYNTAX Counter32
			MAX-ACCESS read-only
			STATUS current
			DESCRIPTION
				"Display G.FAST CPE Port's Up Stream Severely Errored Seconds."
			::= { gfastCpeStatCounterEntry 9 }

		
		-- 1.3.6.1.4.1.6296.9.102.2.1.6.1.10
		gfastCpeStatDsUas OBJECT-TYPE
			SYNTAX Counter32
			MAX-ACCESS read-only
			STATUS current
			DESCRIPTION
				"Display G.FAST CPE Port's Down Stream Unavailable Seconds."
			::= { gfastCpeStatCounterEntry 10 }

		
		-- 1.3.6.1.4.1.6296.9.102.2.1.6.1.11
		gfastCpeStatUsUas OBJECT-TYPE
			SYNTAX Counter32
			MAX-ACCESS read-only
			STATUS current
			DESCRIPTION
				"Display G.FAST CPE Port's Up Stream Unavailable Seconds."
			::= { gfastCpeStatCounterEntry 11 }

		
		-- 1.3.6.1.4.1.6296.9.102.2.1.6.1.12
		gfastCpeStatDsLoss OBJECT-TYPE
			SYNTAX Counter32
			MAX-ACCESS read-only
			STATUS current
			DESCRIPTION
				"Display G.FAST CPE Port's Down Stream Loss of Signal Seconds."
			::= { gfastCpeStatCounterEntry 12 }

		
		-- 1.3.6.1.4.1.6296.9.102.2.1.6.1.13
		gfastCpeStatUsLoss OBJECT-TYPE
			SYNTAX Counter32
			MAX-ACCESS read-only
			STATUS current
			DESCRIPTION
				"Display G.FAST CPE Port's Up Stream Loss of Signal Seconds."
			::= { gfastCpeStatCounterEntry 13 }

		
		-- 1.3.6.1.4.1.6296.9.102.2.1.6.1.14
		gfastCpeStatDsLofs OBJECT-TYPE
			SYNTAX Counter32
			MAX-ACCESS read-only
			STATUS current
			DESCRIPTION
				"Display G.FAST CPE Port's Down Stream Loss Of Frame Seconds."
			::= { gfastCpeStatCounterEntry 14 }

		
		-- 1.3.6.1.4.1.6296.9.102.2.1.6.1.15
		gfastCpeStatUsLofs OBJECT-TYPE
			SYNTAX Counter32
			MAX-ACCESS read-only
			STATUS current
			DESCRIPTION
				"Display G.FAST CPE Port's Up Stream Loss Of Frame Seconds."
			::= { gfastCpeStatCounterEntry 15 }

		
		-- 1.3.6.1.4.1.6296.9.102.2.1.6.1.16
		gfastCpeStatDsLoms OBJECT-TYPE
			SYNTAX Counter32
			MAX-ACCESS read-only
			STATUS current
			DESCRIPTION
				"Display G.FAST CPE Port's Down Stream LOM Seconds."
			::= { gfastCpeStatCounterEntry 16 }

		
		-- 1.3.6.1.4.1.6296.9.102.2.1.6.1.17
		gfastCpeStatUsLoms OBJECT-TYPE
			SYNTAX Counter32
			MAX-ACCESS read-only
			STATUS current
			DESCRIPTION
				"Display G.FAST CPE Port's Up Stream LOM Seconds."
			::= { gfastCpeStatCounterEntry 17 }

		
		-- 1.3.6.1.4.1.6296.9.102.2.1.6.1.18
		gfastCpeStatRetrain OBJECT-TYPE
			SYNTAX Counter32
			MAX-ACCESS read-only
			STATUS current
			DESCRIPTION
				"Display G.FAST CPE Port's Count of total retrains."
			::= { gfastCpeStatCounterEntry 18 }

		
--  *********************************************************************
-- * gfastCpeMacTable : Mac Address Group
-- *********************************************************************
		-- 1.3.6.1.4.1.6296.9.102.2.1.7
		gfastCpeMacTable OBJECT-TYPE
			SYNTAX SEQUENCE OF GfastCpeMacEntry
			MAX-ACCESS not-accessible
			STATUS current
			DESCRIPTION
				"This table includes G.FAST CPE mac address table"
			::= { gfastCpeInfoGroup 7 }

		
		-- 1.3.6.1.4.1.6296.9.102.2.1.7.1
		gfastCpeMacEntry OBJECT-TYPE
			SYNTAX GfastCpeMacEntry
			MAX-ACCESS not-accessible
			STATUS current
			DESCRIPTION
				"An entry in G.FAST CPE mac address Table"
			INDEX { gfastCpeSystemIndex, gfastCpeMacIndex }
			::= { gfastCpeMacTable 1 }

		
		GfastCpeMacEntry ::=
			SEQUENCE { 
				gfastCpeMacIndex
					INTEGER,
				gfastCpeMacAddr
					DisplayString,
				gfastCpeMacPort
					INTEGER
			 }

		-- 1.3.6.1.4.1.6296.9.102.2.1.7.1.1
		gfastCpeMacIndex OBJECT-TYPE
			SYNTAX INTEGER
			MAX-ACCESS read-only
			STATUS current
			DESCRIPTION
				"The identifier for G.FAST CPE mac address table"
			::= { gfastCpeMacEntry 1 }

		
		-- 1.3.6.1.4.1.6296.9.102.2.1.7.1.2
		gfastCpeMacAddr OBJECT-TYPE
			SYNTAX DisplayString
			MAX-ACCESS read-only
			STATUS current
			DESCRIPTION
				"Display G.FAST CPE learning mac address"
			::= { gfastCpeMacEntry 2 }

		
		-- 1.3.6.1.4.1.6296.9.102.2.1.7.1.3
		gfastCpeMacPort OBJECT-TYPE
			SYNTAX INTEGER
			MAX-ACCESS read-only
			STATUS current
			DESCRIPTION
				"Display G.FAST CPE learning port"
			::= { gfastCpeMacEntry 3 }

		
--  *********************************************************************
-- * gfastCpeIgsTable : IGMP Group Table
-- *********************************************************************
		-- 1.3.6.1.4.1.6296.9.102.2.1.8
		gfastCpeIgsTable OBJECT-TYPE
			SYNTAX SEQUENCE OF GfastCpeIgsEntry
			MAX-ACCESS not-accessible
			STATUS current
			DESCRIPTION
				"This table includes G.FAST CPE IGMP snooping group table"
			::= { gfastCpeInfoGroup 8 }

		
		-- 1.3.6.1.4.1.6296.9.102.2.1.8.1
		gfastCpeIgsEntry OBJECT-TYPE
			SYNTAX GfastCpeIgsEntry
			MAX-ACCESS not-accessible
			STATUS current
			DESCRIPTION
				"An entry in G.FAST CPE IGMP snooping group table"
			INDEX { gfastCpeSystemIndex, gfastCpeIgsIndex }
			::= { gfastCpeIgsTable 1 }

		
		GfastCpeIgsEntry ::=
			SEQUENCE { 
				gfastCpeIgsIndex
					INTEGER,
				gfastCpeIgsGrpAddress
					IpAddress,
				gfastCpeIgsGrpPortMask
					DisplayString
			 }

		-- 1.3.6.1.4.1.6296.9.102.2.1.8.1.1
		gfastCpeIgsIndex OBJECT-TYPE
			SYNTAX INTEGER
			MAX-ACCESS read-only
			STATUS current
			DESCRIPTION
				"The identifier for G.FAST CPE IGMP snooping group table"
			::= { gfastCpeIgsEntry 1 }

		
		-- 1.3.6.1.4.1.6296.9.102.2.1.8.1.2
		gfastCpeIgsGrpAddress OBJECT-TYPE
			SYNTAX IpAddress
			MAX-ACCESS read-only
			STATUS current
			DESCRIPTION
				"Display G.FAST CPE IGMP snooping group address"
			::= { gfastCpeIgsEntry 2 }

		
		-- 1.3.6.1.4.1.6296.9.102.2.1.8.1.3
		gfastCpeIgsGrpPortMask OBJECT-TYPE
			SYNTAX DisplayString
			MAX-ACCESS read-only
			STATUS current
			DESCRIPTION
				"Display G.FAST CPE IGMP snooping group port mask"
			::= { gfastCpeIgsEntry 3 }

		
--  *******************************************************************
-- * Rate Limit Table Group
-- *******************************************************************
		-- 1.3.6.1.4.1.6296.9.102.2.1.9
		gfastCpeRateLimitTable OBJECT-TYPE
			SYNTAX SEQUENCE OF GfastCpeRateLimitEntry
			MAX-ACCESS not-accessible
			STATUS current
			DESCRIPTION
				"The gfast cpe port Rate Limit table"
			::= { gfastCpeInfoGroup 9 }

		
		-- 1.3.6.1.4.1.6296.9.102.2.1.9.1
		gfastCpeRateLimitEntry OBJECT-TYPE
			SYNTAX GfastCpeRateLimitEntry
			MAX-ACCESS not-accessible
			STATUS current
			DESCRIPTION
				"an entry of the gfast cpe port Rate Limit table"
			INDEX { gfastCpeSystemIndex, gfastCpeRateLimitIndex }
			::= { gfastCpeRateLimitTable 1 }

		
		GfastCpeRateLimitEntry ::=
			SEQUENCE { 
				gfastCpeRateLimitIndex
					INTEGER,
				gfastCpeRateLimitEgress
					INTEGER
			 }

		-- 1.3.6.1.4.1.6296.9.102.2.1.9.1.1
		gfastCpeRateLimitIndex OBJECT-TYPE
			SYNTAX INTEGER
			MAX-ACCESS read-only
			STATUS current
			DESCRIPTION
				"The identifier for G.FAST CPE port."
			::= { gfastCpeRateLimitEntry 1 }

		
		-- 1.3.6.1.4.1.6296.9.102.2.1.9.1.2
		gfastCpeRateLimitEgress OBJECT-TYPE
			SYNTAX INTEGER { unlimited(0) }
			MAX-ACCESS read-write
			STATUS current
			DESCRIPTION
				"Specifies the G.FAST CPE Lan port Rate Limit Egress. range is 64 to 1048000. unit is 1Kbps. 
				(steps of 64Kbps)"
			::= { gfastCpeRateLimitEntry 2 }

		
		-- 1.3.6.1.4.1.6296.9.102.2.1.10
		gfastCpeVlan OBJECT IDENTIFIER ::= { gfastCpeInfoGroup 10 }

		
-- *******************************************************************
-- * VLAN Table Group
-- *******************************************************************
		-- 1.3.6.1.4.1.6296.9.102.2.1.10.1
		gfastCpeVlanTable OBJECT-TYPE
			SYNTAX SEQUENCE OF GfastCpeVlanEntry
			MAX-ACCESS not-accessible
			STATUS current
			DESCRIPTION
				"The gfast cpe port vlan table."
			::= { gfastCpeVlan 1 }

		
		-- 1.3.6.1.4.1.6296.9.102.2.1.10.1.1
		gfastCpeVlanEntry OBJECT-TYPE
			SYNTAX GfastCpeVlanEntry
			MAX-ACCESS not-accessible
			STATUS current
			DESCRIPTION
				"An entry of the gfast cpe port vlan table."
			INDEX { gfastCpeSystemIndex, gfastCpeVlanIndex }
			::= { gfastCpeVlanTable 1 }

		
		GfastCpeVlanEntry ::=
			SEQUENCE { 
				gfastCpeVlanIndex
					INTEGER,
				gfastCpeVlanId
					INTEGER,
				gfastCpeVlanMemberPort
					OCTET STRING,
				gfastCpeVlanUntagPort
					OCTET STRING
			 }

		-- 1.3.6.1.4.1.6296.9.102.2.1.10.1.1.1
		gfastCpeVlanIndex OBJECT-TYPE
			SYNTAX INTEGER (1..17)
			MAX-ACCESS read-only
			STATUS current
			DESCRIPTION
				"The vlan index."
			::= { gfastCpeVlanEntry 1 }

		
		-- 1.3.6.1.4.1.6296.9.102.2.1.10.1.1.2
		gfastCpeVlanId OBJECT-TYPE
			SYNTAX INTEGER (1..4094)
			MAX-ACCESS read-only
			STATUS current
			DESCRIPTION
				"The vlan-identifier of G.FAST CPE port."
			::= { gfastCpeVlanEntry 2 }

		
		-- 1.3.6.1.4.1.6296.9.102.2.1.10.1.1.3
		gfastCpeVlanMemberPort OBJECT-TYPE
			SYNTAX OCTET STRING (SIZE (0..16))
			MAX-ACCESS read-only
			STATUS current
			DESCRIPTION
				"The identifier for G.FAST CPE member port. ex) 1 | 1,4 | 1-4
				(1-4 : LAN port, 5 : WAN port)"
			::= { gfastCpeVlanEntry 3 }

		
		-- 1.3.6.1.4.1.6296.9.102.2.1.10.1.1.4
		gfastCpeVlanUntagPort OBJECT-TYPE
			SYNTAX OCTET STRING (SIZE (0..16))
			MAX-ACCESS read-only
			STATUS current
			DESCRIPTION
				"The identifier for G.FAST CPE untag port. ex) 1 | 1,4 | 1-4
				(1-4 : LAN port, 5 : WAN port)"
			::= { gfastCpeVlanEntry 4 }

		
		-- 1.3.6.1.4.1.6296.9.102.2.1.10.2
		gfastCpeVlanControl OBJECT IDENTIFIER ::= { gfastCpeVlan 2 }

		
		-- 1.3.6.1.4.1.6296.9.102.2.1.10.2.1
		gfastCpeVlanControlRequest OBJECT-TYPE
			SYNTAX INTEGER
				{
				setCpeVlan(1),
				destroyCpeVlan(2)
				}
			MAX-ACCESS read-write
			STATUS current
			DESCRIPTION
				"setCpeVlan:
				 gfastCpeVlanControlSystemPort
				 gfastCpeVlanControlVlanId
				 gfastCpeVlanControlCpeMemberPort
				 gfastCpeVlanControlCpeUntagPort
				
				destroyCpeVlan:
				 gfastCpeVlanControlSystemPort
				 gfastCpeVlanControlVlanId"
			::= { gfastCpeVlanControl 1 }

		
		-- 1.3.6.1.4.1.6296.9.102.2.1.10.2.2
		gfastCpeVlanControlSystemPort OBJECT-TYPE
			SYNTAX OCTET STRING (SIZE (0..32))
			MAX-ACCESS read-write
			STATUS current
			DESCRIPTION
				"The identifier for G.FAST CPE system port. ex) 1 | 1,4 | 1-4"
			::= { gfastCpeVlanControl 2 }

		
		-- 1.3.6.1.4.1.6296.9.102.2.1.10.2.3
		gfastCpeVlanControlVlanId OBJECT-TYPE
			SYNTAX OCTET STRING (SIZE (0..128))
			MAX-ACCESS read-write
			STATUS current
			DESCRIPTION
				"The vlan-identifier of G.FAST CPE port. ex) 1 | 1,4 | 1-4
				(max vlan count : 16)"
			::= { gfastCpeVlanControl 3 }

		
		-- 1.3.6.1.4.1.6296.9.102.2.1.10.2.4
		gfastCpeVlanControlMemberPort OBJECT-TYPE
			SYNTAX OCTET STRING (SIZE (0..16))
			MAX-ACCESS read-write
			STATUS current
			DESCRIPTION
				"The identifier for G.FAST CPE member port. ex) 1 | 1,4 | 1-4
				(1-4 : LAN port, 5 : WAN port)"
			::= { gfastCpeVlanControl 4 }

		
		-- 1.3.6.1.4.1.6296.9.102.2.1.10.2.5
		gfastCpeVlanControlUntagPort OBJECT-TYPE
			SYNTAX OCTET STRING (SIZE (0..16))
			MAX-ACCESS read-write
			STATUS current
			DESCRIPTION
				"The identifier for G.FAST CPE untag port. ex) 1 | 1,4 | 1-4
				(1-4 : LAN port, 5 : WAN port)"
			::= { gfastCpeVlanControl 5 }

		
		-- 1.3.6.1.4.1.6296.9.102.2.1.10.2.6
		gfastCpeVlanControlApply OBJECT-TYPE
			SYNTAX INTEGER
				{
				none(0),
				apply(1)
				}
			MAX-ACCESS read-write
			STATUS current
			DESCRIPTION
				"System Apply."
			::= { gfastCpeVlanControl 6 }

		
-- *******************************************************************
-- * PVID Table Group
-- *******************************************************************
		-- 1.3.6.1.4.1.6296.9.102.2.1.10.3
		gfastCpePvidTable OBJECT-TYPE
			SYNTAX SEQUENCE OF GfastCpePvidEntry
			MAX-ACCESS not-accessible
			STATUS current
			DESCRIPTION
				"The gfast cpe port pvid table."
			::= { gfastCpeVlan 3 }

		
		-- 1.3.6.1.4.1.6296.9.102.2.1.10.3.1
		gfastCpePvidEntry OBJECT-TYPE
			SYNTAX GfastCpePvidEntry
			MAX-ACCESS not-accessible
			STATUS current
			DESCRIPTION
				"An entry of the gfast cpe port pvid table."
			INDEX { gfastCpeSystemIndex, gfastCpeRateLimitIndex }
			::= { gfastCpePvidTable 1 }

		
		GfastCpePvidEntry ::=
			SEQUENCE { 
				gfastCpePvid
					INTEGER
			 }

		-- 1.3.6.1.4.1.6296.9.102.2.1.10.3.1.1
		gfastCpePvid OBJECT-TYPE
			SYNTAX INTEGER (1..4094)
			MAX-ACCESS read-only
			STATUS current
			DESCRIPTION
				"The PVID of G.FAST CPE port."
			::= { gfastCpePvidEntry 1 }

		
		-- 1.3.6.1.4.1.6296.9.102.2.1.10.4
		gfastCpePvidControl OBJECT IDENTIFIER ::= { gfastCpeVlan 4 }

		
		-- 1.3.6.1.4.1.6296.9.102.2.1.10.4.1
		gfastCpePvidControlRequest OBJECT-TYPE
			SYNTAX INTEGER { setCpePvid(1) }
			MAX-ACCESS read-write
			STATUS current
			DESCRIPTION
				"setCpePvid:
				 gfastCpePvidControlSystemPort
				 gfastCpePvidControlPvid
				 gfastCpePvidControlCpePort"
			::= { gfastCpePvidControl 1 }

		
		-- 1.3.6.1.4.1.6296.9.102.2.1.10.4.2
		gfastCpePvidControlSystemPort OBJECT-TYPE
			SYNTAX OCTET STRING (SIZE (0..32))
			MAX-ACCESS read-write
			STATUS current
			DESCRIPTION
				"The identifier for G.FAST CPE system port. ex) 1 | 1,4 | 1-4"
			::= { gfastCpePvidControl 2 }

		
		-- 1.3.6.1.4.1.6296.9.102.2.1.10.4.3
		gfastCpePvidControlPvid OBJECT-TYPE
			SYNTAX INTEGER (1..4094)
			MAX-ACCESS read-write
			STATUS current
			DESCRIPTION
				"The PVID of G.FAST CPE port."
			::= { gfastCpePvidControl 3 }

		
		-- 1.3.6.1.4.1.6296.9.102.2.1.10.4.4
		gfastCpePvidControlPort OBJECT-TYPE
			SYNTAX OCTET STRING (SIZE (0..16))
			MAX-ACCESS read-write
			STATUS current
			DESCRIPTION
				"The identifier for G.FAST CPE port. ex) 1 | 1,4 | 1-4
				(1-4 : LAN port, 5 : WAN port)"
			::= { gfastCpePvidControl 4 }

		
		-- 1.3.6.1.4.1.6296.9.102.2.1.10.4.5
		gfastCpePvidControlApply OBJECT-TYPE
			SYNTAX INTEGER
				{
				none(0),
				apply(1)
				}
			MAX-ACCESS read-write
			STATUS current
			DESCRIPTION
				"System Apply."
			::= { gfastCpePvidControl 5 }

		
	
	END

--
-- DASAN-GFAST-MIB.my
--
