--
-- phyTdmXcon.mib
-- MIB generated by MG-SOFT Visual MIB Builder Version 2.5 Build 225
-- Thursday, May 16, 2002 at 16:07:00
--

	TDM-XCON-MIB DEFINITIONS ::= BEGIN

		IMPORTS 
			OBJECT-GROUP			
				FROM SNMPv2-CONF			
			Integer32, OBJECT-TYPE, MODULE-IDENTITY			
				FROM SNMPv2-SMI			
			zhoneDsx			
				FROM Zhone			
			ZhoneRowStatus			
				FROM Zhone-TC;
	
	
-- 
-- 
		zhoneTdmXconMib MODULE-IDENTITY
			LAST-UPDATED "200009120959Z"
			ORGANIZATION
				"Zhone Technologies, Inc."
			CONTACT-INFO
				"  Postal: 
				           Zhone Technologies, Inc.
				           @ Zhone Way
				           7001 Oakport Street
				           Oakland, CA  94621
				           USA
				Toll-Free: +1 877-ZHONE20 (+1 877-946-6320)
				      Tel: +1-510-777-7000
				      Fax: +1-510-777-7001
				   E-mail: support@zhone.com
				
				"
			DESCRIPTION
				"The zhone Ds0 XCON MIB for configuration of the line, as each TS
				be assign to a service.  "
			REVISION "200009121333Z"
			DESCRIPTION
				"V01.00.00 - Initial Release"
			::= { zhoneDsx 11 }
		
	
	
--
-- Node definitions
--
	
		zhoneTdmXconObjectsGroup OBJECT-GROUP
			OBJECTS {  zhoneXconType, zhoneXconToPortGroupID, zhoneXconToTS, 
				zhoneXconHighway, zhoneXconRowStatus }
			STATUS current
			DESCRIPTION
				"Description."
			::= { zhoneTdmXconMib 1 }
		
		zhoneTdmXconTable OBJECT-TYPE
			SYNTAX SEQUENCE OF ZhoneTdmXconEntry
			MAX-ACCESS not-accessible
			STATUS current
			DESCRIPTION
				"The DS0 cross connect table.
				A table of the top level Tdm Xcon information in 
				a system.  Each xcon has an entry in table 
				for each connection provisioned for the
				xcon. For each xcon type in use, XconTS and 
				LineGroupId's. Type defines what kind of xcon i.e voice (fxs,
				fxo), data(v.35), or wan etc. "
			::= { zhoneDsx 12 }
		
		zhoneTdmXconEntry OBJECT-TYPE
			SYNTAX ZhoneTdmXconEntry
			MAX-ACCESS not-accessible
			STATUS current
			DESCRIPTION
				"An entry in the DS0 cross connect table."
			INDEX { zhoneXconFromWanGroupID, zhoneXconFromTS }
			::= { zhoneTdmXconTable 1 }
		
		ZhoneTdmXconEntry ::=
			SEQUENCE { 
				zhoneXconFromWanGroupID
					Integer32,
				zhoneXconFromTS
					Integer32,
				zhoneXconType
					INTEGER,
				zhoneXconToPortGroupID
					Integer32,
				zhoneXconToTS
					Integer32,
				zhoneXconHighway
					INTEGER,
				zhoneXconRowStatus
					ZhoneRowStatus
			 }

-- 
-- 
		zhoneXconFromWanGroupID OBJECT-TYPE
			SYNTAX Integer32 (1..2147483647)
			MAX-ACCESS not-accessible
			STATUS current
			DESCRIPTION
				"This is a unique number that is obtained
				by the zhoneXconFromWanGroupID field.
				               
				The range for zhoneXconFromWanGroupID is
				1..2147483647 .
				"
			::= { zhoneTdmXconEntry 1 }
		
-- 
-- 
		zhoneXconFromTS OBJECT-TYPE
			SYNTAX Integer32 (1..32)
			MAX-ACCESS not-accessible
			STATUS current
			DESCRIPTION
				"These are the time slot values, as there are 24 time slot for T1.
				 "
			::= { zhoneTdmXconEntry 2 }
		
-- 
		zhoneXconType OBJECT-TYPE
			SYNTAX INTEGER
				{
				none(1),
				voice(2),
				dropAndInsert(3),
				hdlc(4),
				wan(5),
				v35-56KInvertedClock(6),
				v35-56KNormalClock(7),
				v35-64KInvertedClock(8),
				v35-64KNormalClock(9),
				rs232ASync2400(10),
				rs232ASync4800(11),
				rs232ASync9600(12),
				rs232Sync56K(13),
				rs232Sync64K(14),
				rs232ASync2400b5(15),
				rs232ASync2400b10(16),
				rs232ASync2400b20(17),
				rs232ASync4800b5(18),
				rs232ASync4800b10(19),
				rs232ASync9600b5(20),
				rs232Sync9600(21),
				rs232Sync9600b5(22)
				}
			MAX-ACCESS read-create
			STATUS current
			DESCRIPTION
				"These are the xcon types for each TS selected in field
				zhoneXconFromTS and zhoneXconToTS.
				
				'voice(1)', making voice TS xcon.
				
				'dropAndInsert(2)', assigning a specific TS to be in
				drop and insert mode.
				
				'hdlc(3)', assigning a specific TS to be in hdlc mode,
				as this feature is used for TS24 of the DS1 to handle
				hdlc (IP) format type packets talking to CISCO routers.
				
				'wan(4)' when making xcon between two wans (DS1's)
				
				'v35-56KInvertedClock(5)', A data cross connect where 56K
				 rate is selected with clock Inverted option for that port.
				
				'v35-56KNormalClock(6)', A data cross connect where 56K
				 rate is selected with clock Normal option for that port.
				
				'v35-64KInvertedClock(7)', A data cross connect where 64K
				 rate is selected with clock Inverted option for that port.
				
				'v35-64KNormalClock(8)', A data cross connect where 64K
				 rate is selected with clock Normal option for that port.
				
				'rs232ASync2400(9)', ASYNC. data cross connect where bud rate of 2400
				is selected for that port.
				
				'rs232ASync4800(10)', ASYNC. data cross connect where bud rate of 4800
				is selected for that port.
				
				'rs232ASync9600(11)', ASYNC. data cross connect where bud rate of 9600
				is selected for that port.
				
				'rs232Sync56K(12)', SYNC. data cross connect where 56K rate
				is selected for that port.
				
				'rs232Sync64K(13)', SYNC. data cross connect where 64K rate
				is selected for that port.
				"
			::= { zhoneTdmXconEntry 3 }
		
		zhoneXconToPortGroupID OBJECT-TYPE
			SYNTAX Integer32 (1..2147483647)
			MAX-ACCESS read-create
			STATUS current
			DESCRIPTION
				"This is a unique number
				that is obtained by the zhoneXconToLineGroupId field.
				                
				The range for zhoneXconToLineGroupId is
				1..2147483647.
				"
			::= { zhoneTdmXconEntry 4 }
		
-- 
		zhoneXconToTS OBJECT-TYPE
			SYNTAX Integer32 (0..32)
			MAX-ACCESS read-create
			STATUS current
			DESCRIPTION
				"Its a time slot values, as there are 24 time slot for T1.
				0 will be only used when TS is not applicable. An example for a
				TS 0 usage is when zhoneWanLineGroupId along with zhoneXconFromTS
				is assign to Types like fxs or fxo where zhoneXconToTS is not required.
				so zhoneXconToTS will be a 0 entry.
				
				"
			::= { zhoneTdmXconEntry 5 }
		
-- 
		zhoneXconHighway OBJECT-TYPE
			SYNTAX INTEGER
				{
				na(1),
				busA(2),
				busB(3)
				}
			MAX-ACCESS read-create
			STATUS current
			DESCRIPTION
				"TDM highway buses where each TS will be mapped, a case like data
				xcon (V.35/RS232 activation).  Right now this field is not used 
				in Zplex10. so na(0) should be picked all the xcon's."
			::= { zhoneTdmXconEntry 6 }
		
		zhoneXconRowStatus OBJECT-TYPE
			SYNTAX ZhoneRowStatus
			MAX-ACCESS read-create
			STATUS current
			DESCRIPTION
				"In any case where a new row can be created either via
				the cli or zms there will always be a proprietary mib
				entity called zhrowstatus which has the basic 
				equivalence of the standard rowstatus object_id with 
				the following exceptions:
				
				1)	all column entries that are not defaulted are
				        documented in the DESCRIPTION for the object.
				2)	Only CREATE_AND_GO will be supported as all 
				        mib values for the row should be specified in 
				        a single request (via either zms or cli).
				
				Note that even though a standard mib may have a 
				rowstatus field already defined in it's mib, it will 
				not be supported and all sets to this field will 
				return a E_NOSUCHINSTANCE error code. 'get's to this 
				value will return an active value and no 
				error code so as not to fail a mibwalk or standard's 
				based browser.
				
				NOTE 1:
				ZhoneRowStatus will also support active(1) as 
				READ-ONLY instead of the conventional READ-WRITE or 
				READ-CREATE.  The row creation mechanism in the 
				SNMPv2 framework uses 3 actions states: createAndGo, 
				createAndWait, and destroy, combined with two desired 
				states: active and notInService, and a current state: 
				notReady.   
				
				ZhoneRowStatus will not support createAndWait,
				notInService, and notReady.  However, when an SNMP SET 
				using createAndGo succeeds, a new row is created - and 
				the RowStatus value automatically becomes active. Later
				if we want to delete the row, we can issue an SNMP SET 
				with RowStatus destroy.  We can subsequently SNMP GET 
				the RowStatus on a successfully created row, and the 
				returned RowStatus value will be active.  
				
				In the RowStatus interaction state machine/diagram, 
				the notInService(2) state is transitioned to via a 
				notInService action, which we will not support. 
				Similarly, the notReady(3) state is transitioned to 
				via the createAndWait action which we also don't 
				support.  So there is no reason to support 
				notInService(2) or notReady(3) because the operations 
				required to place the row in either of two states are 
				not supported and there is no legal way for our 
				supported RowStatus state machine to take us to either 
				notInService or notReady.
								
						
				ZhoneRowStatus implements the one-shot row creation 
				or activation form.  In one-shot mode, all values 
				required to activate a row in a single SET operation 
				along with an assignment of the status variable to 
				createAndGo.  If all requirements are satisfied and 
				an instance of the resource is created, then the status 
				of the row transitions to active.
				
				If the values of the row do not make sense, or there 
				were not enough values specified in the SET to fill in 
				the row, the agent returns an error code.  The only 
				appropriate error code is inconsistentValue (in SNMPv2)."
			::= { zhoneTdmXconEntry 7 }
		
	
	END

--
-- phyTdmXcon.mib
--
