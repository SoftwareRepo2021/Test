-- Toplevel MIB for Eltek power system

ELTEK-COMMON-MIB DEFINITIONS ::= BEGIN

IMPORTS
	MODULE-IDENTITY, enterprises
		FROM SNMPv2-SMI;

eltek MODULE-IDENTITY
	LAST-UPDATED "201110171334Z"
	ORGANIZATION 
		"ELTEK power System MIB Working Group"
	CONTACT-INFO 
		"Eltek R&D.
		         Postal: Eltek ASA
		         P.O. Box 3043
		         N-3003 Drammen
		         Norway
		         Tel: +47-32 20 32 00
		         Fax: +47-32 20 31 20
		         web:  www.eltek.com
		         "
	DESCRIPTION 
		"An ongoing effort toward a generic MIB for all ELTEK products.
		         Branch overview:
		         Aeongold branch will be 1
		         AL175 branch will be 2
		         AL6000 branch will be 3
		         Internal used branch will be 4
		         Internal used branch will be 5
		         OEM Smartpack branch will be 6
		         ELTEK Common branch will be 7 (SmartPack, MCU, AEON w/WebPower sw V2.x)
		         ELTEK Distributed branch will be 8 (SmartPack w/WebPower sw V3.x)
		         ELTEK Distributed V2 branch will be 9 (SmartPack w/WebPower sw V4.0)
		         ELTEK Distributed V3 branch will be 9 (SmartPack w/WebPower sw V4.1)
		         ELTEK Distributed V4 branch will be 9 (SmartPack w/WebPower sw V4.1, V4.2, V4.3, V4.5 and compack V1.0, V1.01, V1.02, V1.03)
		         ELTEK Distributed V5 branch will be 9 (SmartPack w/WebPower sw V4.1, V4.2, V4.3, V4.5, V4.6)
		         ELTEK Distributed V6 branch will be 9 (SmartPack2 sw V1.1, V1.2, V1.3)
		         ELTEK Distributed V7 branch will be 9 (SmartPack w/WebPower sw V4.1, V4.2, V4.3, V4.5, V4.6, V4.7 and compack V1.04, V1.05)
		         ELTEK eNexus MIB branch will be 10 (SmartPack2 V2.x, SmartPack S V2.x and Compack V2.x)
		         ELTEK Brasil office will have branch 11
		         ELTEK BMS-EM MIB will have branch 12
		                        "

	REVISION "201111250958Z"
	DESCRIPTION 
		"additional values to all alarm status enums"

	REVISION "201110171334Z"
	DESCRIPTION 
		"Major changes in OID order and names; added mains monitor energy log and generator fail status"

	REVISION "201108190916Z"
	DESCRIPTION 
		"hopefully final version. Stared implementation of eltek api"

	REVISION "201108190947Z"
	DESCRIPTION 
		"adjustment"

	REVISION "201105091128Z"
	DESCRIPTION 
		"fixed up mains group"
::= { enterprises 12148 }

END


-- This MIB was created using NuDesign Team's Visual MIBuilder (Ver 4.4).
