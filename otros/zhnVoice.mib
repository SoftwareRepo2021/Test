--
-- ZHNVOICE.my.mib
-- MIB generated by MG-SOFT Visual MIB Builder Version 3.0 Build 285
-- Monday, October 31, 2011 at 15:44:03
--

--  Copyright (C) 2010-2011 by Zhone Technologies.  All Rights Reserved.
-- ======================================================================
-- ==                                                                  ==
-- ==                    ZHNVOICE MIB                                  ==
-- ==                                                                  ==
-- ==  Copyright (C) 2010-2011 Zhone Technologies, Inc.                ==
-- ==  Confidential, Unpublished Property of Zhone Technologies.       ==
-- ==  Rights Reserved Under the Copyright Laws of the United States.  ==
-- ==                                                                  ==
-- ======================================================================

	ZHNVOICE DEFINITIONS ::= BEGIN
 
		IMPORTS
			OBJECT-GROUP, MODULE-COMPLIANCE, NOTIFICATION-GROUP			
				FROM SNMPv2-CONF			
			IpAddress, Integer32, Unsigned32, OBJECT-TYPE, MODULE-IDENTITY, 
			NOTIFICATION-TYPE			
				FROM SNMPv2-SMI			
			TruthValue, TEXTUAL-CONVENTION			
				FROM SNMPv2-TC			
			zhoneWtn			
				FROM Zhone			
			ZhoneRowStatus			
				FROM Zhone-TC;
	
	
--  1.3.6.1.4.1.5504.2.5.40
-- Oct 28, 2011
-- Oct 28, 2011
-- Feb 24, 2011
-- Apr 01, 2010
		-- 1.3.6.1.4.1.5504.2.5.40
		zhnVoice MODULE-IDENTITY 
			LAST-UPDATED "201110280000Z"		-- October 28, 2011 at 00:00 GMT
			ORGANIZATION 
				"Zhone Technologies, Inc."
			CONTACT-INFO 
				"Zhone Technologies, Inc.
				Florida Design Center
				8545 126th Avenue North
				Largo, FL 33773
				
				Toll-Free: +1 877-ZHONE20 (+1 877-946-6320)
				Tel: +1-510-777-7000
				Fax: +1-510-777-7001
				E-mail: support@zhone.com"
			DESCRIPTION 
				"This file defines the private Enterprise MIB extensions
				that define voice related objects supported by the Zhone
				VoIP CPEs. "
			REVISION "201004010000Z"		-- April 01, 2010 at 00:00 GMT
			DESCRIPTION 
				"First Draft"
			REVISION "201102240000Z"		-- February 24, 2011 at 00:00 GMT
			DESCRIPTION 
				"Second Draft"
			REVISION "201110280000Z"		-- October 28, 2011 at 00:00 GMT
			DESCRIPTION 
				"Added Voice Registration Up/Down Notifications"
			::= { zhoneWtn 40 }

		
	
--
-- Textual conventions
--
	
--  Textual Conventions
-- 
		VoiceProfileLineStateType ::= TEXTUAL-CONVENTION
			STATUS current
			DESCRIPTION 
				"Voice Profile line state for all lines in a profile.
				Enumeration of:
				   Disabled
				Quiescent
				Enabled
				"
			SYNTAX OCTET STRING (SIZE (0..16))

		DTMFMethodValues ::= TEXTUAL-CONVENTION
			STATUS current
			DESCRIPTION 
				"DTMF Method values.
				Enumeration of:
				   InBand
				   Rfc2833
				   SipInfo
				"
			SYNTAX OCTET STRING (SIZE (0..16))

		HookFlashMethodValues ::= TEXTUAL-CONVENTION
			STATUS current
			DESCRIPTION 
				"Hook Flash Method values.
				Enumeration of:
				   None
				   SipInfo
				"
			SYNTAX OCTET STRING (SIZE (0..16))

		VoiceTransportValues ::= TEXTUAL-CONVENTION
			STATUS current
			DESCRIPTION 
				"Transport protocol to be used in connecting to the 
				SIP server.
				Enumeration of:
				   UDP
				   TCP
				TLS
				SCTP
				"
			SYNTAX OCTET STRING (SIZE (0..32))

		VoiceLineStatusValues ::= TEXTUAL-CONVENTION
			STATUS current
			DESCRIPTION 
				"Current status of a voice line.
				Enumeration of:
				   Up
				   Initializing
				Registering
				Unregistering
				Error
				Testing
				   Quiescent
				   Disabled
				"
			SYNTAX OCTET STRING (SIZE (0..32))

		VoiceLineCallStateValues ::= TEXTUAL-CONVENTION
			STATUS current
			DESCRIPTION 
				"Current call state for a voice line.
				Enumeration of:
				   Idle
				   Calling
				Ringing
				Connecting
				InCall
				Hold
				   Disconnecting
				"
			SYNTAX OCTET STRING (SIZE (0..32))

	
--
-- Node definitions
--
	
--  1.3.6.1.4.1.5504.2.5.40.1
-- Notifications
		-- 1.3.6.1.4.1.5504.2.5.40.0
		zhnVoiceNotifications OBJECT IDENTIFIER ::= { zhnVoice 0 }

		
--  ****************************************************************************
-- 
-- Notifications - Voice
-- 
		-- 1.3.6.1.4.1.5504.2.5.40.0.1
		voiceRegistrationUp NOTIFICATION-TYPE
			STATUS current
			DESCRIPTION 
				"This notification is generated when the Voice Client has
				successfully registered with the configured Call Agent."
			::= { zhnVoiceNotifications 1 }

		
		-- 1.3.6.1.4.1.5504.2.5.40.0.2
		voiceRegistrationDown NOTIFICATION-TYPE
			STATUS current
			DESCRIPTION 
				"This notification is generated when the Voice Client 
				registration with the configured Call Agent fails."
			::= { zhnVoiceNotifications 2 }

		
--  Tables, Scalars
		-- 1.3.6.1.4.1.5504.2.5.40.1
		zhnVoiceServiceObjects OBJECT IDENTIFIER ::= { zhnVoice 1 }

		
--  Voice Services Objects 
-- TR-104 InternetGatewayDevice.Services.VoiceService.{i}.
-- 
-- 1.3.6.1.4.1.5504.2.5.40.1.1
-- 
		-- 1.3.6.1.4.1.5504.2.5.40.1.1
		voiceServiceTable OBJECT-TYPE
			SYNTAX SEQUENCE OF VoiceServiceEntry
			MAX-ACCESS not-accessible
			STATUS current
			DESCRIPTION
				"Table of voice services, including voice profiles, capabilities, and
				physical interfaces"
			::= { zhnVoiceServiceObjects 1 }

		
		-- 1.3.6.1.4.1.5504.2.5.40.1.1.1
		voiceServiceEntry OBJECT-TYPE
			SYNTAX VoiceServiceEntry
			MAX-ACCESS not-accessible
			STATUS current
			DESCRIPTION
				"Table of voice services including voice profiles, capabilities, and
				physical interfaces"
			INDEX { voiceServiceIndex }
			::= { voiceServiceTable 1 }

		
		VoiceServiceEntry ::=
			SEQUENCE { 
				voiceProfileNumberOfEntries
					Unsigned32,
				voiceBoundIfName
					OCTET STRING,
				voiceBoundIpAddr
					IpAddress,
				voiceServiceIndex
					Unsigned32
			 }

		-- 1.3.6.1.4.1.5504.2.5.40.1.1.1.1
		voiceProfileNumberOfEntries OBJECT-TYPE
			SYNTAX Unsigned32
			MAX-ACCESS read-only
			STATUS current
			DESCRIPTION
				"Voice Service Index"
			::= { voiceServiceEntry 1 }

		
		-- 1.3.6.1.4.1.5504.2.5.40.1.1.1.2
		voiceBoundIfName OBJECT-TYPE
			SYNTAX OCTET STRING (SIZE (0..63))
			MAX-ACCESS read-write
			STATUS current
			DESCRIPTION
				"Name of the network interface that the voice service should 
				run on. For example, brvlan300."
			::= { voiceServiceEntry 2 }

		
		-- 1.3.6.1.4.1.5504.2.5.40.1.1.1.3
		voiceBoundIpAddr OBJECT-TYPE
			SYNTAX IpAddress
			MAX-ACCESS read-only
			STATUS current
			DESCRIPTION
				"IP address of the network interface that the bound interface is 
				configured for."
			::= { voiceServiceEntry 3 }

		
		-- 1.3.6.1.4.1.5504.2.5.40.1.1.1.4
		voiceServiceIndex OBJECT-TYPE
			SYNTAX Unsigned32
			MAX-ACCESS read-only
			STATUS current
			DESCRIPTION
				"Voice Service Index"
			::= { voiceServiceEntry 4 }

		
--  Voice Services Capabilities Objects 
-- TR-104 InternetGatewayDevice.Services.VoiceService.{i}.Capabilities
-- 
		-- 1.3.6.1.4.1.5504.2.5.40.1.2
		capabilities OBJECT IDENTIFIER ::= { zhnVoiceServiceObjects 2 }

		
		-- 1.3.6.1.4.1.5504.2.5.40.1.2.1
		capabilitiesTable OBJECT-TYPE
			SYNTAX SEQUENCE OF CapabilitiesEntry
			MAX-ACCESS not-accessible
			STATUS current
			DESCRIPTION
				"Table of voice service capabilities "
			::= { capabilities 1 }

		
		-- 1.3.6.1.4.1.5504.2.5.40.1.2.1.1
		capabilitiesEntry OBJECT-TYPE
			SYNTAX CapabilitiesEntry
			MAX-ACCESS not-accessible
			STATUS current
			DESCRIPTION
				"Table of voice service capabilities"
			INDEX { voiceServiceIndex }
			::= { capabilitiesTable 1 }

		
		CapabilitiesEntry ::=
			SEQUENCE { 
				maxProfileCount
					Unsigned32,
				maxLineCount
					Unsigned32,
				maxSessionsPerLine
					Unsigned32,
				maxSessionCount
					Unsigned32,
				signalingProtocols
					OCTET STRING,
				regions
					OCTET STRING,
				rtcp
					TruthValue,
				srtp
					TruthValue,
				rtpRedundancy
					TruthValue,
				dscpCoupled
					TruthValue,
				ethernetTaggingCoupled
					TruthValue,
				pstnSoftSwitchOver
					TruthValue,
				faxT38
					TruthValue,
				faxPassThrough
					TruthValue,
				modemPassThrough
					TruthValue,
				toneGeneration
					TruthValue,
				ringGeneration
					TruthValue,
				digitMapCapabilities
					TruthValue,
				numberingPlan
					TruthValue,
				buttonMap
					TruthValue,
				voicePortTests
					TruthValue
			 }

		-- 1.3.6.1.4.1.5504.2.5.40.1.2.1.1.1
		maxProfileCount OBJECT-TYPE
			SYNTAX Unsigned32
			MAX-ACCESS read-only
			STATUS current
			DESCRIPTION
				"Maximum total number of distinct voice profiles supported."
			::= { capabilitiesEntry 1 }

		
		-- 1.3.6.1.4.1.5504.2.5.40.1.2.1.1.2
		maxLineCount OBJECT-TYPE
			SYNTAX Unsigned32
			MAX-ACCESS read-only
			STATUS current
			DESCRIPTION
				"Maximum total number of lines supported across all profiles.
				This parameter is applicable only for a VoIP endpoint."
			::= { capabilitiesEntry 2 }

		
		-- 1.3.6.1.4.1.5504.2.5.40.1.2.1.1.3
		maxSessionsPerLine OBJECT-TYPE
			SYNTAX Unsigned32
			MAX-ACCESS read-only
			STATUS current
			DESCRIPTION
				"Maximum number of voice sessions supported for any given line
				across all profiles. A value greater than one indicates support 
				for CPE provided conference calling. This parameter is applicable 
				only for a VoIP endpoint."
			::= { capabilitiesEntry 3 }

		
		-- 1.3.6.1.4.1.5504.2.5.40.1.2.1.1.4
		maxSessionCount OBJECT-TYPE
			SYNTAX Unsigned32
			MAX-ACCESS read-only
			STATUS current
			DESCRIPTION
				"Maximum total number of voice sessions supported across all lines 
				and profiles. This might differ from MaxLineCount if each line can 
				support more than one session for CPE provided conference calling. 
				This value MAY be less than the product of maxLineCount and 
				maxSessionsPerLine."
			::= { capabilitiesEntry 4 }

		
		-- 1.3.6.1.4.1.5504.2.5.40.1.2.1.1.5
		signalingProtocols OBJECT-TYPE
			SYNTAX OCTET STRING (SIZE (0..63))
			MAX-ACCESS read-only
			STATUS current
			DESCRIPTION
				"Comma-separated list of signaling protocols supported. Each item 
				is an enumeration of: 
				
				     SIP
				MGCP
				MGCP-NCS 
				H.248
				H.323  
				
				Each entry MAY be appended with a version indicator in the form 
				protocol/X.Y. For example: SIP/2.0"
			::= { capabilitiesEntry 5 }

		
		-- 1.3.6.1.4.1.5504.2.5.40.1.2.1.1.6
		regions OBJECT-TYPE
			SYNTAX OCTET STRING (SIZE (0..255))
			MAX-ACCESS read-only
			STATUS current
			DESCRIPTION
				"Comma-separated list of geographic regions supported by the CPE. 
				Each item in the list MUST be an alpha-2 (two-character alphabetic) 
				country code as specified by ISO 3166. An empty list indicates that 
				the CPE does not support region-based customization via the Region 
				parameter in the VoiceService.{i}.VoiceProfile.{i} object."
			::= { capabilitiesEntry 6 }

		
		-- 1.3.6.1.4.1.5504.2.5.40.1.2.1.1.7
		rtcp OBJECT-TYPE
			SYNTAX TruthValue
			MAX-ACCESS read-only
			STATUS current
			DESCRIPTION
				"Support for RTCP. A true value indicates support for the object 
				VoiceService.{i}.VoiceProfile.{i}.RTP.RTCP. This parameter is 
				applicable only for a VoIP endpoint."
			::= { capabilitiesEntry 7 }

		
		-- 1.3.6.1.4.1.5504.2.5.40.1.2.1.1.8
		srtp OBJECT-TYPE
			SYNTAX TruthValue
			MAX-ACCESS read-only
			STATUS current
			DESCRIPTION
				"Support for SRTP. A true value indicates support for the object 
				VoiceService.{i}.VoiceProfile.{i}.RTP.SRTP. This parameter is applicable 
				only for a VoIP endpoint."
			::= { capabilitiesEntry 8 }

		
		-- 1.3.6.1.4.1.5504.2.5.40.1.2.1.1.9
		rtpRedundancy OBJECT-TYPE
			SYNTAX TruthValue
			MAX-ACCESS read-only
			STATUS current
			DESCRIPTION
				"Support for RTP payload redundancy as defined in RFC 2198. A true 
				value indicates support for VoiceService.{i}.VoiceProfile.{i}.RTP.Redundancy.
				This parameter is applicable only for a VoIP endpoint."
			::= { capabilitiesEntry 9 }

		
		-- 1.3.6.1.4.1.5504.2.5.40.1.2.1.1.10
		dscpCoupled OBJECT-TYPE
			SYNTAX TruthValue
			MAX-ACCESS read-only
			STATUS current
			DESCRIPTION
				"A true value indicates that the CPE is constrained such that transmitted 
				call control packets use the same DSCP marking as transmitted RTP packets. 
				If the value is true, the CPE MUST NOT support the DSCPMark parameter for 
				call control. This parameter is applicable only for a VoIP endpoint."
			::= { capabilitiesEntry 10 }

		
		-- 1.3.6.1.4.1.5504.2.5.40.1.2.1.1.11
		ethernetTaggingCoupled OBJECT-TYPE
			SYNTAX TruthValue
			MAX-ACCESS read-only
			STATUS current
			DESCRIPTION
				"A true value indicates that the CPE is constrained such that transmitted 
				call control packets use the same Ethernet tagging (VLAN ID Ethernet Priority) 
				as transmitted RTP packets. If the value is true, the CPE MUST NOT support 
				the VLANIDMark or EthernetPriorityMark parameters within a call control 
				object (e.g., SIP, MGCP, or H323). This parameter is applicable only for a 
				VoIP endpoint."
			::= { capabilitiesEntry 11 }

		
		-- 1.3.6.1.4.1.5504.2.5.40.1.2.1.1.12
		pstnSoftSwitchOver OBJECT-TYPE
			SYNTAX TruthValue
			MAX-ACCESS read-only
			STATUS current
			DESCRIPTION
				"A true value indicates the CPE is capable of supporting the PSO_Activate 
				Facility Action, which allows a call to be switched to a PSTN FXO (Foreign 
				eXchange Office) line. This parameter is applicable only for a VoIP endpoint."
			::= { capabilitiesEntry 12 }

		
		-- 1.3.6.1.4.1.5504.2.5.40.1.2.1.1.13
		faxT38 OBJECT-TYPE
			SYNTAX TruthValue
			MAX-ACCESS read-only
			STATUS current
			DESCRIPTION
				"Support for T.38 fax. A true value indicates support for the object 
				VoiceService.{i}.VoiceProfile.{i}.FaxT38. This parameter is applicable only 
				for a VoIP endpoint."
			::= { capabilitiesEntry 13 }

		
		-- 1.3.6.1.4.1.5504.2.5.40.1.2.1.1.14
		faxPassThrough OBJECT-TYPE
			SYNTAX TruthValue
			MAX-ACCESS read-only
			STATUS current
			DESCRIPTION
				"Support for fax pass-through. A true value indicates support for the 
				parameter VoiceService.{i}.VoiceProfile.{i}.FaxPassThrough. This parameter 
				is applicable only for a VoIP endpoint."
			::= { capabilitiesEntry 14 }

		
		-- 1.3.6.1.4.1.5504.2.5.40.1.2.1.1.15
		modemPassThrough OBJECT-TYPE
			SYNTAX TruthValue
			MAX-ACCESS read-only
			STATUS current
			DESCRIPTION
				"Support for modem pass-through. A true value indicates support for the 
				parameter VoiceService.{i}.VoiceProfile.{i}.ModemPassThrough. This parameter 
				is applicable only for a VoIP endpoint."
			::= { capabilitiesEntry 15 }

		
		-- 1.3.6.1.4.1.5504.2.5.40.1.2.1.1.16
		toneGeneration OBJECT-TYPE
			SYNTAX TruthValue
			MAX-ACCESS read-only
			STATUS current
			DESCRIPTION
				"Support for tone generation. A true value indicates support for the object 
				VoiceService.{i}.VoiceProfile.{i}.Tone. A true value also indicates that the 
				ToneDescriptionsEditable, PatternBasedToneGeneration, and FileBasedToneGeneration
				parameters in this object are present. This parameter is applicable only for a 
				VoIP endpoint."
			::= { capabilitiesEntry 16 }

		
		-- 1.3.6.1.4.1.5504.2.5.40.1.2.1.1.17
		ringGeneration OBJECT-TYPE
			SYNTAX TruthValue
			MAX-ACCESS read-only
			STATUS current
			DESCRIPTION
				"Support for ring generation. A true value indicates support for control of 
				ring generation via the VoiceService.{i}.VoiceProfile.{i}.Line.{i}.Ringer 
				object. A true value also indicates that the RingDescriptionsEditable, 
				PatternBasedRingGeneration, and FileBasedRingGeneration parameters in this 
				object are present.  This parameter is applicable only for a VoIP endpoint."
			::= { capabilitiesEntry 17 }

		
		-- 1.3.6.1.4.1.5504.2.5.40.1.2.1.1.18
		digitMapCapabilities OBJECT-TYPE
			SYNTAX TruthValue
			MAX-ACCESS read-only
			STATUS current
			DESCRIPTION
				"Support for a configurable digit map string. A true value indicates full 
				support for the VoiceService.{i}.VoiceProfile.{i}.DigitMap parameter."
			::= { capabilitiesEntry 18 }

		
		-- 1.3.6.1.4.1.5504.2.5.40.1.2.1.1.19
		numberingPlan OBJECT-TYPE
			SYNTAX TruthValue
			MAX-ACCESS read-only
			STATUS current
			DESCRIPTION
				"Support for a configurable numbering plan. A true value indicates support 
				for a configurable numbering plan via the VoiceService.{i}.VoiceProfile.{i}.
				NumberingPlan object. This parameter is applicable only for a VoIP endpoint."
			::= { capabilitiesEntry 19 }

		
		-- 1.3.6.1.4.1.5504.2.5.40.1.2.1.1.20
		buttonMap OBJECT-TYPE
			SYNTAX TruthValue
			MAX-ACCESS read-only
			STATUS current
			DESCRIPTION
				"Support for a configurable button map. A true value indicates support for 
				a configurable button map via the VoiceService.{i}.VoiceProfile.{i}.ButtonMap 
				NumberingPlan object. This parameter is applicable only for a VoIP endpoint."
			::= { capabilitiesEntry 20 }

		
		-- 1.3.6.1.4.1.5504.2.5.40.1.2.1.1.21
		voicePortTests OBJECT-TYPE
			SYNTAX TruthValue
			MAX-ACCESS read-only
			STATUS current
			DESCRIPTION
				"Support for remotely accessible voice-port tests. A true value indicates 
				support for the VoiceService.{i}.PhyInterface.{i}.Tests object. This parameter 
				is applicable only for a VoIP endpoint."
			::= { capabilitiesEntry 21 }

		
--  Voice Services SIP Capabilities Objects 
-- TR-104 InternetGatewayDevice.Services.VoiceService.{i}.Capabilities.SIP
-- 
		-- 1.3.6.1.4.1.5504.2.5.40.1.2.2
		capabilitiesSIPTable OBJECT-TYPE
			SYNTAX SEQUENCE OF CapabilitiesSIPEntry
			MAX-ACCESS not-accessible
			STATUS current
			DESCRIPTION
				"Table of SIP-specific capabilities. Applicable only if SIP is among the list of supported 
				protocols."
			::= { capabilities 2 }

		
		-- 1.3.6.1.4.1.5504.2.5.40.1.2.2.1
		capabilitiesSIPEntry OBJECT-TYPE
			SYNTAX CapabilitiesSIPEntry
			MAX-ACCESS not-accessible
			STATUS current
			DESCRIPTION
				"Table of SIP-specific capabilities. Applicable only if SIP is among the list of supported 
				protocols."
			INDEX { voiceServiceIndex }
			::= { capabilitiesSIPTable 1 }

		
		CapabilitiesSIPEntry ::=
			SEQUENCE { 
				role
					OCTET STRING,
				extensionsSIP
					OCTET STRING,
				transports
					OCTET STRING,
				uriSchemes
					OCTET STRING,
				eventSubscription
					TruthValue,
				responseMap
					TruthValue,
				tlsKeyExchangeProtocols
					OCTET STRING
			 }

		-- 1.3.6.1.4.1.5504.2.5.40.1.2.2.1.1
		role OBJECT-TYPE
			SYNTAX OCTET STRING (SIZE (0..47))
			MAX-ACCESS read-only
			STATUS current
			DESCRIPTION
				"The role of this VoIP CPE. Enumeration of: 
				
				UserAgent
				BackToBackUserAgents
				OutboundProxy. 
				
				A single VoiceService instance MUST have only one role. If a device
				includes the capabilities for more than one role, each role MUST be 
				represented as separate VoiceService instance."
			::= { capabilitiesSIPEntry 1 }

		
		-- 1.3.6.1.4.1.5504.2.5.40.1.2.2.1.2
		extensionsSIP OBJECT-TYPE
			SYNTAX OCTET STRING (SIZE (0..255))
			MAX-ACCESS read-only
			STATUS current
			DESCRIPTION
				"Comma-separated list of SIP extension methods supported. SIP extension methods 
				MUST be in the form of the method name in upper case. The list MAY include 
				vendor-specific extensions, which MUST use the format defined in TR-106. 
				
				Examples: 
				    REFER
				INFO
				X_EXAMPLE-COM_MyExt
				"
			::= { capabilitiesSIPEntry 2 }

		
		-- 1.3.6.1.4.1.5504.2.5.40.1.2.2.1.3
		transports OBJECT-TYPE
			SYNTAX OCTET STRING (SIZE (0..47))
			MAX-ACCESS read-only
			STATUS current
			DESCRIPTION
				"Comma-separated list of SIP transport protocols supported. Each entry is an 
				enumeration of: 
				
				   UDP
				   TCP
				   TLS
				   SCTP
				   
				The list MAY include vendor-specific transports, which MUST use the format 
				defined in TR-106"
			::= { capabilitiesSIPEntry 3 }

		
		-- 1.3.6.1.4.1.5504.2.5.40.1.2.2.1.4
		uriSchemes OBJECT-TYPE
			SYNTAX OCTET STRING (SIZE (0..255))
			MAX-ACCESS read-only
			STATUS current
			DESCRIPTION
				"Comma-separated list of URI schemes supported beyond the URI schemes 
				required by the SIP specification. Each URI scheme is given by the 
				URI prefix, without the colon separator. 
				
				Example: tel, fax "
			::= { capabilitiesSIPEntry 4 }

		
		-- 1.3.6.1.4.1.5504.2.5.40.1.2.2.1.5
		eventSubscription OBJECT-TYPE
			SYNTAX TruthValue
			MAX-ACCESS read-only
			STATUS current
			DESCRIPTION
				"Support for SIP event subscription. A true value indicates support for 
				the VoiceService.{i}.VoiceProfile.{i}.SIP.EventSubscribe and 
				VoiceService.{i}.VoiceProfile.{i}.Line.{i}.SIP.EventSubscribe.{i} objects."
			::= { capabilitiesSIPEntry 5 }

		
		-- 1.3.6.1.4.1.5504.2.5.40.1.2.2.1.6
		responseMap OBJECT-TYPE
			SYNTAX TruthValue
			MAX-ACCESS read-only
			STATUS current
			DESCRIPTION
				"Support for SIP response map. A true value indicates support for the 
				VoiceService.{i}.VoiceProfile.{i}.SIP.ResponseMap object. This parameter 
				is applicable only for a VoIP endpoint."
			::= { capabilitiesSIPEntry 6 }

		
		-- 1.3.6.1.4.1.5504.2.5.40.1.2.2.1.7
		tlsKeyExchangeProtocols OBJECT-TYPE
			SYNTAX OCTET STRING (SIZE (0..31))
			MAX-ACCESS read-only
			STATUS current
			DESCRIPTION
				"Comma-separated list of authentication protocols supported for TLS transport. 
				Each item listed is an enumeration of: 
				    RSA
				DSS 
				
				The list MAY include vendor-specific protocols, which MUST use the format 
				defined in TR-106. Support for this parameter is applicable only if the 
				Transports parameter in this object includes the value TLS and the 
				TLSEncryptionProtocols parameter in this object is present and non-empty
				and includes at least one value other than Null"
			::= { capabilitiesSIPEntry 7 }

		
--  Voice Services MGCP Capabilities Objects 
-- TR-104 InternetGatewayDevice.Services.VoiceService.{i}.Capabilities.MGCP
-- 
		-- 1.3.6.1.4.1.5504.2.5.40.1.2.3
		capabilitiesMGCPTable OBJECT-TYPE
			SYNTAX SEQUENCE OF CapabilitiesMGCPEntry
			MAX-ACCESS not-accessible
			STATUS current
			DESCRIPTION
				"Table of MGCP-specific capabilities. Applicable only if MGCP is among the list of supported 
				protocols."
			::= { capabilities 3 }

		
		-- 1.3.6.1.4.1.5504.2.5.40.1.2.3.1
		capabilitiesMGCPEntry OBJECT-TYPE
			SYNTAX CapabilitiesMGCPEntry
			MAX-ACCESS not-accessible
			STATUS current
			DESCRIPTION
				"Table of MGCP-specific capabilities. Applicable only if MGCP is among the list of supported 
				protocols."
			INDEX { voiceServiceIndex }
			::= { capabilitiesMGCPTable 1 }

		
		CapabilitiesMGCPEntry ::=
			SEQUENCE { 
				extensionsMGCP
					OCTET STRING
			 }

		-- 1.3.6.1.4.1.5504.2.5.40.1.2.3.1.1
		extensionsMGCP OBJECT-TYPE
			SYNTAX OCTET STRING (SIZE (0..255))
			MAX-ACCESS read-only
			STATUS current
			DESCRIPTION
				"Comma-separated list of MGCP extension methods supported. MGCP extension methods 
				MUST be in the form of the method name in upper case. The list MAY include 
				vendor-specific extensions, which MUST use the format defined in TR-106. 
				
				Examples: 
				    REFER
				INFO
				X_EXAMPLE-COM_MyExt
				"
			::= { capabilitiesMGCPEntry 1 }

		
--  Voice Services Codecs Capabilities Objects 
-- TR-104 InternetGatewayDevice.Services.VoiceService.{i}.Capabilities.Codecs.{i}
-- 
		-- 1.3.6.1.4.1.5504.2.5.40.1.2.4
		capabilitiesCodecsTable OBJECT-TYPE
			SYNTAX SEQUENCE OF CapabilitiesCodecsEntry
			MAX-ACCESS not-accessible
			STATUS current
			DESCRIPTION
				"Table to describe the set of supported codecs. Each entry refers to a 
				distinct combination of codec and bit rate. The table MUST include a 
				distinct entry for each supported combination of these parameters. 
				Applicable only for a VoIP endpoint."
			::= { capabilities 4 }

		
		-- 1.3.6.1.4.1.5504.2.5.40.1.2.4.1
		capabilitiesCodecsEntry OBJECT-TYPE
			SYNTAX CapabilitiesCodecsEntry
			MAX-ACCESS not-accessible
			STATUS current
			DESCRIPTION
				"The Codecs Service table MUST include a distinct entry for each 
				supported combination of these parameters."
			INDEX { voiceServiceIndex, codecIndex }
			::= { capabilitiesCodecsTable 1 }

		
		CapabilitiesCodecsEntry ::=
			SEQUENCE { 
				codecIndex
					Unsigned32,
				entryID
					Unsigned32,
				codec
					OCTET STRING,
				bitRate
					Unsigned32,
				packetizationPeriod
					OCTET STRING,
				silenceSuppression
					TruthValue
			 }

		-- 1.3.6.1.4.1.5504.2.5.40.1.2.4.1.1
		codecIndex OBJECT-TYPE
			SYNTAX Unsigned32
			MAX-ACCESS read-only
			STATUS current
			DESCRIPTION
				"Codecs table index"
			::= { capabilitiesCodecsEntry 1 }

		
		-- 1.3.6.1.4.1.5504.2.5.40.1.2.4.1.2
		entryID OBJECT-TYPE
			SYNTAX Unsigned32
			MAX-ACCESS read-only
			STATUS current
			DESCRIPTION
				"Codecs table index"
			::= { capabilitiesCodecsEntry 2 }

		
		-- 1.3.6.1.4.1.5504.2.5.40.1.2.4.1.3
		codec OBJECT-TYPE
			SYNTAX OCTET STRING (SIZE (0..63))
			MAX-ACCESS read-only
			STATUS current
			DESCRIPTION
				"Identifier of the type of codec. Enumeration of: 
				G.711MuLaw
				G.711ALaw
				G.726
				G.729
				G.729a
				G.729e
				G.728
				G.723.1
				G.722
				G.722.1
				G.722.2
				GSM-FR
				GSM-HR
				GSM-EFR
				iLBC
				
				The parameter MAY instead be a vendor-specific codec, which MUST be 
				in the format defined in TR-106. For example: X_EXAMPLE-COM_MyCodec"
			::= { capabilitiesCodecsEntry 3 }

		
		-- 1.3.6.1.4.1.5504.2.5.40.1.2.4.1.4
		bitRate OBJECT-TYPE
			SYNTAX Unsigned32
			MAX-ACCESS read-only
			STATUS current
			DESCRIPTION
				"Bit rate, in bits per second. The value MUST be among the values 
				appropriate for the specified codec."
			::= { capabilitiesCodecsEntry 4 }

		
		-- 1.3.6.1.4.1.5504.2.5.40.1.2.4.1.5
		packetizationPeriod OBJECT-TYPE
			SYNTAX OCTET STRING (SIZE (0..63))
			MAX-ACCESS read-only
			STATUS current
			DESCRIPTION
				"Comma-separate list of supported packetization periods, in milliseconds, 
				or continuous ranges of packetization periods. Ranges are indicated as a 
				hyphen-separated pair of unsigned integers. Examples: 
				    20 indicates a single discrete value 
				10, 20, 30 indicates a set of discrete values. 
				5-40 indicates a continuous inclusive range. 
				5-10, 20, 30 indicates a continuous range in addition to a set of discrete values. 
				
				A range MUST only be indicated if all values within the range are supported."
			::= { capabilitiesCodecsEntry 5 }

		
		-- 1.3.6.1.4.1.5504.2.5.40.1.2.4.1.6
		silenceSuppression OBJECT-TYPE
			SYNTAX TruthValue
			MAX-ACCESS read-only
			STATUS current
			DESCRIPTION
				"Indicates support for silence suppression for this codec."
			::= { capabilitiesCodecsEntry 6 }

		
--  Voice Services Voice Profile Objects 
-- TR-104 InternetGatewayDevice.Services.VoiceService.{i}.VoiceProfile.{i}
-- 
		-- 1.3.6.1.4.1.5504.2.5.40.1.3
		voiceProfiles OBJECT IDENTIFIER ::= { zhnVoiceServiceObjects 3 }

		
		-- 1.3.6.1.4.1.5504.2.5.40.1.3.1
		voiceProfileTable OBJECT-TYPE
			SYNTAX SEQUENCE OF VoiceProfileEntry
			MAX-ACCESS not-accessible
			STATUS current
			DESCRIPTION
				"Table of voice profile objects"
			::= { voiceProfiles 1 }

		
		-- 1.3.6.1.4.1.5504.2.5.40.1.3.1.1
		voiceProfileEntry OBJECT-TYPE
			SYNTAX VoiceProfileEntry
			MAX-ACCESS not-accessible
			STATUS current
			DESCRIPTION
				"Object associated with a collection of voice lines with common characteristics. 
				By default, a single VoiceProfile object SHOULD be present in a VoiceService, initially 
				in the disabled state."
			INDEX { voiceServiceIndex, voiceProfileIndex }
			::= { voiceProfileTable 1 }

		
		VoiceProfileEntry ::=
			SEQUENCE { 
				voiceProfileIndex
					Unsigned32,
				voiceProfileEnable
					VoiceProfileLineStateType,
				voiceProfileReset
					TruthValue,
				voiceProfileNumberOfLines
					Unsigned32,
				voiceProfileName
					OCTET STRING,
				voiceProfileSignalingProtocol
					OCTET STRING,
				voiceProfileMaxSessions
					Unsigned32,
				voiceProfileDtmfMethod
					DTMFMethodValues,
				voiceProfileDtmfMethodG711
					DTMFMethodValues,
				voiceProfileHookFlashMethod
					HookFlashMethodValues,
				voiceProfileRegion
					OCTET STRING,
				voiceProfileDigitMap
					OCTET STRING,
				voiceProfileDigitMapEnable
					TruthValue,
				voiceProfileStunEnable
					TruthValue,
				voiceProfileStunServer
					OCTET STRING,
				voiceProfileStunServerPort
					Unsigned32,
				voiceProfileLogServer
					OCTET STRING,
				voiceProfileLogServerPort
					Unsigned32,
				voiceProfileSpNum
					Unsigned32,
				voiceProfileV18Support
					TruthValue
			 }

		-- 1.3.6.1.4.1.5504.2.5.40.1.3.1.1.1
		voiceProfileIndex OBJECT-TYPE
			SYNTAX Unsigned32 (0..20)
			MAX-ACCESS read-only
			STATUS current
			DESCRIPTION
				"Voice Profile Index"
			::= { voiceProfileEntry 1 }

		
		-- 1.3.6.1.4.1.5504.2.5.40.1.3.1.1.2
		voiceProfileEnable OBJECT-TYPE
			SYNTAX VoiceProfileLineStateType
			MAX-ACCESS read-write
			STATUS current
			DESCRIPTION
				"Enables or disables all lines in this profile, or places it into 
				a quiescent state. Enumeration of: 
				    Disabled
				Quiescent
				Enabled
				On creation, a profile MUST be in the Disabled state. In the Quiescent 
				state, in-progress sessions remain intact, but no new sessions are allowed. 
				Support for the Quiescent state in a CPE is optional. If this parameter 
				is set to Quiescent in a CPE that does not support the Quiescent state, 
				it MUST treat it the same as the Disabled state."
			::= { voiceProfileEntry 2 }

		
		-- 1.3.6.1.4.1.5504.2.5.40.1.3.1.1.3
		voiceProfileReset OBJECT-TYPE
			SYNTAX TruthValue
			MAX-ACCESS read-write
			STATUS current
			DESCRIPTION
				"When written as true, forces the all lines in this profile to be reset, 
				causing it to re-initialize and perform all start-up actions such as 
				registration. Always False when read."
			::= { voiceProfileEntry 3 }

		
		-- 1.3.6.1.4.1.5504.2.5.40.1.3.1.1.4
		voiceProfileNumberOfLines OBJECT-TYPE
			SYNTAX Unsigned32
			MAX-ACCESS read-only
			STATUS current
			DESCRIPTION
				"Number of instances of Line within this VoiceProfile. Applicable only 
				for a VoIP endpoint."
			::= { voiceProfileEntry 4 }

		
		-- 1.3.6.1.4.1.5504.2.5.40.1.3.1.1.5
		voiceProfileName OBJECT-TYPE
			SYNTAX OCTET STRING (SIZE (0..63))
			MAX-ACCESS read-write
			STATUS current
			DESCRIPTION
				"Human-readable string to identify the profile instance."
			::= { voiceProfileEntry 5 }

		
		-- 1.3.6.1.4.1.5504.2.5.40.1.3.1.1.6
		voiceProfileSignalingProtocol OBJECT-TYPE
			SYNTAX OCTET STRING (SIZE (0..31))
			MAX-ACCESS read-write
			STATUS current
			DESCRIPTION
				"The protocol to be used for this profile. A single protocol selected 
				from among the available protocols indicated in 
				VoiceService.{i}.Capabilities.SignalingProtocols."
			::= { voiceProfileEntry 6 }

		
		-- 1.3.6.1.4.1.5504.2.5.40.1.3.1.1.7
		voiceProfileMaxSessions OBJECT-TYPE
			SYNTAX Unsigned32
			MAX-ACCESS read-write
			STATUS current
			DESCRIPTION
				"Limit on the number of simultaneous voice sessions across all lines in this
				profile. Must be less than or equal to VoiceService.{i}.Capabilities.MaxSessionCount. 
				(This MAY be greater than the number of lines if each line can support more 
				than one session, for example for CPE provided conference calling.)"
			::= { voiceProfileEntry 7 }

		
		-- 1.3.6.1.4.1.5504.2.5.40.1.3.1.1.8
		voiceProfileDtmfMethod OBJECT-TYPE
			SYNTAX DTMFMethodValues
			MAX-ACCESS read-write
			STATUS current
			DESCRIPTION
				"Method by which DTMF digits MUST be passed. Enumeration of: 
				InBand
				RFC2833
				SIPInfo
				If the parameter dtmfMethodG711 is non-empty, then this parameter applies 
				only when the current codec is not G.711. The value SIPInfo is applicable 
				only if the SignalingProtocol is SIP. This parameter is applicable only 
				for a VoIP endpoint."
			::= { voiceProfileEntry 8 }

		
		-- 1.3.6.1.4.1.5504.2.5.40.1.3.1.1.9
		voiceProfileDtmfMethodG711 OBJECT-TYPE
			SYNTAX DTMFMethodValues
			MAX-ACCESS read-write
			STATUS current
			DESCRIPTION
				"Method by which DTMF digits MUST be passed if the current codec is G.711. 
				Enumeration of: 
				    InBand
				RFC2833
				SIPInfo
				 An empty value for this parameter indicates that the value of the dtmfMethod 
				 parameter is to apply whether or not the current codec is G.711. The value 
				 SIPInfo is applicable only if the SignalingProtocol is SIP. This parameter 
				 is applicable only for a VoIP endpoint."
			::= { voiceProfileEntry 9 }

		
		-- 1.3.6.1.4.1.5504.2.5.40.1.3.1.1.10
		voiceProfileHookFlashMethod OBJECT-TYPE
			SYNTAX HookFlashMethodValues
			MAX-ACCESS read-write
			STATUS current
			DESCRIPTION
				"This object specifies which hookflash relay method to use. A value of None 
				implies hook flash will be handled locally. A value of SIPInfo implies the
				hook flash will be sent via the SIP info."
			::= { voiceProfileEntry 10 }

		
		-- 1.3.6.1.4.1.5504.2.5.40.1.3.1.1.11
		voiceProfileRegion OBJECT-TYPE
			SYNTAX OCTET STRING (SIZE (0..7))
			MAX-ACCESS read-write
			STATUS current
			DESCRIPTION
				"The geographic region associated with this profile. This MAY be used by 
				the CPE to customize localization settings. The value MUST be either one 
				value selected from among the available regions indicated in 
				VoiceService.{i}.Capabilities.Regions, or MAY be empty. An empty value 
				indicates that the region is unspecified and the CPE SHOULD use default
				localization settings. 
				
				This parameter is applicable only if VoiceService.{i}.Capabilities.Regions 
				is non-empty."
			::= { voiceProfileEntry 11 }

		
		-- 1.3.6.1.4.1.5504.2.5.40.1.3.1.1.12
		voiceProfileDigitMap OBJECT-TYPE
			SYNTAX OCTET STRING (SIZE (0..255))
			MAX-ACCESS read-write
			STATUS current
			DESCRIPTION
				"Digit map controlling the transmission of dialed digit information. The 
				string defines the criteria to be met as digits are collected before an 
				outgoing request (e.g., a SIP INVITE) can be initiated. The syntax of this 
				parameter is exactly the syntax used by MGCP as defined in RFC3435, 
				section 2.1.5. 
				
				This parameter is applicable only if the device supports a dialing mechanism 
				for which a dialing plan is needed (for example, a device with an explicit 
				Dial button may not need to be aware of the dialing plan) and if the device 
				does not already support a dialing plan mechanism for this profile 
				(e.g. in-band via MGCP).
				
				If this object is supported, the capability VoiceService.{i}.Capabilities.DigitMap 
				MUST be equal to true. Applicable only for a VoIP endpoint."
			::= { voiceProfileEntry 12 }

		
		-- 1.3.6.1.4.1.5504.2.5.40.1.3.1.1.13
		voiceProfileDigitMapEnable OBJECT-TYPE
			SYNTAX TruthValue
			MAX-ACCESS read-write
			STATUS current
			DESCRIPTION
				"Enables the use of the DigitMap parameter in this object. When enabled, 
				the content of the VoiceService.{i}.VoiceProfile.{i}.NumberingPlan object, 
				if present, MUST be ignored. 
				
				This parameter is required if and only if both the digitMap object 
				and the VoiceService.{i}.VoiceProfile.{i}.NumberingPlan object are 
				present. Applicable only for a VoIP endpoint."
			::= { voiceProfileEntry 13 }

		
		-- 1.3.6.1.4.1.5504.2.5.40.1.3.1.1.14
		voiceProfileStunEnable OBJECT-TYPE
			SYNTAX TruthValue
			MAX-ACCESS read-write
			STATUS current
			DESCRIPTION
				"Enable or disable use of STUN to allow operation through NAT. Note: 
				enabling STUN is to be interpreted as enabling the use of STUN for 
				discovery, not use as a keep-alive mechanism."
			::= { voiceProfileEntry 14 }

		
		-- 1.3.6.1.4.1.5504.2.5.40.1.3.1.1.15
		voiceProfileStunServer OBJECT-TYPE
			SYNTAX OCTET STRING (SIZE (0..255))
			MAX-ACCESS read-write
			STATUS current
			DESCRIPTION
				"Domain name or IP address of the STUN server."
			::= { voiceProfileEntry 15 }

		
		-- 1.3.6.1.4.1.5504.2.5.40.1.3.1.1.16
		voiceProfileStunServerPort OBJECT-TYPE
			SYNTAX Unsigned32
			MAX-ACCESS read-write
			STATUS current
			DESCRIPTION
				"STUN server port number."
			::= { voiceProfileEntry 16 }

		
		-- 1.3.6.1.4.1.5504.2.5.40.1.3.1.1.17
		voiceProfileLogServer OBJECT-TYPE
			SYNTAX OCTET STRING (SIZE (0..63))
			MAX-ACCESS read-write
			STATUS current
			DESCRIPTION
				"Domain name or IP address of the Log server."
			::= { voiceProfileEntry 17 }

		
		-- 1.3.6.1.4.1.5504.2.5.40.1.3.1.1.18
		voiceProfileLogServerPort OBJECT-TYPE
			SYNTAX Unsigned32
			MAX-ACCESS read-write
			STATUS current
			DESCRIPTION
				"Log server port number."
			::= { voiceProfileEntry 18 }

		
		-- 1.3.6.1.4.1.5504.2.5.40.1.3.1.1.19
		voiceProfileSpNum OBJECT-TYPE
			SYNTAX Unsigned32
			MAX-ACCESS read-write
			STATUS current
			DESCRIPTION
				"Service Provider number."
			::= { voiceProfileEntry 19 }

		
		-- 1.3.6.1.4.1.5504.2.5.40.1.3.1.1.20
		voiceProfileV18Support OBJECT-TYPE
			SYNTAX TruthValue
			MAX-ACCESS read-write
			STATUS current
			DESCRIPTION
				"Enable or disable v18 support."
			::= { voiceProfileEntry 20 }

		
--  Voice Services Voice Profile Service Provider Objects 
-- TR-104 InternetGatewayDevice.Services.VoiceService.{i}.VoiceProfile.{i}.ServiceProviderInfo
-- 
		-- 1.3.6.1.4.1.5504.2.5.40.1.3.2
		voiceProfileServiceProviderTable OBJECT-TYPE
			SYNTAX SEQUENCE OF VoiceProfileServiceProviderEntry
			MAX-ACCESS not-accessible
			STATUS current
			DESCRIPTION
				"Table of voice profile service provider objects"
			::= { voiceProfiles 2 }

		
		-- 1.3.6.1.4.1.5504.2.5.40.1.3.2.1
		voiceProfileServiceProviderEntry OBJECT-TYPE
			SYNTAX VoiceProfileServiceProviderEntry
			MAX-ACCESS not-accessible
			STATUS current
			DESCRIPTION
				"Service provider objects associated with a specific voice profile."
			INDEX { voiceServiceIndex, voiceProfileIndex }
			::= { voiceProfileServiceProviderTable 1 }

		
		VoiceProfileServiceProviderEntry ::=
			SEQUENCE { 
				voiceProfileServiceProviderName
					OCTET STRING
			 }

		-- 1.3.6.1.4.1.5504.2.5.40.1.3.2.1.1
		voiceProfileServiceProviderName OBJECT-TYPE
			SYNTAX OCTET STRING (SIZE (0..255))
			MAX-ACCESS read-only
			STATUS current
			DESCRIPTION
				"Human-readable string identifying the service provider. "
			::= { voiceProfileServiceProviderEntry 1 }

		
--  Voice Services Voice Profile SIP Objects 
-- TR-104 InternetGatewayDevice.Services.VoiceService.{i}.VoiceProfile.{i}.SIP
-- 
		-- 1.3.6.1.4.1.5504.2.5.40.1.3.3
		voiceProfileSIPTable OBJECT-TYPE
			SYNTAX SEQUENCE OF VoiceProfileSIPEntry
			MAX-ACCESS not-accessible
			STATUS current
			DESCRIPTION
				"Table of SIP objects for a specific voice profile"
			::= { voiceProfiles 3 }

		
		-- 1.3.6.1.4.1.5504.2.5.40.1.3.3.1
		voiceProfileSIPEntry OBJECT-TYPE
			SYNTAX VoiceProfileSIPEntry
			MAX-ACCESS not-accessible
			STATUS current
			DESCRIPTION
				"SIP objects associated with a specific voice profile."
			INDEX { voiceServiceIndex, voiceProfileIndex }
			::= { voiceProfileSIPTable 1 }

		
		VoiceProfileSIPEntry ::=
			SEQUENCE { 
				voiceProfileSIPProxyServer
					OCTET STRING,
				voiceProfileSIPProxyServerPort
					Unsigned32,
				voiceProfileSIPProxyServerTransport
					VoiceTransportValues,
				voiceProfileSIPRegistrarServer
					OCTET STRING,
				voiceProfileSIPRegistrarServerPort
					Unsigned32,
				voiceProfileSIPRegistrarServerTransport
					VoiceTransportValues,
				voiceProfileSIPToTagMatching
					TruthValue,
				voiceProfileSIPMusicServer
					OCTET STRING,
				voiceProfileSIPMusicServerPort
					Unsigned32,
				voiceProfileSIPPlarGateway
					OCTET STRING,
				voiceProfileSIPPlarPort
					Unsigned32,
				voiceProfileSIPUserAgentDomain
					OCTET STRING,
				voiceProfileSIPUserAgentPort
					Unsigned32,
				voiceProfileSIPUserAgentTransport
					VoiceTransportValues,
				voiceProfileSIPOutboundProxy
					OCTET STRING,
				voiceProfileSIPOutboundProxyPort
					Unsigned32,
				voiceProfileSIPOrganization
					OCTET STRING,
				voiceProfileSIPRegistrationPeriod
					Unsigned32,
				voiceProfileSIPRegisterExpires
					Unsigned32,
				voiceProfileSIPRegisterRetryInterval
					Unsigned32,
				voiceProfileSIPDSCPMark
					Unsigned32,
				voiceProfileSIPVLANIDMark
					Integer32,
				voiceProfileSIPEthernetPriorityMark
					Integer32
			 }

		-- 1.3.6.1.4.1.5504.2.5.40.1.3.3.1.1
		voiceProfileSIPProxyServer OBJECT-TYPE
			SYNTAX OCTET STRING (SIZE (0..255))
			MAX-ACCESS read-write
			STATUS current
			DESCRIPTION
				"Host name or IP address of the SIP proxy server. All SIP signaling 
				traffic MUST be sent to the host indicated by this parameter and the 
				port indicated by the ProxyServerPort parameter unless OutboundProxy 
				is non-empty or a different route was discovered during normal
				operations SIP routing operation. Regardless of which host the traffic
				gets sent to (the ProxyServer or the OutboundProxy), the value of 
				this parameter MUST be used to derive the URI placed into the SIP Route 
				header field of all requests originated by this end-point unless a 
				different proxy host was discovered dynamically during normal SIP routing
				operations. "
			::= { voiceProfileSIPEntry 1 }

		
		-- 1.3.6.1.4.1.5504.2.5.40.1.3.3.1.2
		voiceProfileSIPProxyServerPort OBJECT-TYPE
			SYNTAX Unsigned32
			MAX-ACCESS read-write
			STATUS current
			DESCRIPTION
				"Destination port to be used in connecting to the SIP server. "
			::= { voiceProfileSIPEntry 2 }

		
		-- 1.3.6.1.4.1.5504.2.5.40.1.3.3.1.3
		voiceProfileSIPProxyServerTransport OBJECT-TYPE
			SYNTAX VoiceTransportValues
			MAX-ACCESS read-write
			STATUS current
			DESCRIPTION
				"Transport protocol to be used in connecting to the SIP server.
				Must be chosen from among the transports supported, as indicated by
				VoiceService.{i}.Capabilities.SIP.Transports.
				Enumeration of:
				         UDP
				  TCP
				  TLS
				  SCTP 
				"
			::= { voiceProfileSIPEntry 3 }

		
		-- 1.3.6.1.4.1.5504.2.5.40.1.3.3.1.4
		voiceProfileSIPRegistrarServer OBJECT-TYPE
			SYNTAX OCTET STRING (SIZE (0..255))
			MAX-ACCESS read-write
			STATUS current
			DESCRIPTION
				"Host name or IP address of the SIP registrar server. If this parameter
				is empty, the CPE MUST obtain all of the registrar server configuration 
				information, including host name or IP address, port, and transport
				protocol, from the corresponding Proxy Server parameters (ProxyServer, 
				Proxy-ServerPort, and ProxyServerTransport), ignoring all of the 
				registrar server parameters (Registrar-Server, RegistrarServerPort and
				RegistrarServer-Transport). "
			::= { voiceProfileSIPEntry 4 }

		
		-- 1.3.6.1.4.1.5504.2.5.40.1.3.3.1.5
		voiceProfileSIPRegistrarServerPort OBJECT-TYPE
			SYNTAX Unsigned32
			MAX-ACCESS read-write
			STATUS current
			DESCRIPTION
				"Destination port to be used in connecting to the SIP registrar server.
				If the RegistrarServer parameter is empty, the CPE MUST obtain all 
				of the registrar server configuration information, including host name 
				or IP address, port, and transport protocol, from the corresponding
				ProxyServer parameters (Proxy-Server, ProxyServerPort, and ProxyServer-
				Transport), ignoring all of the registrar server parameters 
				(RegistrarServer, RegistrarServerPort and RegistrarServerTransport). "
			::= { voiceProfileSIPEntry 5 }

		
		-- 1.3.6.1.4.1.5504.2.5.40.1.3.3.1.6
		voiceProfileSIPRegistrarServerTransport OBJECT-TYPE
			SYNTAX VoiceTransportValues
			MAX-ACCESS read-write
			STATUS current
			DESCRIPTION
				"Transport protocol to be used in connecting to the registrar server.
				Must be chosen from among the transports supported, as indicated by 
				VoiceService.{i}.Capabilities.SIP.Transports. 
				Enumeration of: 
				      UDP
				TCP
				TLS
				SCTP
				If the RegistrarServer parameter is empty, the CPE MUST obtain all 
				of the registrar server configuration information, including host name 
				or IP address, port, and transport protocol, from the corresponding
				ProxyServer parameters (Proxy-Server, ProxyServerPort, and ProxyServer-
				Transport), ignoring all of the registrar server parameters 
				(Registrar-Server, RegistrarServerPort and RegistrarServer-Transport)."
			::= { voiceProfileSIPEntry 6 }

		
		-- 1.3.6.1.4.1.5504.2.5.40.1.3.3.1.7
		voiceProfileSIPToTagMatching OBJECT-TYPE
			SYNTAX TruthValue
			MAX-ACCESS read-write
			STATUS current
			DESCRIPTION
				"Enable/Disable SIP to tag matching. "
			::= { voiceProfileSIPEntry 7 }

		
		-- 1.3.6.1.4.1.5504.2.5.40.1.3.3.1.8
		voiceProfileSIPMusicServer OBJECT-TYPE
			SYNTAX OCTET STRING (SIZE (0..255))
			MAX-ACCESS read-write
			STATUS current
			DESCRIPTION
				"Music server address. "
			::= { voiceProfileSIPEntry 8 }

		
		-- 1.3.6.1.4.1.5504.2.5.40.1.3.3.1.9
		voiceProfileSIPMusicServerPort OBJECT-TYPE
			SYNTAX Unsigned32
			MAX-ACCESS read-write
			STATUS current
			DESCRIPTION
				"Music server port number. "
			::= { voiceProfileSIPEntry 9 }

		
		-- 1.3.6.1.4.1.5504.2.5.40.1.3.3.1.10
		voiceProfileSIPPlarGateway OBJECT-TYPE
			SYNTAX OCTET STRING (SIZE (0..63))
			MAX-ACCESS read-write
			STATUS current
			DESCRIPTION
				"PLAR gateway address. "
			::= { voiceProfileSIPEntry 10 }

		
		-- 1.3.6.1.4.1.5504.2.5.40.1.3.3.1.11
		voiceProfileSIPPlarPort OBJECT-TYPE
			SYNTAX Unsigned32
			MAX-ACCESS read-write
			STATUS current
			DESCRIPTION
				"Plar gateway port number. "
			::= { voiceProfileSIPEntry 11 }

		
		-- 1.3.6.1.4.1.5504.2.5.40.1.3.3.1.12
		voiceProfileSIPUserAgentDomain OBJECT-TYPE
			SYNTAX OCTET STRING (SIZE (0..255))
			MAX-ACCESS read-write
			STATUS current
			DESCRIPTION
				"CPE domain string. If empty, the CPE SHOULD se its IP address as 
				the domain. "
			::= { voiceProfileSIPEntry 12 }

		
		-- 1.3.6.1.4.1.5504.2.5.40.1.3.3.1.13
		voiceProfileSIPUserAgentPort OBJECT-TYPE
			SYNTAX Unsigned32
			MAX-ACCESS read-write
			STATUS current
			DESCRIPTION
				"Port used for incoming call control signaling. "
			::= { voiceProfileSIPEntry 13 }

		
		-- 1.3.6.1.4.1.5504.2.5.40.1.3.3.1.14
		voiceProfileSIPUserAgentTransport OBJECT-TYPE
			SYNTAX VoiceTransportValues
			MAX-ACCESS read-write
			STATUS current
			DESCRIPTION
				"Transport protocol to be used for incoming call control signaling. 
				Must be chosen from among the transports supported, as indicated by 
				VoiceService.{i}.Capabilities.SIP.Transports.
				Enumeration of: 
				      UDP
				TCP
				TLS
				SCTP
				"
			::= { voiceProfileSIPEntry 14 }

		
		-- 1.3.6.1.4.1.5504.2.5.40.1.3.3.1.15
		voiceProfileSIPOutboundProxy OBJECT-TYPE
			SYNTAX OCTET STRING (SIZE (0..255))
			MAX-ACCESS read-write
			STATUS current
			DESCRIPTION
				"Host name or IP address of the outbound proxy. If a non-empty value 
				is specified, the SIP endpoint MUST send all SIP traffic (requests 
				and responses) to the host indicated by this parameter and the port 
				indicated by the OutboundProxyPort parameter. This MUST be done
				regardless of the routes discovered using normal SIP operations,
				including use of Route headers initialized from Service-Route and
				Record-Route headers previously received. The OutboundProxy value
				is NOT used to generate the URI placed into the Route header of 
				any requests. "
			::= { voiceProfileSIPEntry 15 }

		
		-- 1.3.6.1.4.1.5504.2.5.40.1.3.3.1.16
		voiceProfileSIPOutboundProxyPort OBJECT-TYPE
			SYNTAX Unsigned32
			MAX-ACCESS read-write
			STATUS current
			DESCRIPTION
				"Destination port to be used in connecting to the outbound proxy.
				This parameter MUST be ignored unless the value of the OutboundProxy 
				parameter in this object is non-empty. "
			::= { voiceProfileSIPEntry 16 }

		
		-- 1.3.6.1.4.1.5504.2.5.40.1.3.3.1.17
		voiceProfileSIPOrganization OBJECT-TYPE
			SYNTAX OCTET STRING (SIZE (0..255))
			MAX-ACCESS read-write
			STATUS current
			DESCRIPTION
				"Text string to be used in the Organization header. "
			::= { voiceProfileSIPEntry 17 }

		
		-- 1.3.6.1.4.1.5504.2.5.40.1.3.3.1.18
		voiceProfileSIPRegistrationPeriod OBJECT-TYPE
			SYNTAX Unsigned32
			MAX-ACCESS read-write
			STATUS current
			DESCRIPTION
				"Period over which the user agent must periodically register,
				in seconds. "
			::= { voiceProfileSIPEntry 18 }

		
		-- 1.3.6.1.4.1.5504.2.5.40.1.3.3.1.19
		voiceProfileSIPRegisterExpires OBJECT-TYPE
			SYNTAX Unsigned32
			MAX-ACCESS read-write
			STATUS current
			DESCRIPTION
				"Register request Expires header value, in seconds. "
			::= { voiceProfileSIPEntry 19 }

		
		-- 1.3.6.1.4.1.5504.2.5.40.1.3.3.1.20
		voiceProfileSIPRegisterRetryInterval OBJECT-TYPE
			SYNTAX Unsigned32
			MAX-ACCESS read-write
			STATUS current
			DESCRIPTION
				"Register retry interval, in seconds. "
			::= { voiceProfileSIPEntry 20 }

		
		-- 1.3.6.1.4.1.5504.2.5.40.1.3.3.1.21
		voiceProfileSIPDSCPMark OBJECT-TYPE
			SYNTAX Unsigned32
			MAX-ACCESS read-write
			STATUS current
			DESCRIPTION
				"Diffserv code point to be used for outgoing SIP signaling packets. "
			::= { voiceProfileSIPEntry 21 }

		
		-- 1.3.6.1.4.1.5504.2.5.40.1.3.3.1.22
		voiceProfileSIPVLANIDMark OBJECT-TYPE
			SYNTAX Integer32
			MAX-ACCESS read-write
			STATUS current
			DESCRIPTION
				"VLAN ID (as defined in 802.1Q) to be used for outgoing SIP signaling
				packets for this profile. A value of -1 indicates the default value
				is to be used. If either the VLANIDMark or EthernetPriorityMark are
				greater than zero, then the outgoing frames MUST be tagged. Otherwise,
				the outgoing frames MAY be tagged or untagged. "
			::= { voiceProfileSIPEntry 22 }

		
		-- 1.3.6.1.4.1.5504.2.5.40.1.3.3.1.23
		voiceProfileSIPEthernetPriorityMark OBJECT-TYPE
			SYNTAX Integer32
			MAX-ACCESS read-write
			STATUS current
			DESCRIPTION
				"Ethernet priority code (as defined in 802.1D) to be used for 
				outgoing SIP signaling packets for this profile. A value of -1 
				indicates the default value is to be used. If either the VLANIDMark
				or EthernetPriorityMark are greater than zero, then the outgoing
				frames MUST be tagged. Otherwise, the outgoing frames MAY be tagged
				or untagged. "
			::= { voiceProfileSIPEntry 23 }

		
--  Voice Services Voice Profile SIP Event Subscriber Objects 
-- TR-104 InternetGatewayDevice.Services.VoiceService.{i}.VoiceProfile.{i}.SIP.EventSubscribe
-- 
		-- 1.3.6.1.4.1.5504.2.5.40.1.3.4
		voiceProfileSIPEventSubscribeTable OBJECT-TYPE
			SYNTAX SEQUENCE OF VoiceProfileSIPEventSubscribeEntry
			MAX-ACCESS not-accessible
			STATUS current
			DESCRIPTION
				"Table of SIP subscriber event objects for a specific voice profile"
			::= { voiceProfiles 4 }

		
		-- 1.3.6.1.4.1.5504.2.5.40.1.3.4.1
		voiceProfileSIPEventSubscribeEntry OBJECT-TYPE
			SYNTAX VoiceProfileSIPEventSubscribeEntry
			MAX-ACCESS not-accessible
			STATUS current
			DESCRIPTION
				"SIP subscriber events objects associated with a specific voice profile."
			INDEX { voiceServiceIndex, voiceProfileIndex }
			::= { voiceProfileSIPEventSubscribeTable 1 }

		
		VoiceProfileSIPEventSubscribeEntry ::=
			SEQUENCE { 
				voiceProfileSIPEventSubscribeEvent
					OCTET STRING,
				voiceProfileSIPEventSubscribeNotifier
					OCTET STRING,
				voiceProfileSIPEventSubscribeNotifierPort
					Unsigned32,
				voiceProfileSIPEventSubscribeNotifierTransport
					VoiceTransportValues
			 }

		-- 1.3.6.1.4.1.5504.2.5.40.1.3.4.1.1
		voiceProfileSIPEventSubscribeEvent OBJECT-TYPE
			SYNTAX OCTET STRING (SIZE (0..31))
			MAX-ACCESS read-write
			STATUS current
			DESCRIPTION
				"SIP event name to appear in the EVENT header of the SIP SUBSCRIBE
				request."
			::= { voiceProfileSIPEventSubscribeEntry 1 }

		
		-- 1.3.6.1.4.1.5504.2.5.40.1.3.4.1.2
		voiceProfileSIPEventSubscribeNotifier OBJECT-TYPE
			SYNTAX OCTET STRING (SIZE (0..255))
			MAX-ACCESS read-write
			STATUS current
			DESCRIPTION
				"Host name or IP address of the event notify server."
			::= { voiceProfileSIPEventSubscribeEntry 2 }

		
		-- 1.3.6.1.4.1.5504.2.5.40.1.3.4.1.3
		voiceProfileSIPEventSubscribeNotifierPort OBJECT-TYPE
			SYNTAX Unsigned32
			MAX-ACCESS read-write
			STATUS current
			DESCRIPTION
				"Destination port to be used in connecting to the event notifier."
			::= { voiceProfileSIPEventSubscribeEntry 3 }

		
		-- 1.3.6.1.4.1.5504.2.5.40.1.3.4.1.4
		voiceProfileSIPEventSubscribeNotifierTransport OBJECT-TYPE
			SYNTAX VoiceTransportValues
			MAX-ACCESS read-write
			STATUS current
			DESCRIPTION
				"Transport protocol to be used in connecting to the registrar server.
				Must be chosen from among the transports supported, as indicated by 
				VoiceService.{i}.Capabilities.SIP.Transports. 
				Enumeration of: 
				      UDP
				TCP
				TLS
				SCTP
				"
			::= { voiceProfileSIPEventSubscribeEntry 4 }

		
--  Voice Services Voice Profile MGCP Objects 
-- TR-104 InternetGatewayDevice.Services.VoiceService.{i}.VoiceProfile.{i}.MGCP
-- 
		-- 1.3.6.1.4.1.5504.2.5.40.1.3.5
		voiceProfileMGCPTable OBJECT-TYPE
			SYNTAX SEQUENCE OF VoiceProfileMGCPEntry
			MAX-ACCESS not-accessible
			STATUS current
			DESCRIPTION
				"Table of MGCP objects for a specific voice profile"
			::= { voiceProfiles 5 }

		
		-- 1.3.6.1.4.1.5504.2.5.40.1.3.5.1
		voiceProfileMGCPEntry OBJECT-TYPE
			SYNTAX VoiceProfileMGCPEntry
			MAX-ACCESS not-accessible
			STATUS current
			DESCRIPTION
				"MGCP objects associated with a specific voice profile."
			INDEX { voiceServiceIndex, voiceProfileIndex }
			::= { voiceProfileMGCPTable 1 }

		
		VoiceProfileMGCPEntry ::=
			SEQUENCE { 
				voiceProfileMGCPCallAgent1
					OCTET STRING,
				voiceProfileMGCPUser
					OCTET STRING,
				voiceProfilePersistentNotify
					TruthValue
			 }

		-- 1.3.6.1.4.1.5504.2.5.40.1.3.5.1.1
		voiceProfileMGCPCallAgent1 OBJECT-TYPE
			SYNTAX OCTET STRING (SIZE (0..255))
			MAX-ACCESS read-write
			STATUS current
			DESCRIPTION
				"Host name or IP address of the main MGCP call agent."
			::= { voiceProfileMGCPEntry 1 }

		
		-- 1.3.6.1.4.1.5504.2.5.40.1.3.5.1.2
		voiceProfileMGCPUser OBJECT-TYPE
			SYNTAX OCTET STRING (SIZE (0..63))
			MAX-ACCESS read-write
			STATUS current
			DESCRIPTION
				"User string used in accessing the call agent."
			::= { voiceProfileMGCPEntry 2 }

		
		-- 1.3.6.1.4.1.5504.2.5.40.1.3.5.1.3
		voiceProfilePersistentNotify OBJECT-TYPE
			SYNTAX TruthValue
			MAX-ACCESS read-write
			STATUS current
			DESCRIPTION
				"This field directs the MGCP stack to notify the switch for every 
				hd or hu event when in the RQNT is Q:LOOP."
			::= { voiceProfileMGCPEntry 3 }

		
--  Voice Services Voice Profile RTP Objects 
-- TR-104 InternetGatewayDevice.Services.VoiceService.{i}.VoiceProfile.{i}.RTP
-- 
		-- 1.3.6.1.4.1.5504.2.5.40.1.3.6
		voiceProfileRTPTable OBJECT-TYPE
			SYNTAX SEQUENCE OF VoiceProfileRTPEntry
			MAX-ACCESS not-accessible
			STATUS current
			DESCRIPTION
				"Table of RTP objects for a specific voice profile"
			::= { voiceProfiles 6 }

		
		-- 1.3.6.1.4.1.5504.2.5.40.1.3.6.1
		voiceProfileRTPEntry OBJECT-TYPE
			SYNTAX VoiceProfileRTPEntry
			MAX-ACCESS not-accessible
			STATUS current
			DESCRIPTION
				"RTP objects associated with a specific voice profile."
			INDEX { voiceServiceIndex, voiceProfileIndex }
			::= { voiceProfileRTPTable 1 }

		
		VoiceProfileRTPEntry ::=
			SEQUENCE { 
				voiceProfileRTPLocalPortMin
					Unsigned32,
				voiceProfileRTPLocalPortMax
					Unsigned32,
				voiceProfileRTPDSCPMark
					Unsigned32,
				voiceProfileRTPTelephoneEventPayloadType
					Unsigned32
			 }

		-- 1.3.6.1.4.1.5504.2.5.40.1.3.6.1.1
		voiceProfileRTPLocalPortMin OBJECT-TYPE
			SYNTAX Unsigned32 (0..65525)
			MAX-ACCESS read-write
			STATUS current
			DESCRIPTION
				"Base of port range to be used for incoming RTP streams for this profile."
			::= { voiceProfileRTPEntry 1 }

		
		-- 1.3.6.1.4.1.5504.2.5.40.1.3.6.1.2
		voiceProfileRTPLocalPortMax OBJECT-TYPE
			SYNTAX Unsigned32 (0..65525)
			MAX-ACCESS read-write
			STATUS current
			DESCRIPTION
				"Top of port range to be used for incoming RTP streams for this profile."
			::= { voiceProfileRTPEntry 2 }

		
		-- 1.3.6.1.4.1.5504.2.5.40.1.3.6.1.3
		voiceProfileRTPDSCPMark OBJECT-TYPE
			SYNTAX Unsigned32 (0..63)
			MAX-ACCESS read-write
			STATUS current
			DESCRIPTION
				"Diffserv code point to be used for outgoing RTP &#10;packets for this
				profile. It is RECOMMENDED that by default the DSCP for RTP traffic be 
				set to the value to indicate EF traffic."
			::= { voiceProfileRTPEntry 3 }

		
		-- 1.3.6.1.4.1.5504.2.5.40.1.3.6.1.4
		voiceProfileRTPTelephoneEventPayloadType OBJECT-TYPE
			SYNTAX Unsigned32 (0..128)
			MAX-ACCESS read-write
			STATUS current
			DESCRIPTION
				"Payload type to be used for RTP telephone events. This parameter 
				indicates the payload type to be used for DTMF events if RFC 2833 
				transmission of DTMF information is in use."
			::= { voiceProfileRTPEntry 4 }

		
--  Voice Services Voice Profile Fax T38 Objects 
-- TR-104 InternetGatewayDevice.Services.VoiceService.{i}.VoiceProfile.{i}.FaxT38
-- 
		-- 1.3.6.1.4.1.5504.2.5.40.1.3.7
		voiceProfileFaxT38Table OBJECT-TYPE
			SYNTAX SEQUENCE OF VoiceProfileFaxT38Entry
			MAX-ACCESS not-accessible
			STATUS current
			DESCRIPTION
				"Table of Fax T.38 objects for a specific voice profile"
			::= { voiceProfiles 7 }

		
		-- 1.3.6.1.4.1.5504.2.5.40.1.3.7.1
		voiceProfileFaxT38Entry OBJECT-TYPE
			SYNTAX VoiceProfileFaxT38Entry
			MAX-ACCESS not-accessible
			STATUS current
			DESCRIPTION
				"Fax T38 objects associated with a specific voice profile."
			INDEX { voiceServiceIndex, voiceProfileIndex }
			::= { voiceProfileFaxT38Table 1 }

		
		VoiceProfileFaxT38Entry ::=
			SEQUENCE { 
				voiceProfileFaxT38Enable
					TruthValue,
				voiceProfileFaxT38BitRate
					Unsigned32,
				voiceProfileFaxT38HighSpeedPacketRate
					Unsigned32
			 }

		-- 1.3.6.1.4.1.5504.2.5.40.1.3.7.1.1
		voiceProfileFaxT38Enable OBJECT-TYPE
			SYNTAX TruthValue
			MAX-ACCESS read-write
			STATUS current
			DESCRIPTION
				"Enable or disable the use of T.38."
			::= { voiceProfileFaxT38Entry 1 }

		
		-- 1.3.6.1.4.1.5504.2.5.40.1.3.7.1.2
		voiceProfileFaxT38BitRate OBJECT-TYPE
			SYNTAX Unsigned32
			MAX-ACCESS read-write
			STATUS current
			DESCRIPTION
				"Maximum data rate for fax. Enumeration of the following values:
				2400 
				4800
				7200
				9600
				12000
				14400
				33600
				"
			::= { voiceProfileFaxT38Entry 2 }

		
		-- 1.3.6.1.4.1.5504.2.5.40.1.3.7.1.3
		voiceProfileFaxT38HighSpeedPacketRate OBJECT-TYPE
			SYNTAX Unsigned32
			MAX-ACCESS read-write
			STATUS current
			DESCRIPTION
				"The rate at which high speed data will be sent across the network
				in milliseconds. Enumeration of the following values:
				    10 
				    20
				    30
				    40
				"
			::= { voiceProfileFaxT38Entry 3 }

		
--  Voice Services Voice Profile Line Objects 
-- TR-104 InternetGatewayDevice.Services.VoiceService.{i}.VoiceProfile.{i}.Line.{i}
-- 
		-- 1.3.6.1.4.1.5504.2.5.40.1.3.8
		voiceProfileLines OBJECT IDENTIFIER ::= { voiceProfiles 8 }

		
		-- 1.3.6.1.4.1.5504.2.5.40.1.3.8.1
		voiceProfileLineTable OBJECT-TYPE
			SYNTAX SEQUENCE OF VoiceProfileLineEntry
			MAX-ACCESS not-accessible
			STATUS current
			DESCRIPTION
				"Table of voice profile line objects"
			::= { voiceProfileLines 1 }

		
		-- 1.3.6.1.4.1.5504.2.5.40.1.3.8.1.1
		voiceProfileLineEntry OBJECT-TYPE
			SYNTAX VoiceProfileLineEntry
			MAX-ACCESS not-accessible
			STATUS current
			DESCRIPTION
				"Object associated with a distinct voice line. Support for adding and removing 
				lines is conditional on whether the CPE supports more than one line in total 
				as indicated by VoiceService.{i}.Capabilities.MaxLineCount. By default, on 
				creation of a given VoiceProfile, a single Line object MUST be present, 
				initially in the disabled state. Applicable only for a VoIP endpoint."
			INDEX { voiceServiceIndex, voiceProfileIndex, voiceProfileLineIndex }
			::= { voiceProfileLineTable 1 }

		
		VoiceProfileLineEntry ::=
			SEQUENCE { 
				voiceProfileLineIndex
					Unsigned32,
				voiceProfileLineEnable
					VoiceProfileLineStateType,
				voiceProfileLineDirectoryNumber
					OCTET STRING,
				voiceProfileLineStatus
					VoiceLineStatusValues,
				voiceProfileLineCallState
					VoiceLineCallStateValues,
				voiceProfileLinePhyReferenceList
					OCTET STRING,
				voiceProfileLineCMAcntNum
					Unsigned32,
				voiceProfileLineOnhook
					TruthValue,
				voiceProfileLineRowStatus
					ZhoneRowStatus
			 }

		-- 1.3.6.1.4.1.5504.2.5.40.1.3.8.1.1.1
		voiceProfileLineIndex OBJECT-TYPE
			SYNTAX Unsigned32
			MAX-ACCESS read-only
			STATUS current
			DESCRIPTION
				"Voice Profile Line Index"
			::= { voiceProfileLineEntry 1 }

		
		-- 1.3.6.1.4.1.5504.2.5.40.1.3.8.1.1.2
		voiceProfileLineEnable OBJECT-TYPE
			SYNTAX VoiceProfileLineStateType
			MAX-ACCESS read-write
			STATUS current
			DESCRIPTION
				"Enables or disables this line, or places it into a quiescent 
				state. Enumeration of:
				               Disabled
				               Quiescent
				        Enabled
				
				On creation, a line MUST be in the Disabled state. In the Quiescent 
				state, in-progress sessions remain intact, but no new sessions are 
				allowed. Support for the Quiescent state in a CPE is optional. If 
				this parameter is set to Quiescent in a CPE that does not support 
				the Quiescent state, it MUST treat it the same as the Disabled 
				state (and indicate Disabled in the Status parameter). 
				"
			::= { voiceProfileLineEntry 2 }

		
		-- 1.3.6.1.4.1.5504.2.5.40.1.3.8.1.1.3
		voiceProfileLineDirectoryNumber OBJECT-TYPE
			SYNTAX OCTET STRING (SIZE (0..31))
			MAX-ACCESS read-write
			STATUS current
			DESCRIPTION
				"Directory number associated with this line. May be used to identify
				the line to the user. In case of H.323 signaling, this MUST be an 
				E.164 number."
			::= { voiceProfileLineEntry 3 }

		
		-- 1.3.6.1.4.1.5504.2.5.40.1.3.8.1.1.4
		voiceProfileLineStatus OBJECT-TYPE
			SYNTAX VoiceLineStatusValues
			MAX-ACCESS read-only
			STATUS current
			DESCRIPTION
				"Indicates the status of this line. Enumeration of:
				Up
				Initializing
				Registering
				Unregistering
				Error
				Testing
				Quiescent
				Disabled
				"
			::= { voiceProfileLineEntry 4 }

		
		-- 1.3.6.1.4.1.5504.2.5.40.1.3.8.1.1.5
		voiceProfileLineCallState OBJECT-TYPE
			SYNTAX VoiceLineCallStateValues
			MAX-ACCESS read-only
			STATUS current
			DESCRIPTION
				"Indicates the call state for this line. Enumeration of:
				Idle
				Calling
				Ringing
				Connecting
				InCall
				Hold
				Disconnecting
				"
			::= { voiceProfileLineEntry 5 }

		
		-- 1.3.6.1.4.1.5504.2.5.40.1.3.8.1.1.6
		voiceProfileLinePhyReferenceList OBJECT-TYPE
			SYNTAX OCTET STRING (SIZE (0..31))
			MAX-ACCESS read-write
			STATUS current
			DESCRIPTION
				"A comma separated list of Physical Interface Identifiers that
				this Line is associated with. Each item corresponds to the value
				of the InterfaceID paraeter in a particular instance of the 
				VoiceService.{i}.PhyInterface.{i}. table."
			::= { voiceProfileLineEntry 6 }

		
		-- 1.3.6.1.4.1.5504.2.5.40.1.3.8.1.1.7
		voiceProfileLineCMAcntNum OBJECT-TYPE
			SYNTAX Unsigned32 (0..20)
			MAX-ACCESS read-write
			STATUS current
			DESCRIPTION
				"Indicates the call manager account number associated with
				this line instance."
			::= { voiceProfileLineEntry 7 }

		
		-- 1.3.6.1.4.1.5504.2.5.40.1.3.8.1.1.8
		voiceProfileLineOnhook OBJECT-TYPE
			SYNTAX TruthValue
			MAX-ACCESS read-write
			STATUS current
			DESCRIPTION
				"State of phones Receiver. On Hook if True, OffHook if False."
			::= { voiceProfileLineEntry 8 }

		
		-- 1.3.6.1.4.1.5504.2.5.40.1.3.8.1.1.9
		voiceProfileLineRowStatus OBJECT-TYPE
			SYNTAX ZhoneRowStatus
			MAX-ACCESS read-write
			STATUS current
			DESCRIPTION
				"The SNMP RowStatus of the current row."
			::= { voiceProfileLineEntry 9 }

		
--  Voice Services Voice Profile Line SIP Objects 
-- TR-104 InternetGatewayDevice.Services.VoiceService.{i}.VoiceProfile.{i}.Line.{i}.SIP
-- 
		-- 1.3.6.1.4.1.5504.2.5.40.1.3.8.2
		voiceProfileLineSIPTable OBJECT-TYPE
			SYNTAX SEQUENCE OF VoiceProfileLineSIPEntry
			MAX-ACCESS not-accessible
			STATUS current
			DESCRIPTION
				"Table of voice profile line SIP objects"
			::= { voiceProfileLines 2 }

		
		-- 1.3.6.1.4.1.5504.2.5.40.1.3.8.2.1
		voiceProfileLineSIPEntry OBJECT-TYPE
			SYNTAX VoiceProfileLineSIPEntry
			MAX-ACCESS not-accessible
			STATUS current
			DESCRIPTION
				"Line SIP objects associated with a specific voice profile."
			INDEX { voiceServiceIndex, voiceProfileIndex, voiceProfileLineIndex }
			::= { voiceProfileLineSIPTable 1 }

		
		VoiceProfileLineSIPEntry ::=
			SEQUENCE { 
				voiceProfileLineSIPAuthUserName
					OCTET STRING,
				voiceProfileLineSIPAuthPassword
					OCTET STRING,
				voiceProfileLineSIPURI
					OCTET STRING,
				voiceProfileLineSIPPlarUserName
					OCTET STRING
			 }

		-- 1.3.6.1.4.1.5504.2.5.40.1.3.8.2.1.1
		voiceProfileLineSIPAuthUserName OBJECT-TYPE
			SYNTAX OCTET STRING (SIZE (0..127))
			MAX-ACCESS read-write
			STATUS current
			DESCRIPTION
				"Username used to authenticate the connection to the server."
			::= { voiceProfileLineSIPEntry 1 }

		
		-- 1.3.6.1.4.1.5504.2.5.40.1.3.8.2.1.2
		voiceProfileLineSIPAuthPassword OBJECT-TYPE
			SYNTAX OCTET STRING (SIZE (0..127))
			MAX-ACCESS read-write
			STATUS current
			DESCRIPTION
				"Password used to authenticate the connection to the server. When read, 
				this parameter returns an empty string, regardless of the actual value."
			::= { voiceProfileLineSIPEntry 2 }

		
		-- 1.3.6.1.4.1.5504.2.5.40.1.3.8.2.1.3
		voiceProfileLineSIPURI OBJECT-TYPE
			SYNTAX OCTET STRING (SIZE (0..389))
			MAX-ACCESS read-write
			STATUS current
			DESCRIPTION
				"URI by which the user agent will identify itself for this line. If 
				empty, the actual URI used in the SIP signaling SHOULD be automatically 
				formed by the CPE as sip:UserName"
			::= { voiceProfileLineSIPEntry 3 }

		
		-- 1.3.6.1.4.1.5504.2.5.40.1.3.8.2.1.4
		voiceProfileLineSIPPlarUserName OBJECT-TYPE
			SYNTAX OCTET STRING (SIZE (0..63))
			MAX-ACCESS read-write
			STATUS current
			DESCRIPTION
				"PLAR gateway username."
			::= { voiceProfileLineSIPEntry 4 }

		
--  Voice Services Voice Profile Line MGCP Objects 
-- TR-104 InternetGatewayDevice.Services.VoiceService.{i}.VoiceProfile.{i}.Line.{i}.MGCP
-- 
		-- 1.3.6.1.4.1.5504.2.5.40.1.3.8.3
		voiceProfileLineMGCPTable OBJECT-TYPE
			SYNTAX SEQUENCE OF VoiceProfileLineMGCPEntry
			MAX-ACCESS not-accessible
			STATUS current
			DESCRIPTION
				"Table of voice profile line MGCP objects"
			::= { voiceProfileLines 3 }

		
		-- 1.3.6.1.4.1.5504.2.5.40.1.3.8.3.1
		voiceProfileLineMGCPEntry OBJECT-TYPE
			SYNTAX VoiceProfileLineMGCPEntry
			MAX-ACCESS not-accessible
			STATUS current
			DESCRIPTION
				"Line MGCP objects associated with a specific voice profile."
			INDEX { voiceServiceIndex, voiceProfileIndex, voiceProfileLineIndex }
			::= { voiceProfileLineMGCPTable 1 }

		
		VoiceProfileLineMGCPEntry ::=
			SEQUENCE { 
				voiceProfileLineMGCPLineName
					OCTET STRING
			 }

		-- 1.3.6.1.4.1.5504.2.5.40.1.3.8.3.1.1
		voiceProfileLineMGCPLineName OBJECT-TYPE
			SYNTAX OCTET STRING (SIZE (0..31))
			MAX-ACCESS read-write
			STATUS current
			DESCRIPTION
				"Used to identify the line when using MGCP signaling. If empty, the CPE SHOULD 
				use the default names aaln/1, etc."
			::= { voiceProfileLineMGCPEntry 1 }

		
--  Voice Services Voice Profile Line Voice Processing Objects 
-- TR-104 InternetGatewayDevice.Services.VoiceService.{i}.VoiceProfile.{i}.Line.{i}.VoiceProcessing
-- 
		-- 1.3.6.1.4.1.5504.2.5.40.1.3.8.4
		voiceProfileLineProcessingTable OBJECT-TYPE
			SYNTAX SEQUENCE OF VoiceProfileLineProcessingEntry
			MAX-ACCESS not-accessible
			STATUS current
			DESCRIPTION
				"Table of voice profile line processing objects"
			::= { voiceProfileLines 4 }

		
		-- 1.3.6.1.4.1.5504.2.5.40.1.3.8.4.1
		voiceProfileLineProcessingEntry OBJECT-TYPE
			SYNTAX VoiceProfileLineProcessingEntry
			MAX-ACCESS not-accessible
			STATUS current
			DESCRIPTION
				"Line Processing objects associated with a specific voice profile."
			INDEX { voiceServiceIndex, voiceProfileIndex, voiceProfileLineIndex }
			::= { voiceProfileLineProcessingTable 1 }

		
		VoiceProfileLineProcessingEntry ::=
			SEQUENCE { 
				voiceProfileLineTransmitGain
					Integer32,
				voiceProfileLineReceiveGain
					Integer32,
				voiceProfileLineEchoCancellationEnable
					TruthValue,
				voiceProfileLineEchoCancellationInUse
					TruthValue
			 }

		-- 1.3.6.1.4.1.5504.2.5.40.1.3.8.4.1.1
		voiceProfileLineTransmitGain OBJECT-TYPE
			SYNTAX Integer32
			MAX-ACCESS read-write
			STATUS current
			DESCRIPTION
				"Gain in units of 0.1 dB to apply to the transmitted voice signal 
				prior to encoding. This gain is a modifier of the default transmit-gain, 
				which is unspecified."
			::= { voiceProfileLineProcessingEntry 1 }

		
		-- 1.3.6.1.4.1.5504.2.5.40.1.3.8.4.1.2
		voiceProfileLineReceiveGain OBJECT-TYPE
			SYNTAX Integer32
			MAX-ACCESS read-write
			STATUS current
			DESCRIPTION
				"Gain in units of 0.1 dB to apply to the received voice signal 
				after decoding. This gain is a modifier of the default receive-gain, 
				which is unspecified."
			::= { voiceProfileLineProcessingEntry 2 }

		
		-- 1.3.6.1.4.1.5504.2.5.40.1.3.8.4.1.3
		voiceProfileLineEchoCancellationEnable OBJECT-TYPE
			SYNTAX TruthValue
			MAX-ACCESS read-write
			STATUS current
			DESCRIPTION
				"Enable or disable echo cancellation for this line."
			::= { voiceProfileLineProcessingEntry 3 }

		
		-- 1.3.6.1.4.1.5504.2.5.40.1.3.8.4.1.4
		voiceProfileLineEchoCancellationInUse OBJECT-TYPE
			SYNTAX TruthValue
			MAX-ACCESS read-only
			STATUS current
			DESCRIPTION
				"Indication of whether or not echo cancellation is currently in use for 
				this line. "
			::= { voiceProfileLineProcessingEntry 4 }

		
--  Voice Services Voice Profile Line CODEC Objects 
-- TR-104 InternetGatewayDevice.Services.VoiceService.{i}.VoiceProfile.{i}.Line.{i}.Codec
-- TR-104 InternetGatewayDevice.Services.VoiceService.{i}.VoiceProfile.{i}.Line.{i}.Codec.List.{i}
-- 
		-- 1.3.6.1.4.1.5504.2.5.40.1.3.8.5
		voiceProfileLineCodecTable OBJECT-TYPE
			SYNTAX SEQUENCE OF VoiceProfileLineCodecEntry
			MAX-ACCESS not-accessible
			STATUS current
			DESCRIPTION
				"Table of voice profile CODEC objects, per line"
			::= { voiceProfileLines 5 }

		
		-- 1.3.6.1.4.1.5504.2.5.40.1.3.8.5.1
		voiceProfileLineCodecEntry OBJECT-TYPE
			SYNTAX VoiceProfileLineCodecEntry
			MAX-ACCESS not-accessible
			STATUS current
			DESCRIPTION
				"The Voice Line CODEC list MUST include a distinct entry for each 
				supported combination of these parameters."
			INDEX { voiceServiceIndex, voiceProfileIndex, voiceProfileLineIndex, voiceProfileLineCodecIndex }
			::= { voiceProfileLineCodecTable 1 }

		
		VoiceProfileLineCodecEntry ::=
			SEQUENCE { 
				voiceProfileLineCodecIndex
					Unsigned32,
				voiceProfileLineCodecEntryID
					Unsigned32,
				voiceProfileLineCodec
					OCTET STRING,
				voiceProfileLineCodecBitRate
					Unsigned32,
				voiceProfileLineCodecPacketizationPeriod
					OCTET STRING,
				voiceProfileLineCodecSilenceSuppression
					TruthValue,
				voiceProfileLineCodecEnable
					TruthValue,
				voiceProfileLineCodecPriority
					Unsigned32
			 }

		-- 1.3.6.1.4.1.5504.2.5.40.1.3.8.5.1.1
		voiceProfileLineCodecIndex OBJECT-TYPE
			SYNTAX Unsigned32
			MAX-ACCESS read-only
			STATUS current
			DESCRIPTION
				"Unique identifier for each entry in this table. The value MUST 
				match that of the corresponding entry in the 
				VoiceService.{i}.Capabilities.Codecs table."
			::= { voiceProfileLineCodecEntry 1 }

		
		-- 1.3.6.1.4.1.5504.2.5.40.1.3.8.5.1.2
		voiceProfileLineCodecEntryID OBJECT-TYPE
			SYNTAX Unsigned32
			MAX-ACCESS read-only
			STATUS current
			DESCRIPTION
				"Unique identifier for each entry in this table. The value MUST 
				match that of the corresponding entry in the 
				VoiceService.{i}.Capabilities.Codecs table."
			::= { voiceProfileLineCodecEntry 2 }

		
		-- 1.3.6.1.4.1.5504.2.5.40.1.3.8.5.1.3
		voiceProfileLineCodec OBJECT-TYPE
			SYNTAX OCTET STRING (SIZE (0..63))
			MAX-ACCESS read-only
			STATUS current
			DESCRIPTION
				"Identifier of the codec type. The value MUST match that of the 
				corresponding entry in the VoiceService.{i}.Capabilities.Codecs 
				table."
			::= { voiceProfileLineCodecEntry 3 }

		
		-- 1.3.6.1.4.1.5504.2.5.40.1.3.8.5.1.4
		voiceProfileLineCodecBitRate OBJECT-TYPE
			SYNTAX Unsigned32
			MAX-ACCESS read-only
			STATUS current
			DESCRIPTION
				"Bit rate, in bits per second. The value MUST match that of the 
				corresponding entry in the VoiceService.{i}.Capabilities.Codecs table."
			::= { voiceProfileLineCodecEntry 4 }

		
		-- 1.3.6.1.4.1.5504.2.5.40.1.3.8.5.1.5
		voiceProfileLineCodecPacketizationPeriod OBJECT-TYPE
			SYNTAX OCTET STRING (SIZE (0..63))
			MAX-ACCESS read-write
			STATUS current
			DESCRIPTION
				"Comma-separate list of supported packetization periods, in milliseconds, 
				or continuous ranges of packetization periods as defined in 
				VoiceService.{i}.Capabilities.Codecs.PacketizationPeriod. The set of 
				packetization periods may be restricted by modifying the value of this 
				parameter to a more restricted set of values than is listed in 
				VoiceService.{i}.Capabilities.Codecs.PacketizationPeriod. The CPE MUST 
				ignore any values or portions of ranges outside of those specified in 
				VoiceService.{i}.Capabilities.Codecs.Packetization.Period."
			::= { voiceProfileLineCodecEntry 5 }

		
		-- 1.3.6.1.4.1.5504.2.5.40.1.3.8.5.1.6
		voiceProfileLineCodecSilenceSuppression OBJECT-TYPE
			SYNTAX TruthValue
			MAX-ACCESS read-write
			STATUS current
			DESCRIPTION
				"Indicates support for silence suppression for this codec. If silence 
				suppression is supported, it can be disabled for this codec/bit-rate 
				by setting this parameter to false."
			::= { voiceProfileLineCodecEntry 6 }

		
		-- 1.3.6.1.4.1.5504.2.5.40.1.3.8.5.1.7
		voiceProfileLineCodecEnable OBJECT-TYPE
			SYNTAX TruthValue
			MAX-ACCESS read-write
			STATUS current
			DESCRIPTION
				"Enable or disable the use of this combination of codec parameters."
			::= { voiceProfileLineCodecEntry 7 }

		
		-- 1.3.6.1.4.1.5504.2.5.40.1.3.8.5.1.8
		voiceProfileLineCodecPriority OBJECT-TYPE
			SYNTAX Unsigned32
			MAX-ACCESS read-write
			STATUS current
			DESCRIPTION
				"Indicates the priority for this combination of codec parameters, where 
				1 is the highest priority. Where the priority differs between entries in 
				this table, the CPE SHOULD use the highest priority (lowest numbered) 
				entry among those supported by the remote endpoint and consistent with 
				the available bandwidth. Where the priorities are equal among multiple 
				entries, the CPE MAY apply a local criterion for choosing among them."
			::= { voiceProfileLineCodecEntry 8 }

		
--  Voice Services Voice Profile Line Calling Features Objects 
-- TR-104 InternetGatewayDevice.Services.VoiceService.{i}.VoiceProfile.{i}.Line.{i}.CallingFeatures
-- 
-- Note that many TR-104 Calling Features are specified. Not all calling features
-- are required to be supported by a CPE.
-- 
		-- 1.3.6.1.4.1.5504.2.5.40.1.3.8.6
		voiceProfileLineCallingFeaturesTable OBJECT-TYPE
			SYNTAX SEQUENCE OF VoiceProfileLineCallingFeaturesEntry
			MAX-ACCESS not-accessible
			STATUS current
			DESCRIPTION
				"Table of voice calling features, per line"
			::= { voiceProfileLines 6 }

		
		-- 1.3.6.1.4.1.5504.2.5.40.1.3.8.6.1
		voiceProfileLineCallingFeaturesEntry OBJECT-TYPE
			SYNTAX VoiceProfileLineCallingFeaturesEntry
			MAX-ACCESS not-accessible
			STATUS current
			DESCRIPTION
				"The list of voice line calling features supported."
			INDEX { voiceServiceIndex, voiceProfileIndex, voiceProfileLineIndex }
			::= { voiceProfileLineCallingFeaturesTable 1 }

		
		VoiceProfileLineCallingFeaturesEntry ::=
			SEQUENCE { 
				voiceProfileLineCallingFeatureCallerIDEnable
					TruthValue,
				voiceProfileLineCallingFeatureCallerIDName
					OCTET STRING,
				voiceProfileLineCallingFeatureCallWaitingEnable
					TruthValue,
				voiceProfileLineCallingFeatureMaxSessions
					Unsigned32,
				voiceProfileLineCallingFeatureMWIEnable
					TruthValue
			 }

		-- 1.3.6.1.4.1.5504.2.5.40.1.3.8.6.1.1
		voiceProfileLineCallingFeatureCallerIDEnable OBJECT-TYPE
			SYNTAX TruthValue
			MAX-ACCESS read-write
			STATUS current
			DESCRIPTION
				"Enable or disable the transmission of caller ID information on 
				outgoing calls."
			::= { voiceProfileLineCallingFeaturesEntry 1 }

		
		-- 1.3.6.1.4.1.5504.2.5.40.1.3.8.6.1.2
		voiceProfileLineCallingFeatureCallerIDName OBJECT-TYPE
			SYNTAX OCTET STRING (SIZE (0..255))
			MAX-ACCESS read-write
			STATUS current
			DESCRIPTION
				"String used to identify the caller."
			::= { voiceProfileLineCallingFeaturesEntry 2 }

		
		-- 1.3.6.1.4.1.5504.2.5.40.1.3.8.6.1.3
		voiceProfileLineCallingFeatureCallWaitingEnable OBJECT-TYPE
			SYNTAX TruthValue
			MAX-ACCESS read-write
			STATUS current
			DESCRIPTION
				"Enable or disable call waiting in the endpoint."
			::= { voiceProfileLineCallingFeaturesEntry 3 }

		
		-- 1.3.6.1.4.1.5504.2.5.40.1.3.8.6.1.4
		voiceProfileLineCallingFeatureMaxSessions OBJECT-TYPE
			SYNTAX Unsigned32
			MAX-ACCESS read-only
			STATUS current
			DESCRIPTION
				"Indicates the maximum number of simultaneous sessions that may
				be conferenced together by the endpoint. For example, to enable 
				three way conferencing, set the value of this object to 2. This 
				value SHOULD be less than the value of 
				VoiceService.{i}.Capabilities.maxSessionsPerLine."
			::= { voiceProfileLineCallingFeaturesEntry 4 }

		
		-- 1.3.6.1.4.1.5504.2.5.40.1.3.8.6.1.5
		voiceProfileLineCallingFeatureMWIEnable OBJECT-TYPE
			SYNTAX TruthValue
			MAX-ACCESS read-write
			STATUS current
			DESCRIPTION
				"Enable or disable call waiting in the endpoint."
			::= { voiceProfileLineCallingFeaturesEntry 5 }

		
--  End of notifications.
-- ****************************************************************************
-- 
-- Conformance Information
-- 
		-- 1.3.6.1.4.1.5504.2.5.40.2
		zhnVoiceConformance OBJECT IDENTIFIER ::= { zhnVoice 2 }

		
		-- 1.3.6.1.4.1.5504.2.5.40.2.1
		zhnVoiceGroups OBJECT IDENTIFIER ::= { zhnVoiceConformance 1 }

		
--  Units of Conformance
-- 
		-- 1.3.6.1.4.1.5504.2.5.40.2.1.1
		zhnVoiceServiceGroup OBJECT-GROUP
			OBJECTS { voiceProfileNumberOfEntries, voiceBoundIfName, voiceBoundIpAddr, voiceServiceIndex }
			STATUS current
			DESCRIPTION 
				"A collection of Zhone Voice objects that describe the voice 
				services of the device."
			::= { zhnVoiceGroups 1 }

		
		-- 1.3.6.1.4.1.5504.2.5.40.2.1.2
		zhnVoiceCapabilitiesGroup OBJECT-GROUP
			OBJECTS { maxProfileCount, maxLineCount, maxSessionsPerLine, maxSessionCount, signalingProtocols, 
				regions, rtcp, srtp, rtpRedundancy, dscpCoupled, 
				ethernetTaggingCoupled, pstnSoftSwitchOver, faxT38, faxPassThrough, modemPassThrough, 
				toneGeneration, ringGeneration, digitMapCapabilities, numberingPlan, buttonMap, 
				voicePortTests }
			STATUS current
			DESCRIPTION 
				"A collection of Zhone Voice objects that describe the voice 
				capabilities of the device."
			::= { zhnVoiceGroups 2 }

		
		-- 1.3.6.1.4.1.5504.2.5.40.2.1.3
		zhnVoiceCapabilitiesSIPGroup OBJECT-GROUP
			OBJECTS { role, extensionsSIP, transports, uriSchemes, eventSubscription, 
				responseMap, tlsKeyExchangeProtocols }
			STATUS current
			DESCRIPTION 
				"A collection of Zhone Voice objects that describe the voice 
				SIP or SIP PLAR capabilities of the device."
			::= { zhnVoiceGroups 3 }

		
		-- 1.3.6.1.4.1.5504.2.5.40.2.1.4
		zhnVoiceCapabilitiesMGCPGroup OBJECT-GROUP
			OBJECTS { extensionsMGCP }
			STATUS current
			DESCRIPTION 
				"A collection of Zhone Voice objects that describe the voice 
				MGCP capabilities of the device."
			::= { zhnVoiceGroups 4 }

		
		-- 1.3.6.1.4.1.5504.2.5.40.2.1.5
		zhnVoiceCapabilitiesCodecsGroup OBJECT-GROUP
			OBJECTS { codecIndex, entryID, codec, bitRate, packetizationPeriod, 
				silenceSuppression }
			STATUS current
			DESCRIPTION 
				"A collection of Zhone Voice objects that identify the set 
				of supported codecs."
			::= { zhnVoiceGroups 5 }

		
		-- 1.3.6.1.4.1.5504.2.5.40.2.1.6
		zhnVoiceProfileGroup OBJECT-GROUP
			OBJECTS { voiceProfileIndex, voiceProfileEnable, voiceProfileReset, voiceProfileNumberOfLines, voiceProfileName, 
				voiceProfileSignalingProtocol, voiceProfileMaxSessions, voiceProfileDtmfMethod, voiceProfileDtmfMethodG711, voiceProfileHookFlashMethod, 
				voiceProfileRegion, voiceProfileDigitMap, voiceProfileDigitMapEnable, voiceProfileStunEnable, voiceProfileStunServer, 
				voiceProfileStunServerPort, voiceProfileLogServer, voiceProfileLogServerPort, voiceProfileSpNum, voiceProfileV18Support
				 }
			STATUS current
			DESCRIPTION 
				"A collection of Zhone Voice objects that describe a voice
				profile."
			::= { zhnVoiceGroups 6 }

		
		-- 1.3.6.1.4.1.5504.2.5.40.2.1.7
		zhnVoiceProfileServiceProviderGroup OBJECT-GROUP
			OBJECTS { voiceProfileServiceProviderName }
			STATUS current
			DESCRIPTION 
				"A collection of Zhone Voice Profile objects that describe a 
				service provider."
			::= { zhnVoiceGroups 7 }

		
		-- 1.3.6.1.4.1.5504.2.5.40.2.1.8
		zhnVoiceProfileSIPGroup OBJECT-GROUP
			OBJECTS { voiceProfileSIPProxyServer, voiceProfileSIPProxyServerPort, voiceProfileSIPProxyServerTransport, voiceProfileSIPRegistrarServer, voiceProfileSIPRegistrarServerPort, 
				voiceProfileSIPRegistrarServerTransport, voiceProfileSIPToTagMatching, voiceProfileSIPMusicServer, voiceProfileSIPMusicServerPort, voiceProfileSIPPlarGateway, 
				voiceProfileSIPPlarPort, voiceProfileSIPUserAgentDomain, voiceProfileSIPUserAgentPort, voiceProfileSIPUserAgentTransport, voiceProfileSIPOutboundProxy, 
				voiceProfileSIPOutboundProxyPort, voiceProfileSIPOrganization, voiceProfileSIPRegistrationPeriod, voiceProfileSIPRegisterExpires, voiceProfileSIPRegisterRetryInterval, 
				voiceProfileSIPDSCPMark, voiceProfileSIPVLANIDMark, voiceProfileSIPEthernetPriorityMark }
			STATUS current
			DESCRIPTION 
				"A collection of Zhone Voice Profile objects that describe SIP
				information."
			::= { zhnVoiceGroups 8 }

		
		-- 1.3.6.1.4.1.5504.2.5.40.2.1.9
		zhnVoiceProfileSIPEventSubscribeGroup OBJECT-GROUP
			OBJECTS { voiceProfileSIPEventSubscribeEvent, voiceProfileSIPEventSubscribeNotifier, voiceProfileSIPEventSubscribeNotifierPort, voiceProfileSIPEventSubscribeNotifierTransport }
			STATUS current
			DESCRIPTION 
				"A collection of Zhone Voice Profile objects that describe SIP
				subscriber events information."
			::= { zhnVoiceGroups 9 }

		
		-- 1.3.6.1.4.1.5504.2.5.40.2.1.10
		zhnVoiceProfileMGCPEntry OBJECT-GROUP
			OBJECTS { voiceProfileMGCPCallAgent1, voiceProfileMGCPUser, voiceProfilePersistentNotify }
			STATUS current
			DESCRIPTION 
				"A collection of Zhone Voice Profile objects that describe MGCP
				information."
			::= { zhnVoiceGroups 10 }

		
		-- 1.3.6.1.4.1.5504.2.5.40.2.1.11
		zhnVoiceProfileRTPEntry OBJECT-GROUP
			OBJECTS { voiceProfileRTPLocalPortMin, voiceProfileRTPLocalPortMax, voiceProfileRTPDSCPMark, voiceProfileRTPTelephoneEventPayloadType }
			STATUS current
			DESCRIPTION 
				"A collection of Zhone Voice Profile objects that describe 
				Real-time Transport Protocol (RTP) information."
			::= { zhnVoiceGroups 11 }

		
		-- 1.3.6.1.4.1.5504.2.5.40.2.1.12
		zhnVoiceProfileFaxT38Entry OBJECT-GROUP
			OBJECTS { voiceProfileFaxT38Enable, voiceProfileFaxT38BitRate, voiceProfileFaxT38HighSpeedPacketRate }
			STATUS current
			DESCRIPTION 
				"A collection of Zhone Voice Profile objects that describe 
				FAX T.38 information."
			::= { zhnVoiceGroups 12 }

		
		-- 1.3.6.1.4.1.5504.2.5.40.2.1.13
		zhnVoiceProfileLineGroup OBJECT-GROUP
			OBJECTS { voiceProfileLineIndex, voiceProfileLineEnable, voiceProfileLineDirectoryNumber, voiceProfileLineStatus, voiceProfileLineCallState, 
				voiceProfileLinePhyReferenceList, voiceProfileLineCMAcntNum, voiceProfileLineOnhook, voiceProfileLineRowStatus }
			STATUS current
			DESCRIPTION 
				"A collection of Zhone Voice objects that describe physical 
				line information for a voice profile."
			::= { zhnVoiceGroups 13 }

		
		-- 1.3.6.1.4.1.5504.2.5.40.2.1.14
		zhnVoiceProfileLineProcessingGroup OBJECT-GROUP
			OBJECTS { voiceProfileLineTransmitGain, voiceProfileLineReceiveGain, voiceProfileLineEchoCancellationEnable, voiceProfileLineEchoCancellationInUse }
			STATUS current
			DESCRIPTION 
				"A collection of Zhone Voice objects that describe physical 
				line processing information for a voice profile."
			::= { zhnVoiceGroups 14 }

		
		-- 1.3.6.1.4.1.5504.2.5.40.2.1.15
		zhnVoiceProfileLineSIPGroup OBJECT-GROUP
			OBJECTS { voiceProfileLineSIPAuthUserName, voiceProfileLineSIPAuthPassword, voiceProfileLineSIPURI, voiceProfileLineSIPPlarUserName }
			STATUS current
			DESCRIPTION 
				"A collection of Zhone Voice objects that describe voice line
				information specific to SIP call signaling for a voice profile."
			::= { zhnVoiceGroups 15 }

		
		-- 1.3.6.1.4.1.5504.2.5.40.2.1.16
		zhnVoiceProfileLineMGCPGroup OBJECT-GROUP
			OBJECTS { voiceProfileLineMGCPLineName }
			STATUS current
			DESCRIPTION 
				"A collection of Zhone Voice objects that describe voice line
				information specific to MGCP call signaling for a voice profile."
			::= { zhnVoiceGroups 16 }

		
		-- 1.3.6.1.4.1.5504.2.5.40.2.1.17
		zhnVoiceProfileLineCodecsGroup OBJECT-GROUP
			OBJECTS { voiceProfileLineCodecIndex, voiceProfileLineCodecEntryID, voiceProfileLineCodec, voiceProfileLineCodecBitRate, voiceProfileLineCodecPacketizationPeriod, 
				voiceProfileLineCodecSilenceSuppression, voiceProfileLineCodecEnable, voiceProfileLineCodecPriority }
			STATUS current
			DESCRIPTION 
				"A collection of Zhone Voice objects that describe voice line CODECS
				information."
			::= { zhnVoiceGroups 17 }

		
		-- 1.3.6.1.4.1.5504.2.5.40.2.1.18
		zhnVoiceLineCallingFeaturesGroup OBJECT-GROUP
			OBJECTS { voiceProfileLineCallingFeatureCallerIDEnable, voiceProfileLineCallingFeatureCallerIDName, voiceProfileLineCallingFeatureCallWaitingEnable, voiceProfileLineCallingFeatureMaxSessions, voiceProfileLineCallingFeatureMWIEnable
				 }
			STATUS current
			DESCRIPTION 
				"A collection of optionable, configurable Zhone Voice Line calling features."
			::= { zhnVoiceGroups 18 }

		
		-- 1.3.6.1.4.1.5504.2.5.40.2.1.19
		zhnVoiceNotificationGroup NOTIFICATION-GROUP
			NOTIFICATIONS { voiceRegistrationUp, voiceRegistrationDown }
			STATUS current
			DESCRIPTION 
				"Collection of objects for controlling the Zhone Voice notifications."
			::= { zhnVoiceGroups 19 }

		
		-- 1.3.6.1.4.1.5504.2.5.40.2.2
		zhnVoiceCompliances OBJECT IDENTIFIER ::= { zhnVoiceConformance 2 }

		
--  Compliance Statements
-- 
-- this module
		-- 1.3.6.1.4.1.5504.2.5.40.2.2.1
		zhnVoiceCompliance MODULE-COMPLIANCE
			STATUS current
			DESCRIPTION 
				"The Compliance statement for SNMP entities which
				manage display the Zhone CPE Voice Information"
			MODULE -- this module
				MANDATORY-GROUPS { zhnVoiceServiceGroup, zhnVoiceCapabilitiesGroup, zhnVoiceCapabilitiesCodecsGroup, zhnVoiceProfileGroup, zhnVoiceProfileServiceProviderGroup, 
					zhnVoiceProfileLineGroup, zhnVoiceProfileLineProcessingGroup, zhnVoiceProfileLineCodecsGroup }
				GROUP zhnVoiceCapabilitiesSIPGroup
					DESCRIPTION 
						"This group is mandatory for devices that support
						SIP or SIP PLAR call signaling. Write access is not
						required for all objects in this group."
				GROUP zhnVoiceCapabilitiesMGCPGroup
					DESCRIPTION 
						"This group is mandatory for devices that support
						MGCP call signaling. Write access is not
						required for all objects in this group."
				GROUP zhnVoiceProfileSIPGroup
					DESCRIPTION 
						"This group is mandatory for devices that support
						SIP call signaling. Write access is not
						required for all objects in this group."
				GROUP zhnVoiceProfileSIPEventSubscribeGroup
					DESCRIPTION 
						"This group is mandatory for devices that support
						SIP call signaling. Write access is not
						required for all objects in this group."
				GROUP zhnVoiceProfileMGCPEntry
					DESCRIPTION 
						"This group is mandatory for devices that support
						MGCP call signaling. Write access is not
						required for all objects in this group."
				GROUP zhnVoiceProfileRTPEntry
					DESCRIPTION 
						"Write access is not required for all objects in 
						this group."
				GROUP zhnVoiceProfileFaxT38Entry
					DESCRIPTION 
						"Write access is not required for all objects in 
						this group."
				GROUP zhnVoiceNotificationGroup
					DESCRIPTION 
						"This group is only mandatory for implementations
						that support the Voice notifications."
			::= { zhnVoiceCompliances 1 }

		
	
	END

--
-- ZHNVOICE.my.mib
--
