ADSL-TC-MIB DEFINITIONS ::= BEGIN

IMPORTS
    transmission,
    MODULE-IDENTITY, Gauge32            FROM SNMPv2-SMI
    TEXTUAL-CONVENTION                  FROM SNMPv2-TC;

adsltcmib MODULE-IDENTITY

LAST-UPDATED "9908190000Z"

ORGANIZATION "IETF ADSL MIB Working Group"

CONTACT-INFO
    "
    Gregory Bathrick
    AG Communication Systems
    A Subsidiary of Lucent Technologies
    2500 W Utopia Rd.
    Phoenix, AZ 85027 USA
    Tel: +1 602-582-7679
    Fax: +1 602-582-7697
    E-mail: bathricg@agcs.com

    Faye Ly
    Copper Mountain Networks
    Norcal Office
    2470 Embarcadero Way
    Palo Alto, CA 94303
    Tel: +1 650-858-8500
    Fax: +1 650-858-8085
    E-Mail: faye@coppermountain.com

    IETF ADSL MIB Working Group (adsl@xlist.agcs.com)
    "
    DESCRIPTION
        "The MIB module which provides a ADSL
        Line Coding Textual Convention to be used
        by ADSL Lines."

    --  Revision history
    REVISION     "9908190000Z"  -- 19 August 1999, midnight
    DESCRIPTION  "Initial Version, published as RFC 2662"

    ::= { transmission 94 2 } -- adslMIB 2

    AdslLineCodingType ::= TEXTUAL-CONVENTION
        STATUS       current
        DESCRIPTION
            "This data type is used as the syntax for the ADSL
            Line Code."
        SYNTAX  INTEGER {
            other(1),-- none of the following
            dmt (2), -- Discrete MultiTone
            cap (3), -- Carrierless Amplitude &amp; Phase modulation
            qam (4)  -- Quadrature Amplitude Modulation
        }

    AdslPerfCurrDayCount ::= TEXTUAL-CONVENTION
        STATUS  current
        DESCRIPTION
            "A counter associated with interface performance
            measurements in a current 1-day (24 hour) measurement
            interval.

            The value of this counter starts at zero at the
            beginning of an interval and is increased when
            associated events occur, until the end of the
            1-day interval.  At that time the value of the
            counter is stored in the previous 1-day history
            interval, if available, and the current interval
            counter is restarted at zero.

            In the case where the agent has no valid data available
            for this interval the corresponding object
            instance is not available and upon a retrieval
            request a corresponding error message shall be
            returned to indicate that this instance does
            not exist (for example, a noSuchName error for
            SNMPv1 and a noSuchInstance for SNMPv2 GET
            operation)."

         SYNTAX  Gauge32

    AdslPerfPrevDayCount ::= TEXTUAL-CONVENTION
        STATUS  current
        DESCRIPTION
            "A counter associated with interface performance
            measurements during the most previous 1-day (24 hour)
            measurement interval.  The value of this counter is
            equal to the value of the current day counter at
            the end of its most recent interval.

            In the case where the agent has no valid data available
            for this interval the corresponding object
            instance is not available and upon a retrieval
            request a corresponding error message shall be
            returned to indicate that this instance does
            not exist (for example, a noSuchName error for
            SNMPv1 and a noSuchInstance for SNMPv2 GET
            operation)."
        SYNTAX  Gauge32

    AdslPerfTimeElapsed ::= TEXTUAL-CONVENTION
        STATUS current
        DESCRIPTION
            "The number of seconds that have elapsed since
            the beginning of the current measurement period.
            If, for some reason, such as an adjustment in the
            system's time-of-day clock, the current interval
            exceeds the maximum value, the agent will return
            the maximum value."
        SYNTAX  Gauge32

END


ADSL-TC-MIB DEFINITIONS ::= BEGIN

IMPORTS
    transmission,
    MODULE-IDENTITY, Gauge32            FROM SNMPv2-SMI
    TEXTUAL-CONVENTION                  FROM SNMPv2-TC;

adsltcmib MODULE-IDENTITY

LAST-UPDATED "9908190000Z"

ORGANIZATION "IETF ADSL MIB Working Group"

CONTACT-INFO
    "
    Gregory Bathrick
    AG Communication Systems
    A Subsidiary of Lucent Technologies
    2500 W Utopia Rd.
    Phoenix, AZ 85027 USA
    Tel: +1 602-582-7679
    Fax: +1 602-582-7697
    E-mail: bathricg@agcs.com

    Faye Ly
    Copper Mountain Networks
    Norcal Office
    2470 Embarcadero Way
    Palo Alto, CA 94303
    Tel: +1 650-858-8500
    Fax: +1 650-858-8085
    E-Mail: faye@coppermountain.com

    IETF ADSL MIB Working Group (adsl@xlist.agcs.com)
    "
    DESCRIPTION
        "The MIB module which provides a ADSL
        Line Coding Textual Convention to be used
        by ADSL Lines."

    --  Revision history
    REVISION     "9908190000Z"  -- 19 August 1999, midnight
    DESCRIPTION  "Initial Version, published as RFC 2662"

    ::= { transmission 94 2 } -- adslMIB 2

    AdslLineCodingType ::= TEXTUAL-CONVENTION
        STATUS       current
        DESCRIPTION
            "This data type is used as the syntax for the ADSL
            Line Code."
        SYNTAX  INTEGER {
            other(1),-- none of the following
            dmt (2), -- Discrete MultiTone
            cap (3), -- Carrierless Amplitude &amp; Phase modulation
            qam (4)  -- Quadrature Amplitude Modulation
        }

    AdslPerfCurrDayCount ::= TEXTUAL-CONVENTION
        STATUS  current
        DESCRIPTION
            "A counter associated with interface performance
            measurements in a current 1-day (24 hour) measurement
            interval.

            The value of this counter starts at zero at the
            beginning of an interval and is increased when
            associated events occur, until the end of the
            1-day interval.  At that time the value of the
            counter is stored in the previous 1-day history
            interval, if available, and the current interval
            counter is restarted at zero.

            In the case where the agent has no valid data available
            for this interval the corresponding object
            instance is not available and upon a retrieval
            request a corresponding error message shall be
            returned to indicate that this instance does
            not exist (for example, a noSuchName error for
            SNMPv1 and a noSuchInstance for SNMPv2 GET
            operation)."

         SYNTAX  Gauge32

    AdslPerfPrevDayCount ::= TEXTUAL-CONVENTION
        STATUS  current
        DESCRIPTION
            "A counter associated with interface performance
            measurements during the most previous 1-day (24 hour)
            measurement interval.  The value of this counter is
            equal to the value of the current day counter at
            the end of its most recent interval.

            In the case where the agent has no valid data available
            for this interval the corresponding object
            instance is not available and upon a retrieval
            request a corresponding error message shall be
            returned to indicate that this instance does
            not exist (for example, a noSuchName error for
            SNMPv1 and a noSuchInstance for SNMPv2 GET
            operation)."
        SYNTAX  Gauge32

    AdslPerfTimeElapsed ::= TEXTUAL-CONVENTION
        STATUS current
        DESCRIPTION
            "The number of seconds that have elapsed since
            the beginning of the current measurement period.
            If, for some reason, such as an adjustment in the
            system's time-of-day clock, the current interval
            exceeds the maximum value, the agent will return
            the maximum value."
        SYNTAX  Gauge32

END

ADSL-LINE-MIB DEFINITIONS ::= BEGIN

IMPORTS
    MODULE-IDENTITY, OBJECT-TYPE,
    Counter32, Gauge32,
    NOTIFICATION-TYPE,
    transmission, Unsigned32          FROM SNMPv2-SMI
    RowStatus,
    TruthValue, VariablePointer       FROM SNMPv2-TC
    MODULE-COMPLIANCE, OBJECT-GROUP,
    NOTIFICATION-GROUP                FROM SNMPv2-CONF
    ifIndex                           FROM IF-MIB
    PerfCurrentCount,
    PerfIntervalCount                 FROM PerfHist-TC-MIB

    SnmpAdminString                   FROM SNMP-FRAMEWORK-MIB
    AdslPerfCurrDayCount,
    AdslPerfPrevDayCount,
    AdslPerfTimeElapsed,
    AdslLineCodingType                FROM ADSL-TC-MIB
    ;

adslMIB MODULE-IDENTITY

LAST-UPDATED "9908190000Z"

ORGANIZATION "IETF ADSL MIB Working Group"

CONTACT-INFO
    "
    Gregory Bathrick
    AG Communication Systems
    A Subsidiary of Lucent Technologies
    2500 W Utopia Rd.
    Phoenix, AZ 85027 USA
    Tel: +1 602-582-7679
    Fax: +1 602-582-7697
    E-mail: bathricg@agcs.com

    Faye Ly
    Copper Mountain Networks
    Norcal Office
    2470 Embarcadero Way
    Palo Alto, CA 94303
    Tel: +1 650-858-8500
    Fax: +1 650-858-8085
    E-Mail: faye@coppermountain.com

    (ADSL Forum input only)
    John Burgess
    Predictive Systems, Inc.
    25A Vreeland Rd.
    Florham Park, NJ 07932 USA
    Tel: +1 973-301-5610
    Fax: +1 973-301-5699
    E-mail: jtburgess@predictive.com

    IETF ADSL MIB Working Group (adsl@xlist.agcs.com)
    "

DESCRIPTION
    "The MIB module defining objects for the management of a pair of
    ADSL modems at each end of the ADSL line.  Each such line has

    an entry in an ifTable which may include multiple modem lines.
    An agent may reside at either end of the ADSL line however the
    MIB is designed to require no management communication between
    them beyond that inherent in the low-level ADSL line protocol.
    The agent may monitor and control this protocol for its needs.

    ADSL lines may support optional Fast or Interleaved channels.
    If these are supported, additional entries corresponding to the
    supported channels must be created in the ifTable. Thus an ADSL
    line that supports both channels will have three entries in the
    ifTable, one for each physical, fast, and interleaved, whose
    ifType values are equal to adsl(94), fast(125), and
    interleaved(124), respectively. The ifStackTable is used to
    represent the relationship between the entries.

    Naming Conventions:
              Atuc -- (ATUC) modem at near (Central) end of line
              Atur -- (ATUR) modem at Remote end of line
              Curr -- Current
              Prev -- Previous
              Atn -- Attenuation
              ES  -- Errored Second.
              LCS -- Line Code Specific
              Lof -- Loss of Frame
              Lol -- Loss of Link
              Los -- Loss of Signal
              Lpr -- Loss of Power
              xxxs-- interval of Seconds in which xxx occurs
                      (e.g., xxx=Lof, Los, Lpr)
              Max -- Maximum
              Mgn -- Margin
              Min -- Minimum
              Psd -- Power Spectral Density
              Snr -- Signal to Noise Ratio
              Tx  -- Transmit
              Blks-- Blocks, a data unit, see
                     adslAtuXChanCrcBlockLength
      "
      --  Revision history
      REVISION     "9908190000Z"  -- 19 August 1999, midnight
      DESCRIPTION  "Initial Version, published as RFC 2662"

::= { transmission 94 }

adslLineMib OBJECT IDENTIFIER ::= { adslMIB 1 }

adslMibObjects OBJECT IDENTIFIER ::= { adslLineMib 1 }


-- objects
      adslLineTable   OBJECT-TYPE
          SYNTAX          SEQUENCE OF AdslLineEntry
          MAX-ACCESS      not-accessible
          STATUS          current
          DESCRIPTION
              "This table includes common attributes describing
              both ends of the line.  It is required for all ADSL
              physical interfaces.  ADSL physical interfaces are
              those ifEntries where ifType is equal to adsl(94)."
      ::= { adslMibObjects 1 }

      adslLineEntry   OBJECT-TYPE
          SYNTAX          AdslLineEntry
          MAX-ACCESS      not-accessible
          STATUS          current
          DESCRIPTION     "An entry in adslLineTable."
          INDEX           { ifIndex }
      ::= { adslLineTable 1 }

      AdslLineEntry ::=
          SEQUENCE {
          adslLineCoding           AdslLineCodingType,
          adslLineType             INTEGER,
          adslLineSpecific         VariablePointer,
          adslLineConfProfile      SnmpAdminString,
          adslLineAlarmConfProfile SnmpAdminString
          }

      adslLineCoding OBJECT-TYPE
          SYNTAX      AdslLineCodingType
          MAX-ACCESS  read-only
          STATUS      current
          DESCRIPTION
              "Specifies the ADSL coding type used on this
              line."
      ::= { adslLineEntry 1 }

     adslLineType OBJECT-TYPE
          SYNTAX      INTEGER {
              noChannel (1),        -- no channels exist
              fastOnly (2),         -- fast channel exists only
              interleavedOnly (3),  -- interleaved channel exists
                                    -- only
              fastOrInterleaved (4),-- either fast or interleaved
                                    -- channels can exist, but
                                    -- only one at any time
              fastAndInterleaved (5)-- both fast or interleaved

                                    -- channels exist
          }
          MAX-ACCESS  read-only
          STATUS      current
          DESCRIPTION
              "Defines the type of ADSL physical line
              entity that exists, by defining whether and how
              the line is channelized.  If the line is channelized,
              the value will be other than noChannel(1).  This
              object defines which channel type(s) are supported.

              In the case that the line is channelized, the manager
              can use the ifStackTable to determine the ifIndex for
              the associated channel(s)."
      ::= { adslLineEntry 2 }

      adslLineSpecific OBJECT-TYPE
          SYNTAX      VariablePointer
          MAX-ACCESS  read-only
          STATUS      current
          DESCRIPTION
              "OID instance in vendor-specific MIB. The Instance may
              be used to determine shelf/slot/port of the ATUC
              interface in a DSLAM."
      ::= { adslLineEntry 3 }

     adslLineConfProfile OBJECT-TYPE
          SYNTAX      SnmpAdminString (SIZE (1..32))
          MAX-ACCESS  read-write
          STATUS      current
          DESCRIPTION
              "The value of this object identifies the row
              in the ADSL Line Configuration Profile Table,
              (adslLineConfProfileTable), which applies for this
              ADSL line, and channels if applicable.

              For `dynamic' mode, in the case which the
              configuration profile has not been set, the
              value will be set to `DEFVAL'.

              If the implementator of this MIB has chosen not
              to implement `dynamic assignment' of profiles, this
              object's MIN-ACCESS is read-only."
      ::= { adslLineEntry 4 }

     adslLineAlarmConfProfile OBJECT-TYPE
          SYNTAX      SnmpAdminString (SIZE (1..32))
          MAX-ACCESS  read-write

          STATUS      current
          DESCRIPTION
              "The value of this object identifies the row
              in the ADSL Line Alarm Configuration Profile Table,
              (adslLineAlarmConfProfileTable), which applies to this
              ADSL line, and channels if applicable.

              For `dynamic' mode, in the case which the
              alarm profile has not been set, the
              value will be set to `DEFVAL'.

              If the implementator of this MIB has chosen not
              to implement `dynamic assignment' of profiles, this
              object's MIN-ACCESS is read-only."
      ::= { adslLineEntry 5 }

      adslAtucPhysTable       OBJECT-TYPE
          SYNTAX          SEQUENCE OF AdslAtucPhysEntry
          MAX-ACCESS      not-accessible
          STATUS          current
          DESCRIPTION
              "This table provides one row for each ATUC.
              Each row contains the Physical Layer Parameters
              table for that ATUC. ADSL physical interfaces are
              those ifEntries where ifType is equal to adsl(94)."
      ::= { adslMibObjects 2 }

      adslAtucPhysEntry       OBJECT-TYPE
          SYNTAX          AdslAtucPhysEntry
          MAX-ACCESS      not-accessible
          STATUS          current
          DESCRIPTION     "An entry in the adslAtucPhysTable."
          INDEX           { ifIndex }
      ::= { adslAtucPhysTable 1 }

      AdslAtucPhysEntry ::=
          SEQUENCE {
          adslAtucInvSerialNumber         SnmpAdminString,
          adslAtucInvVendorID             SnmpAdminString,
          adslAtucInvVersionNumber        SnmpAdminString,
          adslAtucCurrSnrMgn              INTEGER,
          adslAtucCurrAtn                 Gauge32,
          adslAtucCurrStatus              BITS,
          adslAtucCurrOutputPwr           INTEGER,
          adslAtucCurrAttainableRate      Gauge32
          }

      -- inventory group

      --
      -- These items should describe the lowest level identifiable
      -- component, be it a stand-alone modem, a card in a rack,
      -- a child-board, etc.
      --
      adslAtucInvSerialNumber OBJECT-TYPE
          SYNTAX      SnmpAdminString (SIZE (0..32))
          MAX-ACCESS  read-only
          STATUS      current
          DESCRIPTION
              "The vendor specific string that identifies the
              vendor equipment."
      ::= { adslAtucPhysEntry 1 }

      adslAtucInvVendorID OBJECT-TYPE
          SYNTAX      SnmpAdminString (SIZE (0..16))
          MAX-ACCESS  read-only
          STATUS      current
          DESCRIPTION
              "The vendor ID code is a copy of the binary
              vendor identification field defined by the
              PHY[10] and expressed as readable characters."

          REFERENCE "ANSI T1.413[10]"
      ::= { adslAtucPhysEntry 2 }

      adslAtucInvVersionNumber OBJECT-TYPE
          SYNTAX      SnmpAdminString (SIZE (0..16))
          MAX-ACCESS  read-only
          STATUS      current
          DESCRIPTION
              "The vendor specific version number sent by this ATU
              as part of the initialization messages.  It is a copy
              of the binary version number field defined by the
              PHY[10] and expressed as readable characters."
          REFERENCE "ANSI T1.413[10]"
      ::= { adslAtucPhysEntry 3 }

      -- current status group
      --
      adslAtucCurrSnrMgn OBJECT-TYPE
          SYNTAX      INTEGER (-640..640)
          UNITS       "tenth dB"
          MAX-ACCESS  read-only
          STATUS      current
          DESCRIPTION
              "Noise Margin as seen by this ATU with respect to its
              received signal in tenth dB."

      ::= { adslAtucPhysEntry 4 }

      adslAtucCurrAtn OBJECT-TYPE
          SYNTAX      Gauge32(0..630)
          UNITS       "tenth dB"
          MAX-ACCESS  read-only
          STATUS      current
          DESCRIPTION
              "Measured difference in the total power transmitted by
              the peer ATU and the total power received by this ATU."
      ::= { adslAtucPhysEntry 5 }

     adslAtucCurrStatus OBJECT-TYPE
          SYNTAX      BITS {
                            noDefect(0),
                            lossOfFraming(1),
                            lossOfSignal(2),
                            lossOfPower(3),
                            lossOfSignalQuality(4),
                            lossOfLink(5),
                            dataInitFailure(6),
                            configInitFailure(7),
                            protocolInitFailure(8),
                            noPeerAtuPresent(9)
                           }
          MAX-ACCESS  read-only
          STATUS      current
          DESCRIPTION
              "Indicates current state of the ATUC line.  This is a
              bit-map of possible conditions.  The various bit
              positions are:

       0      noDefect             There no defects on the line

       1      lossOfFraming        ATUC failure due to not
                                   receiving valid frame.

       2      lossOfSignal         ATUC failure due to not
                                   receiving signal.

       3      lossOfPower          ATUC failure due to loss of
                                   power.
                                   Note: the Agent may still
                                   function.

       4      lossOfSignalQuality  Loss of Signal Quality is
                                   declared when the Noise Margin
                                   falls below the Minimum Noise

                                   Margin, or the bit-error-rate
                                   exceeds 10^-7.

       5      lossOfLink           ATUC failure due to inability
                                   to link with ATUR.

       6      dataInitFailure      ATUC failure during
                                   initialization due to bit
                                   errors corrupting startup
                                   exchange data.

       7      configInitFailure    ATUC failure during
                                   initialization due to peer
                                   ATU not able to support
                                   requested configuration

       8      protocolInitFailure  ATUC failure during
                                   initialization due to
                                   incompatible protocol used by
                                   the peer ATU.

       9      noPeerAtuPresent     ATUC failure during
                                   initialization due to no
                                   activation sequence detected
                                   from peer ATU.

              This is intended to supplement ifOperStatus."
      ::= { adslAtucPhysEntry 6 }

      adslAtucCurrOutputPwr OBJECT-TYPE
          SYNTAX      INTEGER (-310..310)
          UNITS       "tenth dBm"
          MAX-ACCESS  read-only
          STATUS      current
          DESCRIPTION
              "Measured total output power transmitted by this ATU.
              This is the measurement that was reported during
              the last activation sequence."
      ::= { adslAtucPhysEntry 7 }

      adslAtucCurrAttainableRate OBJECT-TYPE
          SYNTAX      Gauge32
          UNITS       "bps"
          MAX-ACCESS  read-only
          STATUS      current
          DESCRIPTION
              "Indicates the maximum currently attainable data rate
              by the ATU.  This value will be equal or greater than

              the current line rate."
      ::= { adslAtucPhysEntry 8 }

      adslAturPhysTable        OBJECT-TYPE
          SYNTAX          SEQUENCE OF AdslAturPhysEntry
          MAX-ACCESS      not-accessible
          STATUS          current
          DESCRIPTION
              "This table provides one row for each ATUR
              Each row contains the Physical Layer Parameters
              table for that ATUR. ADSL physical interfaces are
              those ifEntries where ifType is equal to adsl(94)."
      ::= { adslMibObjects 3 }

      adslAturPhysEntry       OBJECT-TYPE
          SYNTAX          AdslAturPhysEntry
          MAX-ACCESS      not-accessible
          STATUS          current
          DESCRIPTION     "An entry in the adslAturPhysTable."
          INDEX           { ifIndex }
      ::= { adslAturPhysTable 1 }

      AdslAturPhysEntry ::=
          SEQUENCE {
          adslAturInvSerialNumber         SnmpAdminString,
          adslAturInvVendorID             SnmpAdminString,
          adslAturInvVersionNumber        SnmpAdminString,
          adslAturCurrSnrMgn              INTEGER,
          adslAturCurrAtn                 Gauge32,
          adslAturCurrStatus              BITS,
          adslAturCurrOutputPwr           INTEGER,
          adslAturCurrAttainableRate      Gauge32
          }

      -- inventory group
      --
      adslAturInvSerialNumber OBJECT-TYPE
          SYNTAX      SnmpAdminString (SIZE (0..32))
          MAX-ACCESS  read-only
          STATUS      current
          DESCRIPTION
              "The vendor specific string that identifies the
              vendor equipment."
      ::= { adslAturPhysEntry 1 }

      adslAturInvVendorID OBJECT-TYPE
          SYNTAX      SnmpAdminString (SIZE (0..16))
          MAX-ACCESS  read-only

          STATUS      current
          DESCRIPTION
              "The vendor ID code is a copy of the binary
              vendor identification field defined by the
              PHY[10] and expressed as readable characters."
          REFERENCE "ANSI T1.413"
      ::= { adslAturPhysEntry 2 }

      adslAturInvVersionNumber OBJECT-TYPE
          SYNTAX      SnmpAdminString (SIZE (0..16))
          MAX-ACCESS  read-only
          STATUS      current
          DESCRIPTION
              "The vendor specific version number sent by this ATU
              as part of the initialization messages.  It is a copy
              of the binary version number field defined by the
              PHY[10] and expressed as readable characters."
          REFERENCE "ANSI T1.413"
      ::= { adslAturPhysEntry 3 }

      -- current status group
      --
      adslAturCurrSnrMgn OBJECT-TYPE
          SYNTAX      INTEGER (-640..640)
          UNITS       "tenth dB"
          MAX-ACCESS  read-only
          STATUS      current
          DESCRIPTION
              "Noise Margin as seen by this ATU with respect to its
              received signal in tenth dB."
      ::= { adslAturPhysEntry 4 }

      adslAturCurrAtn OBJECT-TYPE
          SYNTAX      Gauge32(0..630)
          UNITS       "tenth dB"
          MAX-ACCESS  read-only
          STATUS      current
          DESCRIPTION
              "Measured difference in the total power transmitted by
              the peer ATU and the total power received by this ATU."
      ::= { adslAturPhysEntry 5 }

     adslAturCurrStatus OBJECT-TYPE
          SYNTAX     BITS {
                           noDefect(0),
                           lossOfFraming(1),
                           lossOfSignal(2),
                           lossOfPower(3),

                           lossOfSignalQuality(4)
                          }
          MAX-ACCESS  read-only
          STATUS      current
          DESCRIPTION
              "Indicates current state of the ATUR line.  This is a
              bit-map of possible conditions.  Due to the isolation
              of the ATUR when line problems occur, many state
              conditions like loss of power, loss of quality signal,
              and initialization errors,  can not be determined.
              While trouble shooting ATUR, also use object,
              adslAtucCurrStatus.  The various bit positions are:

       0      noDefect             There no defects on the line

       1      lossOfFraming        ATUR failure due to not
                                   receiving valid frame

       2      lossOfSignal         ATUR failure due to not
                                   receiving signal

       3      lossOfPower          ATUR failure due to loss of
                                   power

       4      lossOfSignalQuality  Loss of Signal Quality is
                                   declared when the Noise Margin
                                   falls below the Minimum Noise
                                   Margin, or the
                                   bit-error-rate exceeds 10^-7.

              This is intended to supplement ifOperStatus."
      ::= { adslAturPhysEntry 6 }

      adslAturCurrOutputPwr OBJECT-TYPE
          SYNTAX      INTEGER (-310..310)
          UNITS       "tenth dBm"
          MAX-ACCESS  read-only
          STATUS      current
          DESCRIPTION
              "Measured total output power transmitted by this ATU.
              This is the measurement that was reported during
              the last activation sequence."
      ::= { adslAturPhysEntry 7 }

      adslAturCurrAttainableRate OBJECT-TYPE
          SYNTAX      Gauge32
          UNITS       "bps"
          MAX-ACCESS  read-only

          STATUS      current
          DESCRIPTION
              "Indicates the maximum currently attainable data rate
              by the ATU.  This value will be equal or greater than
              the current line rate."
      ::= { adslAturPhysEntry 8 }

      adslAtucChanTable       OBJECT-TYPE
          SYNTAX          SEQUENCE OF AdslAtucChanEntry
          MAX-ACCESS      not-accessible
          STATUS          current
          DESCRIPTION
              "This table provides one row for each ATUC channel.
              ADSL channel interfaces are those ifEntries
              where ifType is equal to adslInterleave(124)
              or adslFast(125)."
      ::= { adslMibObjects 4 }

      adslAtucChanEntry       OBJECT-TYPE
          SYNTAX          AdslAtucChanEntry
          MAX-ACCESS      not-accessible
          STATUS          current
          DESCRIPTION     "An entry in the adslAtucChanTable."
          INDEX           { ifIndex }
      ::= { adslAtucChanTable 1 }

      AdslAtucChanEntry ::=
          SEQUENCE {
          adslAtucChanInterleaveDelay     Gauge32,
          adslAtucChanCurrTxRate          Gauge32,
          adslAtucChanPrevTxRate          Gauge32,
          adslAtucChanCrcBlockLength      Gauge32
          }

      -- current group
      --
      adslAtucChanInterleaveDelay OBJECT-TYPE
          SYNTAX      Gauge32
          UNITS       "milli-seconds"
          MAX-ACCESS  read-only
          STATUS      current
          DESCRIPTION
              "Interleave Delay for this channel.

              Interleave delay applies only to the
              interleave channel and defines the mapping
              (relative spacing) between subsequent input
              bytes at the interleaver input and their placement

              in the bit stream at the interleaver output.
              Larger numbers provide greater separation between
              consecutive input bytes in the output bit stream
              allowing for improved impulse noise immunity at
              the expense of payload latency.

              In the case where the ifType is Fast(125), use
              noSuchObject."
      ::= { adslAtucChanEntry 1 }

      adslAtucChanCurrTxRate  OBJECT-TYPE
          SYNTAX      Gauge32
          UNITS       "bps"
          MAX-ACCESS  read-only
          STATUS      current
          DESCRIPTION
              "Actual transmit rate on this channel."
      ::= { adslAtucChanEntry 2 }

      adslAtucChanPrevTxRate OBJECT-TYPE
          SYNTAX      Gauge32
          UNITS        "bps"
          MAX-ACCESS  read-only
          STATUS      current
          DESCRIPTION
              "The rate at the time of the last
              adslAtucRateChangeTrap event. It is also set at
              initialization to prevent a trap being sent.

              Rate changes less than adslAtucThresh(*)RateDown
              or less than adslAtucThresh(*)RateUp will not
              cause a trap or cause this object to change.
              (*) == Fast or Interleave.
              See AdslLineAlarmConfProfileEntry."
      ::= { adslAtucChanEntry 3 }

      adslAtucChanCrcBlockLength OBJECT-TYPE
          SYNTAX      Gauge32
          UNITS        "byte"
          MAX-ACCESS  read-only
          STATUS      current
          DESCRIPTION
              "Indicates the length of the channel data-block
              on which the CRC operates.  Refer to Line Code
              Specific MIBs, [11] and [12] for more
              information."
      ::= { adslAtucChanEntry 4 }


     adslAturChanTable       OBJECT-TYPE
          SYNTAX          SEQUENCE OF AdslAturChanEntry
          MAX-ACCESS      not-accessible
          STATUS          current
          DESCRIPTION
              "This table provides one row for each ATUR channel.
              ADSL channel interfaces are those ifEntries
              where ifType is equal to adslInterleave(124)
              or adslFast(125)."
      ::= { adslMibObjects 5 }

      adslAturChanEntry       OBJECT-TYPE
          SYNTAX          AdslAturChanEntry
          MAX-ACCESS      not-accessible
          STATUS          current
          DESCRIPTION     "An entry in the adslAturChanTable."
          INDEX           { ifIndex }
      ::= { adslAturChanTable 1 }

      AdslAturChanEntry ::=
          SEQUENCE {
          adslAturChanInterleaveDelay     Gauge32,
          adslAturChanCurrTxRate          Gauge32,
          adslAturChanPrevTxRate          Gauge32,
          adslAturChanCrcBlockLength      Gauge32
          }

      -- current group
      --
      adslAturChanInterleaveDelay OBJECT-TYPE
          SYNTAX      Gauge32
          UNITS       "milli-seconds"
          MAX-ACCESS  read-only
          STATUS      current
          DESCRIPTION
              "Interleave Delay for this channel.

              Interleave delay applies only to the
              interleave channel and defines the mapping
              (relative spacing) between subsequent input
              bytes at the interleaver input and their placement
              in the bit stream at the interleaver output.
              Larger numbers provide greater separation between
              consecutive input bytes in the output bit stream
              allowing for improved impulse noise immunity at
              the expense of payload latency.

              In the case where the ifType is Fast(125), use

              noSuchObject."
      ::= { adslAturChanEntry 1 }

      adslAturChanCurrTxRate  OBJECT-TYPE
          SYNTAX      Gauge32
          UNITS       "bps"
          MAX-ACCESS  read-only
          STATUS      current
          DESCRIPTION
              "Actual transmit rate on this channel."
      ::= { adslAturChanEntry 2 }

      adslAturChanPrevTxRate OBJECT-TYPE
          SYNTAX      Gauge32
          UNITS       "bps"
          MAX-ACCESS  read-only
          STATUS      current
          DESCRIPTION
             "The rate at the time of the last
              adslAturRateChangeTrap event. It is also set at
              initialization to prevent a trap being sent.
              Rate changes less than adslAturThresh(*)RateDown
              or less than adslAturThresh(*)RateUp will not
              cause a trap or cause this object to change.
              (*) == Fast or Interleave.
              See AdslLineAlarmConfProfileEntry."
      ::= { adslAturChanEntry 3 }

      adslAturChanCrcBlockLength OBJECT-TYPE
          SYNTAX      Gauge32
          MAX-ACCESS  read-only
          STATUS      current
          DESCRIPTION
              "Indicates the length of the channel data-block
              on which the CRC operates.  Refer to Line Code
              Specific MIBs, [11] and [12] for more
              information."
      ::= { adslAturChanEntry 4 }

      adslAtucPerfDataTable   OBJECT-TYPE
          SYNTAX          SEQUENCE OF AdslAtucPerfDataEntry
          MAX-ACCESS      not-accessible
          STATUS          current
          DESCRIPTION
              "This table provides one row for each ATUC.
              ADSL physical interfaces are
              those ifEntries where ifType is equal to adsl(94)."
      ::= { adslMibObjects 6 }

      adslAtucPerfDataEntry       OBJECT-TYPE
          SYNTAX          AdslAtucPerfDataEntry
          MAX-ACCESS      not-accessible
          STATUS          current
          DESCRIPTION     "An entry in adslAtucPerfDataTable."
          INDEX           { ifIndex }
      ::= { adslAtucPerfDataTable 1 }

      AdslAtucPerfDataEntry ::=
          SEQUENCE {
          adslAtucPerfLofs                 Counter32,
          adslAtucPerfLoss                 Counter32,
          adslAtucPerfLols                 Counter32,
          adslAtucPerfLprs                 Counter32,
          adslAtucPerfESs                  Counter32,
          adslAtucPerfInits                Counter32,
          adslAtucPerfValidIntervals       INTEGER,
          adslAtucPerfInvalidIntervals     INTEGER,
          adslAtucPerfCurr15MinTimeElapsed AdslPerfTimeElapsed,
          adslAtucPerfCurr15MinLofs        PerfCurrentCount,
          adslAtucPerfCurr15MinLoss        PerfCurrentCount,
          adslAtucPerfCurr15MinLols        PerfCurrentCount,
          adslAtucPerfCurr15MinLprs        PerfCurrentCount,
          adslAtucPerfCurr15MinESs         PerfCurrentCount,
          adslAtucPerfCurr15MinInits       PerfCurrentCount,
          adslAtucPerfCurr1DayTimeElapsed  AdslPerfTimeElapsed,
          adslAtucPerfCurr1DayLofs         AdslPerfCurrDayCount,
          adslAtucPerfCurr1DayLoss         AdslPerfCurrDayCount,
          adslAtucPerfCurr1DayLols         AdslPerfCurrDayCount,
          adslAtucPerfCurr1DayLprs         AdslPerfCurrDayCount,
          adslAtucPerfCurr1DayESs          AdslPerfCurrDayCount,
          adslAtucPerfCurr1DayInits        AdslPerfCurrDayCount,
          adslAtucPerfPrev1DayMoniSecs     INTEGER,
          adslAtucPerfPrev1DayLofs         AdslPerfPrevDayCount,
          adslAtucPerfPrev1DayLoss         AdslPerfPrevDayCount,
          adslAtucPerfPrev1DayLols         AdslPerfPrevDayCount,
          adslAtucPerfPrev1DayLprs         AdslPerfPrevDayCount,
          adslAtucPerfPrev1DayESs          AdslPerfPrevDayCount,
          adslAtucPerfPrev1DayInits        AdslPerfPrevDayCount
          }

      -- Event Counters
      --
      -- Also see adslAtucIntervalTable for 15 minute interval
      -- elapsed counters.
      --
      adslAtucPerfLofs OBJECT-TYPE
          SYNTAX      Counter32

          MAX-ACCESS  read-only
          STATUS      current
          DESCRIPTION
              "Count of the number of Loss of Framing failures since
              agent reset."
      ::= { adslAtucPerfDataEntry 1 }

      adslAtucPerfLoss  OBJECT-TYPE
          SYNTAX      Counter32
          MAX-ACCESS  read-only
          STATUS      current
          DESCRIPTION
              "Count of the number of Loss of Signal failures since
              agent reset."
      ::= { adslAtucPerfDataEntry 2 }

      adslAtucPerfLols OBJECT-TYPE
          SYNTAX      Counter32
          MAX-ACCESS  read-only
          STATUS      current
          DESCRIPTION
              "Count of the number of Loss of Link failures since
              agent reset."
      ::= { adslAtucPerfDataEntry 3 }

      adslAtucPerfLprs OBJECT-TYPE
          SYNTAX      Counter32
          MAX-ACCESS  read-only
          STATUS      current
          DESCRIPTION
              "Count of the number of Loss of Power failures since
              agent reset."
      ::= { adslAtucPerfDataEntry 4 }

      adslAtucPerfESs OBJECT-TYPE
          SYNTAX      Counter32
          MAX-ACCESS  read-only
          STATUS      current
          DESCRIPTION
              "Count of the number of Errored Seconds since agent
              reset.  The errored second parameter is a count of
              one-second intervals containing one or more crc
              anomalies, or one or more los or sef defects."
      ::= { adslAtucPerfDataEntry 5 }

      adslAtucPerfInits OBJECT-TYPE
          SYNTAX      Counter32
          MAX-ACCESS  read-only

          STATUS      current
          DESCRIPTION
              "Count of the line initialization attempts since
              agent reset. Includes both successful and failed
              attempts."
      ::= { adslAtucPerfDataEntry 6 }

      -- general 15 min interval information
      --

      adslAtucPerfValidIntervals OBJECT-TYPE
          SYNTAX      INTEGER(0..96)
          MAX-ACCESS  read-only
          STATUS      current
          DESCRIPTION
              "The number of previous 15-minute intervals in the
              interval table for which data was collected.  Given
              that &lt;n&gt; is the maximum # of intervals supported.
              The value will be &lt;n&gt; unless the measurement was
              (re-)started within the last (&lt;n&gt;*15) minutes, in which
              case the value will be the number of complete 15
              minute intervals for which the agent has at least
              some data. In certain cases (e.g., in the case
              where the agent is a proxy) it is possible that some
              intervals are unavailable.  In this case, this
              interval is the maximum interval number for
              which data is available."
      ::= { adslAtucPerfDataEntry 7 }

      adslAtucPerfInvalidIntervals OBJECT-TYPE
          SYNTAX      INTEGER(0..96)
          MAX-ACCESS  read-only
          STATUS      current
          DESCRIPTION
              "The number of intervals in the range from
              0 to the value of adslAtucPerfValidIntervals
              for which no data is available. This object
              will typically be zero except in cases where
              the data for some intervals are not available
              (e.g., in proxy situations)."
      ::= { adslAtucPerfDataEntry 8 }

      -- 15 min current performance group
      --
      adslAtucPerfCurr15MinTimeElapsed OBJECT-TYPE
          SYNTAX      AdslPerfTimeElapsed(0..899)
          UNITS       "seconds"
          MAX-ACCESS  read-only

          STATUS      current
          DESCRIPTION
              "Total elapsed seconds in this interval."
      ::= { adslAtucPerfDataEntry 9 }

      adslAtucPerfCurr15MinLofs OBJECT-TYPE
          SYNTAX      PerfCurrentCount
          UNITS       "seconds"
          MAX-ACCESS  read-only
          STATUS      current
          DESCRIPTION
              "Count of seconds in the current 15 minute interval
              when there was Loss of Framing."
      ::= { adslAtucPerfDataEntry 10 }

      adslAtucPerfCurr15MinLoss  OBJECT-TYPE
          SYNTAX      PerfCurrentCount
          UNITS       "seconds"
          MAX-ACCESS  read-only
          STATUS      current
          DESCRIPTION
              "Count of seconds in the current 15 minute interval
              when there was Loss of Signal."
      ::= { adslAtucPerfDataEntry 11 }

      adslAtucPerfCurr15MinLols  OBJECT-TYPE
          SYNTAX      PerfCurrentCount
          UNITS       "seconds"
          MAX-ACCESS  read-only
          STATUS      current
          DESCRIPTION
              "Count of seconds in the current 15 minute interval
              when there was Loss of Link."
      ::= { adslAtucPerfDataEntry 12 }

      adslAtucPerfCurr15MinLprs  OBJECT-TYPE
          SYNTAX      PerfCurrentCount
          UNITS       "seconds"
          MAX-ACCESS  read-only
          STATUS      current
          DESCRIPTION
              "Count of seconds in the current 15 minute interval
              when there was Loss of Power."
      ::= { adslAtucPerfDataEntry 13 }

      adslAtucPerfCurr15MinESs OBJECT-TYPE
          SYNTAX      PerfCurrentCount
          UNITS       "seconds"

          MAX-ACCESS  read-only
          STATUS      current
          DESCRIPTION
              "Count of Errored Seconds in the current 15 minute
              interval.  The errored second parameter is a count of
              one-second intervals containing one or more crc
              anomalies, or one or more los or sef defects."
      ::= { adslAtucPerfDataEntry 14 }

      adslAtucPerfCurr15MinInits  OBJECT-TYPE
          SYNTAX      PerfCurrentCount
          MAX-ACCESS  read-only
          STATUS      current
          DESCRIPTION
              "Count of the line initialization attempts in the
              current 15 minute interval. Includes both successful
              and failed attempts."
      ::= { adslAtucPerfDataEntry 15 }

      -- 1-day current and previous performance group
      --
      adslAtucPerfCurr1DayTimeElapsed OBJECT-TYPE
          SYNTAX      AdslPerfTimeElapsed(0..86399)
          UNITS       "seconds"
          MAX-ACCESS  read-only
          STATUS      current
          DESCRIPTION
              "Number of seconds that have elapsed since the
              beginning of the current 1-day interval."
      ::= { adslAtucPerfDataEntry 16 }

      adslAtucPerfCurr1DayLofs  OBJECT-TYPE
          SYNTAX      AdslPerfCurrDayCount
          UNITS       "seconds"
          MAX-ACCESS  read-only
          STATUS      current
          DESCRIPTION
              "Count of the number of seconds when there was Loss of
              Framing during the current day as measured by
              adslAtucPerfCurr1DayTimeElapsed."
      ::= { adslAtucPerfDataEntry 17 }

      adslAtucPerfCurr1DayLoss  OBJECT-TYPE
          SYNTAX      AdslPerfCurrDayCount
          UNITS       "seconds"
          MAX-ACCESS  read-only
          STATUS      current
          DESCRIPTION

              "Count of the number of seconds when there was Loss of
              Signal during the current day as measured by
              adslAtucPerfCurr1DayTimeElapsed."
      ::= { adslAtucPerfDataEntry 18 }

      adslAtucPerfCurr1DayLols  OBJECT-TYPE
          SYNTAX      AdslPerfCurrDayCount
          UNITS       "seconds"
          MAX-ACCESS  read-only
          STATUS      current
          DESCRIPTION
              "Count of the number of seconds when there was Loss of
              Link during the current day as measured by
              adslAtucPerfCurr1DayTimeElapsed."
      ::= { adslAtucPerfDataEntry 19 }

      adslAtucPerfCurr1DayLprs  OBJECT-TYPE
          SYNTAX      AdslPerfCurrDayCount
          UNITS       "seconds"
          MAX-ACCESS  read-only
          STATUS      current
          DESCRIPTION
              "Count of the number of seconds when there was Loss of
              Power during the current day as measured by
              adslAtucPerfCurr1DayTimeElapsed."
      ::= { adslAtucPerfDataEntry 20 }

      adslAtucPerfCurr1DayESs OBJECT-TYPE
          SYNTAX      AdslPerfCurrDayCount
          UNITS       "seconds"
          MAX-ACCESS  read-only
          STATUS      current
          DESCRIPTION
              "Count of Errored Seconds during the current day as
              measured by adslAtucPerfCurr1DayTimeElapsed.
              The errored second parameter is a count of
              one-second intervals containing one or more crc
              anomalies, or one or more los or sef defects."
      ::= { adslAtucPerfDataEntry 21 }

      adslAtucPerfCurr1DayInits  OBJECT-TYPE
          SYNTAX      AdslPerfCurrDayCount
          MAX-ACCESS  read-only
          STATUS      current
          DESCRIPTION
              "Count of the line initialization attempts in the
              day as measured by adslAtucPerfCurr1DayTimeElapsed.
              Includes both successful and failed attempts."

      ::= { adslAtucPerfDataEntry 22 }

      adslAtucPerfPrev1DayMoniSecs OBJECT-TYPE
          SYNTAX      INTEGER(0..86400)
          UNITS       "seconds"
          MAX-ACCESS  read-only
          STATUS      current
          DESCRIPTION
              "The amount of time in the previous 1-day interval
              over which the performance monitoring information
              is actually counted. This value will be the same as
              the interval duration except in a situation where
              performance monitoring data could not be collected
              for any reason."
      ::= { adslAtucPerfDataEntry 23 }

      adslAtucPerfPrev1DayLofs  OBJECT-TYPE
          SYNTAX      AdslPerfPrevDayCount
          UNITS       "seconds"
          MAX-ACCESS  read-only
          STATUS      current
          DESCRIPTION
              "Count of seconds in the interval when there was
              Loss of Framing within the most recent previous
              1-day period."
      ::= { adslAtucPerfDataEntry 24 }

      adslAtucPerfPrev1DayLoss  OBJECT-TYPE
          SYNTAX      AdslPerfPrevDayCount
          UNITS       "seconds"
          MAX-ACCESS  read-only
          STATUS      current
          DESCRIPTION
              "Count of seconds in the interval when there was
              Loss of Signal within the most recent previous
              1-day period."
      ::= { adslAtucPerfDataEntry 25 }

      adslAtucPerfPrev1DayLols  OBJECT-TYPE
          SYNTAX      AdslPerfPrevDayCount
          UNITS       "seconds"
          MAX-ACCESS  read-only
          STATUS      current
          DESCRIPTION
              "Count of seconds in the interval when there was
              Loss of Link within the most recent previous
              1-day period."
      ::= { adslAtucPerfDataEntry 26 }

      adslAtucPerfPrev1DayLprs  OBJECT-TYPE
          SYNTAX      AdslPerfPrevDayCount
          UNITS       "seconds"
          MAX-ACCESS  read-only
          STATUS      current
          DESCRIPTION
              "Count of seconds in the interval when there was
              Loss of Power within the most recent previous
              1-day period."
      ::= { adslAtucPerfDataEntry 27 }

      adslAtucPerfPrev1DayESs OBJECT-TYPE
          SYNTAX      AdslPerfPrevDayCount
          UNITS       "seconds"
          MAX-ACCESS  read-only
          STATUS      current
          DESCRIPTION
              "Count of Errored Seconds within the most recent
              previous 1-day period. The errored second parameter is
              a count of one-second intervals containing one or more
              crc anomalies, or one or more los or sef defects."
      ::= { adslAtucPerfDataEntry 28 }

      adslAtucPerfPrev1DayInits  OBJECT-TYPE
          SYNTAX      AdslPerfPrevDayCount
          MAX-ACCESS  read-only
          STATUS      current
          DESCRIPTION
              "Count of the line initialization attempts in the most
              recent previous 1-day period. Includes both successful
              and failed attempts."
      ::= { adslAtucPerfDataEntry 29 }

      adslAturPerfDataTable   OBJECT-TYPE
          SYNTAX          SEQUENCE OF AdslAturPerfDataEntry
          MAX-ACCESS      not-accessible
          STATUS          current
          DESCRIPTION
              "This table provides one row for each ATUR.
              ADSL physical interfaces are
              those ifEntries where ifType is equal to adsl(94)."
      ::= { adslMibObjects 7 }

      adslAturPerfDataEntry       OBJECT-TYPE
          SYNTAX          AdslAturPerfDataEntry
          MAX-ACCESS      not-accessible
          STATUS          current
          DESCRIPTION     "An entry in adslAturPerfDataTable."

          INDEX           { ifIndex }
      ::= { adslAturPerfDataTable 1 }

      AdslAturPerfDataEntry ::=
          SEQUENCE {
          adslAturPerfLofs                 Counter32,
          adslAturPerfLoss                 Counter32,
          adslAturPerfLprs                 Counter32,
          adslAturPerfESs                  Counter32,
          adslAturPerfValidIntervals       INTEGER,
          adslAturPerfInvalidIntervals     INTEGER,
          adslAturPerfCurr15MinTimeElapsed AdslPerfTimeElapsed,
          adslAturPerfCurr15MinLofs        PerfCurrentCount,
          adslAturPerfCurr15MinLoss        PerfCurrentCount,
          adslAturPerfCurr15MinLprs        PerfCurrentCount,
          adslAturPerfCurr15MinESs         PerfCurrentCount,
          adslAturPerfCurr1DayTimeElapsed  AdslPerfTimeElapsed,
          adslAturPerfCurr1DayLofs         AdslPerfCurrDayCount,
          adslAturPerfCurr1DayLoss         AdslPerfCurrDayCount,
          adslAturPerfCurr1DayLprs         AdslPerfCurrDayCount,
          adslAturPerfCurr1DayESs          AdslPerfCurrDayCount,
          adslAturPerfPrev1DayMoniSecs     INTEGER,
          adslAturPerfPrev1DayLofs         AdslPerfPrevDayCount,
          adslAturPerfPrev1DayLoss         AdslPerfPrevDayCount,
          adslAturPerfPrev1DayLprs         AdslPerfPrevDayCount,
          adslAturPerfPrev1DayESs          AdslPerfPrevDayCount
          }

      -- Event (Raw) Counters
      --
      -- Also see adslAturIntervalTable for 15 minute interval
      -- elapsed counters.
      --
      adslAturPerfLofs OBJECT-TYPE
          SYNTAX      Counter32
          UNITS       "seconds"
          MAX-ACCESS  read-only
          STATUS      current
          DESCRIPTION
              "Count of the number of Loss of Framing failures since
              agent reset."
      ::= { adslAturPerfDataEntry 1 }

      adslAturPerfLoss  OBJECT-TYPE
          SYNTAX      Counter32
          UNITS       "seconds"
          MAX-ACCESS  read-only
          STATUS      current

          DESCRIPTION
              "Count of the number of Loss of Signal failures since
              agent reset."
      ::= { adslAturPerfDataEntry 2 }

     adslAturPerfLprs  OBJECT-TYPE
          SYNTAX      Counter32
          UNITS       "seconds"
          MAX-ACCESS  read-only
          STATUS      current
          DESCRIPTION
              "Count of the number of Loss of Power failures since
              agent reset."
      ::= { adslAturPerfDataEntry 3 }

      adslAturPerfESs  OBJECT-TYPE
          SYNTAX      Counter32
          UNITS       "seconds"
          MAX-ACCESS  read-only
          STATUS      current
          DESCRIPTION
              "Count of the number of Errored Seconds since agent
              reset.  The errored second parameter is a count of
              one-second intervals containing one or more crc
              anomalies, or one or more los or sef defects."
      ::= { adslAturPerfDataEntry 4 }

      -- general 15 min interval information
      --
      adslAturPerfValidIntervals OBJECT-TYPE
          SYNTAX      INTEGER(0..96)
          MAX-ACCESS  read-only
          STATUS      current
          DESCRIPTION
              "The number of previous 15-minute intervals in the
              interval table for which data was collected.  Given
              that &lt;n&gt; is the maximum # of intervals supported.
              The value will be &lt;n&gt; unless the measurement was
              (re-)started within the last (&lt;n&gt;*15) minutes, in which
              case the value will be the number of complete 15
              minute intervals for which the agent has at least
              some data. In certain cases (e.g., in the case
              where the agent is a proxy) it is possible that some
              intervals are unavailable.  In this case, this
              interval is the maximum interval number for
              which data is available."
      ::= { adslAturPerfDataEntry 5 }


      adslAturPerfInvalidIntervals OBJECT-TYPE
          SYNTAX      INTEGER(0..96)
          MAX-ACCESS  read-only
          STATUS      current
          DESCRIPTION
              "The number of intervals in the range from
              0 to the value of adslAturPerfValidIntervals
              for which no data is available. This object
              will typically be zero except in cases where
              the data for some intervals are not available
              (e.g., in proxy situations)."
      ::= { adslAturPerfDataEntry 6 }

      -- 15 min current performance group
      --
      adslAturPerfCurr15MinTimeElapsed OBJECT-TYPE
          SYNTAX      AdslPerfTimeElapsed(0..899)
          UNITS       "seconds"
          MAX-ACCESS  read-only
          STATUS      current
          DESCRIPTION
              "Total elapsed seconds in this interval."
      ::= { adslAturPerfDataEntry 7 }

      adslAturPerfCurr15MinLofs OBJECT-TYPE
          SYNTAX      PerfCurrentCount
          UNITS       "seconds"
          MAX-ACCESS  read-only
          STATUS      current
          DESCRIPTION
              "Count of seconds in the current 15 minute interval
              when there was Loss of Framing."
      ::= { adslAturPerfDataEntry 8 }

      adslAturPerfCurr15MinLoss  OBJECT-TYPE
          SYNTAX      PerfCurrentCount
          UNITS       "seconds"
          MAX-ACCESS  read-only
          STATUS      current
          DESCRIPTION
              "Count of seconds in the current 15 minute interval
              when there was Loss of Signal."
      ::= { adslAturPerfDataEntry 9 }

      adslAturPerfCurr15MinLprs  OBJECT-TYPE
          SYNTAX      PerfCurrentCount
          UNITS       "seconds"
          MAX-ACCESS  read-only

          STATUS      current
          DESCRIPTION
              "Count of seconds in the current 15 minute interval
              when there was Loss of Power."
      ::= { adslAturPerfDataEntry 10 }

      adslAturPerfCurr15MinESs OBJECT-TYPE
          SYNTAX      PerfCurrentCount
          UNITS       "seconds"
          MAX-ACCESS  read-only
          STATUS      current
          DESCRIPTION
             "Count of Errored Seconds in the current 15 minute
             interval.  The errored second parameter is a count of
             one-second intervals containing one or more crc
             anomalies, or one or more los or sef defects."

      ::= { adslAturPerfDataEntry 11 }

      -- 1-day current and previous performance group
      --
      adslAturPerfCurr1DayTimeElapsed OBJECT-TYPE
          SYNTAX      AdslPerfTimeElapsed(0..86399)
          UNITS       "seconds"
          MAX-ACCESS  read-only
          STATUS      current
          DESCRIPTION
              "Number of seconds that have elapsed since the
              beginning of the current 1-day interval."
      ::= { adslAturPerfDataEntry 12 }

      adslAturPerfCurr1DayLofs  OBJECT-TYPE
          SYNTAX      AdslPerfCurrDayCount
          UNITS       "seconds"
          MAX-ACCESS  read-only
          STATUS      current
          DESCRIPTION
              "Count of the number of seconds when there was Loss
              of Framing during the current day as measured by
              adslAturPerfCurr1DayTimeElapsed."
      ::= { adslAturPerfDataEntry 13 }

      adslAturPerfCurr1DayLoss  OBJECT-TYPE
          SYNTAX      AdslPerfCurrDayCount
          UNITS       "seconds"
          MAX-ACCESS  read-only
          STATUS      current
          DESCRIPTION

              "Count of the number of seconds when there was Loss
              of Signal during the current day as measured by
              adslAturPerfCurr1DayTimeElapsed."
      ::= { adslAturPerfDataEntry 14 }

      adslAturPerfCurr1DayLprs  OBJECT-TYPE
          SYNTAX      AdslPerfCurrDayCount
          UNITS       "seconds"
          MAX-ACCESS  read-only
          STATUS      current
          DESCRIPTION
              "Count of the number of seconds when there was Loss
              of Power during the current day as measured by
              adslAturPerfCurr1DayTimeElapsed."
      ::= { adslAturPerfDataEntry 15 }

 adslAturPerfCurr1DayESs OBJECT-TYPE
          SYNTAX      AdslPerfCurrDayCount
          UNITS       "seconds"
          MAX-ACCESS  read-only
          STATUS      current
          DESCRIPTION
              "Count of Errored Seconds during the current day as
              measured by adslAturPerfCurr1DayTimeElapsed.
              The errored second parameter is a count of
              one-second intervals containing one or more crc
              anomalies, or one or more los or sef defects."
      ::= { adslAturPerfDataEntry 16 }

      adslAturPerfPrev1DayMoniSecs OBJECT-TYPE
          SYNTAX      INTEGER(0..86400)
          UNITS       "seconds"
          MAX-ACCESS  read-only
          STATUS      current
          DESCRIPTION
              "The amount of time in the previous 1-day interval
              over which the performance monitoring information
              is actually counted. This value will be the same as
              the interval duration except in a situation where
              performance monitoring data could not be collected
              for any reason."
      ::= { adslAturPerfDataEntry 17 }

      adslAturPerfPrev1DayLofs  OBJECT-TYPE
          SYNTAX      AdslPerfPrevDayCount
          UNITS       "seconds"
          MAX-ACCESS  read-only
          STATUS      current

          DESCRIPTION
              "Count of seconds in the interval when there was
              Loss of Framing within the most recent previous
              1-day period."
      ::= { adslAturPerfDataEntry 18 }

      adslAturPerfPrev1DayLoss  OBJECT-TYPE
          SYNTAX      AdslPerfPrevDayCount
          UNITS       "seconds"
          MAX-ACCESS  read-only
          STATUS      current
          DESCRIPTION
              "Count of seconds in the interval when there was
              Loss of Signal within the most recent previous
              1-day period."
      ::= { adslAturPerfDataEntry 19 }

      adslAturPerfPrev1DayLprs  OBJECT-TYPE
          SYNTAX      AdslPerfPrevDayCount
          UNITS       "seconds"
          MAX-ACCESS  read-only
          STATUS      current
          DESCRIPTION
              "Count of seconds in the interval when there was
              Loss of Power within the most recent previous
              1-day period."
      ::= { adslAturPerfDataEntry 20 }

      adslAturPerfPrev1DayESs OBJECT-TYPE
          SYNTAX      AdslPerfPrevDayCount
          UNITS       "seconds"
          MAX-ACCESS  read-only
          STATUS      current
          DESCRIPTION
              "Count of Errored Seconds within the most recent
              previous 1-day period. The errored second parameter is
              a count of one-second intervals containing one or more
              crc anomalies, or one or more los or sef defects."
      ::= { adslAturPerfDataEntry 21 }

      adslAtucIntervalTable   OBJECT-TYPE
          SYNTAX          SEQUENCE OF AdslAtucIntervalEntry
          MAX-ACCESS      not-accessible
          STATUS          current
          DESCRIPTION
              "This table provides one row for each ATUC
              performance data collection interval.
              ADSL physical interfaces are

              those ifEntries where ifType is equal to adsl(94)."
      ::= { adslMibObjects 8 }

      adslAtucIntervalEntry   OBJECT-TYPE
          SYNTAX          AdslAtucIntervalEntry
          MAX-ACCESS      not-accessible
          STATUS          current
          DESCRIPTION     "An entry in the adslAtucIntervalTable."
          INDEX           { ifIndex, adslAtucIntervalNumber }
      ::= { adslAtucIntervalTable 1 }

      AdslAtucIntervalEntry ::=
          SEQUENCE {
          adslAtucIntervalNumber          INTEGER,
          adslAtucIntervalLofs            PerfIntervalCount,
          adslAtucIntervalLoss            PerfIntervalCount,
          adslAtucIntervalLols            PerfIntervalCount,
          adslAtucIntervalLprs            PerfIntervalCount,
          adslAtucIntervalESs             PerfIntervalCount,
          adslAtucIntervalInits           PerfIntervalCount,
          adslAtucIntervalValidData       TruthValue
          }

      adslAtucIntervalNumber OBJECT-TYPE
          SYNTAX      INTEGER(1..96)
          MAX-ACCESS  not-accessible
          STATUS      current
          DESCRIPTION
              "Performance Data Interval number 1 is the
              the most recent previous interval; interval
              96 is 24 hours ago.  Intervals 2..96 are
              optional."
      ::= { adslAtucIntervalEntry 1 }

      adslAtucIntervalLofs OBJECT-TYPE
          SYNTAX      PerfIntervalCount
          UNITS       "seconds"
          MAX-ACCESS  read-only
          STATUS      current
          DESCRIPTION
              "Count of seconds in the interval when there was Loss
              of Framing."
      ::= { adslAtucIntervalEntry 2 }

      adslAtucIntervalLoss  OBJECT-TYPE
          SYNTAX      PerfIntervalCount
          UNITS       "seconds"
          MAX-ACCESS  read-only

          STATUS      current
          DESCRIPTION
              "Count of seconds in the interval when there was Loss
              of Signal."
      ::= { adslAtucIntervalEntry 3 }

      adslAtucIntervalLols  OBJECT-TYPE
          SYNTAX      PerfIntervalCount
          UNITS       "seconds"
          MAX-ACCESS  read-only
          STATUS      current
          DESCRIPTION
              "Count of seconds in the interval when there was Loss
              of Link."
      ::= { adslAtucIntervalEntry 4 }

      adslAtucIntervalLprs  OBJECT-TYPE
          SYNTAX      PerfIntervalCount
          UNITS       "seconds"
          MAX-ACCESS  read-only
          STATUS      current
          DESCRIPTION
              "Count of seconds in the interval when there was Loss
              of Power."
      ::= { adslAtucIntervalEntry 5 }

      adslAtucIntervalESs OBJECT-TYPE
          SYNTAX      PerfIntervalCount
          UNITS       "seconds"
          MAX-ACCESS  read-only
          STATUS      current
          DESCRIPTION
              "Count of Errored Seconds in the interval.
              The errored second parameter is a count of
              one-second intervals containing one or more crc
              anomalies, or one or more los or sef defects."
      ::= { adslAtucIntervalEntry 6 }

      adslAtucIntervalInits  OBJECT-TYPE
          SYNTAX      PerfIntervalCount
          MAX-ACCESS  read-only
          STATUS      current
          DESCRIPTION
              "Count of the line initialization attempts
              during the interval. Includes both successful
              and failed attempts."
      ::= { adslAtucIntervalEntry 7 }


      adslAtucIntervalValidData OBJECT-TYPE
          SYNTAX TruthValue
          MAX-ACCESS read-only
          STATUS current
          DESCRIPTION
              "This variable indicates if the data for this
              interval is valid."
      ::= { adslAtucIntervalEntry 8 }

      adslAturIntervalTable   OBJECT-TYPE
          SYNTAX          SEQUENCE OF AdslAturIntervalEntry
          MAX-ACCESS      not-accessible
          STATUS          current
          DESCRIPTION
              "This table provides one row for each ATUR
              performance data collection interval.
              ADSL physical interfaces are those
              ifEntries where ifType is equal to adsl(94)."
      ::= { adslMibObjects 9 }

      adslAturIntervalEntry   OBJECT-TYPE
          SYNTAX          AdslAturIntervalEntry
          MAX-ACCESS      not-accessible
          STATUS          current
          DESCRIPTION     "An entry in the adslAturIntervalTable."
          INDEX           { ifIndex, adslAturIntervalNumber }
      ::= { adslAturIntervalTable 1 }

      AdslAturIntervalEntry ::=
          SEQUENCE {
          adslAturIntervalNumber          INTEGER,
          adslAturIntervalLofs            PerfIntervalCount,
          adslAturIntervalLoss            PerfIntervalCount,
          adslAturIntervalLprs            PerfIntervalCount,
          adslAturIntervalESs             PerfIntervalCount,
          adslAturIntervalValidData       TruthValue
          }

      adslAturIntervalNumber OBJECT-TYPE
          SYNTAX      INTEGER(1..96)
          MAX-ACCESS  not-accessible
          STATUS      current
          DESCRIPTION
              "Performance Data Interval number 1 is the
              the most recent previous interval; interval
              96 is 24 hours ago.  Intervals 2..96 are
              optional."
      ::= { adslAturIntervalEntry 1 }

      adslAturIntervalLofs OBJECT-TYPE
          SYNTAX      PerfIntervalCount
          UNITS       "seconds"
          MAX-ACCESS  read-only
          STATUS      current
          DESCRIPTION
              "Count of seconds in the interval when there was
              Loss of Framing."
      ::= { adslAturIntervalEntry 2 }

      adslAturIntervalLoss  OBJECT-TYPE
          SYNTAX      PerfIntervalCount
          UNITS       "seconds"
          MAX-ACCESS  read-only
          STATUS      current
          DESCRIPTION
              "Count of seconds in the interval when there was
              Loss of Signal."
      ::= { adslAturIntervalEntry 3 }

      adslAturIntervalLprs  OBJECT-TYPE
          SYNTAX      PerfIntervalCount
          UNITS       "seconds"
          MAX-ACCESS  read-only
          STATUS      current
          DESCRIPTION
              "Count of seconds in the interval when there was
              Loss of Power."
      ::= { adslAturIntervalEntry 4 }

      adslAturIntervalESs OBJECT-TYPE
          SYNTAX      PerfIntervalCount
          UNITS       "seconds"
          MAX-ACCESS  read-only
          STATUS      current
          DESCRIPTION
              "Count of Errored Seconds in the interval.
              The errored second parameter is a count of
              one-second intervals containing one or more crc
              anomalies, or one or more los or sef defects."
      ::= { adslAturIntervalEntry 5 }

      adslAturIntervalValidData OBJECT-TYPE
          SYNTAX TruthValue
          MAX-ACCESS read-only
          STATUS current
          DESCRIPTION
              "This variable indicates if the data for this

              interval is valid."
      ::= { adslAturIntervalEntry 6 }

      adslAtucChanPerfDataTable       OBJECT-TYPE
          SYNTAX          SEQUENCE OF AdslAtucChanPerfDataEntry
          MAX-ACCESS      not-accessible
          STATUS          current
          DESCRIPTION
              "This table provides one row for each ATUC channel.
              ADSL channel interfaces are those ifEntries
              where ifType is equal to adslInterleave(124)
              or adslFast(125)."
      ::= { adslMibObjects 10 }

      adslAtucChanPerfDataEntry       OBJECT-TYPE

          SYNTAX          AdslAtucChanPerfDataEntry
          MAX-ACCESS      not-accessible
          STATUS          current
          DESCRIPTION     "An entry in adslAtucChanPerfDataTable."
          INDEX           { ifIndex }
      ::= { adslAtucChanPerfDataTable 1 }

      AdslAtucChanPerfDataEntry ::=
       SEQUENCE {
       adslAtucChanReceivedBlks                 Counter32,
       adslAtucChanTransmittedBlks              Counter32,
       adslAtucChanCorrectedBlks                Counter32,
       adslAtucChanUncorrectBlks                Counter32,
       adslAtucChanPerfValidIntervals           INTEGER,
       adslAtucChanPerfInvalidIntervals         INTEGER,
       adslAtucChanPerfCurr15MinTimeElapsed     AdslPerfTimeElapsed,
       adslAtucChanPerfCurr15MinReceivedBlks    PerfCurrentCount,
       adslAtucChanPerfCurr15MinTransmittedBlks PerfCurrentCount,
       adslAtucChanPerfCurr15MinCorrectedBlks   PerfCurrentCount,
       adslAtucChanPerfCurr15MinUncorrectBlks   PerfCurrentCount,
       adslAtucChanPerfCurr1DayTimeElapsed      AdslPerfTimeElapsed,
       adslAtucChanPerfCurr1DayReceivedBlks     AdslPerfCurrDayCount,
       adslAtucChanPerfCurr1DayTransmittedBlks  AdslPerfCurrDayCount,
       adslAtucChanPerfCurr1DayCorrectedBlks    AdslPerfCurrDayCount,
       adslAtucChanPerfCurr1DayUncorrectBlks    AdslPerfCurrDayCount,
       adslAtucChanPerfPrev1DayMoniSecs         INTEGER,
       adslAtucChanPerfPrev1DayReceivedBlks     AdslPerfPrevDayCount,
       adslAtucChanPerfPrev1DayTransmittedBlks  AdslPerfPrevDayCount,
       adslAtucChanPerfPrev1DayCorrectedBlks    AdslPerfPrevDayCount,
       adslAtucChanPerfPrev1DayUncorrectBlks    AdslPerfPrevDayCount
      }
      -- performance group

      --
      -- Note: block is intended to be the length of the channel
      --       data-block on which the CRC operates. See
      --       adslAtucChanCrcBlockLength for more information.
      --
      adslAtucChanReceivedBlks OBJECT-TYPE
          SYNTAX      Counter32
          MAX-ACCESS  read-only
          STATUS      current
          DESCRIPTION
              "Count of all encoded blocks received on this channel
              since agent reset."
      ::= { adslAtucChanPerfDataEntry 1 }

      adslAtucChanTransmittedBlks  OBJECT-TYPE
          SYNTAX      Counter32
          MAX-ACCESS  read-only
          STATUS      current
          DESCRIPTION
              "Count of all encoded blocks transmitted on this
              channel since agent reset."
      ::= { adslAtucChanPerfDataEntry 2 }

      adslAtucChanCorrectedBlks  OBJECT-TYPE
          SYNTAX      Counter32
          MAX-ACCESS  read-only
          STATUS      current
          DESCRIPTION
              "Count of all blocks received with errors that were
              corrected since agent reset.  These blocks are passed
              on as good data."
      ::= { adslAtucChanPerfDataEntry 3 }

      adslAtucChanUncorrectBlks  OBJECT-TYPE
          SYNTAX      Counter32
          MAX-ACCESS  read-only
          STATUS      current
          DESCRIPTION
              "Count of all blocks received with uncorrectable
              errors since agent reset."
      ::= { adslAtucChanPerfDataEntry 4 }

      -- general 15 min interval information
      --
      adslAtucChanPerfValidIntervals OBJECT-TYPE
          SYNTAX      INTEGER(0..96)
          MAX-ACCESS  read-only
          STATUS      current

          DESCRIPTION
              "The number of previous 15-minute intervals in the
              interval table for which data was collected.  Given
              that &lt;n&gt; is the maximum # of intervals supported.
              The value will be &lt;n&gt; unless the measurement was
              (re-)started within the last (&lt;n&gt;*15) minutes, in which
              case the value will be the number of complete 15
              minute intervals for which the agent has at least
              some data. In certain cases (e.g., in the case
              where the agent is a proxy) it is possible that some
              intervals are unavailable.  In this case, this
              interval is the maximum interval number for
              which data is available."
      ::= { adslAtucChanPerfDataEntry 5 }

      adslAtucChanPerfInvalidIntervals OBJECT-TYPE
          SYNTAX      INTEGER(0..96)
          MAX-ACCESS  read-only
          STATUS      current
          DESCRIPTION
              "The number of intervals in the range from
              0 to the value of adslAtucChanPerfValidIntervals
              for which no data is available. This object
              will typically be zero except in cases where
              the data for some intervals are not available
              (e.g., in proxy situations)."
      ::= { adslAtucChanPerfDataEntry 6 }

      -- 15 min current performance group
      --
      adslAtucChanPerfCurr15MinTimeElapsed OBJECT-TYPE
          SYNTAX      AdslPerfTimeElapsed(0..899)
          UNITS       "seconds"
          MAX-ACCESS  read-only
          STATUS      current
          DESCRIPTION
              "Total elapsed seconds in this interval."
      ::= { adslAtucChanPerfDataEntry 7 }

      adslAtucChanPerfCurr15MinReceivedBlks OBJECT-TYPE
          SYNTAX      PerfCurrentCount
          MAX-ACCESS  read-only
          STATUS      current
          DESCRIPTION
              "Count of all encoded blocks received on this channel
              within the current 15 minute interval."
      ::= { adslAtucChanPerfDataEntry 8 }


      adslAtucChanPerfCurr15MinTransmittedBlks OBJECT-TYPE
          SYNTAX      PerfCurrentCount
          MAX-ACCESS  read-only
          STATUS      current
          DESCRIPTION
              "Count of all encoded blocks transmitted on this
              channel within the current 15 minute interval."
      ::= { adslAtucChanPerfDataEntry 9 }

      adslAtucChanPerfCurr15MinCorrectedBlks  OBJECT-TYPE
          SYNTAX      PerfCurrentCount
          MAX-ACCESS  read-only
          STATUS      current
          DESCRIPTION
              "Count of all blocks received with errors that were
              corrected on this channel within the current 15 minute
              interval."
      ::= { adslAtucChanPerfDataEntry 10 }

      adslAtucChanPerfCurr15MinUncorrectBlks  OBJECT-TYPE
          SYNTAX      PerfCurrentCount
          MAX-ACCESS  read-only
          STATUS      current
          DESCRIPTION
              "Count of all blocks received with uncorrectable
              errors on this channel within the current 15 minute
              interval."
      ::= { adslAtucChanPerfDataEntry 11 }

      -- 1-day current and previous performance group
      --
      adslAtucChanPerfCurr1DayTimeElapsed OBJECT-TYPE
          SYNTAX      AdslPerfTimeElapsed(0..86399)
          UNITS       "seconds"
          MAX-ACCESS  read-only
          STATUS      current
          DESCRIPTION
              "Number of seconds that have elapsed since the
              beginning of the current 1-day interval."
      ::= { adslAtucChanPerfDataEntry 12 }

      adslAtucChanPerfCurr1DayReceivedBlks  OBJECT-TYPE
          SYNTAX      AdslPerfCurrDayCount
          MAX-ACCESS  read-only
          STATUS      current
          DESCRIPTION
              "Count of all encoded blocks received on this
              channel during the current day as measured by

              adslAtucChanPerfCurr1DayTimeElapsed."
      ::= { adslAtucChanPerfDataEntry 13 }

      adslAtucChanPerfCurr1DayTransmittedBlks  OBJECT-TYPE
          SYNTAX      AdslPerfCurrDayCount
          MAX-ACCESS  read-only
          STATUS      current
          DESCRIPTION
              "Count of all encoded blocks transmitted on this
              channel during the current day as measured by
              adslAtucChanPerfCurr1DayTimeElapsed."
      ::= { adslAtucChanPerfDataEntry 14 }

      adslAtucChanPerfCurr1DayCorrectedBlks  OBJECT-TYPE
          SYNTAX      AdslPerfCurrDayCount
          MAX-ACCESS  read-only
          STATUS      current
          DESCRIPTION
              "Count of all blocks received with errors that were
              corrected on this channel during the current day as
              measured by adslAtucChanPerfCurr1DayTimeElapsed."
      ::= { adslAtucChanPerfDataEntry 15 }

      adslAtucChanPerfCurr1DayUncorrectBlks  OBJECT-TYPE
          SYNTAX      AdslPerfCurrDayCount
          MAX-ACCESS  read-only
          STATUS      current
          DESCRIPTION
              "Count of all blocks received with uncorrectable
              errors on this channel during the current day as
              measured by adslAtucChanPerfCurr1DayTimeElapsed."
      ::= { adslAtucChanPerfDataEntry 16 }

      adslAtucChanPerfPrev1DayMoniSecs OBJECT-TYPE
          SYNTAX      INTEGER(0..86400)
          UNITS       "seconds"
          MAX-ACCESS  read-only
          STATUS      current
          DESCRIPTION
              "The amount of time in the previous 1-day interval
              over which the performance monitoring information
              is actually counted. This value will be the same as
              the interval duration except in a situation where
              performance monitoring data could not be collected
              for any reason."
      ::= { adslAtucChanPerfDataEntry 17 }

      adslAtucChanPerfPrev1DayReceivedBlks  OBJECT-TYPE

          SYNTAX      AdslPerfPrevDayCount
          MAX-ACCESS  read-only
          STATUS      current
          DESCRIPTION
              "Count of all encoded blocks received on this
              channel within the most recent previous 1-day
              period."
      ::= { adslAtucChanPerfDataEntry 18 }

      adslAtucChanPerfPrev1DayTransmittedBlks  OBJECT-TYPE
          SYNTAX      AdslPerfPrevDayCount
          MAX-ACCESS  read-only
          STATUS      current
          DESCRIPTION
              "Count of all encoded blocks transmitted on this
              channel within the most recent previous 1-day
              period."
      ::= { adslAtucChanPerfDataEntry 19 }

      adslAtucChanPerfPrev1DayCorrectedBlks  OBJECT-TYPE
          SYNTAX      AdslPerfPrevDayCount
          MAX-ACCESS  read-only
          STATUS      current
          DESCRIPTION
              "Count of all blocks received with errors that were
              corrected on this channel within the most recent
              previous 1-day period."
      ::= { adslAtucChanPerfDataEntry 20 }

      adslAtucChanPerfPrev1DayUncorrectBlks  OBJECT-TYPE
          SYNTAX      AdslPerfPrevDayCount
          MAX-ACCESS  read-only
          STATUS      current
          DESCRIPTION
              "Count of all blocks received with uncorrectable
              errors on this channel within the most recent previous
              1-day period."
      ::= { adslAtucChanPerfDataEntry 21 }

      adslAturChanPerfDataTable       OBJECT-TYPE
          SYNTAX          SEQUENCE OF AdslAturChanPerfDataEntry
          MAX-ACCESS      not-accessible
          STATUS          current
          DESCRIPTION
              "This table provides one row for each ATUR channel.
              ADSL channel interfaces are those ifEntries
              where ifType is equal to adslInterleave(124)
              or adslFast(125)."

      ::= { adslMibObjects 11 }

      adslAturChanPerfDataEntry       OBJECT-TYPE
          SYNTAX          AdslAturChanPerfDataEntry
          MAX-ACCESS      not-accessible
          STATUS          current
          DESCRIPTION     "An entry in adslAturChanPerfDataTable."
          INDEX           { ifIndex }
      ::= { adslAturChanPerfDataTable 1 }

      AdslAturChanPerfDataEntry ::=
       SEQUENCE {
       adslAturChanReceivedBlks                 Counter32,
       adslAturChanTransmittedBlks              Counter32,
       adslAturChanCorrectedBlks                Counter32,
       adslAturChanUncorrectBlks                Counter32,
       adslAturChanPerfValidIntervals           INTEGER,
       adslAturChanPerfInvalidIntervals         INTEGER,
       adslAturChanPerfCurr15MinTimeElapsed     AdslPerfTimeElapsed,
       adslAturChanPerfCurr15MinReceivedBlks    PerfCurrentCount,
       adslAturChanPerfCurr15MinTransmittedBlks PerfCurrentCount,
       adslAturChanPerfCurr15MinCorrectedBlks   PerfCurrentCount,
       adslAturChanPerfCurr15MinUncorrectBlks   PerfCurrentCount,
       adslAturChanPerfCurr1DayTimeElapsed      AdslPerfTimeElapsed,
       adslAturChanPerfCurr1DayReceivedBlks     AdslPerfCurrDayCount,
       adslAturChanPerfCurr1DayTransmittedBlks  AdslPerfCurrDayCount,
       adslAturChanPerfCurr1DayCorrectedBlks    AdslPerfCurrDayCount,
       adslAturChanPerfCurr1DayUncorrectBlks    AdslPerfCurrDayCount,
       adslAturChanPerfPrev1DayMoniSecs         INTEGER,
       adslAturChanPerfPrev1DayReceivedBlks     AdslPerfPrevDayCount,
       adslAturChanPerfPrev1DayTransmittedBlks  AdslPerfPrevDayCount,
       adslAturChanPerfPrev1DayCorrectedBlks    AdslPerfPrevDayCount,
       adslAturChanPerfPrev1DayUncorrectBlks    AdslPerfPrevDayCount
       }
      -- performance group
      --
      -- Note: block is intended to be the length of the channel
      --       data-block on which the CRC operates. See
      --       adslAturChanCrcBlockLength for more information.
      --
      adslAturChanReceivedBlks OBJECT-TYPE
          SYNTAX      Counter32
          MAX-ACCESS  read-only
          STATUS      current
          DESCRIPTION
              "Count of all encoded blocks received on this channel
              since agent reset."
      ::= { adslAturChanPerfDataEntry 1 }

      adslAturChanTransmittedBlks  OBJECT-TYPE
          SYNTAX      Counter32
          MAX-ACCESS  read-only
          STATUS      current
          DESCRIPTION
              "Count of all encoded blocks transmitted on this
              channel since agent reset."
      ::= { adslAturChanPerfDataEntry 2 }

      adslAturChanCorrectedBlks  OBJECT-TYPE
          SYNTAX      Counter32
          MAX-ACCESS  read-only
          STATUS      current
          DESCRIPTION
              "Count of all blocks received with errors that were
              corrected since agent reset.  These blocks are passed
              on as good data."
      ::= { adslAturChanPerfDataEntry 3 }

      adslAturChanUncorrectBlks  OBJECT-TYPE
          SYNTAX      Counter32
          MAX-ACCESS  read-only
          STATUS      current
          DESCRIPTION
              "Count of all blocks received with uncorrectable
              errors since agent reset."
      ::= { adslAturChanPerfDataEntry 4 }

      -- general 15 min interval information
      --
      adslAturChanPerfValidIntervals OBJECT-TYPE
          SYNTAX      INTEGER(0..96)
          MAX-ACCESS  read-only
          STATUS      current
          DESCRIPTION
              "The number of previous 15-minute intervals in the
              interval table for which data was collected.  Given
              that &lt;n&gt; is the maximum # of intervals supported.
              The value will be &lt;n&gt; unless the measurement was
              (re-)started within the last (&lt;n&gt;*15) minutes, in which
              case the value will be the number of complete 15
              minute intervals for which the agent has at least
              some data. In certain cases (e.g., in the case
              where the agent is a proxy) it is possible that some
              intervals are unavailable.  In this case, this
              interval is the maximum interval number for
              which data is available."
      ::= { adslAturChanPerfDataEntry 5 }

      adslAturChanPerfInvalidIntervals OBJECT-TYPE
          SYNTAX      INTEGER(0..96)
          MAX-ACCESS  read-only
          STATUS      current
          DESCRIPTION
              "The number of intervals in the range from
              0 to the value of adslAturChanPerfValidIntervals
              for which no data is available. This object
              will typically be zero except in cases where
              the data for some intervals are not available
              (e.g., in proxy situations)."
      ::= { adslAturChanPerfDataEntry 6 }

      -- 15 min current performance group
      --
      adslAturChanPerfCurr15MinTimeElapsed OBJECT-TYPE
          SYNTAX      AdslPerfTimeElapsed(0..899)
          UNITS       "seconds"
          MAX-ACCESS  read-only
          STATUS      current
          DESCRIPTION
              "Total elapsed seconds in this interval.
              A full interval is 900 seconds."
      ::= { adslAturChanPerfDataEntry 7 }

      adslAturChanPerfCurr15MinReceivedBlks OBJECT-TYPE
          SYNTAX      PerfCurrentCount
          MAX-ACCESS  read-only
          STATUS      current
          DESCRIPTION
              "Count of all encoded blocks received on this
              channel within the current 15 minute interval."
      ::= { adslAturChanPerfDataEntry 8 }

      adslAturChanPerfCurr15MinTransmittedBlks OBJECT-TYPE
          SYNTAX      PerfCurrentCount
          MAX-ACCESS  read-only
          STATUS      current
          DESCRIPTION
              "Count of all encoded blocks transmitted on this
              channel within the current 15 minute interval."
      ::= { adslAturChanPerfDataEntry 9 }

      adslAturChanPerfCurr15MinCorrectedBlks  OBJECT-TYPE
          SYNTAX      PerfCurrentCount
          MAX-ACCESS  read-only
          STATUS      current
          DESCRIPTION

              "Count of all blocks received with errors that were
              corrected on this channel within the current 15 minute
              interval."
      ::= { adslAturChanPerfDataEntry 10 }

      adslAturChanPerfCurr15MinUncorrectBlks  OBJECT-TYPE
          SYNTAX      PerfCurrentCount
          MAX-ACCESS  read-only
          STATUS      current
          DESCRIPTION
              "Count of all blocks received with uncorrectable
              errors on this channel within the current 15 minute
              interval."
      ::= { adslAturChanPerfDataEntry 11 }

      -- 1-day current and previous performance group
      --
      adslAturChanPerfCurr1DayTimeElapsed OBJECT-TYPE
          SYNTAX      AdslPerfTimeElapsed(0..86399)
          UNITS       "seconds"
          MAX-ACCESS  read-only
          STATUS      current
          DESCRIPTION
              "Number of seconds that have elapsed since the
              beginning of the current 1-day interval."
      ::= { adslAturChanPerfDataEntry 12 }

      adslAturChanPerfCurr1DayReceivedBlks  OBJECT-TYPE
          SYNTAX      AdslPerfCurrDayCount
          MAX-ACCESS  read-only
          STATUS      current
          DESCRIPTION
              "Count of all encoded blocks received on this
              channel during the current day as measured by
              adslAturChanPerfCurr1DayTimeElapsed."
      ::= { adslAturChanPerfDataEntry 13 }

      adslAturChanPerfCurr1DayTransmittedBlks  OBJECT-TYPE
          SYNTAX      AdslPerfCurrDayCount
          MAX-ACCESS  read-only
          STATUS      current
          DESCRIPTION
              "Count of all encoded blocks transmitted on this
              channel during the current day as measured by
              adslAturChanPerfCurr1DayTimeElapsed."

      ::= { adslAturChanPerfDataEntry 14 }


      adslAturChanPerfCurr1DayCorrectedBlks  OBJECT-TYPE
          SYNTAX      AdslPerfCurrDayCount
          MAX-ACCESS  read-only
          STATUS      current
          DESCRIPTION
              "Count of all blocks received with errors that were
              corrected on this channel during the current day as
              measured by adslAturChanPerfCurr1DayTimeElapsed."
      ::= { adslAturChanPerfDataEntry 15 }

      adslAturChanPerfCurr1DayUncorrectBlks  OBJECT-TYPE
          SYNTAX      AdslPerfCurrDayCount
          MAX-ACCESS  read-only
          STATUS      current
          DESCRIPTION
              "Count of all blocks received with uncorrectable
              errors on this channel during the current day as
              measured by adslAturChanPerfCurr1DayTimeElapsed."
      ::= { adslAturChanPerfDataEntry 16 }

      adslAturChanPerfPrev1DayMoniSecs OBJECT-TYPE
          SYNTAX      INTEGER(0..86400)
          UNITS       "seconds"
          MAX-ACCESS  read-only
          STATUS      current
          DESCRIPTION
              "The amount of time in the previous 1-day interval
              over which the performance monitoring information
              is actually counted. This value will be the same as
              the interval duration except in a situation where
              performance monitoring data could not be collected
              for any reason."
      ::= { adslAturChanPerfDataEntry 17 }

      adslAturChanPerfPrev1DayReceivedBlks  OBJECT-TYPE
          SYNTAX      AdslPerfPrevDayCount
          MAX-ACCESS  read-only
          STATUS      current
          DESCRIPTION
              "Count of all encoded blocks received on this
              channel within the most recent previous 1-day
              period."
      ::= { adslAturChanPerfDataEntry 18 }

      adslAturChanPerfPrev1DayTransmittedBlks  OBJECT-TYPE
          SYNTAX      AdslPerfPrevDayCount
          MAX-ACCESS  read-only
          STATUS      current

          DESCRIPTION
              "Count of all encoded blocks transmitted on this
              channel within the most recent previous 1-day
              period."
      ::= { adslAturChanPerfDataEntry 19 }

      adslAturChanPerfPrev1DayCorrectedBlks  OBJECT-TYPE
          SYNTAX      AdslPerfPrevDayCount
          MAX-ACCESS  read-only
          STATUS      current
          DESCRIPTION
              "Count of all blocks received with errors that were
              corrected on this channel within the most recent
              previous 1-day period."
      ::= { adslAturChanPerfDataEntry 20 }

      adslAturChanPerfPrev1DayUncorrectBlks  OBJECT-TYPE
          SYNTAX      AdslPerfPrevDayCount
          MAX-ACCESS  read-only
          STATUS      current
          DESCRIPTION
              "Count of all blocks received with uncorrectable
              errors on this channel within the most recent previous
              1-day period."
      ::= { adslAturChanPerfDataEntry 21 }

      adslAtucChanIntervalTable   OBJECT-TYPE
          SYNTAX          SEQUENCE OF AdslAtucChanIntervalEntry
          MAX-ACCESS      not-accessible
          STATUS          current
          DESCRIPTION
              "This table provides one row for each ATUC channel's
              performance data collection interval.
              ADSL channel interfaces are those ifEntries
              where ifType is equal to adslInterleave(124)
              or adslFast(125)."
      ::= { adslMibObjects 12 }

      adslAtucChanIntervalEntry   OBJECT-TYPE
          SYNTAX          AdslAtucChanIntervalEntry
          MAX-ACCESS      not-accessible
          STATUS          current
          DESCRIPTION     "An entry in the adslAtucIntervalTable."
          INDEX           { ifIndex, adslAtucChanIntervalNumber }
      ::= { adslAtucChanIntervalTable 1 }

      AdslAtucChanIntervalEntry ::=
          SEQUENCE {

          adslAtucChanIntervalNumber          INTEGER,
          adslAtucChanIntervalReceivedBlks    PerfIntervalCount,
          adslAtucChanIntervalTransmittedBlks PerfIntervalCount,
          adslAtucChanIntervalCorrectedBlks   PerfIntervalCount,
          adslAtucChanIntervalUncorrectBlks   PerfIntervalCount,
          adslAtucChanIntervalValidData       TruthValue
          }
      adslAtucChanIntervalNumber OBJECT-TYPE
          SYNTAX      INTEGER(1..96)
          MAX-ACCESS  not-accessible
          STATUS      current
          DESCRIPTION
              "Performance Data Interval number 1 is the
              the most recent previous interval; interval
              96 is 24 hours ago.  Intervals 2..96 are
              optional."
      ::= { adslAtucChanIntervalEntry 1 }

      adslAtucChanIntervalReceivedBlks OBJECT-TYPE
          SYNTAX      PerfIntervalCount
          MAX-ACCESS  read-only
          STATUS      current
          DESCRIPTION
              "Count of all encoded blocks received on this channel
              during this interval."
      ::= { adslAtucChanIntervalEntry 2 }

      adslAtucChanIntervalTransmittedBlks  OBJECT-TYPE
          SYNTAX      PerfIntervalCount
          MAX-ACCESS  read-only
          STATUS      current
          DESCRIPTION
              "Count of all encoded blocks transmitted on this
              channel during this interval."
      ::= { adslAtucChanIntervalEntry 3 }

      adslAtucChanIntervalCorrectedBlks  OBJECT-TYPE
          SYNTAX      PerfIntervalCount
          MAX-ACCESS  read-only
          STATUS      current
          DESCRIPTION
              "Count of all blocks received with errors that were
              corrected on this channel during this interval."
      ::= { adslAtucChanIntervalEntry 4 }

      adslAtucChanIntervalUncorrectBlks  OBJECT-TYPE
          SYNTAX      PerfIntervalCount
          MAX-ACCESS  read-only

          STATUS      current
          DESCRIPTION
              "Count of all blocks received with uncorrectable
              errors on this channel during this interval."
      ::= { adslAtucChanIntervalEntry 5 }

      adslAtucChanIntervalValidData OBJECT-TYPE
          SYNTAX TruthValue
          MAX-ACCESS read-only
          STATUS current
          DESCRIPTION
              "This variable indicates if the data for this
              interval is valid."
      ::= { adslAtucChanIntervalEntry 6 }

      adslAturChanIntervalTable   OBJECT-TYPE
          SYNTAX          SEQUENCE OF AdslAturChanIntervalEntry
          MAX-ACCESS      not-accessible
          STATUS          current
          DESCRIPTION
              "This table provides one row for each ATUR channel's
              performance data collection interval.
              ADSL channel interfaces are those ifEntries
              where ifType is equal to adslInterleave(124)
              or adslFast(125)."
      ::= { adslMibObjects 13 }

      adslAturChanIntervalEntry   OBJECT-TYPE
          SYNTAX          AdslAturChanIntervalEntry
          MAX-ACCESS      not-accessible
          STATUS          current
          DESCRIPTION     "An entry in the adslAturIntervalTable."
          INDEX           { ifIndex, adslAturChanIntervalNumber }
      ::= { adslAturChanIntervalTable 1 }

      AdslAturChanIntervalEntry ::=
          SEQUENCE {
          adslAturChanIntervalNumber               INTEGER,
          adslAturChanIntervalReceivedBlks         PerfIntervalCount,
          adslAturChanIntervalTransmittedBlks      PerfIntervalCount,
          adslAturChanIntervalCorrectedBlks        PerfIntervalCount,
          adslAturChanIntervalUncorrectBlks        PerfIntervalCount,
          adslAturChanIntervalValidData            TruthValue
          }
      adslAturChanIntervalNumber OBJECT-TYPE
          SYNTAX      INTEGER(1..96)
          MAX-ACCESS  not-accessible
          STATUS      current

          DESCRIPTION
              "Performance Data Interval number 1 is the
              the most recent previous interval; interval
              96 is 24 hours ago.  Intervals 2..96 are
              optional."
      ::= { adslAturChanIntervalEntry 1 }

      adslAturChanIntervalReceivedBlks OBJECT-TYPE
          SYNTAX      PerfIntervalCount
          MAX-ACCESS  read-only
          STATUS      current
          DESCRIPTION
              "Count of all encoded blocks received on this channel
              during this interval."
      ::= { adslAturChanIntervalEntry 2 }

      adslAturChanIntervalTransmittedBlks  OBJECT-TYPE
          SYNTAX      PerfIntervalCount
          MAX-ACCESS  read-only
          STATUS      current
          DESCRIPTION
              "Count of all encoded blocks transmitted on this
              channel during this interval."
      ::= { adslAturChanIntervalEntry 3 }

      adslAturChanIntervalCorrectedBlks  OBJECT-TYPE
          SYNTAX      PerfIntervalCount
          MAX-ACCESS  read-only
          STATUS      current
          DESCRIPTION
              "Count of all blocks received with errors that were
              corrected on this channel during this interval."
      ::= { adslAturChanIntervalEntry 4 }

      adslAturChanIntervalUncorrectBlks  OBJECT-TYPE
          SYNTAX      PerfIntervalCount
          MAX-ACCESS  read-only
          STATUS      current
          DESCRIPTION
              "Count of all blocks received with uncorrectable
              errors on this channel during this interval."
      ::= { adslAturChanIntervalEntry 5 }

      adslAturChanIntervalValidData OBJECT-TYPE
          SYNTAX TruthValue
          MAX-ACCESS read-only
          STATUS current
          DESCRIPTION

              "This variable indicates if the data for this
              interval is valid."
      ::= { adslAturChanIntervalEntry 6 }

      -- Profile Group
      --

      adslLineConfProfileTable    OBJECT-TYPE
          SYNTAX          SEQUENCE OF AdslLineConfProfileEntry
          MAX-ACCESS      not-accessible
          STATUS          current
          DESCRIPTION
              "This table contains information on the ADSL line
              configuration.  One entry in this table reflects a
              profile defined by a manager which can be used to
              configure the ADSL line."
      ::= { adslMibObjects 14}

      adslLineConfProfileEntry    OBJECT-TYPE
          SYNTAX          AdslLineConfProfileEntry
          MAX-ACCESS      not-accessible
          STATUS          current
          DESCRIPTION
              "Each entry consists of a list of parameters that
              represents the configuration of an ADSL modem.

              When `dynamic' profiles are implemented, a default
              profile will always exist.  This profile's name will
              be set to `DEFVAL' and its parameters will be set
              to vendor specific values, unless otherwise specified
              in this document.

              When `static' profiles are implemented, profiles
              are automaticly created or destroyed as ADSL
              physical lines are discovered and removed by
              the system.  The name of the profile will be
              equivalent to the decimal value of the line's
              interface index.
              "
          INDEX { IMPLIED adslLineConfProfileName}
      ::= { adslLineConfProfileTable 1}

      AdslLineConfProfileEntry ::=
          SEQUENCE {
          adslLineConfProfileName               SnmpAdminString,
          adslAtucConfRateMode                  INTEGER,
          adslAtucConfRateChanRatio             INTEGER,
          adslAtucConfTargetSnrMgn              INTEGER,

          adslAtucConfMaxSnrMgn                 INTEGER,
          adslAtucConfMinSnrMgn                 INTEGER,
          adslAtucConfDownshiftSnrMgn           INTEGER,
          adslAtucConfUpshiftSnrMgn             INTEGER,
          adslAtucConfMinUpshiftTime            INTEGER,
          adslAtucConfMinDownshiftTime          INTEGER,
          adslAtucChanConfFastMinTxRate         Unsigned32,
          adslAtucChanConfInterleaveMinTxRate   Unsigned32,
          adslAtucChanConfFastMaxTxRate         Unsigned32,
          adslAtucChanConfInterleaveMaxTxRate   Unsigned32,
          adslAtucChanConfMaxInterleaveDelay    INTEGER,
          adslAturConfRateMode                  INTEGER,
          adslAturConfRateChanRatio             INTEGER,
          adslAturConfTargetSnrMgn              INTEGER,
          adslAturConfMaxSnrMgn                 INTEGER,
          adslAturConfMinSnrMgn                 INTEGER,
          adslAturConfDownshiftSnrMgn           INTEGER,
          adslAturConfUpshiftSnrMgn             INTEGER,
          adslAturConfMinUpshiftTime            INTEGER,
          adslAturConfMinDownshiftTime          INTEGER,
          adslAturChanConfFastMinTxRate         Unsigned32,
          adslAturChanConfInterleaveMinTxRate   Unsigned32,
          adslAturChanConfFastMaxTxRate         Unsigned32,
          adslAturChanConfInterleaveMaxTxRate   Unsigned32,
          adslAturChanConfMaxInterleaveDelay    INTEGER,
          adslLineConfProfileRowStatus          RowStatus
      }

      adslLineConfProfileName    OBJECT-TYPE
              SYNTAX          SnmpAdminString (SIZE (1..32))
              MAX-ACCESS      not-accessible
              STATUS          current
              DESCRIPTION
              "This object is used by the line configuration table
              in order to identify a row of this table.

              When `dynamic' profiles are implemented, the profile
              name is user specified.  Also, the system will always
              provide a default profile whose name is `DEFVAL'.

              When `static' profiles are implemented, there is an
              one-to-one relationship between each line and its
              profile.  In which case, the profile name will
              need to algorithmicly represent the Line's ifIndex.
              Therefore, the profile's name is a decimalized string
              of the ifIndex that is fixed-length (i.e., 10) with
              leading zero(s).  For example, the profile name for
              ifIndex which equals '15' will be '0000000015'."

      ::= { adslLineConfProfileEntry 1 }

      adslAtucConfRateMode OBJECT-TYPE
          SYNTAX      INTEGER {
              fixed (1),              -- no rate adaptation
              adaptAtStartup (2),     -- perform rate adaptation
                                      -- only at initialization
              adaptAtRuntime (3)      -- perform rate adaptation at
                                      -- any time
          }
          MAX-ACCESS  read-create
          STATUS      current
          DESCRIPTION
              "Defines what form of transmit rate adaptation is
              configured on this modem.  See ADSL Forum TR-005 [3]
              for more information."
      ::= { adslLineConfProfileEntry 2 }

      adslAtucConfRateChanRatio OBJECT-TYPE
          SYNTAX      INTEGER(0..100)
          UNITS        "%"
          MAX-ACCESS  read-create
          STATUS      current
          DESCRIPTION
              "Configured allocation ratio of excess transmit
              bandwidth between fast and interleaved channels.  Only
              applies when two channel mode and RADSL are supported.
              Distribute bandwidth on each channel in excess of the
              corresponding ChanConfMinTxRate so that:
              adslAtucConfRateChanRatio =

                      [Fast / (Fast + Interleaved)] * 100

              In other words this value is the fast channel
              percentage."
      ::= { adslLineConfProfileEntry 3 }

    adslAtucConfTargetSnrMgn OBJECT-TYPE
          SYNTAX      INTEGER (0..310)
          UNITS       "tenth dB"
          MAX-ACCESS  read-create
          STATUS      current
          DESCRIPTION
              "Configured Target Signal/Noise Margin.
              This is the Noise Margin the modem must achieve
              with a BER of 10-7 or better to successfully complete
              initialization."
      ::= { adslLineConfProfileEntry 4 }

    adslAtucConfMaxSnrMgn OBJECT-TYPE
          SYNTAX      INTEGER (0..310)
          UNITS       "tenth dB"
          MAX-ACCESS  read-create
          STATUS      current
          DESCRIPTION
              "Configured Maximum acceptable Signal/Noise Margin.
              If the Noise Margin is above this the modem should
              attempt to reduce its power output to optimize its
              operation."
      ::= { adslLineConfProfileEntry 5 }

      adslAtucConfMinSnrMgn  OBJECT-TYPE
          SYNTAX      INTEGER (0..310)
          UNITS       "tenth dB"
          MAX-ACCESS  read-create
          STATUS      current
          DESCRIPTION
              "Configured Minimum acceptable Signal/Noise Margin.
              If the noise margin falls below this level, the modem
              should attempt to increase its power output.  If that
              is not possible the modem will attempt to
              re-initialize or shut down."
      ::= { adslLineConfProfileEntry 6 }

      adslAtucConfDownshiftSnrMgn  OBJECT-TYPE
          SYNTAX      INTEGER (0..310)
          UNITS       "tenth dB"
          MAX-ACCESS  read-create
          STATUS      current
          DESCRIPTION
              "Configured Signal/Noise Margin for rate downshift.
              If the noise margin falls below this level, the modem
              should attempt to decrease its transmit rate.  In
              the case that RADSL mode is not present,
              the value will be `0'."
      ::= { adslLineConfProfileEntry 7 }

      adslAtucConfUpshiftSnrMgn  OBJECT-TYPE
          SYNTAX      INTEGER (0..310)
          UNITS       "tenth dB"
          MAX-ACCESS  read-create
          STATUS      current
          DESCRIPTION
              "Configured Signal/Noise Margin for rate upshift.
              If the noise margin rises above this level, the modem
              should attempt to increase its transmit rate.    In
              the case that RADSL is not present, the value will

              be `0'."
      ::= { adslLineConfProfileEntry 8 }

      adslAtucConfMinUpshiftTime OBJECT-TYPE
          SYNTAX      INTEGER(0..16383)
          UNITS       "seconds"
          MAX-ACCESS  read-create
          STATUS      current
          DESCRIPTION
              "Minimum time that the current margin is above
              UpshiftSnrMgn before an upshift occurs.
              In the case that RADSL is not present, the value will
              be `0'."
      ::= { adslLineConfProfileEntry 9 }
     adslAtucConfMinDownshiftTime OBJECT-TYPE
          SYNTAX      INTEGER(0..16383)
          UNITS       "seconds"
          MAX-ACCESS  read-create
          STATUS      current
          DESCRIPTION
              "Minimum time that the current margin is below
              DownshiftSnrMgn before a downshift occurs.
              In the case that RADSL mode is not present,
              the value will be `0'."
      ::= { adslLineConfProfileEntry 10 }

      adslAtucChanConfFastMinTxRate  OBJECT-TYPE
          SYNTAX      Unsigned32
          UNITS       "bps"
          MAX-ACCESS  read-create
          STATUS      current
          DESCRIPTION
              "Configured Minimum Transmit rate for `Fast' channels,
              in bps.  See adslAtucConfRateChanRatio for information
              regarding RADSL mode and ATUR transmit rate for
              ATUC receive rates."
      ::= { adslLineConfProfileEntry 11 }

      adslAtucChanConfInterleaveMinTxRate OBJECT-TYPE
          SYNTAX      Unsigned32
          UNITS       "bps"
          MAX-ACCESS  read-create
          STATUS      current
          DESCRIPTION
              "Configured Minimum Transmit rate for `Interleave'
              channels, in bps.  See adslAtucConfRateChanRatio for
              information regarding RADSL mode and see
              ATUR transmit rate for receive rates."

      ::= { adslLineConfProfileEntry 12 }

      adslAtucChanConfFastMaxTxRate  OBJECT-TYPE
          SYNTAX      Unsigned32
          UNITS       "bps"
          MAX-ACCESS  read-create
          STATUS      current
          DESCRIPTION
              "Configured Maximum Transmit rate for `Fast' channels,
              in bps.  See adslAtucConfRateChanRatio for information
              regarding RADSL mode and see ATUR transmit rate for
              ATUC receive rates."
      ::= { adslLineConfProfileEntry 13 }

      adslAtucChanConfInterleaveMaxTxRate OBJECT-TYPE
          SYNTAX      Unsigned32
          UNITS       "bps"
          MAX-ACCESS  read-create
          STATUS      current
          DESCRIPTION
              "Configured Maximum Transmit rate for `Interleave'
              channels, in bps.  See adslAtucConfRateChanRatio for
              information regarding RADSL mode and ATUR transmit
              rate for ATUC receive rates."
      ::= { adslLineConfProfileEntry 14 }

      adslAtucChanConfMaxInterleaveDelay OBJECT-TYPE
          SYNTAX      INTEGER(0..255)
          UNITS        "milli-seconds"
          MAX-ACCESS  read-create
          STATUS      current
          DESCRIPTION
              "Configured maximum Interleave Delay for this channel.

              Interleave delay applies only to the interleave channel
              and defines the mapping (relative spacing) between
              subsequent input bytes at the interleaver input and
              their placement in the bit stream at the interleaver
              output.  Larger numbers provide greater separation
              between consecutive input bytes in the output bit
              stream allowing for improved impulse noise immunity
              at the expense of payload latency."
      ::= { adslLineConfProfileEntry 15 }

      adslAturConfRateMode OBJECT-TYPE
          SYNTAX      INTEGER {
              fixed (1),              -- no rate adaptation
              adaptAtStartup (2),     -- perform rate adaptation

                                      -- only at initialization
              adaptAtRuntime (3)      -- perform rate adaptation at
                                      -- any time
          }
          MAX-ACCESS  read-create
          STATUS      current
          DESCRIPTION
              "Defines what form of transmit rate adaptation is
              configured on this modem.  See ADSL Forum TR-005 [3]
              for more information."
      ::= { adslLineConfProfileEntry 16 }

      adslAturConfRateChanRatio OBJECT-TYPE
          SYNTAX      INTEGER(0..100)
          UNITS        "%"
          MAX-ACCESS  read-create
          STATUS      current
          DESCRIPTION
              "Configured allocation ratio of excess transmit
              bandwidth between fast and interleaved channels.  Only
              applies when two channel mode and RADSL are supported.
              Distribute bandwidth on each channel in excess of the
              corresponding ChanConfMinTxRate so that:
              adslAturConfRateChanRatio =

                      [Fast / (Fast + Interleaved)] * 100

              In other words this value is the fast channel
              percentage."
      ::= { adslLineConfProfileEntry 17 }

    adslAturConfTargetSnrMgn OBJECT-TYPE
          SYNTAX      INTEGER (0..310)
          UNITS       "tenth dB"
          MAX-ACCESS  read-create
          STATUS      current
          DESCRIPTION
              "Configured Target Signal/Noise Margin.
              This is the Noise Margin the modem must achieve
              with a BER of 10-7 or better to successfully complete
              initialization."
      ::= { adslLineConfProfileEntry 18 }

    adslAturConfMaxSnrMgn OBJECT-TYPE
          SYNTAX      INTEGER (0..310)
          UNITS       "tenth dB"
          MAX-ACCESS  read-create
          STATUS      current

          DESCRIPTION
              "Configured Maximum acceptable Signal/Noise Margin.
              If the Noise Margin is above this the modem should
              attempt to reduce its power output to optimize its
              operation."
      ::= { adslLineConfProfileEntry 19 }

     adslAturConfMinSnrMgn  OBJECT-TYPE
          SYNTAX      INTEGER (0..310)
          UNITS       "tenth dB"
          MAX-ACCESS  read-create
          STATUS      current
          DESCRIPTION
              "Configured Minimum acceptable Signal/Noise Margin.
              If the noise margin falls below this level, the modem
              should attempt to increase its power output.  If that
              is not possible the modem will attempt to
              re-initialize or shut down."
      ::= { adslLineConfProfileEntry 20 }

      adslAturConfDownshiftSnrMgn  OBJECT-TYPE
          SYNTAX      INTEGER (0..310)
          UNITS       "tenth dB"
          MAX-ACCESS  read-create
          STATUS      current
          DESCRIPTION
              "Configured Signal/Noise Margin for rate downshift.
              If the noise margin falls below this level, the modem
              should attempt to decrease its transmit rate.
              In the case that RADSL mode is not present,
              the value will be `0'."
      ::= { adslLineConfProfileEntry 21 }

      adslAturConfUpshiftSnrMgn  OBJECT-TYPE
          SYNTAX      INTEGER (0..310)
          UNITS       "tenth dB"
          MAX-ACCESS  read-create
          STATUS      current
          DESCRIPTION
              "Configured Signal/Noise Margin for rate upshift.
              If the noise margin rises above this level, the modem
              should attempt to increase its transmit rate.
              In the case that RADSL is not present,
              the value will be `0'."
      ::= { adslLineConfProfileEntry 22 }

      adslAturConfMinUpshiftTime OBJECT-TYPE
          SYNTAX      INTEGER(0..16383)

          UNITS       "seconds"
          MAX-ACCESS  read-create
          STATUS      current
          DESCRIPTION
              "Minimum time that the current margin is above
              UpshiftSnrMgn before an upshift occurs.
              In the case that RADSL is not present, the value will
              be `0'."
      ::= { adslLineConfProfileEntry 23 }

     adslAturConfMinDownshiftTime OBJECT-TYPE
          SYNTAX      INTEGER(0..16383)
          UNITS       "seconds"
          MAX-ACCESS  read-create
          STATUS      current
          DESCRIPTION
              "Minimum time that the current margin is below
              DownshiftSnrMgn before a downshift occurs.
              In the case that RADSL mode is not present,
              the value will be `0'."
      ::= { adslLineConfProfileEntry 24 }

      adslAturChanConfFastMinTxRate  OBJECT-TYPE
          SYNTAX      Unsigned32
          UNITS       "bps"
          MAX-ACCESS  read-create
          STATUS      current
          DESCRIPTION
              "Configured Minimum Transmit rate for `Fast' channels,
              in bps.  See adslAturConfRateChanRatio for information
              regarding RADSL mode and ATUC transmit rate
              for ATUR receive rates."
      ::= { adslLineConfProfileEntry 25 }

      adslAturChanConfInterleaveMinTxRate OBJECT-TYPE
          SYNTAX      Unsigned32
          UNITS       "bps"
          MAX-ACCESS  read-create
          STATUS      current
          DESCRIPTION
              "Configured Minimum Transmit rate for `Interleave'
              channels, in bps.  See adslAturConfRateChanRatio for
              information regarding RADSL mode and ATUC transmit rate
              for ATUR receive rates."
      ::= { adslLineConfProfileEntry 26 }

      adslAturChanConfFastMaxTxRate  OBJECT-TYPE
          SYNTAX      Unsigned32

          UNITS       "bps"
          MAX-ACCESS  read-create
          STATUS      current
          DESCRIPTION
              "Configured Maximum Transmit rate for `Fast' channels,
              in bps.  See adslAturConfRateChanRatio for information
              regarding RADSL mode and ATUC transmit rate
              for ATUR receive rates."
      ::= { adslLineConfProfileEntry 27 }

      adslAturChanConfInterleaveMaxTxRate OBJECT-TYPE
          SYNTAX      Unsigned32
          UNITS       "bps"
          MAX-ACCESS  read-create
          STATUS      current
          DESCRIPTION
              "Configured Maximum Transmit rate for `Interleave'
              channels, in bps.  See adslAturConfRateChanRatio for
              information regarding RADSL mode and see
              ATUC transmit rate for ATUR receive rates."
      ::= { adslLineConfProfileEntry 28 }

      adslAturChanConfMaxInterleaveDelay OBJECT-TYPE
          SYNTAX      INTEGER(0..255)
          UNITS        "milli-seconds"
          MAX-ACCESS  read-create
          STATUS      current
          DESCRIPTION
              "Configured maximum Interleave Delay for this channel.

              Interleave delay applies only to the interleave channel
              and defines the mapping (relative spacing) between
              subsequent input bytes at the interleaver input and
              their placement in the bit stream at the interleaver
              output.  Larger numbers provide greater separation
              between consecutive input bytes in the output bit
              stream allowing for improved impulse noise immunity
              at the expense of payload latency."
      ::= { adslLineConfProfileEntry 29 }

      adslLineConfProfileRowStatus OBJECT-TYPE
          SYNTAX          RowStatus
          MAX-ACCESS      read-create
          STATUS          current
          DESCRIPTION
              "This object is used to create a new row or modify or
              delete an existing row in this table.


              A profile activated by setting this object to
              `active'.  When `active' is set, the system
              will validate the profile.

              Before a profile can be deleted or taken out of
              service, (by setting this object to `destroy' or
              `outOfService') it must be first unreferenced
              from all associated lines.

              If the implementator of this MIB has chosen not
              to implement `dynamic assignment' of profiles, this
              object's MIN-ACCESS is read-only and its value
              is always to be `active'."
      ::= { adslLineConfProfileEntry 30 }

      adslLineAlarmConfProfileTable    OBJECT-TYPE
          SYNTAX          SEQUENCE OF AdslLineAlarmConfProfileEntry
          MAX-ACCESS      not-accessible
          STATUS          current
          DESCRIPTION
              "This table contains information on the ADSL line
              configuration.  One entry in this table reflects a
              profile defined by a manager which can be used to
              configure the modem for a physical line"
      ::= { adslMibObjects 15}

      adslLineAlarmConfProfileEntry    OBJECT-TYPE
          SYNTAX          AdslLineAlarmConfProfileEntry
          MAX-ACCESS      not-accessible
          STATUS          current
          DESCRIPTION
              "Each entry consists of a list of parameters that
              represents the configuration of an ADSL modem.

              When `dynamic' profiles are implemented, a default
              profile will always exist.  This profile's name will
              be set to `DEFVAL' and its parameters will be set to
              vendor specific values, unless otherwise specified
              in this document.

              When `static' profiles are implemented, profiles
              are automaticly created or destroyed as ADSL
              physical lines are discovered and removed by
              the system.  The name of the profile will be
              equivalent to the decimal value of the line's
              interface index.
              "
          INDEX { IMPLIED adslLineAlarmConfProfileName}

      ::= { adslLineAlarmConfProfileTable 1}

      AdslLineAlarmConfProfileEntry ::=
          SEQUENCE {
          adslLineAlarmConfProfileName          SnmpAdminString,
          adslAtucThresh15MinLofs               INTEGER,
          adslAtucThresh15MinLoss               INTEGER,
          adslAtucThresh15MinLols               INTEGER,
          adslAtucThresh15MinLprs               INTEGER,
          adslAtucThresh15MinESs                INTEGER,
          adslAtucThreshFastRateUp              Unsigned32,
          adslAtucThreshInterleaveRateUp        Unsigned32,
          adslAtucThreshFastRateDown            Unsigned32,
          adslAtucThreshInterleaveRateDown      Unsigned32,
          adslAtucInitFailureTrapEnable         INTEGER,
          adslAturThresh15MinLofs               INTEGER,
          adslAturThresh15MinLoss               INTEGER,
          adslAturThresh15MinLprs               INTEGER,
          adslAturThresh15MinESs                INTEGER,
          adslAturThreshFastRateUp              Unsigned32,
          adslAturThreshInterleaveRateUp        Unsigned32,
          adslAturThreshFastRateDown            Unsigned32,
          adslAturThreshInterleaveRateDown      Unsigned32,
          adslLineAlarmConfProfileRowStatus     RowStatus
          }

      adslLineAlarmConfProfileName    OBJECT-TYPE
          SYNTAX          SnmpAdminString (SIZE (1..32))
          MAX-ACCESS      not-accessible
          STATUS          current
          DESCRIPTION
              "This object is used by the line alarm configuration
              table in order to identify a row of this table.

              When `dynamic' profiles are implemented, the profile
              name is user specified.  Also, the system will always
              provide a default profile whose name is `DEFVAL'.

              When `static' profiles are implemented, there is an
              one-to-one relationship between each line and its
              profile.  In which case, the profile name will
              need to algorithmicly represent the Line's ifIndex.
              Therefore, the profile's name is a decimalized string
              of the ifIndex that is fixed-length (i.e., 10) with
              leading zero(s).  For example, the profile name for
              ifIndex which equals '15' will be '0000000015'."
      ::= { adslLineAlarmConfProfileEntry 1}


      adslAtucThresh15MinLofs OBJECT-TYPE
          SYNTAX      INTEGER(0..900)
          UNITS       "seconds"
          MAX-ACCESS  read-create
          STATUS      current
          DESCRIPTION
              "The number of Loss of Frame Seconds
              encountered by an ADSL interface within any given 15
              minutes performance data collection period, which
              causes the SNMP agent to send an
              adslAtucPerfLofsThreshTrap.
              One trap will be sent per interval per interface.
              A value of `0' will disable the trap."
      ::= { adslLineAlarmConfProfileEntry 2}

      adslAtucThresh15MinLoss  OBJECT-TYPE
          SYNTAX      INTEGER(0..900)
          UNITS       "seconds"
          MAX-ACCESS  read-create
          STATUS      current
          DESCRIPTION
              "The number of Loss of Signal Seconds
              encountered by an ADSL interface within any given 15
              minutes performance data collection period, which
              causes the SNMP agent to send an
              adslAtucPerfLossThreshTrap.
              One trap will be sent per interval per interface.
              A value of `0' will disable the trap."
      ::= { adslLineAlarmConfProfileEntry 3}

      adslAtucThresh15MinLols  OBJECT-TYPE
          SYNTAX      INTEGER(0..900)
          UNITS       "seconds"
          MAX-ACCESS  read-create
          STATUS      current
          DESCRIPTION
              "The number of Loss of Link Seconds
              encountered by an ADSL interface within any given 15
              minutes performance data collection period, which
              causes the SNMP agent to send an
              adslAtucPerfLolsThreshTrap.
              One trap will be sent per interval per interface.
              A value of `0' will disable the trap."
      ::= { adslLineAlarmConfProfileEntry 4}

      adslAtucThresh15MinLprs  OBJECT-TYPE
          SYNTAX      INTEGER(0..900)
          UNITS       "seconds"

          MAX-ACCESS  read-create
          STATUS      current
          DESCRIPTION
              "The number of Loss of Power Seconds
              encountered by an ADSL interface within any given 15
              minutes performance data collection period, which
              causes the SNMP agent to send an
              adslAtucPerfLprsThreshTrap.
              One trap will be sent per interval per interface.
              A value of `0' will disable the trap."
      ::= { adslLineAlarmConfProfileEntry 5}

      adslAtucThresh15MinESs  OBJECT-TYPE
          SYNTAX      INTEGER(0..900)
          UNITS       "seconds"
          MAX-ACCESS  read-create
          STATUS      current
          DESCRIPTION
              "The number of Errored Seconds
              encountered by an ADSL interface within any given 15
              minutes performance data collection period, which
              causes the SNMP agent to send an
              adslAtucPerfESsThreshTrap.
              One trap will be sent per interval per interface.
              A value of `0' will disable the trap."
      ::= { adslLineAlarmConfProfileEntry 6}

      adslAtucThreshFastRateUp OBJECT-TYPE
          SYNTAX      Unsigned32
          UNITS       "bps"
          MAX-ACCESS  read-create
          STATUS      current
          DESCRIPTION
              "Applies to `Fast' channels only.
              Configured change in rate causing an
              adslAtucRateChangeTrap. A trap is produced when:
              ChanCurrTxRate &gt;= ChanPrevTxRate plus the value of
              this object. A value of `0' will disable the trap."
      ::= { adslLineAlarmConfProfileEntry 7}

      adslAtucThreshInterleaveRateUp OBJECT-TYPE
          SYNTAX      Unsigned32
          UNITS       "bps"
          MAX-ACCESS  read-create
          STATUS      current
          DESCRIPTION
              "Applies to `Interleave' channels only.
              Configured change in rate causing an

              adslAtucRateChangeTrap.  A trap is produced when:
              ChanCurrTxRate &gt;= ChanPrevTxRate plus the value of
              this object. A value of `0' will disable the trap."
      ::= { adslLineAlarmConfProfileEntry 8}

      adslAtucThreshFastRateDown OBJECT-TYPE
          SYNTAX      Unsigned32
          UNITS       "bps"
          MAX-ACCESS  read-create
          STATUS      current
          DESCRIPTION
              "Applies to `Fast' channels only.
              Configured change in rate causing an
              adslAtucRateChangeTrap.  A trap is produced when:
              ChanCurrTxRate &lt;= ChanPrevTxRate minus the value of
              this object. A value of `0' will disable the trap."
      ::= { adslLineAlarmConfProfileEntry 9 }

      adslAtucThreshInterleaveRateDown OBJECT-TYPE
          SYNTAX      Unsigned32
          UNITS       "bps"
          MAX-ACCESS  read-create
          STATUS      current
          DESCRIPTION
              "Applies to `Interleave' channels only.
              Configured change in rate causing an
              adslAtucRateChangeTrap.  A trap is produced when:
              ChanCurrTxRate &lt;= ChanPrevTxRate minus the value of
              this object. A value of `0' will disable the trap."
      ::= { adslLineAlarmConfProfileEntry 10 }

      adslAtucInitFailureTrapEnable OBJECT-TYPE
          SYNTAX      INTEGER {
              enable (1),
              disable (2)
          }
          MAX-ACCESS  read-create
          STATUS      current
          DESCRIPTION
              "Enables and disables the InitFailureTrap.  This
              object is defaulted disable(2)."
      DEFVAL { disable }
      ::= { adslLineAlarmConfProfileEntry 11 }

      adslAturThresh15MinLofs OBJECT-TYPE
          SYNTAX      INTEGER(0..900)
          UNITS       "seconds"
          MAX-ACCESS  read-create

          STATUS      current
          DESCRIPTION
              "The number of Loss of Frame Seconds
              encountered by an ADSL interface within any given 15
              minutes performance data collection period, which
              causes the SNMP agent to send an
              adslAturPerfLofsThreshTrap.
              One trap will be sent per interval per interface.
              A value of `0' will disable the trap."
      ::= { adslLineAlarmConfProfileEntry 12 }

      adslAturThresh15MinLoss  OBJECT-TYPE
          SYNTAX      INTEGER(0..900)
          UNITS       "seconds"
          MAX-ACCESS  read-create
          STATUS      current
          DESCRIPTION
              "The number of Loss of Signal Seconds
              encountered by an ADSL interface within any given 15
              minutes performance data collection period, which
              causes the SNMP agent to send an
              adslAturPerfLossThreshTrap.
              One trap will be sent per interval per interface.
              A value of `0' will disable the trap."
      ::= { adslLineAlarmConfProfileEntry 13 }

      adslAturThresh15MinLprs  OBJECT-TYPE
          SYNTAX      INTEGER(0..900)
          UNITS       "seconds"
          MAX-ACCESS  read-create
          STATUS      current
          DESCRIPTION
              "The number of Loss of Power Seconds
              encountered by an ADSL interface within any given 15
              minutes performance data collection period, which
              causes the SNMP agent to send an
              adslAturPerfLprsThreshTrap.
              One trap will be sent per interval per interface.
              A value of `0' will disable the trap."
      ::= { adslLineAlarmConfProfileEntry 14 }

      adslAturThresh15MinESs  OBJECT-TYPE
          SYNTAX      INTEGER(0..900)
          UNITS       "seconds"
          MAX-ACCESS  read-create
          STATUS      current
          DESCRIPTION
              "The number of Errored Seconds

              encountered by an ADSL interface within any given 15
              minutes performance data collection period, which
              causes the SNMP agent to send an
              adslAturPerfESsThreshTrap.
              One trap will be sent per interval per interface.
              A value of `0' will disable the trap."
      ::= { adslLineAlarmConfProfileEntry 15 }

      adslAturThreshFastRateUp OBJECT-TYPE
          SYNTAX      Unsigned32
          UNITS       "bps"
          MAX-ACCESS  read-create
          STATUS      current
          DESCRIPTION
              "Applies to `Fast' channels only.
              Configured change in rate causing an
              adslAturRateChangeTrap.  A trap is produced when:
              ChanCurrTxRate &gt;= ChanPrevTxRate plus the value of
              this object. A value of `0' will disable the trap."
      ::= { adslLineAlarmConfProfileEntry 16 }

      adslAturThreshInterleaveRateUp OBJECT-TYPE
          SYNTAX      Unsigned32
          UNITS       "bps"
          MAX-ACCESS  read-create
          STATUS      current
          DESCRIPTION
              "Applies to `Interleave' channels only.
              configured change in rate causing an
              adslAturRateChangeTrap.  A trap is produced when:
              ChanCurrTxRate &gt;= ChanPrevTxRate plus the value of
              this object. A value of `0' will disable the trap."
      ::= { adslLineAlarmConfProfileEntry 17 }

      adslAturThreshFastRateDown OBJECT-TYPE
          SYNTAX      Unsigned32
          UNITS       "bps"
          MAX-ACCESS  read-create
          STATUS      current
          DESCRIPTION
              "Applies to `Fast' channels only.
              Configured change in rate causing an
              adslAturRateChangeTrap.  A trap is produced when:
              ChanCurrTxRate &lt;= ChanPrevTxRate minus the value of
              this object. A value of `0' will disable the trap."
      ::= { adslLineAlarmConfProfileEntry 18 }

      adslAturThreshInterleaveRateDown OBJECT-TYPE

          SYNTAX      Unsigned32
          UNITS       "bps"
          MAX-ACCESS  read-create
          STATUS      current
          DESCRIPTION
              "Applies to `Interleave' channels only.
              Configured change in rate causing an
              adslAturRateChangeTrap.  A trap is produced when:
              ChanCurrTxRate &lt;= ChanPrevTxRate minus the value of
              this object. A value of `0' will disable the trap."
      ::= { adslLineAlarmConfProfileEntry 19 }

      adslLineAlarmConfProfileRowStatus OBJECT-TYPE
          SYNTAX          RowStatus
          MAX-ACCESS      read-create
          STATUS          current
          DESCRIPTION
              "This object is used to create a new row or modify or
              delete an existing row in this table.

              A profile activated by setting this object to
              `active'.  When `active' is set, the system
              will validate the profile.

              Before a profile can be deleted or taken out of
              service, (by setting this object to `destroy' or
              `outOfService') it must be first unreferenced
              from all associated lines.

              If the implementator of this MIB has chosen not
              to implement `dynamic assignment' of profiles, this
              object's MIN-ACCESS is read-only and its value
              is always to be `active'."
      ::= { adslLineAlarmConfProfileEntry 20 }

      -- Line Code Specific Tables

      -- These are place holders for the Line Code Specific MIBs
      -- once they become available.

      adslLCSMib  OBJECT IDENTIFIER ::= { adslMibObjects 16 }

-- trap definitions

adslTraps OBJECT IDENTIFIER ::= { adslLineMib 2 }

adslAtucTraps OBJECT IDENTIFIER ::= { adslTraps 1 }


      adslAtucPerfLofsThreshTrap      NOTIFICATION-TYPE
          OBJECTS { adslAtucPerfCurr15MinLofs,
                    adslAtucThresh15MinLofs }
          STATUS  current
          DESCRIPTION
              "Loss of Framing 15-minute interval threshold reached."
      ::= { adslAtucTraps 0 1 }

      adslAtucPerfLossThreshTrap      NOTIFICATION-TYPE
          OBJECTS { adslAtucPerfCurr15MinLoss,
                    adslAtucThresh15MinLoss }
          STATUS  current
          DESCRIPTION
              "Loss of Signal 15-minute interval threshold reached."
      ::= { adslAtucTraps 0 2 }

      adslAtucPerfLprsThreshTrap      NOTIFICATION-TYPE
          OBJECTS { adslAtucPerfCurr15MinLprs,
                    adslAtucThresh15MinLprs }
          STATUS  current
          DESCRIPTION
              "Loss of Power 15-minute interval threshold reached."
      ::= { adslAtucTraps 0 3 }

      adslAtucPerfESsThreshTrap       NOTIFICATION-TYPE
          OBJECTS { adslAtucPerfCurr15MinESs,
                    adslAtucThresh15MinESs }
          STATUS  current
          DESCRIPTION
              "Errored Second 15-minute interval threshold reached."
      ::= { adslAtucTraps 0 4 }

      adslAtucRateChangeTrap  NOTIFICATION-TYPE
          OBJECTS { adslAtucChanCurrTxRate,
                    adslAtucChanPrevTxRate }
          STATUS  current
          DESCRIPTION
              "The ATUCs transmit rate has changed (RADSL mode only)"
      ::= { adslAtucTraps 0 5 }

      adslAtucPerfLolsThreshTrap      NOTIFICATION-TYPE
          OBJECTS { adslAtucPerfCurr15MinLols,
                    adslAtucThresh15MinLols }
          STATUS  current
          DESCRIPTION
              "Loss of Link 15-minute interval threshold reached."
      ::= { adslAtucTraps 0 6 }


      adslAtucInitFailureTrap NOTIFICATION-TYPE
          OBJECTS { adslAtucCurrStatus }
          STATUS  current
          DESCRIPTION
              "ATUC initialization failed. See adslAtucCurrStatus
              for potential reasons."
      ::= { adslAtucTraps 0 7 }

adslAturTraps OBJECT IDENTIFIER ::= { adslTraps 2 }

      adslAturPerfLofsThreshTrap      NOTIFICATION-TYPE
          OBJECTS { adslAturPerfCurr15MinLofs,
                    adslAturThresh15MinLofs }
          STATUS  current
          DESCRIPTION
              "Loss of Framing 15-minute interval threshold reached."
      ::= { adslAturTraps 0 1 }

      adslAturPerfLossThreshTrap      NOTIFICATION-TYPE
          OBJECTS { adslAturPerfCurr15MinLoss,
                    adslAturThresh15MinLoss }
          STATUS  current
          DESCRIPTION
              "Loss of Signal 15-minute interval threshold reached."
      ::= { adslAturTraps 0 2 }

      adslAturPerfLprsThreshTrap      NOTIFICATION-TYPE
          OBJECTS { adslAturPerfCurr15MinLprs,
                    adslAturThresh15MinLprs }
          STATUS  current
          DESCRIPTION
              "Loss of Power 15-minute interval threshold reached."
      ::= { adslAturTraps 0 3 }

      adslAturPerfESsThreshTrap       NOTIFICATION-TYPE
          OBJECTS { adslAturPerfCurr15MinESs,
                    adslAturThresh15MinESs }
          STATUS  current
          DESCRIPTION
              "Errored Second 15-minute interval threshold reached."
      ::= { adslAturTraps 0 4 }

      adslAturRateChangeTrap  NOTIFICATION-TYPE
          OBJECTS { adslAturChanCurrTxRate,
                    adslAturChanPrevTxRate }
          STATUS  current
          DESCRIPTION
              "The ATURs transmit rate has changed (RADSL mode only)"

      ::= { adslAturTraps 0 5 }

      -- no adslAturPerfLolsThreshTrap possible { 0 6 }

      -- no adslAturInitFailureTrap possible { 0 7 }

-- conformance information

adslConformance OBJECT IDENTIFIER ::= { adslLineMib 3 }

adslGroups OBJECT IDENTIFIER ::= { adslConformance 1 }
adslCompliances OBJECT IDENTIFIER ::= { adslConformance 2 }

      -- ATU-C agent compliance statements

      adslLineMibAtucCompliance MODULE-COMPLIANCE
          STATUS  current
          DESCRIPTION
              "The compliance statement for SNMP entities
               which manage ADSL ATU-C interfaces."

          MODULE  -- this module
          MANDATORY-GROUPS
             {
             adslLineGroup, adslPhysicalGroup, adslChannelGroup,
             adslAtucPhysPerfIntervalGroup,
             adslAturPhysPerfIntervalGroup, adslLineConfProfileGroup,
             adslLineAlarmConfProfileGroup,
             adslLineConfProfileControlGroup
             }

          GROUP       adslAtucPhysPerfRawCounterGroup
          DESCRIPTION
              "This group is optional.  Implementations which
               require continuous ATU-C physical event counters
               should implement this group."

          GROUP       adslAturPhysPerfRawCounterGroup
          DESCRIPTION
              "This group is optional.  Implementations which
               require continuous ATU-R physical event counters
               should implement this group."

          GROUP       adslAtucChanPerformanceGroup
          DESCRIPTION
              "This group is optional.  Implementations which
               require ATU-C channel block event counters should
               implement this group."

          GROUP       adslAturChanPerformanceGroup
          DESCRIPTION
              "This group is optional.  Implementations which
               require ATU-R channel block event counters should
               implement this group."

          OBJECT      adslLineConfProfile
          MIN-ACCESS  read-only
          DESCRIPTION
              "Read-only access is applicable when static
               profiles are implemented."

          OBJECT      adslAtucConfRateMode
          MIN-ACCESS  read-write
          DESCRIPTION
              "Read-write access is applicable when
               static profiles are implemented."

          OBJECT      adslAtucConfRateChanRatio
          MIN-ACCESS  read-write
          DESCRIPTION
              "Read-write access is applicable when
               static profiles are implemented."

          OBJECT      adslAtucConfTargetSnrMgn
          MIN-ACCESS  read-write
          DESCRIPTION
              "Read-write access is applicable when
               static profiles are implemented."

          OBJECT      adslAtucConfMaxSnrMgn
          MIN-ACCESS  read-write
          DESCRIPTION
              "Read-write access is applicable when
               static profiles are implemented."

          OBJECT      adslAtucConfMinSnrMgn
          MIN-ACCESS  read-write
          DESCRIPTION
              "Read-write access is applicable when
               static profiles are implemented."

          OBJECT      adslAtucConfDownshiftSnrMgn
          MIN-ACCESS  read-write
          DESCRIPTION
              "Read-write access is applicable when
               static profiles are implemented."

          OBJECT      adslAtucConfUpshiftSnrMgn
          MIN-ACCESS  read-write
          DESCRIPTION
              "Read-write access is applicable when
               static profiles are implemented."

          OBJECT      adslAtucConfMinUpshiftTime
          MIN-ACCESS  read-write
          DESCRIPTION
              "Read-write access is applicable when
               static profiles are implemented."

          OBJECT      adslAtucConfMinDownshiftTime
          MIN-ACCESS  read-write
          DESCRIPTION
              "Read-write access is applicable when
               static profiles are implemented."

          OBJECT      adslAtucChanConfFastMinTxRate
          MIN-ACCESS  read-write
          DESCRIPTION
              "Read-write access is applicable when
               static profiles are implemented."

          OBJECT      adslAtucChanConfInterleaveMinTxRate
          MIN-ACCESS  read-write
          DESCRIPTION
              "Read-write access is applicable when
               static profiles are implemented."

          OBJECT      adslAtucChanConfFastMaxTxRate
          MIN-ACCESS  read-write
          DESCRIPTION
              "Read-write access is applicable when
               static profiles are implemented."

          OBJECT      adslAtucChanConfInterleaveMaxTxRate
          MIN-ACCESS  read-write
          DESCRIPTION
              "Read-write access is applicable when
               static profiles are implemented."

          OBJECT      adslAtucChanConfMaxInterleaveDelay
          MIN-ACCESS  read-write
          DESCRIPTION
              "Read-write access is applicable when
               static profiles are implemented."


          OBJECT      adslAturConfRateMode
          MIN-ACCESS  read-write
          DESCRIPTION
              "Read-write access is applicable when
               static profiles are implemented."

          OBJECT      adslAturConfRateChanRatio
          MIN-ACCESS  read-write
          DESCRIPTION
              "Read-write access is applicable when
               static profiles are implemented."

          OBJECT      adslAturConfTargetSnrMgn
          MIN-ACCESS  read-write
          DESCRIPTION
              "Read-write access is applicable when
               static profiles are implemented."

          OBJECT      adslAturConfMaxSnrMgn
          MIN-ACCESS  read-write
          DESCRIPTION
              "Read-write access is applicable when
               static profiles are implemented."

          OBJECT      adslAturConfMinSnrMgn
          MIN-ACCESS  read-write
          DESCRIPTION
              "Read-write access is applicable when
               static profiles are implemented."

          OBJECT      adslAturConfDownshiftSnrMgn
          MIN-ACCESS  read-write
          DESCRIPTION
              "Read-write access is applicable when
               static profiles are implemented."

          OBJECT      adslAturConfUpshiftSnrMgn
          MIN-ACCESS  read-write
          DESCRIPTION
              "Read-write access is applicable when
               static profiles are implemented."

          OBJECT      adslAturConfMinUpshiftTime
          MIN-ACCESS  read-write
          DESCRIPTION
              "Read-write access is applicable when
               static profiles are implemented."


          OBJECT      adslAturConfMinDownshiftTime
          MIN-ACCESS  read-write
          DESCRIPTION
              "Read-write access is applicable when
               static profiles are implemented."

          OBJECT      adslAturChanConfFastMinTxRate
          MIN-ACCESS  read-write
          DESCRIPTION
              "Read-write access is applicable when
               static profiles are implemented."

          OBJECT      adslAturChanConfInterleaveMinTxRate
          MIN-ACCESS  read-write
          DESCRIPTION
              "Read-write access is applicable when
               static profiles are implemented."

          OBJECT      adslAturChanConfFastMaxTxRate
          MIN-ACCESS  read-write
          DESCRIPTION
              "Read-write access is applicable when
               static profiles are implemented."

          OBJECT      adslAturChanConfInterleaveMaxTxRate
          MIN-ACCESS  read-write
          DESCRIPTION
              "Read-write access is applicable when
               static profiles are implemented."

          OBJECT      adslAturChanConfMaxInterleaveDelay
          MIN-ACCESS  read-write
          DESCRIPTION
              "Read-write access is applicable when
               static profiles are implemented."

          OBJECT      adslLineConfProfileRowStatus
          MIN-ACCESS  read-only
          DESCRIPTION
              "Read-only access is applicable only when static
               profiles are implemented."

          OBJECT      adslLineAlarmConfProfile
          MIN-ACCESS  read-only
          DESCRIPTION
              "Read-only access is applicable only when static
               profiles are implemented."


          OBJECT      adslAtucThresh15MinLofs
          MIN-ACCESS  read-write
          DESCRIPTION
              "Read-write access is applicable when
               static profiles are implemented."

          OBJECT      adslAtucThresh15MinLoss
          MIN-ACCESS  read-write
          DESCRIPTION
              "Read-write access is applicable when
               static profiles are implemented."

          OBJECT      adslAtucThresh15MinLols
          MIN-ACCESS  read-write
          DESCRIPTION
              "Read-write access is applicable when
               static profiles are implemented."

          OBJECT      adslAtucThresh15MinLprs
          MIN-ACCESS  read-write
          DESCRIPTION
              "Read-write access is applicable when
               static profiles are implemented."

          OBJECT      adslAtucThresh15MinESs
          MIN-ACCESS  read-write
          DESCRIPTION
              "Read-write access is applicable when
               static profiles are implemented."

          OBJECT      adslAtucThreshFastRateUp
          MIN-ACCESS  read-write
          DESCRIPTION
              "Read-write access is applicable when
               static profiles are implemented."

          OBJECT      adslAtucThreshInterleaveRateUp
          MIN-ACCESS  read-write
          DESCRIPTION
              "Read-write access is applicable when
               static profiles are implemented."

          OBJECT      adslAtucThreshFastRateDown
          MIN-ACCESS  read-write
          DESCRIPTION
              "Read-write access is applicable when
               static profiles are implemented."


          OBJECT      adslAtucThreshInterleaveRateDown
          MIN-ACCESS  read-write
          DESCRIPTION
              "Read-write access is applicable when
               static profiles are implemented."

          OBJECT      adslAtucInitFailureTrapEnable
          MIN-ACCESS  read-write
          DESCRIPTION
              "Read-write access is applicable when
               static profiles are implemented."

          OBJECT      adslAturThresh15MinLofs
          MIN-ACCESS  read-write
          DESCRIPTION
              "Read-write access is applicable when
               static profiles are implemented."

          OBJECT      adslAturThresh15MinLoss
          MIN-ACCESS  read-write
          DESCRIPTION
              "Read-write access is applicable when
               static profiles are implemented."

          OBJECT      adslAturThresh15MinLprs
          MIN-ACCESS  read-write
          DESCRIPTION
              "Read-write access is applicable when
               static profiles are implemented."

          OBJECT      adslAturThresh15MinESs
          MIN-ACCESS  read-write
          DESCRIPTION
              "Read-write access is applicable when
               static profiles are implemented."

          OBJECT      adslAturThreshFastRateUp
          MIN-ACCESS  read-write
          DESCRIPTION
              "Read-write access is applicable when
               static profiles are implemented."

          OBJECT      adslAturThreshInterleaveRateUp
          MIN-ACCESS  read-write
          DESCRIPTION
              "Read-write access is applicable when
               static profiles are implemented."


          OBJECT      adslAturThreshFastRateDown
          MIN-ACCESS  read-write
          DESCRIPTION
              "Read-write access is applicable when
               static profiles are implemented."

          OBJECT      adslAturThreshInterleaveRateDown
          MIN-ACCESS  read-write
          DESCRIPTION
              "Read-write access is applicable when
               static profiles are implemented."

          OBJECT      adslLineAlarmConfProfileRowStatus
          MIN-ACCESS  read-only
          DESCRIPTION
              "Read-only access is applicable only when static
               profiles are implemented."

      ::= { adslCompliances 1 }

      -- ATU-R agent compliance statements

      adslLineMibAturCompliance MODULE-COMPLIANCE
          STATUS  current
          DESCRIPTION
              "The compliance statement for SNMP entities
               which manage ADSL ATU-R interfaces."

          MODULE  -- this module
          MANDATORY-GROUPS
              {
              adslAturLineGroup, adslAturPhysicalGroup,
              adslAturChannelGroup,
              adslAturAtucPhysPerfIntervalGroup,
              adslAturAturPhysPerfIntervalGroup,
              adslAturLineAlarmConfProfileGroup,
              adslAturLineConfProfileControlGroup
              }

          GROUP       adslAturAtucPhysPerfRawCounterGroup
          DESCRIPTION
              "This group is optional.  Implementations which
               require continuous ATU-C physical event counters
               should implement this group."

          GROUP       adslAturAturPhysPerfRawCounterGroup
          DESCRIPTION
              "This group is optional.  Implementations which

               require continuous ATU-R physical event counters
               should implement this group."

          GROUP       adslAturAtucChanPerformanceGroup
          DESCRIPTION
              "This group is optional.  Implementations which
               require ATU-C channel block event counters should
               implement this group."

          GROUP       adslAturAturChanPerformanceGroup
          DESCRIPTION
              "This group is optional.  Implementations which
               require ATU-R channel block event counters should
               implement this group."

          OBJECT      adslLineAlarmConfProfile
          MIN-ACCESS  read-only
          DESCRIPTION
              "Read-only access is applicable only when static
               profiles are implemented."

          OBJECT      adslAtucThresh15MinLofs
          MIN-ACCESS  read-write
          DESCRIPTION
              "Read-write access is applicable when
               static profiles are implemented."

          OBJECT      adslAtucThresh15MinLoss
          MIN-ACCESS  read-write
          DESCRIPTION
              "Read-write access is applicable when
               static profiles are implemented."

          OBJECT      adslAtucThresh15MinESs
          MIN-ACCESS  read-write
          DESCRIPTION
              "Read-write access is applicable when
               static profiles are implemented."

          OBJECT      adslAtucThreshFastRateUp
          MIN-ACCESS  read-write
          DESCRIPTION
              "Read-write access is applicable when
               static profiles are implemented."

          OBJECT      adslAtucThreshInterleaveRateUp
          MIN-ACCESS  read-write
          DESCRIPTION

              "Read-write access is applicable when
               static profiles are implemented."

          OBJECT      adslAtucThreshFastRateDown
          MIN-ACCESS  read-write
          DESCRIPTION
              "Read-write access is applicable when
               static profiles are implemented."

          OBJECT      adslAtucInitFailureTrapEnable
          MIN-ACCESS  read-write

          DESCRIPTION
              "Read-write access is applicable when
               static profiles are implemented."

          OBJECT      adslAturThresh15MinLofs
          MIN-ACCESS  read-write
          DESCRIPTION
              "Read-write access is applicable when
               static profiles are implemented."

          OBJECT      adslAturThresh15MinLoss
          MIN-ACCESS  read-write
          DESCRIPTION
              "Read-write access is applicable when
               static profiles are implemented."

          OBJECT      adslAturThresh15MinLprs
          MIN-ACCESS  read-write
          DESCRIPTION
              "Read-write access is applicable when
               static profiles are implemented."

          OBJECT      adslAturThresh15MinESs
          MIN-ACCESS  read-write
          DESCRIPTION
              "Read-write access is applicable when
               static profiles are implemented."

          OBJECT      adslAturThreshFastRateUp
          MIN-ACCESS  read-write
          DESCRIPTION
              "Read-write access is applicable when
               static profiles are implemented."

          OBJECT      adslAturThreshInterleaveRateUp
          MIN-ACCESS  read-write

          DESCRIPTION
              "Read-write access is applicable when
               static profiles are implemented."

          OBJECT      adslAturThreshFastRateDown
          MIN-ACCESS  read-write
          DESCRIPTION
              "Read-write access is applicable when
               static profiles are implemented."

          OBJECT      adslAturThreshInterleaveRateDown
          MIN-ACCESS  read-write
          DESCRIPTION
              "Read-write access is applicable when
               static profiles are implemented."

          OBJECT      adslLineAlarmConfProfileRowStatus
          MIN-ACCESS  read-only
          DESCRIPTION
              "Read-only access is applicable only when static
               profiles are implemented."

          OBJECT     adslAtucCurrStatus
          SYNTAX   BITS {
                         noDefect(0),
                         lossOfFraming(1),
                         lossOfSignal(2)
                        }
          DESCRIPTION
              "It is allowable to implement only noDefect(0),
              lossOfFraming(1) and lossOfSignal(2) by the ATU-R
              agent."

     ::= { adslCompliances 2 }

      -- units of conformance
      adslLineGroup    OBJECT-GROUP
          OBJECTS {
             adslLineCoding, adslLineType, adslLineSpecific
             }
          STATUS     current
          DESCRIPTION
              "A collection of objects providing configuration
              information about an ADSL Line."
      ::= { adslGroups 1 }

      adslPhysicalGroup    OBJECT-GROUP
          OBJECTS {

             adslAtucInvSerialNumber, adslAtucInvVendorID,
             adslAtucInvVersionNumber, adslAtucCurrSnrMgn,
             adslAtucCurrAtn, adslAtucCurrStatus,
             adslAtucCurrOutputPwr, adslAtucCurrAttainableRate,
             adslAturInvSerialNumber, adslAturInvVendorID,
             adslAturInvVersionNumber, adslAturCurrSnrMgn,
             adslAturCurrAtn, adslAturCurrStatus,
             adslAturCurrOutputPwr, adslAturCurrAttainableRate
             }
          STATUS     current
          DESCRIPTION
              "A collection of objects providing physical
              configuration information of the ADSL Line."
      ::= { adslGroups 2 }

      adslChannelGroup    OBJECT-GROUP
          OBJECTS {
             adslAtucChanInterleaveDelay, adslAtucChanCurrTxRate,
             adslAtucChanPrevTxRate, adslAtucChanCrcBlockLength,
             adslAturChanInterleaveDelay, adslAturChanCurrTxRate,
             adslAturChanPrevTxRate, adslAturChanCrcBlockLength
             }
          STATUS     current
          DESCRIPTION
              "A collection of objects providing configuration
              information about an ADSL channel."
      ::= { adslGroups 3 }

      adslAtucPhysPerfRawCounterGroup OBJECT-GROUP
          OBJECTS {
             adslAtucPerfLofs, adslAtucPerfLoss,
             adslAtucPerfLols, adslAtucPerfLprs,
             adslAtucPerfESs, adslAtucPerfInits
             }
          STATUS     current
          DESCRIPTION
              "A collection of objects providing raw performance
              counts on an ADSL Line (ATU-C end)."
      ::= { adslGroups 4 }

      adslAtucPhysPerfIntervalGroup OBJECT-GROUP
          OBJECTS {
             adslAtucPerfValidIntervals,
             adslAtucPerfInvalidIntervals,
             adslAtucPerfCurr15MinTimeElapsed,
             adslAtucPerfCurr15MinLofs, adslAtucPerfCurr15MinLoss,
             adslAtucPerfCurr15MinLols, adslAtucPerfCurr15MinLprs,
             adslAtucPerfCurr15MinESs, adslAtucPerfCurr15MinInits,

             adslAtucPerfCurr1DayLofs, adslAtucPerfCurr1DayLoss,
             adslAtucPerfCurr1DayLols, adslAtucPerfCurr1DayLprs,
             adslAtucPerfCurr1DayESs, adslAtucPerfCurr1DayInits,
             adslAtucPerfPrev1DayMoniSecs,
             adslAtucPerfPrev1DayLofs, adslAtucPerfPrev1DayLoss,
             adslAtucPerfPrev1DayLols, adslAtucPerfPrev1DayLprs,
             adslAtucPerfPrev1DayESs, adslAtucPerfPrev1DayInits,
             adslAtucIntervalLofs, adslAtucIntervalLoss,
             adslAtucIntervalLols, adslAtucIntervalLprs,
             adslAtucIntervalESs, adslAtucIntervalInits,
             adslAtucIntervalValidData
             }

          STATUS     current
          DESCRIPTION
              "A collection of objects providing current 15-minute,
              1-day; and previous 1-day performance counts on
              ADSL Line (ATU-C end) ."
      ::= { adslGroups 5 }

      adslAturPhysPerfRawCounterGroup OBJECT-GROUP
          OBJECTS {
             adslAturPerfLofs, adslAturPerfLoss,
             adslAturPerfLprs, adslAturPerfESs
             }
          STATUS     current
          DESCRIPTION
              "A collection of objects providing raw performance
              counts on an ADSL Line (ATU-R end)."
      ::= { adslGroups 6 }

      adslAturPhysPerfIntervalGroup OBJECT-GROUP
          OBJECTS {
             adslAturPerfValidIntervals,
             adslAturPerfInvalidIntervals,
             adslAturPerfCurr15MinTimeElapsed,
             adslAturPerfCurr15MinLofs, adslAturPerfCurr15MinLoss,
             adslAturPerfCurr15MinLprs, adslAturPerfCurr15MinESs,
             adslAturPerfCurr1DayTimeElapsed,
             adslAturPerfCurr1DayLofs, adslAturPerfCurr1DayLoss,
             adslAturPerfCurr1DayLprs, adslAturPerfCurr1DayESs,
             adslAturPerfPrev1DayMoniSecs,
             adslAturPerfPrev1DayLofs, adslAturPerfPrev1DayLoss,
             adslAturPerfPrev1DayLprs, adslAturPerfPrev1DayESs,
             adslAturIntervalLofs,
             adslAturIntervalLoss, adslAturIntervalLprs,
             adslAturIntervalESs, adslAturIntervalValidData
             }

          STATUS     current
          DESCRIPTION
              "A collection of objects providing current 15-minute,
              1-day; and previous 1-day performance counts on
              ADSL Line (ATU-R end)."
      ::= { adslGroups 7 }

      adslAtucChanPerformanceGroup OBJECT-GROUP
          OBJECTS {
             adslAtucChanReceivedBlks,
             adslAtucChanTransmittedBlks,
             adslAtucChanCorrectedBlks,
             adslAtucChanUncorrectBlks,
             adslAtucChanPerfValidIntervals,
             adslAtucChanPerfInvalidIntervals,
             adslAtucChanPerfCurr15MinTimeElapsed,
             adslAtucChanPerfCurr15MinReceivedBlks,
             adslAtucChanPerfCurr15MinTransmittedBlks,
             adslAtucChanPerfCurr15MinCorrectedBlks,
             adslAtucChanPerfCurr15MinUncorrectBlks,
             adslAtucChanPerfCurr1DayTimeElapsed,
             adslAtucChanPerfCurr1DayReceivedBlks,
             adslAtucChanPerfCurr1DayTransmittedBlks,
             adslAtucChanPerfCurr1DayCorrectedBlks,
             adslAtucChanPerfCurr1DayUncorrectBlks,
             adslAtucChanPerfPrev1DayMoniSecs,
             adslAtucChanPerfPrev1DayReceivedBlks,
             adslAtucChanPerfPrev1DayTransmittedBlks,
             adslAtucChanPerfPrev1DayCorrectedBlks,
             adslAtucChanPerfPrev1DayUncorrectBlks,
             adslAtucChanIntervalReceivedBlks,
             adslAtucChanIntervalTransmittedBlks,
             adslAtucChanIntervalCorrectedBlks,
             adslAtucChanIntervalUncorrectBlks,
             adslAtucChanIntervalValidData
             }
          STATUS     current
          DESCRIPTION
              "A collection of objects providing channel block
              performance information on an ADSL channel
              (ATU-C end)."
      ::= { adslGroups 8 }

      adslAturChanPerformanceGroup OBJECT-GROUP
          OBJECTS {
             adslAturChanReceivedBlks,
             adslAturChanTransmittedBlks,
             adslAturChanCorrectedBlks,

             adslAturChanUncorrectBlks,
             adslAturChanPerfValidIntervals,
             adslAturChanPerfInvalidIntervals,
             adslAturChanPerfCurr15MinTimeElapsed,
             adslAturChanPerfCurr15MinReceivedBlks,
             adslAturChanPerfCurr15MinTransmittedBlks,
             adslAturChanPerfCurr15MinCorrectedBlks,
             adslAturChanPerfCurr15MinUncorrectBlks,
             adslAturChanPerfCurr1DayTimeElapsed,
             adslAturChanPerfCurr1DayReceivedBlks,
             adslAturChanPerfCurr1DayTransmittedBlks,
             adslAturChanPerfCurr1DayCorrectedBlks,
             adslAturChanPerfCurr1DayUncorrectBlks,
             adslAturChanPerfPrev1DayMoniSecs,
             adslAturChanPerfPrev1DayReceivedBlks,
             adslAturChanPerfPrev1DayTransmittedBlks,
             adslAturChanPerfPrev1DayCorrectedBlks,
             adslAturChanPerfPrev1DayUncorrectBlks,
             adslAturChanIntervalReceivedBlks,
             adslAturChanIntervalTransmittedBlks,
             adslAturChanIntervalCorrectedBlks,
             adslAturChanIntervalUncorrectBlks,
             adslAturChanIntervalValidData
             }
          STATUS     current
          DESCRIPTION
              "A collection of objects providing channel block
              performance information on an ADSL channel
              (ATU-C end)."
      ::= { adslGroups 9 }

      adslLineConfProfileGroup OBJECT-GROUP
          OBJECTS {
             adslAtucConfRateMode, adslAtucConfRateChanRatio,
             adslAtucConfTargetSnrMgn, adslAtucConfMaxSnrMgn,
             adslAtucConfMinSnrMgn,
             adslAtucConfDownshiftSnrMgn,
             adslAtucConfUpshiftSnrMgn,
             adslAtucConfMinUpshiftTime,
             adslAtucConfMinDownshiftTime,
             adslAtucChanConfFastMinTxRate,
             adslAtucChanConfInterleaveMinTxRate,
             adslAtucChanConfFastMaxTxRate,
             adslAtucChanConfInterleaveMaxTxRate,
             adslAtucChanConfMaxInterleaveDelay,
             adslAturConfRateMode, adslAturConfRateChanRatio,
             adslAturConfTargetSnrMgn, adslAturConfMaxSnrMgn,
             adslAturConfMinSnrMgn, adslAturConfDownshiftSnrMgn,

             adslAturConfUpshiftSnrMgn,
             adslAturConfMinUpshiftTime,
             adslAturConfMinDownshiftTime,
             adslAturChanConfFastMinTxRate,
             adslAturChanConfInterleaveMinTxRate,
             adslAturChanConfFastMaxTxRate,
             adslAturChanConfInterleaveMaxTxRate,
             adslAturChanConfMaxInterleaveDelay
             }
          STATUS     current
          DESCRIPTION
              "A collection of objects providing provisioning
              information about an ADSL Line."
      ::= { adslGroups 10 }

      adslLineAlarmConfProfileGroup OBJECT-GROUP
          OBJECTS {
             adslAtucThresh15MinLofs, adslAtucThresh15MinLoss,
             adslAtucThresh15MinLols, adslAtucThresh15MinLprs,
             adslAtucThresh15MinESs, adslAtucThreshFastRateUp,
             adslAtucThreshInterleaveRateUp,
             adslAtucThreshFastRateDown,
             adslAtucThreshInterleaveRateDown,
             adslAtucInitFailureTrapEnable,
             adslAturThresh15MinLofs, adslAturThresh15MinLoss,
             adslAturThresh15MinLprs, adslAturThresh15MinESs,
             adslAturThreshFastRateUp,
             adslAturThreshInterleaveRateUp,
             adslAturThreshFastRateDown,
             adslAturThreshInterleaveRateDown
             }
          STATUS     current
          DESCRIPTION
              "A collection of objects providing alarm provisioning
              information about an ADSL Line."
      ::= { adslGroups 11 }

      adslLineConfProfileControlGroup OBJECT-GROUP
          OBJECTS {
             adslLineConfProfile, adslLineAlarmConfProfile,
             adslLineConfProfileRowStatus,
             adslLineAlarmConfProfileRowStatus
             }
          STATUS     current
          DESCRIPTION
              "A collection of objects providing profile
              control for the ADSL system."
      ::= { adslGroups 12 }

      adslNotificationsGroup NOTIFICATION-GROUP
          NOTIFICATIONS {
             adslAtucPerfLofsThreshTrap,
             adslAtucPerfLossThreshTrap,
             adslAtucPerfLprsThreshTrap,
             adslAtucPerfESsThreshTrap,
             adslAtucRateChangeTrap,
             adslAtucPerfLolsThreshTrap,
             adslAtucInitFailureTrap,
             adslAturPerfLofsThreshTrap,
             adslAturPerfLossThreshTrap,
             adslAturPerfLprsThreshTrap,
             adslAturPerfESsThreshTrap,
             adslAturRateChangeTrap
             }
          STATUS        current
          DESCRIPTION
              "The collection of adsl notifications."
      ::= { adslGroups 13 }

-- units of conformance for ATU-R agent

         adslAturLineGroup    OBJECT-GROUP
             OBJECTS {
                adslLineCoding
                }
             STATUS     current
             DESCRIPTION
                 "A collection of objects providing configuration
                 information about an ADSL Line on the ATU-R side."
         ::= { adslGroups 14 }

         adslAturPhysicalGroup    OBJECT-GROUP
             OBJECTS {
                adslAtucInvVendorID,
                adslAtucInvVersionNumber,
                adslAtucCurrOutputPwr, adslAtucCurrAttainableRate,
                adslAturInvSerialNumber, adslAturInvVendorID,
                adslAturInvVersionNumber, adslAturCurrSnrMgn,
                adslAturCurrAtn, adslAturCurrStatus,
                adslAturCurrOutputPwr, adslAturCurrAttainableRate,
                adslAtucCurrStatus
                }
             STATUS     current
             DESCRIPTION
                 "A collection of objects providing physical
                 configuration information of the ADSL Line on the
                 ATU-R side."

         ::= { adslGroups 15 }

         adslAturChannelGroup    OBJECT-GROUP
             OBJECTS {
                adslAtucChanInterleaveDelay, adslAtucChanCurrTxRate,
                adslAtucChanPrevTxRate,
                adslAturChanInterleaveDelay, adslAturChanCurrTxRate,
                adslAturChanPrevTxRate, adslAturChanCrcBlockLength
                }
             STATUS     current
             DESCRIPTION
                 "A collection of objects providing configuration
                information about an ADSL channel on the ATU-R
                side."
         ::= { adslGroups 16 }

         adslAturAtucPhysPerfRawCounterGroup OBJECT-GROUP
             OBJECTS {
                adslAtucPerfLofs, adslAtucPerfLoss,
                adslAtucPerfESs, adslAtucPerfInits
                }
             STATUS     current
             DESCRIPTION
                 "A collection of objects providing raw performance
                counts on an ADSL Line (ATU-C end) provided by the
                ATU-R agent."
         ::= { adslGroups 17 }

         adslAturAtucPhysPerfIntervalGroup OBJECT-GROUP
             OBJECTS {
                adslAtucPerfValidIntervals,
                adslAtucPerfInvalidIntervals,
                adslAtucPerfCurr15MinTimeElapsed,
                adslAtucPerfCurr15MinLofs, adslAtucPerfCurr15MinLoss,
                adslAtucPerfCurr15MinESs, adslAtucPerfCurr15MinInits,
                adslAtucPerfCurr1DayTimeElapsed,
                adslAtucPerfCurr1DayLofs, adslAtucPerfCurr1DayLoss,
                adslAtucPerfCurr1DayESs, adslAtucPerfCurr1DayInits,
                adslAtucPerfPrev1DayMoniSecs,
                adslAtucPerfPrev1DayLofs, adslAtucPerfPrev1DayLoss,
                adslAtucPerfPrev1DayESs, adslAtucPerfPrev1DayInits,
                adslAtucIntervalLofs, adslAtucIntervalLoss,
                adslAtucIntervalESs, adslAtucIntervalInits,
                adslAtucIntervalValidData
                }
             STATUS     current
             DESCRIPTION
                 "A collection of objects providing current

                15-minute, 1-day; and previous 1-day performance
                counts on ADSL Line (ATU-C end) provided by the
                ATU-R agent."
         ::= { adslGroups 18 }

         adslAturAturPhysPerfRawCounterGroup OBJECT-GROUP
             OBJECTS {
                adslAturPerfLofs, adslAturPerfLoss,
                adslAturPerfLprs, adslAturPerfESs
                }
             STATUS     current
             DESCRIPTION
                 "A collection of objects providing raw performance
                counts on an ADSL Line (ATU-R end) provided by the
                ATU-R agent."
         ::= { adslGroups 19 }

         adslAturAturPhysPerfIntervalGroup OBJECT-GROUP
             OBJECTS {
                adslAturPerfValidIntervals,
                adslAturPerfInvalidIntervals,
                adslAturPerfCurr15MinTimeElapsed,
                adslAturPerfCurr15MinLofs, adslAturPerfCurr15MinLoss,
                adslAturPerfCurr15MinLprs, adslAturPerfCurr15MinESs,
                adslAturPerfCurr1DayTimeElapsed,
                adslAturPerfCurr1DayLofs, adslAturPerfCurr1DayLoss,
                adslAturPerfCurr1DayLprs, adslAturPerfCurr1DayESs,
                adslAturPerfPrev1DayMoniSecs,
                adslAturPerfPrev1DayLofs, adslAturPerfPrev1DayLoss,
                adslAturPerfPrev1DayLprs, adslAturPerfPrev1DayESs,
                adslAturIntervalLofs,
                adslAturIntervalLoss, adslAturIntervalLprs,
                adslAturIntervalESs, adslAturIntervalValidData
                }
             STATUS     current
             DESCRIPTION
                 "A collection of objects providing current
                15-minute, 1-day; and previous 1-day performance
                counts on ADSL Line (ATU-R end) provided by the
                ATU-R agent."
         ::= { adslGroups 20 }

         adslAturAtucChanPerformanceGroup OBJECT-GROUP
             OBJECTS {
                adslAtucChanReceivedBlks,
                adslAtucChanTransmittedBlks,
                adslAtucChanCorrectedBlks,
                adslAtucChanUncorrectBlks,

                adslAtucChanPerfCurr15MinTimeElapsed,
                adslAtucChanPerfCurr15MinReceivedBlks,
                adslAtucChanPerfCurr15MinTransmittedBlks,
                adslAtucChanPerfCurr15MinCorrectedBlks,
                adslAtucChanPerfCurr15MinUncorrectBlks,
                adslAtucChanPerfCurr1DayTimeElapsed,
                adslAtucChanPerfCurr1DayReceivedBlks,
                adslAtucChanPerfCurr1DayTransmittedBlks,
                adslAtucChanPerfCurr1DayCorrectedBlks,
                adslAtucChanPerfCurr1DayUncorrectBlks,
                adslAtucChanPerfPrev1DayMoniSecs,
                adslAtucChanPerfPrev1DayReceivedBlks,
                adslAtucChanPerfPrev1DayTransmittedBlks,
                adslAtucChanPerfPrev1DayCorrectedBlks,
                adslAtucChanPerfPrev1DayUncorrectBlks,
                adslAtucChanPerfValidIntervals,
                adslAtucChanPerfInvalidIntervals,
                adslAtucChanIntervalReceivedBlks,
                adslAtucChanIntervalTransmittedBlks,
                adslAtucChanIntervalCorrectedBlks,
                adslAtucChanIntervalUncorrectBlks,
                adslAtucChanIntervalValidData
                }
             STATUS     current
             DESCRIPTION
                 "A collection of objects providing channel block
                 performance information on an ADSL channel
                 (ATU-C end) provided by the ATU-R agent."
         ::= { adslGroups 21 }

         adslAturAturChanPerformanceGroup OBJECT-GROUP
             OBJECTS {
                adslAturChanReceivedBlks,
                adslAturChanTransmittedBlks,
                adslAturChanCorrectedBlks,
                adslAturChanUncorrectBlks,
                adslAturChanPerfValidIntervals,
                adslAturChanPerfInvalidIntervals,
                adslAturChanPerfCurr15MinTimeElapsed,
                adslAturChanPerfCurr15MinReceivedBlks,
                adslAturChanPerfCurr15MinTransmittedBlks,
                adslAturChanPerfCurr15MinCorrectedBlks,
                adslAturChanPerfCurr15MinUncorrectBlks,
                adslAturChanPerfCurr1DayTimeElapsed,
                adslAturChanPerfCurr1DayReceivedBlks,
                adslAturChanPerfCurr1DayTransmittedBlks,
                adslAturChanPerfCurr1DayCorrectedBlks,
                adslAturChanPerfCurr1DayUncorrectBlks,

                adslAturChanPerfPrev1DayMoniSecs,
                adslAturChanPerfPrev1DayReceivedBlks,
                adslAturChanPerfPrev1DayTransmittedBlks,
                adslAturChanPerfPrev1DayCorrectedBlks,
                adslAturChanPerfPrev1DayUncorrectBlks,
                adslAturChanIntervalReceivedBlks,
                adslAturChanIntervalTransmittedBlks,
                adslAturChanIntervalCorrectedBlks,
                adslAturChanIntervalUncorrectBlks,
                adslAturChanIntervalValidData
                }
             STATUS     current
             DESCRIPTION
                 "A collection of objects providing channel block
                 performance information on an ADSL channel
                 (ATU-R end) provided by the ATU-R agent."
         ::= { adslGroups 22 }

         adslAturLineAlarmConfProfileGroup OBJECT-GROUP
             OBJECTS {
                adslAtucThresh15MinLofs, adslAtucThresh15MinLoss,
                adslAtucThresh15MinESs, adslAtucThreshFastRateUp,
                adslAtucThreshInterleaveRateUp,
                adslAtucThreshFastRateDown,
                adslAtucThreshInterleaveRateDown,
                adslAtucInitFailureTrapEnable,
                adslAturThresh15MinLofs, adslAturThresh15MinLoss,
                adslAturThresh15MinLprs, adslAturThresh15MinESs,
                adslAturThreshFastRateUp,
                adslAturThreshInterleaveRateUp,
                adslAturThreshFastRateDown,
                adslAturThreshInterleaveRateDown
                }
             STATUS     current
             DESCRIPTION
                 "A collection of objects providing alarm
provisioning
                 information about an ADSL Line provided by the
                 ATU-R agent."
         ::= { adslGroups 23 }

         adslAturLineConfProfileControlGroup OBJECT-GROUP
             OBJECTS {
                adslLineAlarmConfProfile,
                adslLineAlarmConfProfileRowStatus
                }
             STATUS     current
             DESCRIPTION

                 "A collection of objects providing profile
                 control for the ADSL system by the ATU-R agent."
         ::= { adslGroups 24 }

         adslAturNotificationsGroup NOTIFICATION-GROUP
             NOTIFICATIONS {
                 adslAtucPerfLofsThreshTrap,
                 adslAtucPerfLossThreshTrap,
                 adslAtucPerfESsThreshTrap,
                 adslAtucRateChangeTrap,
                 adslAturPerfLofsThreshTrap,
                 adslAturPerfLossThreshTrap,
                 adslAturPerfLprsThreshTrap,
                 adslAturPerfESsThreshTrap,
                 adslAturRateChangeTrap
                 }
             STATUS        current
             DESCRIPTION
                 "The collection of ADSL notifications implemented by
                 the ATU-R agent."
         ::= { adslGroups 25 }

END

ADSL-LINE-EXT-MIB DEFINITIONS ::= BEGIN

      IMPORTS
         Counter32,
         Unsigned32,
         NOTIFICATION-TYPE,
         MODULE-IDENTITY, Gauge32,
         OBJECT-TYPE                       FROM SNMPv2-SMI
         MODULE-COMPLIANCE, OBJECT-GROUP,
         NOTIFICATION-GROUP                FROM SNMPv2-CONF
         TEXTUAL-CONVENTION                FROM SNMPv2-TC
         PerfCurrentCount,
         PerfIntervalCount                 FROM PerfHist-TC-MIB
         AdslPerfCurrDayCount,
         AdslPerfPrevDayCount              FROM ADSL-TC-MIB
         SnmpAdminString                   FROM SNMP-FRAMEWORK-MIB
	 ifIndex                           FROM IF-MIB
	 adslLineConfProfileName,
	 adslLineAlarmConfProfileName,
         adslLineAlarmConfProfileEntry,
         adslLineConfProfileEntry,
         adslAturIntervalEntry,
         adslAturPerfDataEntry,
         adslAtucIntervalEntry,
	 adslAtucIntervalNumber,
	 adslAturIntervalNumber,
         adslAtucPerfDataEntry,
         adslLineEntry,
         adslMIB                           FROM ADSL-LINE-MIB
         ;

      adslExtMIB MODULE-IDENTITY

      LAST-UPDATED "200104090000Z"

      ORGANIZATION "IETF ADSL MIB Working Group"

      CONTACT-INFO
            "
             Faye Ly
             Salira Optical Systems
             2698 Orchard Parkway
             San Jose, CA 95134
             Tel: +1 408-382-0088
             Fax: +1 408-382-1688
             E-Mail: faye@salira.com

             Gregory Bathrick
             NOKIA High Speed Access Nodes
             1310 Redwood Way,
             Petaluma, CA 94954
             Tel: +1 707-793-7030
             Fax: +1 707-792-0850
             E-Mail: greg.bathrick@nokia.com

             IETF ADSL MIB Working Group
             &lt;XDSLMIB@LISTSERV.ECIRALEIGH.COM&gt;
             "
      DESCRIPTION
                "This MIB Module is a supplement to the ADSL-LINE-MIB
                 [RFC2662]."
      REVISION     "0108011200Z"  -- YY Month YYYY
      DESCRIPTION  "Initial Version, published as RFC xxxx. This MIB
                    module is supplement to the ADSL-LINE-MIB [RFC2662]."
             ::= { adslMIB 3 }

          adslExtMibObjects  OBJECT IDENTIFIER ::= { adslExtMIB 1 }

          AdslTransmissionModeType ::= TEXTUAL-CONVENTION
              STATUS       current
              DESCRIPTION
                  "A set of ADSL line transmission modes, with one bit
                   per mode.  The notes (F) and (L) denote Full-Rate
                   and G.Lite respectively:
                     Bit 00 : Regional Std. (ANSI T1.413) (F)
                     Bit 01 : Regional Std. (ETSI DTS/TM06006) (F)
                     Bit 02 : G.992.1 POTS non-overlapped (F)
                     Bit 03 : G.992.1 POTS overlapped (F)
                     Bit 04 : G.992.1 ISDN non-overlapped (F)
                     Bit 05 : G.992.1 ISDN overlapped (F)
                     Bit 06 : G.992.1 TCM-ISDN non-overlapped (F)
                     Bit 07 : G.992.1 TCM-ISDN overlapped (F)
                     Bit 08 : G.992.2 POTS non-overlapped (L)
                     Bit 09 : G.992.2 POTS overlapped (L)
                     Bit 10 : G.992.2 with TCM-ISDN non-overlapped (L)
                     Bit 11 : G.992.2 with TCM-ISDN overlapped (L)
                     Bit 12 : G.992.1 TCM-ISDN symmetric (F)
                  "
              SYNTAX      BITS {
                  ansit1413(0),
                  etsi(1),
                  q9921PotsNonOverlapped(2),
                  q9921PotsOverlapped(3),
                  q9921IsdnNonOverlapped(4),
                  q9921isdnOverlapped(5),
                  q9921tcmIsdnNonOverlapped(6),
                  q9921tcmIsdnOverlapped(7),
                  q9922potsNonOverlapeed(8),
                  q9922potsOverlapped(9),
                  q9922tcmIsdnNonOverlapped(10),
                  q9922tcmIsdnOverlapped(11),
                  q9921tcmIsdnSymmetric(12)
              }

            adslLineExtTable   OBJECT-TYPE
                SYNTAX          SEQUENCE OF AdslLineExtEntry
                MAX-ACCESS      not-accessible
                STATUS          current
                DESCRIPTION
                    "This table is an extension of RFC2662.  It
                     contains ADSL line configuration and
                     monitoring information. This includes the ADSL
                     line's capabilities and actual ADSL transmission
                     bbbbbbsystem."
            ::= { adslExtMibObjects 17 }

            adslLineExtEntry   OBJECT-TYPE
                SYNTAX          AdslLineExtEntry
                MAX-ACCESS      not-accessible
                STATUS          current
                DESCRIPTION
                    "An entry extends the adslLineEntry defined in
                     [RFC2662].  Each entry corresponds to an ADSL
                     line."
            INDEX { ifIndex }
            ::= { adslLineExtTable 1 }

            AdslLineExtEntry ::=
                SEQUENCE {
                adslLineTransAtucCap        AdslTransmissionModeType,
                adslLineTransAtucConfig     AdslTransmissionModeType,
                adslLineTransAtucActual     AdslTransmissionModeType,
                adslLineGlitePowerState     INTEGER,
                adslLineConfProfileDualLite SnmpAdminString
                }

            adslLineTransAtucCap OBJECT-TYPE
                SYNTAX      AdslTransmissionModeType
                MAX-ACCESS  read-only
                STATUS      current
                DESCRIPTION
                    "The transmission modes, represented by a
                     bitmask that the ATU-C is capable of
                     supporting.  The modes available are limited
                     by the design of the equipment."
                REFERENCE "Section 7.3.2 ITU G.997.1"
            ::= { adslLineExtEntry 1 }

            adslLineTransAtucConfig OBJECT-TYPE
                SYNTAX      AdslTransmissionModeType
                MAX-ACCESS  read-write
                STATUS      current
                DESCRIPTION
                    "The transmission modes, represented by a bitmask,
                     currently enabled by the ATU-C.  The manager can
                     only set those modes that are supported by the
                     ATU-C.  An ATU-C's supported modes are provided by
                     AdslLineTransAtucCap."
                REFERENCE "Section 7.3.2 ITU G.997.1"
            ::= { adslLineExtEntry 2 }

            adslLineTransAtucActual OBJECT-TYPE
                SYNTAX      AdslTransmissionModeType
                MAX-ACCESS  read-only
                STATUS      current
                DESCRIPTION
                    "The actual transmission mode of the ATU-C.
                     During ADSL line initialization, the ADSL
                     Transceiver Unit - Remote terminal end (ATU-R)
                     will determine the mode used for the link.
                     This value will be limited a single transmission
                     mode that is a subset of those modes enabled
                     by the ATU-C and denoted by adslLineTransAtucConfig.
                     After an initialization has occurred, its mode is
                     saved as the 'Current' mode and is persistence
                     should the link go down. This object returns 0
                     (i.e. BITS with no mode bit set) if the mode is
                     not known."
                REFERENCE "Section 7.3.2 ITU G.997.1 "
            ::= { adslLineExtEntry 3 }

            adslLineGlitePowerState OBJECT-TYPE
                SYNTAX      INTEGER {
                            none(1),
                            l0(2),          -- L0 Power on
                            l1(3),          -- L1 Power on but reduced
                            l3(4)           -- L3 Power off
                            }
                MAX-ACCESS  read-only
                STATUS      current
                DESCRIPTION
                    "The value of this object specifies the power
                     state of this interface.  If the object
                     adslLineTransAtucActual is set to a G.992.2
                     (G.Lite)-type transmission mode, the value of
                     this object will be one of the valid power
                     states: L0(2), L1(3), or L3(4).  Otherwise, its
                     value will be none(1)."
            ::= { adslLineExtEntry 4 }

            adslLineConfProfileDualLite OBJECT-TYPE
                SYNTAX     SnmpAdminString
                MAX-ACCESS read-write
                STATUS     current
                DESCRIPTION
                    "This object extends the definition an ADSL line and
                     associated channels (when applicable) for cases when
                     it is configured in dual mode, and operating in a
                     G.Lite-type mode as denoted by adslLineTransAtucActual.
                     Dual mode exists when the object, adslLineTransAtucConfig,
                     is configured with one or more full-rate modes and one or
                     more G.Lite modes simultaneously.

                     When 'dynamic' profiles are implemented, the value of
                     object is equal to the index of the applicable row in the
                     ADSL Line Configuration Profile Table,
                     AdslLineConfProfileTable defined in ADSL-MIB [RFC2662].

                     In the case when dual-mode has not been enabled, the
                       value of the object will be equal to the value of the
                     object adslLineConfProfile [RFC2662].

                     When `static' profiles are implemented, in much
                     like the case of the object, adslLineConfProfileName
                     [RFC2662], this object's value will need to
                     algorithmically represent the characteristics of the
                     line.  In this case, the value of the line's ifIndex
                     plus a value indicating the line mode type
                     (e.g., G.Lite, Full-rate) will be used. Therefore,
                     the profile's name is a string concatenating the
                     ifIndex and one of the follow values: Full or Lite. This
                     string will be fixed-length (i.e., 14) with leading
                     zero(s).  For example, the profile name for
                     ifIndex that equals '15' and is a full rate
                     line, it will be '0000000015Full'."
                REFERENCE "Section 5.4 Profiles, RFC 2662"
            ::= { adslLineExtEntry 5 }

            adslAtucPerfDataExtTable   OBJECT-TYPE
                SYNTAX          SEQUENCE OF AdslAtucPerfDataExtEntry
                MAX-ACCESS      not-accessible
                STATUS          current
                DESCRIPTION
                    "This table contains ADSL physical line counters
                     with additional ADSL physical line counter
                     information such as unavailable seconds-line and
                     severely errored seconds-line not defined in
		     adslAtucPerfDataTable in [RFC2662]."
            ::= { adslExtMibObjects 18 }

            adslAtucPerfDataExtEntry   OBJECT-TYPE
                SYNTAX          AdslAtucPerfDataExtEntry
                MAX-ACCESS      not-accessible
                STATUS          current
                DESCRIPTION
                    "An entry extends the adslAtucPerfDataEntry defined
                     in [RFC2662].  Each entry corresponds to an ADSL
                     line."
 	        INDEX { ifIndex }
            ::= { adslAtucPerfDataExtTable 1 }

            AdslAtucPerfDataExtEntry ::=
                SEQUENCE {
                adslAtucPerfStatFastR            Counter32,
                adslAtucPerfStatFailedFastR      Counter32,
                adslAtucPerfStatSesL             Counter32,
                adslAtucPerfStatUasL             Counter32,
                adslAtucPerfCurr15MinFastR       PerfCurrentCount,
                adslAtucPerfCurr15MinFailedFastR PerfCurrentCount,
                adslAtucPerfCurr15MinSesL        PerfCurrentCount,
                adslAtucPerfCurr15MinUasL        PerfCurrentCount,
                adslAtucPerfCurr1DayFastR        AdslPerfCurrDayCount,
                adslAtucPerfCurr1DayFailedFastR  AdslPerfCurrDayCount,
                adslAtucPerfCurr1DaySesL         AdslPerfCurrDayCount,
                adslAtucPerfCurr1DayUasL         AdslPerfCurrDayCount,
                adslAtucPerfPrev1DayFastR        AdslPerfPrevDayCount,
                adslAtucPerfPrev1DayFailedFastR  AdslPerfPrevDayCount,
                adslAtucPerfPrev1DaySesL         AdslPerfPrevDayCount,
                adslAtucPerfPrev1DayUasL         AdslPerfPrevDayCount
            }

            adslAtucPerfStatFastR OBJECT-TYPE
                SYNTAX      Counter32
                UNITS       "line retrains"
                MAX-ACCESS  read-only
                STATUS      current
                DESCRIPTION
                    "The value of this object reports the count of
                     the number of fast line bs since last
                     agent reset."
                REFERENCE "ITU G.997.1 Section 7.4.15.1 "
            ::= { adslAtucPerfDataExtEntry 1 }

            adslAtucPerfStatFailedFastR OBJECT-TYPE
                SYNTAX      Counter32
                UNITS       "line retrains"
                MAX-ACCESS  read-only
                STATUS      current
                DESCRIPTION
                    "The value of this object reports the count of
                     the number of failed fast line retrains since
                     last agent reset."
                REFERENCE "ITU G.997.1 Section 7.4.15.2 "
            ::= { adslAtucPerfDataExtEntry 2 }

            adslAtucPerfStatSesL OBJECT-TYPE
                SYNTAX      Counter32
                UNITS       "seconds"
                MAX-ACCESS  read-only
                STATUS      current
                DESCRIPTION
                    "The value of this object reports the count of
                     the number of severely errored seconds-line since
                     last agent reset."
                REFERENCE "ITU G.997.1 Section 7.2.1.1.7 "
            ::= { adslAtucPerfDataExtEntry 3 }

            adslAtucPerfStatUasL OBJECT-TYPE
                SYNTAX      Counter32
                UNITS       "seconds"
                MAX-ACCESS  read-only
                STATUS      current
                DESCRIPTION
                    "The value of this object reports the count of
                     the number of unavailable seconds-line since
                     last agent reset."
                REFERENCE "ITU G.997.1 Section 7.2.1.1.9 "
            ::= { adslAtucPerfDataExtEntry 4 }

            adslAtucPerfCurr15MinFastR OBJECT-TYPE
                SYNTAX      PerfCurrentCount
                UNITS       "seconds"
                MAX-ACCESS  read-only
                STATUS      current
                DESCRIPTION
                    "For the current 15-minute interval,
                     adslAtucPerfCurr15MinFastR reports the current
                     number of seconds during which there have been
                     fast retrains."
                REFERENCE "ITU G.997.1 Section 7.4.15.1 "
            ::= { adslAtucPerfDataExtEntry 5 }

            adslAtucPerfCurr15MinFailedFastR   OBJECT-TYPE
                SYNTAX      PerfCurrentCount
                UNITS       "seconds"
                MAX-ACCESS  read-only
                STATUS      current
                DESCRIPTION
                    "For the current 15-minute interval,
                     adslAtucPerfCurr15MinFailedFastR reports the current
                     number of seconds during which there have been
                     failed fast retrains."
                REFERENCE "ITU G.997.1 Section 7.4.15.2 "
            ::= { adslAtucPerfDataExtEntry 6 }

            adslAtucPerfCurr15MinSesL OBJECT-TYPE
                SYNTAX      PerfCurrentCount
                UNITS       "seconds"
                MAX-ACCESS  read-only
                STATUS      current
                DESCRIPTION
                    "For the current 15-minute interval,
                     adslAtucPerfCurr15MinSesL reports the current
                     number of seconds during which there have been
                     severely errored seconds-line."
                REFERENCE "ITU G.997.1 Section 7.2.1.1.7 "
            ::= { adslAtucPerfDataExtEntry 7 }

            adslAtucPerfCurr15MinUasL   OBJECT-TYPE
                SYNTAX      PerfCurrentCount
                UNITS       "seconds"
                MAX-ACCESS  read-only
                STATUS      current
                DESCRIPTION
                    "For the current 15-minute interval,
                     adslAtucPerfCurr15MinUasL reports the current
                     number of seconds during which there have been
                     unavailable seconds-line."
                REFERENCE "ITU G.997.1 Section 7.2.1.1.9 "
            ::= { adslAtucPerfDataExtEntry 8 }

            adslAtucPerfCurr1DayFastR    OBJECT-TYPE
                SYNTAX      AdslPerfCurrDayCount
                UNITS       "seconds"
                MAX-ACCESS  read-only
                STATUS      current
                DESCRIPTION
                    "For the current day as measured by
                     adslAtucPerfCurr1DayTimeElapsed [RFC 2662],
                     adslAtucPerfCurr1DayFastR reports the number
                     of seconds during which there have been
                     fast retrains."
                REFERENCE "ITU G.997.1 Section 7.4.15.1 "
            ::= { adslAtucPerfDataExtEntry 9 }

            adslAtucPerfCurr1DayFailedFastR    OBJECT-TYPE
                SYNTAX      AdslPerfCurrDayCount
                UNITS       "seconds"
                MAX-ACCESS  read-only
                STATUS      current
                DESCRIPTION
                    "For the current day as measured by
                     adslAtucPerfCurr1DayTimeElapsed [RFC 2662],
                     adslAtucPerfCurr1DayFailedFastR reports the
                     number of seconds during which there have been
                     failed fast retrains."
                REFERENCE "ITU G.997.1 Section 7.4.15.2 "
            ::= { adslAtucPerfDataExtEntry 10 }

            adslAtucPerfCurr1DaySesL    OBJECT-TYPE
                SYNTAX      AdslPerfCurrDayCount
                UNITS       "seconds"
                MAX-ACCESS  read-only
                STATUS      current
                DESCRIPTION
                    "For the current day as measured by
                     adslAtucPerfCurr1DayTimeElapsed [RFC 2662],
                     adslAtucPerfCurr1DaySesL reports the
                     number of seconds during which there have been
                     severely errored seconds-line."
                REFERENCE "ITU G.997.1 Section 7.2.1.1.7 "
            ::= { adslAtucPerfDataExtEntry 11 }

            adslAtucPerfCurr1DayUasL    OBJECT-TYPE
                SYNTAX      AdslPerfCurrDayCount
                UNITS       "seconds"
                MAX-ACCESS  read-only
                STATUS      current
                DESCRIPTION
                    "For the current day as measured by
                     adslAtucPerfCurr1DayTimeElapsed [RFC 2662],
                     adslAtucPerfCurr1DayUasL reports the
                     number of seconds during which there have been
                     unavailable seconds-line."
                REFERENCE "ITU G.997.1 Section 7.2.1.1.9 "
            ::= { adslAtucPerfDataExtEntry 12 }

            adslAtucPerfPrev1DayFastR     OBJECT-TYPE
                SYNTAX      AdslPerfPrevDayCount
                UNITS       "seconds"
                MAX-ACCESS  read-only
                STATUS      current
                DESCRIPTION
                    "For the previous day, adslAtucPerfPrev1DayFastR
                     reports the number of seconds during which there
                     were fast retrains."
                REFERENCE "ITU G.997.1 Section 7.4.15.1 "
            ::= { adslAtucPerfDataExtEntry 13 }

            adslAtucPerfPrev1DayFailedFastR OBJECT-TYPE
                SYNTAX      AdslPerfPrevDayCount
                UNITS       "seconds"
                MAX-ACCESS  read-only
                STATUS      current
                DESCRIPTION
                    "For the previous day, adslAtucPerfPrev1DayFailedFastR
                     reports the number of seconds during which there
                     were failed fast retrains."
                REFERENCE "ITU G.997.1 Section 7.4.15.2 "
            ::= { adslAtucPerfDataExtEntry 14 }

            adslAtucPerfPrev1DaySesL     OBJECT-TYPE
                SYNTAX      AdslPerfPrevDayCount
                UNITS       "seconds"
                MAX-ACCESS  read-only
                STATUS      current
                DESCRIPTION
                    "For the previous day, adslAtucPerfPrev1DaySesL
                     reports the number of seconds during which there
                     were severely errored seconds-line."
                REFERENCE "ITU G.997.1 Section 7.2.1.1.7 "
            ::= { adslAtucPerfDataExtEntry 15 }

            adslAtucPerfPrev1DayUasL OBJECT-TYPE
                SYNTAX      AdslPerfPrevDayCount
                UNITS       "seconds"
                MAX-ACCESS  read-only
                STATUS      current
                DESCRIPTION
                    "For the previous day, adslAtucPerfPrev1DayUasL
                     reports the number of seconds during which there
                     were unavailable seconds-line."
                REFERENCE "ITU G.997.1 Section 7.2.1.1.9 "
            ::= { adslAtucPerfDataExtEntry 16 }

            adslAtucIntervalExtTable   OBJECT-TYPE
                SYNTAX          SEQUENCE OF AdslAtucIntervalExtEntry
                MAX-ACCESS      not-accessible
                STATUS          current
                DESCRIPTION
                    "This table provides one row for each ATU-C
                     performance data collection interval for
                     ADSL physical interfaces whose
                     IfEntries' ifType is equal to adsl(94)."
            ::= { adslExtMibObjects 19 }

            adslAtucIntervalExtEntry   OBJECT-TYPE
                SYNTAX          AdslAtucIntervalExtEntry
                MAX-ACCESS      not-accessible
                STATUS          current
                DESCRIPTION     "An entry in the
                                 adslAtucIntervalExtTable."
                INDEX           { ifIndex, adslAtucIntervalNumber }
            ::= { adslAtucIntervalExtTable 1 }

            AdslAtucIntervalExtEntry ::=
                SEQUENCE {
                adslAtucIntervalFastR            PerfIntervalCount,
                adslAtucIntervalFailedFastR      PerfIntervalCount,
                adslAtucIntervalSesL             PerfIntervalCount,
                adslAtucIntervalUasL             PerfIntervalCount
                }

            adslAtucIntervalFastR OBJECT-TYPE
                SYNTAX      PerfIntervalCount
                UNITS       "seconds"
                MAX-ACCESS  read-only
                STATUS      current
                DESCRIPTION
                    "For the current interval, adslAtucIntervalFastR
                     reports the current number of seconds during which
                     there have been fast retrains."
            ::= { adslAtucIntervalExtEntry 1 }

            adslAtucIntervalFailedFastR OBJECT-TYPE
                SYNTAX      PerfIntervalCount
                UNITS       "seconds"
                MAX-ACCESS  read-only
                STATUS      current
                DESCRIPTION
                    "For the each interval, adslAtucIntervalFailedFastR
                     reports the number of seconds during which
                     there have been failed fast retrains."
            ::= { adslAtucIntervalExtEntry 2 }

            adslAtucIntervalSesL OBJECT-TYPE
                SYNTAX      PerfIntervalCount
                UNITS       "seconds"
                MAX-ACCESS  read-only
                STATUS      current
                DESCRIPTION
                    "For the each interval, adslAtucIntervalSesL
                     reports the number of seconds during which
                     there have been severely errored seconds-line."
            ::= { adslAtucIntervalExtEntry 3 }

            adslAtucIntervalUasL OBJECT-TYPE
                SYNTAX      PerfIntervalCount
                UNITS       "seconds"
                MAX-ACCESS  read-only
                STATUS      current
                DESCRIPTION
                    "For the each interval, adslAtucIntervalUasL
                     reports the number of seconds during which
                     there have been unavailable seconds-line."
            ::= { adslAtucIntervalExtEntry 4 }

            adslAturPerfDataExtTable   OBJECT-TYPE
                SYNTAX          SEQUENCE OF AdslAturPerfDataExtEntry
                MAX-ACCESS      not-accessible
                STATUS          current
                DESCRIPTION
                    "This table contains ADSL physical line counters
                     not defined in the adslAturPerfDataTable
                     from the ADSL-LINE-MIB [RFC2662]."
            ::= { adslExtMibObjects 20 }

            adslAturPerfDataExtEntry   OBJECT-TYPE
                SYNTAX          AdslAturPerfDataExtEntry
                MAX-ACCESS      not-accessible
                STATUS          current
                DESCRIPTION
                    "An entry extends the adslAturPerfDataEntry defined
                     in [RFC2662].  Each entry corresponds to an ADSL
                     line."
                INDEX { ifIndex } 
            ::= { adslAturPerfDataExtTable 1 }

            AdslAturPerfDataExtEntry ::=
                SEQUENCE {
                adslAturPerfStatSesL             Counter32,
                adslAturPerfStatUasL             Counter32,
                adslAturPerfCurr15MinSesL        PerfCurrentCount,
                adslAturPerfCurr15MinUasL        PerfCurrentCount,
                adslAturPerfCurr1DaySesL         AdslPerfCurrDayCount,
                adslAturPerfCurr1DayUasL         AdslPerfCurrDayCount,
                adslAturPerfPrev1DaySesL         AdslPerfPrevDayCount,
                adslAturPerfPrev1DayUasL         AdslPerfPrevDayCount
            }

            adslAturPerfStatSesL OBJECT-TYPE
                SYNTAX      Counter32
                UNITS       "seconds"
                MAX-ACCESS  read-only
                STATUS      current
                DESCRIPTION
                    "The value of this object reports the count of
                     severely errored second-line since the last agent
                     reset."
                REFERENCE "ITU G.997.1 Section 7.2.1.1.7 "
            ::= { adslAturPerfDataExtEntry 1 }

            adslAturPerfStatUasL OBJECT-TYPE
                SYNTAX      Counter32
                UNITS       "seconds"
                MAX-ACCESS  read-only
                STATUS      current
                DESCRIPTION
                    "The value of this object reports the count of
                     unavailable seconds-line since the last agent
                     reset."
                REFERENCE "ITU G.997.1 Section 7.2.1.2.9 "
            ::= { adslAturPerfDataExtEntry 2 }

            adslAturPerfCurr15MinSesL OBJECT-TYPE
                SYNTAX      PerfCurrentCount
                UNITS       "seconds"
                MAX-ACCESS  read-only
                STATUS      current
                DESCRIPTION
                    "For the current 15-minute interval,
                     adslAturPerfCurr15MinSesL reports the current
                     number of seconds during which there have been
                     severely errored seconds-line."
                REFERENCE "ITU G.997.1 Section 7.2.1.2.7 "
            ::= { adslAturPerfDataExtEntry 3 }

            adslAturPerfCurr15MinUasL   OBJECT-TYPE
                SYNTAX      PerfCurrentCount
                UNITS       "seconds"
                MAX-ACCESS  read-only
                STATUS      current
                DESCRIPTION
                    "For the current 15-minute interval,
                     adslAturPerfCurr15MinUasL reports the current
                     number of seconds during which there have been
                     available seconds-line."
                REFERENCE "ITU G.997.1 Section 7.2.1.2.9 "
            ::= { adslAturPerfDataExtEntry 4 }

            adslAturPerfCurr1DaySesL    OBJECT-TYPE
                SYNTAX      AdslPerfCurrDayCount
                UNITS       "seconds"
                MAX-ACCESS  read-only
                STATUS      current
                DESCRIPTION
                    "For the current day as measured by
                     adslAturPerfCurr1DayTimeElapsed [RFC 2662],
                     adslAturPerfCurr1DaySesL reports the
                     number of seconds during which there have been
                     severely errored seconds-line."
                REFERENCE "ITU G.997.1 Section 7.2.1.2.7 "
            ::= { adslAturPerfDataExtEntry 5 }

            adslAturPerfCurr1DayUasL    OBJECT-TYPE
                SYNTAX      AdslPerfCurrDayCount
                UNITS       "seconds"
                MAX-ACCESS  read-only
                STATUS      current
                DESCRIPTION
                    "For the current day as measured by
                     adslAturPerfCurr1DayTimeElapsed [RFC 2662],
                     adslAturPerfCurr1DayUasL reports the
                     number of seconds during which there have been
                     unavailable seconds-line."
                REFERENCE "ITU G.997.1 Section 7.2.1.2.9 "
            ::= { adslAturPerfDataExtEntry 6 }

            adslAturPerfPrev1DaySesL     OBJECT-TYPE
                SYNTAX      AdslPerfPrevDayCount
                UNITS       "seconds"
                MAX-ACCESS  read-only
                STATUS      current
                DESCRIPTION
                    "For the previous day, adslAturPerfPrev1DaySesL
                     reports the number of seconds during which there
                     were severely errored seconds-line."
                REFERENCE "ITU G.997.1 Section 7.2.1.2.7 "
            ::= { adslAturPerfDataExtEntry 7 }

            adslAturPerfPrev1DayUasL OBJECT-TYPE
                SYNTAX      AdslPerfPrevDayCount
                UNITS       "seconds"
                MAX-ACCESS  read-only
                STATUS      current
                DESCRIPTION
                    "For the previous day, adslAturPerfPrev1DayUasL
                     reports the number of seconds during which there
                     were severely errored seconds-line."
                REFERENCE "ITU G.997.1 Section 7.2.1.2.9 "
            ::= { adslAturPerfDataExtEntry 8 }

            adslAturIntervalExtTable   OBJECT-TYPE
                SYNTAX          SEQUENCE OF AdslAturIntervalExtEntry
                MAX-ACCESS      not-accessible
                STATUS          current
                DESCRIPTION
                    "This table provides one row for each ATU-R
                     performance data collection interval for
                     ADSL physical interfaces whose
                     IfEntries' ifType is equal to adsl(94)."
            ::= { adslExtMibObjects 21 }

            adslAturIntervalExtEntry   OBJECT-TYPE
                SYNTAX          AdslAturIntervalExtEntry
                MAX-ACCESS      not-accessible
                STATUS          current
                DESCRIPTION     "An entry in the
                                 adslAturIntervalExtTable."
                INDEX           { ifIndex, adslAturIntervalNumber }
            ::= { adslAturIntervalExtTable 1 }

            AdslAturIntervalExtEntry ::=
                SEQUENCE {
                adslAturIntervalSesL             PerfIntervalCount,
                adslAturIntervalUasL             PerfIntervalCount
                }

            adslAturIntervalSesL OBJECT-TYPE
                SYNTAX      PerfIntervalCount
                UNITS       "seconds"
                MAX-ACCESS  read-only
                STATUS      current
                DESCRIPTION
                    "For the each interval, adslAturIntervalSesL
                     reports the number of seconds during which
                     there have been severely errored seconds-line."
            ::= { adslAturIntervalExtEntry 1 }

            adslAturIntervalUasL OBJECT-TYPE
                SYNTAX      PerfIntervalCount
                UNITS       "seconds"
                MAX-ACCESS  read-only
                STATUS      current
                DESCRIPTION
                    "For the each interval, adslAturIntervalUasL
                     reports the number of seconds during which
                     there have been unavailable seconds-line."
            ::= { adslAturIntervalExtEntry 2 }

            adslConfProfileExtTable   OBJECT-TYPE
                SYNTAX          SEQUENCE OF AdslConfProfileExtEntry
                MAX-ACCESS      not-accessible
                STATUS          current
                DESCRIPTION
                    "The adslConfProfileExtTable extends the ADSL line
                     profile configuration information in the
                     adslLineConfProfileTable from the ADSL-LINE-MIB
                     [RFC2662] by adding the ability to configure the
                     ADSL physical line mode."
            ::= { adslExtMibObjects 22 }

            adslConfProfileExtEntry   OBJECT-TYPE
                SYNTAX          AdslConfProfileExtEntry
                MAX-ACCESS      not-accessible
                STATUS          current
                DESCRIPTION
                    "An entry extends the adslLineConfProfileEntry defined
                     in [RFC2662].  Each entry corresponds to an ADSL line
                     profile."
                     INDEX { IMPLIED adslLineConfProfileName }
            ::= { adslConfProfileExtTable 1 }

            AdslConfProfileExtEntry ::=
                SEQUENCE {
                    adslConfProfileLineType  INTEGER
                }

            adslConfProfileLineType OBJECT-TYPE
                SYNTAX      INTEGER {
                    noChannel (1),        -- no channels exist
                    fastOnly (2),         -- only fast channel exists
                    interleavedOnly (3),  -- only interleaved channel
                                          -- exist
                    fastOrInterleaved (4),-- either fast or interleaved
                                          -- channels can exist, but
                                          -- only one at any time
                    fastAndInterleaved (5)-- both the fast channel and
                                          -- the interleaved channel
                                          -- exist
                    }
                MAX-ACCESS  read-create
                STATUS      current
                DESCRIPTION
                    "This object is used to configure the ADSL physical
                     line mode.  It has following valid values:

                     noChannel(1), when no channels exist.
                     fastOnly(2), when only fast channel exists.
                     interleavedOnly(3), when only interleaved channel
                         exist.
                     fastOrInterleaved(4), when either fast or
                         interleaved channels can exist, but only one
                         at any time.
                     fastAndInterleaved(5), when both the fast channel
                         and the interleaved channel exist.

                     In the case when no value has been set, the default
                     Value is noChannel(1).
                     "
            ::= { adslConfProfileExtEntry 1 }

            adslAlarmConfProfileExtTable   OBJECT-TYPE
                SYNTAX          SEQUENCE OF AdslAlarmConfProfileExtEntry
                MAX-ACCESS      not-accessible
                STATUS          current
                DESCRIPTION
                    "This table extends the adslLineAlarmConfProfileTable
                     and provides threshold parameters for all the
                     counters defined in this MIB module."
            ::= { adslExtMibObjects 23 }

            adslAlarmConfProfileExtEntry   OBJECT-TYPE
                SYNTAX          AdslAlarmConfProfileExtEntry
                MAX-ACCESS      not-accessible
                STATUS          current
                DESCRIPTION
                    "An entry extends the adslLineAlarmConfProfileTable
                     defined in [RFC2662].  Each entry corresponds to
                     an ADSL alarm profile."
                 INDEX { IMPLIED adslLineAlarmConfProfileName } 
            ::= { adslAlarmConfProfileExtTable 1 }

            AdslAlarmConfProfileExtEntry ::=
                SEQUENCE {
                adslAtucThreshold15MinFailedFastR     INTEGER,
                adslAtucThreshold15MinSesL            INTEGER,
                adslAtucThreshold15MinUasL            INTEGER,
                adslAturThreshold15MinSesL            INTEGER,
                adslAturThreshold15MinUasL            INTEGER
            }

            adslAtucThreshold15MinFailedFastR   OBJECT-TYPE
                SYNTAX      INTEGER(0..900)
                UNITS       "seconds"
                MAX-ACCESS  read-create
                STATUS      current
                DESCRIPTION
                    "The first time the value of the corresponding
                     instance of adslAtucPerfCurr15MinFailedFastR reaches
                     or exceeds this value within a given 15-minute
                     performance data collection period, an
                     adslAtucFailedFastRThreshTrap  notifications will
                     be generated. The value '0' will disable the trap.
                     The default value of this object is '0'."
            ::= { adslAlarmConfProfileExtEntry 1 }

            adslAtucThreshold15MinSesL OBJECT-TYPE
                SYNTAX      INTEGER(0..900)
                UNITS       "seconds"
                MAX-ACCESS  read-create
                STATUS      current
                DESCRIPTION
                    "The first time the value of the corresponding instance
                     of adslAtucPerf15MinSesL reaches or exceeds
                     this value within a given 15-minute performance data
                     collection period, an adslAtucSesLThreshTrap
                     notifications will be generated. The value '0' will
                     disable the trap.  The default value of this object is
                     '0'."
            ::= { adslAlarmConfProfileExtEntry 2 }

            adslAtucThreshold15MinUasL OBJECT-TYPE
                SYNTAX      INTEGER(0..900)
                UNITS       "seconds"
                MAX-ACCESS  read-create
                STATUS      current
                DESCRIPTION
                    "The first time the value of the corresponding instance
                     of adslAtucPerf15MinUasL reaches or exceeds
                     this value within a given 15-minute performance data
                     collection period, an adslAtucUasLThreshTrap
                     notifications will be generated. The value '0' will
                     disable the trap.  The default value of this object is
                     '0'."
            ::= { adslAlarmConfProfileExtEntry 3 }

            adslAturThreshold15MinSesL OBJECT-TYPE
                SYNTAX      INTEGER(0..900)
                UNITS       "seconds"
                MAX-ACCESS  read-create
                STATUS      current
                DESCRIPTION
                    "The first time the value of the corresponding instance
                     of adslAturPerf15MinSesL reaches or exceeds
                     this value within a given 15-minute performance data
                     collection period, an adslAturSesLThreshTrap
                     notifications will be generated. The value '0' will
                     disable the trap.  The default value of this object is
                     '0'."
            ::= { adslAlarmConfProfileExtEntry 4 }

            adslAturThreshold15MinUasL OBJECT-TYPE
                SYNTAX      INTEGER(0..900)
                UNITS       "seconds"
                MAX-ACCESS  read-create
                STATUS      current
                DESCRIPTION
                    "The first time the value of the corresponding instance
                     of adslAturPerf15MinUasL reaches or exceeds
                     this value within a given 15-minute performance data
                     collection period, an adslAturUasLThreshTrap
                     notifications will be generated. The value '0' will
                     disable the trap.  The default value of this object is
                     '0'."
            ::= { adslAlarmConfProfileExtEntry 5 }

     -- trap definitions

      adslExtTraps OBJECT IDENTIFIER ::= { adslExtMibObjects 24 }

      adslExtAtucTraps OBJECT IDENTIFIER ::= { adslExtTraps 1 }

            adslAtucFailedFastRThreshTrap      NOTIFICATION-TYPE
                OBJECTS { adslAtucPerfCurr15MinFailedFastR }
                STATUS  current
                DESCRIPTION
                    "Failed Fast Retrains 15-minute threshold reached."
            ::= { adslExtAtucTraps 0 1 }

            adslAtucSesLThreshTrap      NOTIFICATION-TYPE
                OBJECTS { adslAtucPerfCurr15MinSesL }
                STATUS  current
                DESCRIPTION
                    "Severely errored seconds-line 15-minute threshold
                     reached."
            ::= { adslExtAtucTraps 0 2 }

            adslAtucUasLThreshTrap      NOTIFICATION-TYPE
                OBJECTS { adslAtucPerfCurr15MinUasL }
                STATUS  current
                DESCRIPTION
                    "Unavailable seconds-line 15-minute threshold reached."
            ::= { adslExtAtucTraps 0 3 }

      adslExtAturTraps OBJECT IDENTIFIER ::= { adslExtTraps 2 }

            adslAturSesLThreshTrap      NOTIFICATION-TYPE
                OBJECTS { adslAturPerfCurr15MinSesL }
                STATUS  current
                DESCRIPTION
                    "Severely errored seconds-line 15-minute threshold
                     reached."
            ::= { adslExtAturTraps 0 1 }

            adslAturUasLThreshTrap      NOTIFICATION-TYPE
                OBJECTS { adslAturPerfCurr15MinUasL }
                STATUS  current
                DESCRIPTION
                    "Unavailable seconds-line 15-minute threshold reached."
            ::= { adslExtAturTraps 0 2 }

      -- conformance information

      adslExtConformance OBJECT IDENTIFIER ::= { adslExtMIB 2 }

      adslExtGroups OBJECT IDENTIFIER ::= { adslExtConformance 1 }
      adslExtCompliances OBJECT IDENTIFIER ::= { adslExtConformance 2 }

            -- ATU-C agent compliance statements

            adslExtLineMibAtucCompliance MODULE-COMPLIANCE
                STATUS  current
                DESCRIPTION
                    "The compliance statement for SNMP entities which
                     represent ADSL ATU-C interfaces."

                MODULE  -- this module
                MANDATORY-GROUPS
                   {
                   adslExtLineGroup,
                   adslExtLineConfProfileControlGroup,
                   adslExtLineAlarmConfProfileGroup
                   }

                GROUP       adslExtAtucPhysPerfCounterGroup
                DESCRIPTION
                    "This group is optional.  Implementations which
                     require continuous ATU-C physical event counters
                     should implement this group."

                GROUP       adslExtAturPhysPerfCounterGroup
                DESCRIPTION
                    "This group is optional.  Implementations which
                     require continuous ATU-R physical event counters
                     should implement this group."

                OBJECT      adslAtucThreshold15MinFailedFastR
                MIN-ACCESS  read-write
                DESCRIPTION
                    "Read-write access is applicable only when
                     static profiles as defined in ADSL Line MIB
                     [RFC2662] are implemented."

                OBJECT      adslAtucThreshold15MinSesL
                MIN-ACCESS  read-write
                DESCRIPTION
                    "Read-write access is applicable only when
                     static profiles as defined in ADSL Line MIB
                     [RFC2662] are implemented."

                OBJECT      adslAtucThreshold15MinUasL
                MIN-ACCESS  read-write
                DESCRIPTION
                    "Read-write access is applicable only when
                     static profiles as defined in ADSL Line MIB
                     [RFC2662] are implemented."

                OBJECT      adslAturThreshold15MinSesL
                MIN-ACCESS  read-write
                DESCRIPTION
                    "Read-write access is applicable only when
                     static profiles as defined in ADSL Line MIB
                     [RFC2662] are implemented."

                OBJECT      adslAturThreshold15MinUasL
                MIN-ACCESS  read-write
                DESCRIPTION
                    "Read-write access is applicable only when
                     static profiles as defined in ADSL Line MIB
                     [RFC2662] are implemented."

                OBJECT      adslLineConfProfileDualLite
                MIN-ACCESS  read-only
                DESCRIPTION
                    "Read-write access is applicable only when
                     static profiles as defined in ADSL Line MIB
                     [RFC2662] are implemented."

            ::= { adslExtCompliances 1 }

            -- units of conformance
            adslExtLineGroup    OBJECT-GROUP
                OBJECTS {
                    adslLineConfProfileDualLite,
                    adslLineTransAtucCap,
                    adslLineTransAtucConfig,
                    adslLineTransAtucActual,
                    adslLineGlitePowerState
                   }
                STATUS     current
                DESCRIPTION
                    "A collection of objects providing extended
                    configuration information about an ADSL Line."
            ::= { adslExtGroups 1 }

            adslExtAtucPhysPerfCounterGroup OBJECT-GROUP
                OBJECTS {
                    adslAtucPerfStatFastR,
                    adslAtucPerfStatFailedFastR,
                    adslAtucPerfCurr15MinFastR,
                    adslAtucPerfCurr15MinFailedFastR,
                    adslAtucPerfCurr1DayFastR,
                    adslAtucPerfCurr1DayFailedFastR,
                    adslAtucPerfPrev1DayFastR,
                    adslAtucPerfPrev1DayFailedFastR,
                    adslAtucPerfStatSesL,
                    adslAtucPerfStatUasL,
                    adslAtucPerfCurr15MinSesL,
                    adslAtucPerfCurr15MinUasL,
                    adslAtucPerfCurr1DaySesL,
                    adslAtucPerfCurr1DayUasL,
                    adslAtucPerfPrev1DaySesL,
                    adslAtucPerfPrev1DayUasL,
                    adslAtucIntervalFastR,
                    adslAtucIntervalFailedFastR,
                    adslAtucIntervalSesL,
                    adslAtucIntervalUasL
                   }
                STATUS     current
                DESCRIPTION
                    "A collection of objects providing raw performance
                    counts on an ADSL Line (ATU-C end)."
            ::= { adslExtGroups 2 }

            adslExtAturPhysPerfCounterGroup OBJECT-GROUP
                OBJECTS {
                    adslAturPerfStatSesL,
                    adslAturPerfStatUasL,
                    adslAturPerfCurr15MinSesL,
                    adslAturPerfCurr15MinUasL,
                    adslAturPerfCurr1DaySesL,
                    adslAturPerfCurr1DayUasL,
                    adslAturPerfPrev1DaySesL,
                    adslAturPerfPrev1DayUasL,
                    adslAturIntervalSesL, adslAturIntervalUasL
                   }
                STATUS     current
                DESCRIPTION
                    "A collection of objects providing raw performance
                    counts on an ADSL Line (ATU-C end)."
            ::= { adslExtGroups 3 }

            adslExtLineConfProfileControlGroup OBJECT-GROUP
                OBJECTS {
                    adslConfProfileLineType
                   }
                STATUS     current
                DESCRIPTION
                    "A collection of objects providing profile
                    control for the ADSL system."
            ::= { adslExtGroups 4 }

            adslExtLineAlarmConfProfileGroup OBJECT-GROUP
                OBJECTS {
                       adslAtucThreshold15MinFailedFastR,
                       adslAtucThreshold15MinSesL,
                       adslAtucThreshold15MinUasL,
                       adslAturThreshold15MinSesL,
                       adslAturThreshold15MinUasL
                   }
                STATUS     current
                DESCRIPTION
                    "A collection of objects providing alarm profile
                    control for the ADSL system."
            ::= { adslExtGroups 5 }

            adslExtNotificationsGroup NOTIFICATION-GROUP
                NOTIFICATIONS {
                    adslAtucFailedFastRThreshTrap,
                    adslAtucSesLThreshTrap,
                    adslAtucUasLThreshTrap,
                    adslAturSesLThreshTrap,
                    adslAturUasLThreshTrap
                }
                STATUS        current
                DESCRIPTION
                    "The collection of ADSL extension notifications."
               ::= { adslExtGroups 6 }

END

PPP-LCP-MIB DEFINITIONS ::= BEGIN

          IMPORTS
               Counter
                    FROM RFC1155-SMI
               ifIndex, transmission
                    FROM RFC1213-MIB
               OBJECT-TYPE
                    FROM RFC-1212;

               --  PPP MIB

               ppp  OBJECT IDENTIFIER ::= { transmission 23 }

               pppLcp OBJECT IDENTIFIER ::= { ppp 1 }


               -- The individual groups within the PPP-LCP-MIB

               pppLink      OBJECT IDENTIFIER ::= { pppLcp 1 }
               pppLqr       OBJECT IDENTIFIER ::= { pppLcp 2 }
               pppTests     OBJECT IDENTIFIER ::= { pppLcp 3 }

          -- 4.1.  PPP Link Group

          --
          -- The PPP Link Group. Implementation of this
          -- group is mandatory for all PPP entities.
          --

          -- The following object reflect the values of the option
          -- parameters used in the PPP Link Control Protocol
          --   pppLinkStatusLocalMRU
          --   pppLinkStatusRemoteMRU
          --   pppLinkStatusLocalToPeerACCMap
          --   pppLinkStatusPeerToLocalACCMap
          --   pppLinkStatusLocalToRemoteProtocolCompression
          --   pppLinkStatusRemoteToLocalProtocolCompression
          --   pppLinkStatusLocalToRemoteACCompression
          --   pppLinkStatusRemoteToLocalACCompression
          --   pppLinkStatusTransmitFcsSize
          --   pppLinkStatusReceiveFcsSize
          --
          -- These values are not available until after the PPP Option
          -- negotiation has completed, which is indicated by the link
          -- reaching the open state (i.e., ifOperStatus is set to
          -- up).
          --
          -- Therefore, when ifOperStatus is not up
          -- the contents of these objects is undefined. The value
          -- returned when accessing the objects is an implementation
          -- dependent issue.

          pppLinkStatusTable   OBJECT-TYPE
               SYNTAX    SEQUENCE OF PppLinkStatusEntry
               ACCESS    not-accessible
               STATUS    mandatory
               DESCRIPTION
                         "A table containing PPP-link specific variables
                         for this PPP implementation."
               ::= { pppLink 1 }


          pppLinkStatusEntry   OBJECT-TYPE
               SYNTAX    PppLinkStatusEntry
               ACCESS    not-accessible
               STATUS    mandatory
               DESCRIPTION
                         "Management information about a particular PPP
                         Link."
               INDEX     { ifIndex }
               ::= { pppLinkStatusTable 1 }

          PppLinkStatusEntry ::= SEQUENCE {
               pppLinkStatusPhysicalIndex
                    INTEGER,
               pppLinkStatusBadAddresses
                    Counter,
               pppLinkStatusBadControls
                    Counter,
               pppLinkStatusPacketTooLongs
                    Counter,
               pppLinkStatusBadFCSs
                    Counter,
               pppLinkStatusLocalMRU
                    INTEGER,
               pppLinkStatusRemoteMRU
                    INTEGER,
               pppLinkStatusLocalToPeerACCMap
                    OCTET STRING,
               pppLinkStatusPeerToLocalACCMap
                    OCTET STRING,
               pppLinkStatusLocalToRemoteProtocolCompression
                    INTEGER,
               pppLinkStatusRemoteToLocalProtocolCompression
                    INTEGER,
               pppLinkStatusLocalToRemoteACCompression
                    INTEGER,
               pppLinkStatusRemoteToLocalACCompression
                    INTEGER,
               pppLinkStatusTransmitFcsSize
                    INTEGER,
               pppLinkStatusReceiveFcsSize
                    INTEGER
               }
          pppLinkStatusPhysicalIndex   OBJECT-TYPE
               SYNTAX    INTEGER(0..2147483647)
               ACCESS    read-only
               STATUS    mandatory
               DESCRIPTION


                         "The value of ifIndex that identifies the
                         lower-level interface over which this PPP Link
                         is operating. This interface would usually be
                         an HDLC or RS-232 type of interface. If there
                         is no lower-layer interface element, or there
                         is no ifEntry for the element, or the element
                         can not be identified, then the value of this
                         object is 0.  For example, suppose that PPP is
                         operating over a serial port. This would use
                         two entries in the ifTable. The PPP could be
                         running over `interface' number 123 and the
                         serial port could be running over `interface'
                         number 987.  Therefore, ifSpecific.123 would
                         contain the OBJECT IDENTIFIER ppp
                         pppLinkStatusPhysicalIndex.123 would contain
                         987, and ifSpecific.987 would contain the
                         OBJECT IDENTIFIER for the serial-port's media-
                         specific MIB."
               ::= { pppLinkStatusEntry 1 }

          pppLinkStatusBadAddresses   OBJECT-TYPE
               SYNTAX    Counter
               ACCESS    read-only
               STATUS    mandatory
               DESCRIPTION
                         "The number of packets received with an
                         incorrect Address Field. This counter is a
                         component of the ifInErrors variable that is
                         associated with the interface that represents
                         this PPP Link."
               REFERENCE
                         "Section 3.1, Address Field, of RFC1331."
               ::= { pppLinkStatusEntry 2 }

          pppLinkStatusBadControls   OBJECT-TYPE
               SYNTAX    Counter
               ACCESS    read-only
               STATUS    mandatory
               DESCRIPTION
                         "The number of packets received on this link
                         with an incorrect Control Field. This counter
                         is a component of the ifInErrors variable that
                         is associated with the interface that
                         represents this PPP Link."
               REFERENCE
                         "Section 3.1, Control Field, of RFC1331."


               ::= { pppLinkStatusEntry 3 }

          pppLinkStatusPacketTooLongs   OBJECT-TYPE
               SYNTAX    Counter
               ACCESS    read-only
               STATUS    mandatory
               DESCRIPTION
                         "The number of received packets that have been
                         discarded because their length exceeded the
                         MRU. This counter is a component of the
                         ifInErrors variable that is associated with the
                         interface that represents this PPP Link. NOTE,
                         packets which are longer than the MRU but which
                         are successfully received and processed are NOT
                         included in this count."
               ::= { pppLinkStatusEntry 4 }

          pppLinkStatusBadFCSs   OBJECT-TYPE
               SYNTAX    Counter
               ACCESS    read-only
               STATUS    mandatory
               DESCRIPTION
                         "The number of received packets that have been
                         discarded due to having an incorrect FCS. This
                         counter is a component of the ifInErrors
                         variable that is associated with the interface
                         that represents this PPP Link."
               ::= { pppLinkStatusEntry 5 }

          pppLinkStatusLocalMRU   OBJECT-TYPE
               SYNTAX    INTEGER(1..2147483648)
               ACCESS    read-only
               STATUS    mandatory
               DESCRIPTION
                         "The current value of the MRU for the local PPP
                         Entity. This value is the MRU that the remote
                         entity is using when sending packets to the
                         local PPP entity. The value of this object is
                         meaningful only when the link has reached the
                         open state (ifOperStatus is up)."
               ::= { pppLinkStatusEntry 6 }

          pppLinkStatusRemoteMRU   OBJECT-TYPE
               SYNTAX    INTEGER(1..2147483648)


               ACCESS    read-only
               STATUS    mandatory
               DESCRIPTION
                         "The current value of the MRU for the remote
                         PPP Entity. This value is the MRU that the
                         local entity is using when sending packets to
                         the remote PPP entity. The value of this object
                         is meaningful only when the link has reached
                         the open state (ifOperStatus is up)."
               ::= { pppLinkStatusEntry 7 }

          pppLinkStatusLocalToPeerACCMap   OBJECT-TYPE
               SYNTAX    OCTET STRING (SIZE (4))
               ACCESS    read-only
               STATUS    mandatory
               DESCRIPTION
                         "The current value of the ACC Map used for
                         sending packets from the local PPP entity to
                         the remote PPP entity. The value of this object
                         is meaningful only when the link has reached
                         the open state (ifOperStatus is up)."
               ::= { pppLinkStatusEntry 8 }

          pppLinkStatusPeerToLocalACCMap   OBJECT-TYPE
               SYNTAX    OCTET STRING (SIZE (4))
               ACCESS    read-only
               STATUS    mandatory
               DESCRIPTION
                         "The ACC Map used by the remote PPP entity when
                         transmitting packets to the local PPP entity.
                         The value of this object is meaningful only
                         when the link has reached the open state
                         (ifOperStatus is up)."
               ::= { pppLinkStatusEntry 9 }

          pppLinkStatusLocalToRemoteProtocolCompression
               OBJECT-TYPE
               SYNTAX    INTEGER {
                         enabled(1),
                         disabled(2)
                    }
               ACCESS    read-only
               STATUS    mandatory
               DESCRIPTION
                         "Indicates whether the local PPP entity will


                         use Protocol Compression when transmitting
                         packets to the remote PPP entity. The value of
                         this object is meaningful only when the link
                         has reached the open state (ifOperStatus is
                         up)."
               ::= { pppLinkStatusEntry 10 }

          pppLinkStatusRemoteToLocalProtocolCompression
               OBJECT-TYPE
               SYNTAX    INTEGER {
                         enabled(1),
                         disabled(2)
                    }
               ACCESS    read-only
               STATUS    mandatory
               DESCRIPTION
                         "Indicates whether the remote PPP entity will
                         use Protocol Compression when transmitting
                         packets to the local PPP entity. The value of
                         this object is meaningful only when the link
                         has reached the open state (ifOperStatus is
                         up)."
               ::= { pppLinkStatusEntry 11 }

          pppLinkStatusLocalToRemoteACCompression   OBJECT-TYPE
               SYNTAX    INTEGER {
                         enabled(1),
                         disabled(2)
                    }
               ACCESS    read-only
               STATUS    mandatory
               DESCRIPTION
                         "Indicates whether the local PPP entity will
                         use Address and Control Compression when
                         transmitting packets to the remote PPP entity.
                         The value of this object is meaningful only
                         when the link has reached the open state
                         (ifOperStatus is up)."
               ::= { pppLinkStatusEntry 12 }

          pppLinkStatusRemoteToLocalACCompression   OBJECT-TYPE
               SYNTAX    INTEGER {
                         enabled(1),
                         disabled(2)
                    }


               ACCESS    read-only
               STATUS    mandatory
               DESCRIPTION
                         "Indicates whether the remote PPP entity will
                         use Address and Control Compression when
                         transmitting packets to the local PPP entity.
                         The value of this object is meaningful only
                         when the link has reached the open state
                         (ifOperStatus is up)."
               ::= { pppLinkStatusEntry 13 }

          pppLinkStatusTransmitFcsSize   OBJECT-TYPE
               SYNTAX    INTEGER (0..128)
               ACCESS    read-only
               STATUS    mandatory
               DESCRIPTION
                         "The size of the Frame Check Sequence (FCS) in
                         bits that the local node will generate when
                         sending packets to the remote node. The value
                         of this object is meaningful only when the link
                         has reached the open state (ifOperStatus is
                         up)."
               ::= { pppLinkStatusEntry 14 }

          pppLinkStatusReceiveFcsSize   OBJECT-TYPE
               SYNTAX    INTEGER (0..128)
               ACCESS    read-only
               STATUS    mandatory
               DESCRIPTION
                         "The size of the Frame Check Sequence (FCS) in
                         bits that the remote node will generate when
                         sending packets to the local node. The value of
                         this object is meaningful only when the link
                         has reached the open state (ifOperStatus is
                         up)."
               ::= { pppLinkStatusEntry 15 }

          pppLinkConfigTable   OBJECT-TYPE
               SYNTAX    SEQUENCE OF PppLinkConfigEntry
               ACCESS    not-accessible
               STATUS    mandatory
               DESCRIPTION
                         "A table containing the LCP configuration
                         parameters for this PPP Link. These variables
                         represent the initial configuration of the PPP


                         Link. The actual values of the parameters may
                         be changed when the link is brought up via the
                         LCP options negotiation mechanism."
               ::= { pppLink 2 }

          pppLinkConfigEntry   OBJECT-TYPE
               SYNTAX    PppLinkConfigEntry
               ACCESS    not-accessible
               STATUS    mandatory
               DESCRIPTION
                         "Configuration information about a particular
                         PPP Link."
               INDEX     { ifIndex }
               ::= { pppLinkConfigTable 1 }

          PppLinkConfigEntry ::= SEQUENCE {
               pppLinkConfigInitialMRU
                    INTEGER,
               pppLinkConfigReceiveACCMap
                    OCTET STRING,
               pppLinkConfigTransmitACCMap
                    OCTET STRING,
               pppLinkConfigMagicNumber
                    INTEGER,
               pppLinkConfigFcsSize
                    INTEGER
               }

          pppLinkConfigInitialMRU   OBJECT-TYPE
               SYNTAX    INTEGER(0..2147483647)
               ACCESS    read-write
               STATUS    mandatory
               DESCRIPTION
                         "The initial Maximum Receive Unit (MRU) that
                         the local PPP entity will advertise to the
                         remote entity. If the value of this variable is
                         0 then the local PPP entity will not advertise
                         any MRU to the remote entity and the default
                         MRU will be assumed. Changing this object will
                         have effect when the link is next restarted."
               REFERENCE
                         "Section 7.2, Maximum Receive Unit of RFC1331."
               DEFVAL    { 1500 }
               ::= { pppLinkConfigEntry 1 }


          pppLinkConfigReceiveACCMap   OBJECT-TYPE
               SYNTAX    OCTET STRING (SIZE (4))
               ACCESS    read-write
               STATUS    mandatory
               DESCRIPTION
                         "The Asynchronous-Control-Character-Map (ACC)
                         that the local PPP entity requires for use on
                         its receive side. In effect, this is the ACC
                         Map that is required in order to ensure that
                         the local modem will successfully receive all
                         characters. The actual ACC map used on the
                         receive side of the link will be a combination
                         of the local node's pppLinkConfigReceiveACCMap
                         and the remote node's
                         pppLinkConfigTransmitACCMap. Changing this
                         object will have effect when the link is next
                         restarted."
               REFERENCE
                         "Section 7.3, page 4, Async-Control-Character-
                         Map of RFC1331."
               DEFVAL    { 'ffffffff'h }
               ::= { pppLinkConfigEntry 2 }

          pppLinkConfigTransmitACCMap   OBJECT-TYPE
               SYNTAX    OCTET STRING (SIZE (4))
               ACCESS    read-write
               STATUS    mandatory
               DESCRIPTION
                         "The Asynchronous-Control-Character-Map (ACC)
                         that the local PPP entity requires for use on
                         its transmit side. In effect, this is the ACC
                         Map that is required in order to ensure that
                         all characters can be successfully transmitted
                         through the local modem.  The actual ACC map
                         used on the transmit side of the link will be a
                         combination of the local node's
                         pppLinkConfigTransmitACCMap and the remote
                         node's pppLinkConfigReceiveACCMap. Changing
                         this object will have effect when the link is
                         next restarted."
               REFERENCE
                         "Section 7.3, page 4, Async-Control-Character-
                         Map of RFC1331."
               DEFVAL    { 'ffffffff'h }
               ::= { pppLinkConfigEntry 3 }


          pppLinkConfigMagicNumber   OBJECT-TYPE
               SYNTAX    INTEGER {false (1), true (2)}
               ACCESS    read-write
               STATUS    mandatory
               DESCRIPTION
                         "If true(2) then the local node will attempt to
                         perform Magic Number negotiation with the
                         remote node. If false(1) then this negotiation
                         is not performed. In any event, the local node
                         will comply with any magic number negotiations
                         attempted by the remote node, per the PPP
                         specification. Changing this object will have
                         effect when the link is next restarted."
               REFERENCE
                         "Section 7.6, Magic Number, of RFC1331."
               DEFVAL    { false }
               ::= { pppLinkConfigEntry 4 }

          pppLinkConfigFcsSize   OBJECT-TYPE
               SYNTAX    INTEGER (0..128)
               ACCESS    read-write
               STATUS    mandatory
               DESCRIPTION
                         "The size of the FCS, in bits, the local node
                         will attempt to negotiate for use with the
                         remote node. Regardless of the value of this
                         object, the local node will comply with any FCS
                         size negotiations initiated by the remote node,
                         per the PPP specification. Changing this object
                         will have effect when the link is next
                         restarted."
               DEFVAL    { 16 }
               ::= { pppLinkConfigEntry 5 }

          -- 4.2.  PPP LQR Group

               --
               -- The PPP LQR Group.
               -- Implementation of this group is mandatory for all
               -- PPP implementations that implement LQR.
               --

          pppLqrTable   OBJECT-TYPE
               SYNTAX    SEQUENCE OF PppLqrEntry
               ACCESS    not-accessible


               STATUS    mandatory
               DESCRIPTION
                         "Table containing the LQR parameters and
                         statistics for the local PPP entity."
               ::= { pppLqr 1 }

          pppLqrEntry   OBJECT-TYPE
               SYNTAX    PppLqrEntry
               ACCESS    not-accessible
               STATUS    mandatory
               DESCRIPTION
                         "LQR information for a particular PPP link. A
                         PPP link will have an entry in this table if
                         and only if LQR Quality Monitoring has been
                         successfully negotiated for said link."
               INDEX     { ifIndex }
               ::= { pppLqrTable 1 }

          PppLqrEntry ::= SEQUENCE {
               pppLqrQuality
                    INTEGER,
               pppLqrInGoodOctets
                    Counter,
               pppLqrLocalPeriod
                    INTEGER,
               pppLqrRemotePeriod
                    INTEGER,
               pppLqrOutLQRs
                    Counter,
               pppLqrInLQRs
                    Counter
          }

          pppLqrQuality   OBJECT-TYPE
               SYNTAX    INTEGER {
                         good(1),
                         bad(2),
                         not-determined(3)
                    }
               ACCESS    read-only
               STATUS    mandatory
               DESCRIPTION
                         "The current quality of the link as declared by
                         the local PPP entity's Link-Quality Management
                         modules. No effort is made to define good or
                         bad, nor the policy used to determine it. The


                         not-determined value indicates that the entity
                         does not actually evaluate the link's quality.
                         This value is used to disambiguate the
                         `determined to be good' case from the `no
                         determination made and presumed to be good'
                         case."
               ::= { pppLqrEntry 1 }

          pppLqrInGoodOctets   OBJECT-TYPE
               SYNTAX    Counter
               ACCESS    read-only
               STATUS    mandatory
               DESCRIPTION
                         "The LQR InGoodOctets counter for this link."
               REFERENCE
                         "Section 2.2, Counters, of RFC1333."
               ::= { pppLqrEntry 2 }

          pppLqrLocalPeriod   OBJECT-TYPE
               SYNTAX    INTEGER(1..2147483648)
               ACCESS    read-only
               STATUS    mandatory
               DESCRIPTION
                         "The LQR reporting period, in hundredths of a
                         second that is in effect for the local PPP
                         entity."
               REFERENCE
                         "Section 2.5, Configuration Option Format, of
                         RFC1333."
               ::= { pppLqrEntry 3 }

          pppLqrRemotePeriod   OBJECT-TYPE
               SYNTAX    INTEGER(1..2147483648)
               ACCESS    read-only
               STATUS    mandatory
               DESCRIPTION
                         "The LQR reporting period, in hundredths of a
                         second, that is in effect for the remote PPP
                         entity."
               REFERENCE
                         "Section 2.5, Configuration Option Format, of
                         RFC1333."
               ::= { pppLqrEntry 4 }


          pppLqrOutLQRs   OBJECT-TYPE
               SYNTAX    Counter
               ACCESS    read-only
               STATUS    mandatory
               DESCRIPTION
                         "The value of the OutLQRs counter on the local
                         node for the link identified by ifIndex."
               REFERENCE
                         "Section 2.2, Counters, of RFC1333."
               ::= { pppLqrEntry 5 }

          pppLqrInLQRs   OBJECT-TYPE
               SYNTAX    Counter
               ACCESS    read-only
               STATUS    mandatory
               DESCRIPTION
                         "The value of the InLQRs counter on the local
                         node for the link identified by ifIndex."
               REFERENCE
                         "Section 2.2, Counters, of RFC1333."
               ::= { pppLqrEntry 6 }

          --
          -- The PPP LQR Configuration table.
          --

          pppLqrConfigTable   OBJECT-TYPE
               SYNTAX    SEQUENCE OF PppLqrConfigEntry
               ACCESS    not-accessible
               STATUS    mandatory
               DESCRIPTION
                         "Table containing the LQR Configuration
                         parameters for the local PPP entity."
               ::= { pppLqr 2 }

          pppLqrConfigEntry   OBJECT-TYPE
               SYNTAX    PppLqrConfigEntry
               ACCESS    not-accessible
               STATUS    mandatory
               DESCRIPTION
                         "LQR configuration information for a particular
                         PPP link."
               INDEX     { ifIndex }
               ::= { pppLqrConfigTable 1 }


          PppLqrConfigEntry ::= SEQUENCE {
               pppLqrConfigPeriod
                    INTEGER,
               pppLqrConfigStatus
                    INTEGER
          }

          pppLqrConfigPeriod   OBJECT-TYPE
               SYNTAX    INTEGER(0..2147483647)
               ACCESS    read-write
               STATUS    mandatory
               DESCRIPTION
                         "The LQR Reporting Period that the local PPP
                         entity will attempt to negotiate with the
                         remote entity, in units of hundredths of a
                         second. Changing this object will have effect
                         when the link is next restarted."
               REFERENCE
                         "Section 2.5, Configuration Option Format, of
                         RFC1333."
               DEFVAL    { 0 }
               ::= { pppLqrConfigEntry 1 }

          pppLqrConfigStatus   OBJECT-TYPE
               SYNTAX    INTEGER {disabled (1), enabled (2)}
               ACCESS    read-write
               STATUS    mandatory
               DESCRIPTION
                         "If enabled(2) then the local node will attempt
                         to perform LQR negotiation with the remote
                         node. If disabled(1) then this negotiation is
                         not performed. In any event, the local node
                         will comply with any magic number negotiations
                         attempted by the remote node, per the PPP
                         specification. Changing this object will have
                         effect when the link is next restarted.
                         Setting this object to the value disabled(1)
                         has the effect of invalidating the
                         corresponding entry in the pppLqrConfigTable
                         object. It is an implementation-specific matter
                         as to whether the agent removes an invalidated
                         entry from the table. Accordingly, management
                         stations must be prepared to receive tabular
                         information from agents that corresponds to
                         entries not currently in use."
               REFERENCE
                         "Section 7.6, Magic Number, of RFC1331."


               DEFVAL    { enabled }
               ::= { pppLqrConfigEntry 2 }

          -- 4.3.  PPP LQR Extensions Group

          --
          -- The PPP LQR Extensions Group.
          -- Implementation of this group is optional.
          --
          -- The intent of this group is to allow external
          -- implementation of the policy mechanisms that
          -- are used to declare a link to be "bad" or not.
          --
          -- It is not practical to examine the MIB objects
          -- which are used to generate LQR packets since
          -- LQR policies tend to require synchronization of
          -- the values of all data used to determine Link
          -- Quality; i.e. the values of the relevant counters
          -- must all be taken at the same instant in time.
          --

          pppLqrExtnsTable   OBJECT-TYPE
               SYNTAX    SEQUENCE OF PppLqrExtnsEntry
               ACCESS    not-accessible
               STATUS    mandatory
               DESCRIPTION
                         "Table containing additional LQR information
                         for the local PPP entity."
               ::= { pppLqr 3 }

          pppLqrExtnsEntry   OBJECT-TYPE
               SYNTAX    PppLqrExtnsEntry
               ACCESS    not-accessible
               STATUS    mandatory
               DESCRIPTION
                         "Extended LQR information for a particular PPP
                         link. Assuming that this group has been
                         implemented, a PPP link will have an entry in
                         this table if and only if LQR Quality
                         Monitoring has been successfully negotiated for
                         said link."
               INDEX     { ifIndex }
               ::= { pppLqrExtnsTable 1 }

          PppLqrExtnsEntry ::= SEQUENCE {


               pppLqrExtnsLastReceivedLqrPacket
                    OCTET STRING(SIZE(68))
          }

          pppLqrExtnsLastReceivedLqrPacket   OBJECT-TYPE
               SYNTAX    OCTET STRING(SIZE(68))
               ACCESS    read-only
               STATUS    mandatory
               DESCRIPTION
                         "This object contains the most recently
                         received LQR packet.  The format of the packet
                         is as described in the LQM Protocol
                         specificiation. All fields of the packet,
                         including the `save' fields, are stored in this
                         object.

                         The LQR packet is stored in network byte order.
                         The LAP-B and PPP headers are not stored in
                         this object; the first four octets of this
                         variable contain the Magic-Number field, the
                         second four octets contain the LastOutLQRs
                         field and so on. The last four octets of this
                         object contain the SaveInOctets field of the
                         LQR packet."
               REFERENCE
                         "Section 2.6, Packet Format, of RFC1333"
               ::= { pppLqrExtnsEntry 1 }

          -- 4.4.  PPP Tests

          -- The extensions to the interface table in RFC1229 define a
          -- table through which the network manager can instruct the
          -- managed object to perform various tests of the interface. This
          -- is the ifExtnsTestTable.

          -- The PPP MIB defines two such tests.

          -- 4.4.1.  PPP Echo Test

          -- The PPP Echo Test is defined as

               pppEchoTest    OBJECT IDENTIFIER ::= { pppTests 1 }

          -- Invoking this test causes a PPP Echo Packet to be sent on the
          -- line. ifExtnsTestResult returns success(2) if the echo
          -- response came back properly. It returns failed(7) if the
          -- response did not properly return. The definition of "proper"


          -- in this context is left to the discretion of the implementor.

          -- 4.4.2.  PPP Discard Test

          -- The PPP Discard Test is defined as

               pppDiscardTest OBJECT IDENTIFIER ::= { pppTests 2 }

          -- Invoking this test causes a PPP Discard Packet to be sent on
          -- the line. ifExtnsTestResult returns success(2) if the discard
          -- packet was successfully transmitted and failed(7) if an error
          -- was detected on transmission. The definition of "transmission
          -- error" in this context is left to the discretion of the
          -- implementor.

END

BRIDGE-MIB DEFINITIONS ::= BEGIN

IMPORTS
           Counter, TimeTicks
                   FROM RFC1155-SMI
           mib-2
                   FROM RFC1213-MIB
           OBJECT-TYPE
                   FROM RFC-1212
           TRAP-TYPE
                   FROM RFC-1215;

-- All representations of MAC addresses in this MIB Module
-- use, as a textual convention (i.e. this convention does
-- not affect their encoding), the data type:

MacAddress ::= OCTET STRING (SIZE (6))    -- a 6 octet address
                                          -- in the
                                          -- "canonical"
                                          -- order
-- defined by IEEE 802.1a, i.e., as if it were transmitted
-- least significant bit first, even though 802.5 (in
-- contrast to other n802.x protocols) requires MAC
-- addresses to be transmitted most significant bit first.
--
-- 16-bit addresses, if needed, are represented by setting
-- their upper 4 octets to all 0's, i.e., AAFF would be
-- represented as 00000000AAFF.


-- Similarly, all representations of Bridge-Id in this MIB
-- Module use, as a textual convention (i.e. this
-- convention does not affect their encoding), the data
-- type:

BridgeId ::= OCTET STRING (SIZE (8))   -- the
                                       -- Bridge-Identifier
                                       -- as used in the
                                       -- Spanning Tree
-- Protocol to uniquely identify a bridge.  Its first two
-- octets (in network byte order) contain a priority
-- value and its last 6 octets contain the MAC address
-- used to refer to a bridge in a unique fashion
-- (typically, the numerically smallest MAC address
-- of all ports on the bridge).

-- Several objects in this MIB module represent values of
-- timers used by the Spanning Tree Protocol.  In this
-- MIB, these timers have values in units of hundreths of
-- a second (i.e. 1/100 secs).
-- These timers, when stored in a Spanning Tree Protocol's
-- BPDU, are in units of 1/256 seconds.  Note, however,
-- that 802.1D-1990 specifies a settable granularity of
-- no more than 1 second for these timers.  To avoid
-- ambiguity, a data type is defined here as a textual
-- convention and all representation of these timers
-- in this MIB module are defined using this data type.  An
-- algorithm is also defined for converting between the
-- different units, to ensure a timer's value is not
-- distorted by multiple conversions.
-- The data type is:

Timeout ::= INTEGER -- a STP timer in units of 1/100 seconds

-- To convert a Timeout value into a value in units of
-- 1/256 seconds, the following algorithm should be used:
--
--      b  = floor( (n * 256) / 100)
--
-- where:
--      floor   =  quotient [ignore remainder]
--      n is the value in 1/100 second units
--      b is the value in 1/256 second units
--
-- To convert the value from 1/256 second units back to
-- 1/100 seconds, the following algorithm should be used:
--
--      n = ceiling( (b * 100) / 256)
--
-- where:
--      ceiling =  quotient [if remainder is 0], or
--                 quotient + 1 [if remainder is non-zero]
--      n is the value in 1/100 second units
--      b is the value in 1/256 second units
--
-- Note: it is important that the arithmetic operations are
-- done in the order specified (i.e., multiply first, divide
-- second).


   dot1dBridge   OBJECT IDENTIFIER ::= { mib-2 17 }



-- groups in the Bridge MIB

dot1dBase     OBJECT IDENTIFIER ::= { dot1dBridge 1 }

dot1dStp      OBJECT IDENTIFIER ::= { dot1dBridge 2 }

dot1dSr       OBJECT IDENTIFIER ::= { dot1dBridge 3 }
-- separately documented

dot1dTp       OBJECT IDENTIFIER ::= { dot1dBridge 4 }

dot1dStatic   OBJECT IDENTIFIER ::= { dot1dBridge 5 }


-- the dot1dBase group

-- Implementation of the dot1dBase group is mandatory for all
-- bridges.

dot1dBaseBridgeAddress OBJECT-TYPE
    SYNTAX  MacAddress
    ACCESS  read-only
    STATUS  mandatory
    DESCRIPTION
            "The MAC address used by this bridge when it must
            be referred to in a unique fashion.   It is
            recommended that this be the numerically smallest
            MAC address of all ports that belong to this
            bridge.  However it is only required to be unique.
            When concatenated with dot1dStpPriority a unique
            BridgeIdentifier is formed which is used in the
            Spanning Tree Protocol."
    REFERENCE
            "IEEE 802.1D-1990: Sections 6.4.1.1.3 and 3.12.5"
    ::= { dot1dBase 1 }

dot1dBaseNumPorts OBJECT-TYPE
    SYNTAX  INTEGER
    ACCESS  read-only
    STATUS  mandatory
    DESCRIPTION
            "The number of ports controlled by this bridging
            entity."
    REFERENCE
            "IEEE 802.1D-1990: Section 6.4.1.1.3"
    ::= { dot1dBase 2 }

dot1dBaseType OBJECT-TYPE
    SYNTAX  INTEGER {
                unknown(1),
                transparent-only(2),
                sourceroute-only(3),
                srt(4)
            }
    ACCESS  read-only
    STATUS  mandatory
    DESCRIPTION
            "Indicates what type of bridging this bridge can
            perform.  If a bridge is actually performing a
            certain type of bridging this will be indicated by
            entries in the port table for the given type."
    ::= { dot1dBase 3 }

-- The Generic Bridge Port Table

dot1dBasePortTable OBJECT-TYPE
    SYNTAX  SEQUENCE OF Dot1dBasePortEntry
    ACCESS  not-accessible
    STATUS  mandatory
    DESCRIPTION
            "A table that contains generic information about
            every port that is associated with this bridge.
            Transparent, source-route, and srt ports are
            included."
    ::= { dot1dBase 4 }

dot1dBasePortEntry OBJECT-TYPE
    SYNTAX  Dot1dBasePortEntry
    ACCESS  not-accessible
    STATUS  mandatory
    DESCRIPTION
            "A list of information for each port of the
            bridge."
    REFERENCE
            "IEEE 802.1D-1990: Section 6.4.2, 6.6.1"
    INDEX  { dot1dBasePort }
    ::= { dot1dBasePortTable 1 }


Dot1dBasePortEntry ::=
    SEQUENCE {
        dot1dBasePort
            INTEGER,
        dot1dBasePortIfIndex
            INTEGER,
        dot1dBasePortCircuit
            OBJECT IDENTIFIER,
        dot1dBasePortDelayExceededDiscards
            Counter,
        dot1dBasePortMtuExceededDiscards
            Counter
    }

dot1dBasePort OBJECT-TYPE
    SYNTAX  INTEGER (1..65535)
    ACCESS  read-only
    STATUS  mandatory
    DESCRIPTION
            "The port number of the port for which this entry
            contains bridge management information."
    ::= { dot1dBasePortEntry 1 }

dot1dBasePortIfIndex OBJECT-TYPE
    SYNTAX  INTEGER
    ACCESS  read-only
    STATUS  mandatory
    DESCRIPTION
            "The value of the instance of the ifIndex object,
            defined in MIB-II, for the interface corresponding
            to this port."
    ::= { dot1dBasePortEntry 2 }

dot1dBasePortCircuit OBJECT-TYPE
    SYNTAX  OBJECT IDENTIFIER
    ACCESS  read-only
    STATUS  mandatory
    DESCRIPTION
            "For a port which (potentially) has the same value
            of dot1dBasePortIfIndex as another port on the
            same bridge, this object contains the name of an
            object instance unique to this port.  For example,
            in the case where multiple ports correspond one-
            to-one with multiple X.25 virtual circuits, this
            value might identify an (e.g., the first) object
            instance associated with the X.25 virtual circuit
            corresponding to this port.

            For a port which has a unique value of
            dot1dBasePortIfIndex, this object can have the
            value { 0 0 }."
    ::= { dot1dBasePortEntry 3 }

dot1dBasePortDelayExceededDiscards OBJECT-TYPE
    SYNTAX  Counter
    ACCESS  read-only
    STATUS  mandatory
    DESCRIPTION
            "The number of frames discarded by this port due
            to excessive transit delay through the bridge.  It
            is incremented by both transparent and source
            route bridges."
    REFERENCE
             "IEEE 802.1D-1990: Section 6.6.1.1.3"
    ::= { dot1dBasePortEntry 4 }

dot1dBasePortMtuExceededDiscards OBJECT-TYPE
    SYNTAX  Counter
    ACCESS  read-only
    STATUS  mandatory
    DESCRIPTION
            "The number of frames discarded by this port due
            to an excessive size.  It is incremented by both
            transparent and source route bridges."
    REFERENCE
            "IEEE 802.1D-1990: Section 6.6.1.1.3"
    ::= { dot1dBasePortEntry 5 }


-- the dot1dStp group

-- Implementation of the dot1dStp group is optional.  It is
-- implemented by those bridges that support the Spanning Tree
-- Protocol.


dot1dStpProtocolSpecification OBJECT-TYPE
    SYNTAX  INTEGER {
                unknown(1),
                decLb100(2),
                ieee8021d(3)
            }
    ACCESS  read-only
    STATUS  mandatory
    DESCRIPTION
            "An indication of what version of the Spanning
            Tree Protocol is being run.  The value
            'decLb100(2)' indicates the DEC LANbridge 100
            Spanning Tree protocol.  IEEE 802.1d
            implementations will return 'ieee8021d(3)'.  If
            future versions of the IEEE Spanning Tree Protocol
            are released that are incompatible with the
            current version a new value will be defined."
    ::= { dot1dStp 1 }

dot1dStpPriority OBJECT-TYPE
    SYNTAX  INTEGER (0..65535)
    ACCESS  read-write
    STATUS  mandatory
    DESCRIPTION
            "The value of the write-able portion of the Bridge
            ID, i.e., the first two octets of the (8 octet
            long) Bridge ID.  The other (last) 6 octets of the
            Bridge ID are given by the value of
            dot1dBaseBridgeAddress."
    REFERENCE
            "IEEE 802.1D-1990: Section 4.5.3.7"
    ::= { dot1dStp 2 }

dot1dStpTimeSinceTopologyChange OBJECT-TYPE
    SYNTAX  TimeTicks
    ACCESS  read-only
    STATUS  mandatory
    DESCRIPTION
            "The time (in hundredths of a second) since the
            last time a topology change was detected by the
            bridge entity."
    REFERENCE
            "IEEE 802.1D-1990: Section 6.8.1.1.3"
    ::= { dot1dStp 3 }

dot1dStpTopChanges OBJECT-TYPE
    SYNTAX  Counter
    ACCESS  read-only
    STATUS  mandatory
    DESCRIPTION
            "The total number of topology changes detected by
            this bridge since the management entity was last
            reset or initialized."
    REFERENCE
            "IEEE 802.1D-1990: Section 6.8.1.1.3"
    ::= { dot1dStp 4 }

dot1dStpDesignatedRoot OBJECT-TYPE
    SYNTAX  BridgeId
    ACCESS  read-only
    STATUS  mandatory
    DESCRIPTION
            "The bridge identifier of the root of the spanning
            tree as determined by the Spanning Tree Protocol
            as executed by this node.  This value is used as
            the Root Identifier parameter in all Configuration
            Bridge PDUs originated by this node."
    REFERENCE
            "IEEE 802.1D-1990: Section 4.5.3.1"
    ::= { dot1dStp 5 }

dot1dStpRootCost OBJECT-TYPE
    SYNTAX  INTEGER
    ACCESS  read-only
    STATUS  mandatory
    DESCRIPTION
            "The cost of the path to the root as seen from
            this bridge."
    REFERENCE
            "IEEE 802.1D-1990: Section 4.5.3.2"
    ::= { dot1dStp 6 }

dot1dStpRootPort OBJECT-TYPE
    SYNTAX  INTEGER
    ACCESS  read-only
    STATUS  mandatory
    DESCRIPTION
            "The port number of the port which offers the
            lowest cost path from this bridge to the root
            bridge."
    REFERENCE
            "IEEE 802.1D-1990: Section 4.5.3.3"
    ::= { dot1dStp 7 }

dot1dStpMaxAge OBJECT-TYPE
    SYNTAX  Timeout
    ACCESS  read-only
    STATUS  mandatory
    DESCRIPTION
            "The maximum age of Spanning Tree Protocol
            information learned from the network on any port
            before it is discarded, in units of hundredths of
            a second.  This is the actual value that this
            bridge is currently using."
    REFERENCE
            "IEEE 802.1D-1990: Section 4.5.3.4"
    ::= { dot1dStp 8 }

dot1dStpHelloTime OBJECT-TYPE
    SYNTAX  Timeout
    ACCESS  read-only
    STATUS  mandatory
    DESCRIPTION
            "The amount of time between the transmission of
            Configuration bridge PDUs by this node on any port
            when it is the root of the spanning tree or trying
            to become so, in units of hundredths of a second.
            This is the actual value that this bridge is
            currently using."
    REFERENCE
            "IEEE 802.1D-1990: Section 4.5.3.5"
    ::= { dot1dStp 9 }

dot1dStpHoldTime OBJECT-TYPE
    SYNTAX  INTEGER
    ACCESS  read-only
    STATUS  mandatory
    DESCRIPTION
            "This time value determines the interval length
            during which no more than two Configuration bridge
            PDUs shall be transmitted by this node, in units
            of hundredths of a second."
    REFERENCE
            "IEEE 802.1D-1990: Section 4.5.3.14"
    ::= { dot1dStp 10 }

dot1dStpForwardDelay OBJECT-TYPE
    SYNTAX  Timeout
    ACCESS  read-only
    STATUS  mandatory
    DESCRIPTION
            "This time value, measured in units of hundredths
            of a second, controls how fast a port changes its
            spanning state when moving towards the Forwarding
            state.  The value determines how long the port
            stays in each of the Listening and Learning
            states, which precede the Forwarding state.  This
            value is also used, when a topology change has
            been detected and is underway, to age all dynamic
            entries in the Forwarding Database.  [Note that
            this value is the one that this bridge is
            currently using, in contrast to
            dot1dStpBridgeForwardDelay which is the value that
            this bridge and all others would start using
            if/when this bridge were to become the root.]"
    REFERENCE
            "IEEE 802.1D-1990: Section 4.5.3.6"
    ::= { dot1dStp 11 }

dot1dStpBridgeMaxAge OBJECT-TYPE
    SYNTAX  Timeout (600..4000)
    ACCESS  read-write
    STATUS  mandatory
    DESCRIPTION
            "The value that all bridges use for MaxAge when
            this bridge is acting as the root.  Note that
            802.1D-1990 specifies that the range for this
            parameter is related to the value of
            dot1dStpBridgeHelloTime. The granularity of this
            timer is specified by 802.1D-1990 to be 1 second.
            An agent may return a badValue error if a set is
            attempted to a value which is not a whole number
            of seconds."
    REFERENCE
            "IEEE 802.1D-1990: Section 4.5.3.8"
    ::= { dot1dStp 12 }

dot1dStpBridgeHelloTime OBJECT-TYPE
    SYNTAX  Timeout (100..1000)
    ACCESS  read-write
    STATUS  mandatory
    DESCRIPTION
            "The value that all bridges use for HelloTime when
            this bridge is acting as the root.  The
            granularity of this timer is specified by 802.1D-
            1990 to be 1 second.  An agent may return a
            badValue error if a set is attempted to a value
            which is not a whole number of seconds."
    REFERENCE
            "IEEE 802.1D-1990: Section 4.5.3.9"
    ::= { dot1dStp 13 }

dot1dStpBridgeForwardDelay OBJECT-TYPE
    SYNTAX  Timeout (400..3000)
    ACCESS  read-write
    STATUS  mandatory
    DESCRIPTION
            "The value that all bridges use for ForwardDelay
            when this bridge is acting as the root.  Note that
            802.1D-1990 specifies that the range for this
            parameter is related to the value of
            dot1dStpBridgeMaxAge.  The granularity of this
            timer is specified by 802.1D-1990 to be 1 second.
            An agent may return a badValue error if a set is
            attempted to a value which is not a whole number
            of seconds."
    REFERENCE
            "IEEE 802.1D-1990: Section 4.5.3.10"
    ::= { dot1dStp 14 }
-- The Spanning Tree Port Table

dot1dStpPortTable OBJECT-TYPE
    SYNTAX  SEQUENCE OF Dot1dStpPortEntry
    ACCESS  not-accessible
    STATUS  mandatory
    DESCRIPTION
            "A table that contains port-specific information
            for the Spanning Tree Protocol."
    ::= { dot1dStp 15 }

dot1dStpPortEntry OBJECT-TYPE
    SYNTAX  Dot1dStpPortEntry
    ACCESS  not-accessible
    STATUS  mandatory
    DESCRIPTION
            "A list of information maintained by every port
            about the Spanning Tree Protocol state for that
            port."
    INDEX   { dot1dStpPort }
    ::= { dot1dStpPortTable 1 }

Dot1dStpPortEntry ::=
    SEQUENCE {
        dot1dStpPort
            INTEGER,
        dot1dStpPortPriority
            INTEGER,
        dot1dStpPortState
            INTEGER,
        dot1dStpPortEnable
            INTEGER,
        dot1dStpPortPathCost
            INTEGER,
        dot1dStpPortDesignatedRoot
            BridgeId,
        dot1dStpPortDesignatedCost
            INTEGER,
        dot1dStpPortDesignatedBridge
            BridgeId,
        dot1dStpPortDesignatedPort
            OCTET STRING,
        dot1dStpPortForwardTransitions
            Counter
    }

dot1dStpPort OBJECT-TYPE
    SYNTAX  INTEGER (1..65535)
    ACCESS  read-only
    STATUS  mandatory
    DESCRIPTION
            "The port number of the port for which this entry
            contains Spanning Tree Protocol management
            information."
    REFERENCE
            "IEEE 802.1D-1990: Section 6.8.2.1.2"
    ::= { dot1dStpPortEntry 1 }

dot1dStpPortPriority OBJECT-TYPE
    SYNTAX  INTEGER (0..255)
    ACCESS  read-write
    STATUS  mandatory
    DESCRIPTION
            "The value of the priority field which is
            contained in the first (in network byte order)
            octet of the (2 octet long) Port ID.  The other
            octet of the Port ID is given by the value of
            dot1dStpPort."
    REFERENCE
            "IEEE 802.1D-1990: Section 4.5.5.1"
    ::= { dot1dStpPortEntry 2 }

dot1dStpPortState OBJECT-TYPE
    SYNTAX  INTEGER {
                disabled(1),
                blocking(2),
                listening(3),
                learning(4),
                forwarding(5),
                broken(6)
            }
    ACCESS  read-only
    STATUS  mandatory
    DESCRIPTION
            "The port's current state as defined by
            application of the Spanning Tree Protocol.  This
            state controls what action a port takes on
            reception of a frame.  If the bridge has detected
            a port that is malfunctioning it will place that
            port into the broken(6) state.  For ports which
            are disabled (see dot1dStpPortEnable), this object
            will have a value of disabled(1)."
    REFERENCE
            "IEEE 802.1D-1990: Section 4.5.5.2"
    ::= { dot1dStpPortEntry 3 }

dot1dStpPortEnable OBJECT-TYPE
    SYNTAX  INTEGER {
                enabled(1),
                disabled(2)
            }
    ACCESS  read-write
    STATUS  mandatory
    DESCRIPTION
            "The enabled/disabled status of the port."
    REFERENCE
            "IEEE 802.1D-1990: Section 4.5.5.2"
    ::= { dot1dStpPortEntry 4 }

dot1dStpPortPathCost OBJECT-TYPE
    SYNTAX  INTEGER (1..65535)
    ACCESS  read-write
    STATUS  mandatory
    DESCRIPTION
            "The contribution of this port to the path cost of
            paths towards the spanning tree root which include
            this port.  802.1D-1990 recommends that the
            default value of this parameter be in inverse
            proportion to the speed of the attached LAN."
    REFERENCE
            "IEEE 802.1D-1990: Section 4.5.5.3"
    ::= { dot1dStpPortEntry 5 }

dot1dStpPortDesignatedRoot OBJECT-TYPE
    SYNTAX  BridgeId
    ACCESS  read-only
    STATUS  mandatory
    DESCRIPTION
            "The unique Bridge Identifier of the Bridge
            recorded as the Root in the Configuration BPDUs
            transmitted by the Designated Bridge for the
            segment to which the port is attached."
    REFERENCE
            "IEEE 802.1D-1990: Section 4.5.5.4"
    ::= { dot1dStpPortEntry 6 }

dot1dStpPortDesignatedCost OBJECT-TYPE
    SYNTAX  INTEGER
    ACCESS  read-only
    STATUS  mandatory
    DESCRIPTION
            "The path cost of the Designated Port of the
            segment connected to this port.  This value is
            compared to the Root Path Cost field in received
            bridge PDUs."
    REFERENCE
            "IEEE 802.1D-1990: Section 4.5.5.5"
    ::= { dot1dStpPortEntry 7 }

dot1dStpPortDesignatedBridge OBJECT-TYPE
    SYNTAX  BridgeId
    ACCESS  read-only
    STATUS  mandatory
    DESCRIPTION
            "The Bridge Identifier of the bridge which this
            port considers to be the Designated Bridge for
            this port's segment."
    REFERENCE
            "IEEE 802.1D-1990: Section 4.5.5.6"
    ::= { dot1dStpPortEntry 8 }

dot1dStpPortDesignatedPort OBJECT-TYPE
    SYNTAX  OCTET STRING (SIZE (2))
    ACCESS  read-only
    STATUS  mandatory
    DESCRIPTION
            "The Port Identifier of the port on the Designated
            Bridge for this port's segment."
    REFERENCE
            "IEEE 802.1D-1990: Section 4.5.5.7"
    ::= { dot1dStpPortEntry 9 }

dot1dStpPortForwardTransitions OBJECT-TYPE
    SYNTAX  Counter
    ACCESS  read-only
    STATUS  mandatory
    DESCRIPTION
            "The number of times this port has transitioned
            from the Learning state to the Forwarding state."
    ::= { dot1dStpPortEntry 10 }


-- the dot1dTp group

-- Implementation of the dot1dTp group is optional.  It is
-- implemented by those bridges that support the transparent
-- bridging mode.  A transparent or SRT bridge will implement
-- this group.


dot1dTpLearnedEntryDiscards OBJECT-TYPE
    SYNTAX  Counter
    ACCESS  read-only
    STATUS  mandatory
    DESCRIPTION
            "The total number of Forwarding Database entries,
            which have been or would have been learnt, but
            have been discarded due to a lack of space to
            store them in the Forwarding Database.  If this
            counter is increasing, it indicates that the
            Forwarding Database is regularly becoming full (a
            condition which has unpleasant performance effects
            on the subnetwork).  If this counter has a
            significant value but is not presently increasing,
            it indicates that the problem has been occurring
            but is not persistent."
    REFERENCE
            "IEEE 802.1D-1990: Section 6.7.1.1.3"
    ::= { dot1dTp 1 }

dot1dTpAgingTime OBJECT-TYPE
    SYNTAX   INTEGER (10..1000000)
    ACCESS   read-write
    STATUS   mandatory
    DESCRIPTION
            "The timeout period in seconds for aging out
            dynamically learned forwarding information.
            802.1D-1990 recommends a default of 300 seconds."
    REFERENCE
            "IEEE 802.1D-1990: Section 6.7.1.1.3"
    ::= { dot1dTp 2 }


--  The Forwarding Database for Transparent Bridges

dot1dTpFdbTable OBJECT-TYPE
    SYNTAX  SEQUENCE OF Dot1dTpFdbEntry
    ACCESS  not-accessible
    STATUS  mandatory
    DESCRIPTION
            "A table that contains information about unicast
            entries for which the bridge has forwarding and/or
            filtering information.  This information is used
            by the transparent bridging function in
            determining how to propagate a received frame."
    ::= { dot1dTp 3 }

dot1dTpFdbEntry OBJECT-TYPE
    SYNTAX  Dot1dTpFdbEntry
    ACCESS  not-accessible
    STATUS  mandatory
    DESCRIPTION
            "Information about a specific unicast MAC address
            for which the bridge has some forwarding and/or
            filtering information."
    INDEX   { dot1dTpFdbAddress }
    ::= { dot1dTpFdbTable 1 }

Dot1dTpFdbEntry ::=
    SEQUENCE {
        dot1dTpFdbAddress
            MacAddress,
        dot1dTpFdbPort
            INTEGER,
        dot1dTpFdbStatus
            INTEGER
    }

dot1dTpFdbAddress OBJECT-TYPE
    SYNTAX  MacAddress
    ACCESS  read-only
    STATUS  mandatory
    DESCRIPTION
            "A unicast MAC address for which the bridge has
            forwarding and/or filtering information."
    REFERENCE
            "IEEE 802.1D-1990: Section 3.9.1, 3.9.2"
    ::= { dot1dTpFdbEntry 1 }

dot1dTpFdbPort OBJECT-TYPE
    SYNTAX  INTEGER
    ACCESS  read-only
    STATUS  mandatory
    DESCRIPTION
            "Either the value '0', or the port number of the
            port on which a frame having a source address
            equal to the value of the corresponding instance
            of dot1dTpFdbAddress has been seen.  A value of
            '0' indicates that the port number has not been
            learned but that the bridge does have some
            forwarding/filtering information about this
            address (e.g. in the dot1dStaticTable).
            Implementors are encouraged to assign the port
            value to this object whenever it is learned even
            for addresses for which the corresponding value of
            dot1dTpFdbStatus is not learned(3)."
    ::= { dot1dTpFdbEntry 2 }

dot1dTpFdbStatus OBJECT-TYPE
    SYNTAX  INTEGER {
                other(1),
                invalid(2),
                learned(3),
                self(4),
                mgmt(5)
            }
    ACCESS  read-only
    STATUS  mandatory
    DESCRIPTION
            "The status of this entry.  The meanings of the
            values are:

              other(1)   : none of the following.  This would
                           include the case where some other
                           MIB object (not the corresponding
                           instance of dot1dTpFdbPort, nor an
                           entry in the dot1dStaticTable) is
                           being used to determine if and how
                           frames addressed to the value of
                           the corresponding instance of
                           dot1dTpFdbAddress are being
                           forwarded.

              invalid(2) : this entry is not longer valid
                           (e.g., it was learned but has since
                           aged-out), but has not yet been
                           flushed from the table.

              learned(3) : the value of the corresponding
                           instance of dot1dTpFdbPort was
                           learned, and is being used.

              self(4)    : the value of the corresponding
                           instance of dot1dTpFdbAddress
                           represents one of the bridge's
                           addresses.  The corresponding
                           instance of dot1dTpFdbPort
                           indicates which of the bridge's
                           ports has this address.

              mgmt(5)    : the value of the corresponding
                           instance of dot1dTpFdbAddress is
                           also the value of an existing
                           instance of dot1dStaticAddress."
    ::= { dot1dTpFdbEntry 3 }

--  Port Table for Transparent Bridges

dot1dTpPortTable OBJECT-TYPE
    SYNTAX  SEQUENCE OF Dot1dTpPortEntry
    ACCESS  not-accessible
    STATUS  mandatory
    DESCRIPTION
            "A table that contains information about every
            port that is associated with this transparent
            bridge."
    ::= { dot1dTp 4 }

dot1dTpPortEntry OBJECT-TYPE
    SYNTAX  Dot1dTpPortEntry
    ACCESS  not-accessible
    STATUS  mandatory
    DESCRIPTION
            "A list of information for each port of a
            transparent bridge."
    INDEX   { dot1dTpPort }
    ::= { dot1dTpPortTable 1 }

Dot1dTpPortEntry ::=
    SEQUENCE {
        dot1dTpPort
            INTEGER,
        dot1dTpPortMaxInfo
            INTEGER,
        dot1dTpPortInFrames
            Counter,
        dot1dTpPortOutFrames
            Counter,
        dot1dTpPortInDiscards
            Counter
    }

dot1dTpPort OBJECT-TYPE
    SYNTAX  INTEGER (1..65535)
    ACCESS  read-only
    STATUS  mandatory
    DESCRIPTION
            "The port number of the port for which this entry
            contains Transparent bridging management
            information."
    ::= { dot1dTpPortEntry 1 }

-- It would be nice if we could use ifMtu as the size of the
-- largest INFO field, but we can't because ifMtu is defined
-- to be the size that the (inter-)network layer can use which
-- can differ from the MAC layer (especially if several layers
-- of encapsulation are used).

dot1dTpPortMaxInfo OBJECT-TYPE
    SYNTAX  INTEGER
    ACCESS  read-only
    STATUS  mandatory
    DESCRIPTION
            "The maximum size of the INFO (non-MAC) field that
            this port will receive or transmit."
    ::= { dot1dTpPortEntry 2 }

dot1dTpPortInFrames OBJECT-TYPE
    SYNTAX  Counter
    ACCESS  read-only
    STATUS  mandatory
    DESCRIPTION
            "The number of frames that have been received by
            this port from its segment. Note that a frame
            received on the interface corresponding to this
            port is only counted by this object if and only if
            it is for a protocol being processed by the local
            bridging function, including bridge management
            frames."
    REFERENCE
            "IEEE 802.1D-1990: Section 6.6.1.1.3"
    ::= { dot1dTpPortEntry 3 }

dot1dTpPortOutFrames OBJECT-TYPE
    SYNTAX  Counter
    ACCESS  read-only
    STATUS  mandatory
    DESCRIPTION
            "The number of frames that have been transmitted
            by this port to its segment.  Note that a frame
            transmitted on the interface corresponding to this
            port is only counted by this object if and only if
            it is for a protocol being processed by the local
            bridging function, including bridge management
            frames."
    REFERENCE
            "IEEE 802.1D-1990: Section 6.6.1.1.3"
    ::= { dot1dTpPortEntry 4 }

dot1dTpPortInDiscards OBJECT-TYPE
    SYNTAX   Counter
    ACCESS   read-only
    STATUS   mandatory
    DESCRIPTION
            "Count of valid frames received which were
            discarded (i.e., filtered) by the Forwarding
            Process."
    REFERENCE
            "IEEE 802.1D-1990: Section 6.6.1.1.3"
    ::= { dot1dTpPortEntry 5 }


-- The Static (Destination-Address Filtering) Database

-- Implementation of this group is optional.


dot1dStaticTable OBJECT-TYPE
    SYNTAX  SEQUENCE OF Dot1dStaticEntry
    ACCESS  not-accessible
    STATUS  mandatory
    DESCRIPTION
            "A table containing filtering information
            configured into the bridge by (local or network)
            management specifying the set of ports to which
            frames received from specific ports and containing
            specific destination addresses are allowed to be
            forwarded.  The value of zero in this table as the
            port number from which frames with a specific
            destination address are received, is used to
            specify all ports for which there is no specific
            entry in this table for that particular
            destination address.  Entries are valid for
            unicast and for group/broadcast addresses."
    REFERENCE
            "IEEE 802.1D-1990: Section 6.7.2"
    ::= { dot1dStatic 1 }

dot1dStaticEntry OBJECT-TYPE
    SYNTAX  Dot1dStaticEntry
    ACCESS  not-accessible
    STATUS  mandatory
    DESCRIPTION
            "Filtering information configured into the bridge
            by (local or network) management specifying the
            set of ports to which frames received from a
            specific port and containing a specific
            destination address are allowed to be forwarded."
    REFERENCE
            "IEEE 802.1D-1990: Section 6.7.2"
    INDEX   { dot1dStaticAddress, dot1dStaticReceivePort }
    ::= { dot1dStaticTable 1 }

Dot1dStaticEntry ::=
    SEQUENCE {
        dot1dStaticAddress
            MacAddress,
        dot1dStaticReceivePort
            INTEGER,
        dot1dStaticAllowedToGoTo
            OCTET STRING,
        dot1dStaticStatus
            INTEGER
    }

dot1dStaticAddress OBJECT-TYPE
    SYNTAX  MacAddress
    ACCESS  read-write
    STATUS  mandatory
    DESCRIPTION
            "The destination MAC address in a frame to which
            this entry's filtering information applies.  This
            object can take the value of a unicast address, a
            group address or the broadcast address."
    REFERENCE
            "IEEE 802.1D-1990: Section 3.9.1, 3.9.2"
    ::= { dot1dStaticEntry 1 }

dot1dStaticReceivePort OBJECT-TYPE
    SYNTAX  INTEGER
    ACCESS  read-write
    STATUS  mandatory
    DESCRIPTION
            "Either the value '0', or the port number of the
            port from which a frame must be received in order
            for this entry's filtering information to apply.
            A value of zero indicates that this entry applies
            on all ports of the bridge for which there is no
            other applicable entry."
    ::= { dot1dStaticEntry 2 }

dot1dStaticAllowedToGoTo OBJECT-TYPE
    SYNTAX  OCTET STRING
    ACCESS  read-write
    STATUS  mandatory
    DESCRIPTION
            "The set of ports to which frames received from a
            specific port and destined for a specific MAC
            address, are allowed to be forwarded.  Each octet
            within the value of this object specifies a set of
            eight ports, with the first octet specifying ports
            1 through 8, the second octet specifying ports 9
            through 16, etc.  Within each octet, the most
            significant bit represents the lowest numbered
            port, and the least significant bit represents the
            highest numbered port.  Thus, each port of the
            bridge is represented by a single bit within the
            value of this object.  If that bit has a value of
            '1' then that port is included in the set of
            ports; the port is not included if its bit has a
            value of '0'.  (Note that the setting of the bit
            corresponding to the port from which a frame is
            received is irrelevant.)  The default value of
            this object is a string of ones of appropriate
            length."
    ::= { dot1dStaticEntry 3 }

dot1dStaticStatus OBJECT-TYPE
    SYNTAX  INTEGER {
                other(1),
                invalid(2),
                permanent(3),
                deleteOnReset(4),
                deleteOnTimeout(5)
            }
    ACCESS  read-write
    STATUS  mandatory
    DESCRIPTION
            "This object indicates the status of this entry.
            The default value is permanent(3).

                 other(1) - this entry is currently in use but
                      the conditions under which it will
                      remain so are different from each of the
                      following values.
                 invalid(2) - writing this value to the object
                      removes the corresponding entry.
                 permanent(3) - this entry is currently in use
                      and will remain so after the next reset
                      of the bridge.
                 deleteOnReset(4) - this entry is currently in
                      use and will remain so until the next
                      reset of the bridge.
                 deleteOnTimeout(5) - this entry is currently
                      in use and will remain so until it is
                      aged out."
    ::= { dot1dStaticEntry 4 }


-- Traps for use by Bridges

-- Traps for the Spanning Tree Protocol

newRoot TRAP-TYPE
    ENTERPRISE  dot1dBridge
    DESCRIPTION
            "The newRoot trap indicates that the sending agent
            has become the new root of the Spanning Tree; the
            trap is sent by a bridge soon after its election
            as the new root, e.g., upon expiration of the
            Topology Change Timer immediately subsequent to
            its election.  Implementation of this trap is
            optional."
    ::= 1

topologyChange TRAP-TYPE
    ENTERPRISE  dot1dBridge
    DESCRIPTION
            "A topologyChange trap is sent by a bridge when
            any of its configured ports transitions from the
            Learning state to the Forwarding state, or from
            the Forwarding state to the Blocking state.  The
            trap is not sent if a newRoot trap is sent for the
            same transition.  Implementation of this trap is
            optional."
    ::= 2

END

   RS-232-MIB DEFINITIONS ::= BEGIN

   IMPORTS
       MODULE-IDENTITY, OBJECT-TYPE, NOTIFICATION-TYPE,
       Counter32, Integer32
           FROM SNMPv2-SMI
       InterfaceIndex
           FROM IF-MIB
       transmission
           FROM RFC1213-MIB
       MODULE-COMPLIANCE, OBJECT-GROUP
           FROM SNMPv2-CONF;


   rs232 MODULE-IDENTITY
       LAST-UPDATED "9405261700Z"
       ORGANIZATION "IETF Character MIB Working Group"
       CONTACT-INFO
               "        Bob Stewart
                Postal: Xyplex, Inc.
                        295 Foster Street
                        Littleton, MA 01460

                   Tel: 508-952-4816
                   Fax: 508-952-4887
                E-mail: rlstewart@eng.xyplex.com"
       DESCRIPTION
               "The MIB module for RS-232-like hardware devices."
       ::= { transmission 33 }


   -- Generic RS-232-like information

   rs232Number OBJECT-TYPE
       SYNTAX Integer32
       MAX-ACCESS read-only
       STATUS current
       DESCRIPTION
           "The number of ports (regardless of their current
           state) in the RS-232-like general port table."
       ::= { rs232 1 }


   -- RS-232-like General Port Table

   rs232PortTable OBJECT-TYPE
       SYNTAX SEQUENCE OF Rs232PortEntry
       MAX-ACCESS not-accessible
       STATUS current
       DESCRIPTION
           "A list of port entries.  The number of entries is
           given by the value of rs232Number."
       ::= { rs232 2 }

   rs232PortEntry OBJECT-TYPE
       SYNTAX Rs232PortEntry
       MAX-ACCESS not-accessible
       STATUS current
       DESCRIPTION
           "Status and parameter values for a port."
       INDEX { rs232PortIndex }
       ::= { rs232PortTable 1 }

   Rs232PortEntry ::=
       SEQUENCE {
           rs232PortIndex
               InterfaceIndex,
           rs232PortType
               INTEGER,
           rs232PortInSigNumber
               Integer32,
           rs232PortOutSigNumber
               Integer32,
           rs232PortInSpeed
               Integer32,
           rs232PortOutSpeed
               Integer32,
           rs232PortInFlowType
               INTEGER,
           rs232PortOutFlowType
               INTEGER
       }

   rs232PortIndex OBJECT-TYPE
       SYNTAX InterfaceIndex
       MAX-ACCESS read-only
       STATUS current
       DESCRIPTION
           "The value of ifIndex for the port.  By convention
           and if possible, hardware port numbers map directly
           to external connectors.  The value for each port must
           remain constant at least from one re-initialization
           of the network management agent to the next."
       ::= { rs232PortEntry 1 }

   rs232PortType OBJECT-TYPE
       SYNTAX INTEGER { other(1), rs232(2), rs422(3),
                        rs423(4), v35(5), x21(6) }
       MAX-ACCESS read-only
       STATUS current
       DESCRIPTION
           "The port's hardware type."
       ::= { rs232PortEntry 2 }

   rs232PortInSigNumber OBJECT-TYPE
       SYNTAX Integer32
       MAX-ACCESS read-only
       STATUS current
       DESCRIPTION
           "The number of input signals for the port in the
           input signal table (rs232PortInSigTable).  The table
           contains entries only for those signals the software
           can detect and that are useful to observe."
       ::= { rs232PortEntry 3 }


   rs232PortOutSigNumber OBJECT-TYPE
       SYNTAX Integer32
       MAX-ACCESS read-only
       STATUS current
       DESCRIPTION
           "The number of output signals for the port in the
           output signal table (rs232PortOutSigTable).  The
           table contains entries only for those signals the
           software can assert and that are useful to observe."
       ::= { rs232PortEntry 4 }

   rs232PortInSpeed OBJECT-TYPE
       SYNTAX Integer32
       MAX-ACCESS read-write
       STATUS current
       DESCRIPTION
           "The port's input speed in bits per second.  Note that
           non-standard values, such as 9612, are probably not allowed
           on most implementations."
       ::= { rs232PortEntry 5 }

   rs232PortOutSpeed OBJECT-TYPE
       SYNTAX Integer32
       MAX-ACCESS read-write
       STATUS current
       DESCRIPTION
           "The port's output speed in bits per second.  Note that
           non-standard values, such as 9612, are probably not allowed
           on most implementations."
       ::= { rs232PortEntry 6 }

   rs232PortInFlowType OBJECT-TYPE
       SYNTAX INTEGER { none(1), ctsRts(2), dsrDtr(3) }
       MAX-ACCESS read-write
       STATUS current
       DESCRIPTION
           "The port's type of input flow control.  'none'
           indicates no flow control at this level.
           'ctsRts' and 'dsrDtr' indicate use of the indicated
           hardware signals."
       ::= { rs232PortEntry 7 }

   rs232PortOutFlowType OBJECT-TYPE
       SYNTAX INTEGER { none(1), ctsRts(2), dsrDtr(3) }
       MAX-ACCESS read-write
       STATUS current
       DESCRIPTION
           "The port's type of output flow control.  'none'
           indicates no flow control at this level.
           'ctsRts' and 'dsrDtr' indicate use of the indicated
           hardware signals."
       ::= { rs232PortEntry 8 }


   -- RS-232-like Asynchronous Port Table

   rs232AsyncPortTable OBJECT-TYPE
       SYNTAX SEQUENCE OF Rs232AsyncPortEntry
       MAX-ACCESS not-accessible
       STATUS current
       DESCRIPTION
           "A list of asynchronous port entries.  Entries need
           not exist for synchronous ports."
       ::= { rs232 3 }

   rs232AsyncPortEntry OBJECT-TYPE
       SYNTAX Rs232AsyncPortEntry
       MAX-ACCESS not-accessible
       STATUS current
       DESCRIPTION
           "Status and parameter values for an asynchronous
           port."
       INDEX { rs232AsyncPortIndex }
       ::= { rs232AsyncPortTable 1 }

   Rs232AsyncPortEntry ::=
       SEQUENCE {
           rs232AsyncPortIndex
               InterfaceIndex,
           rs232AsyncPortBits
               INTEGER,
           rs232AsyncPortStopBits
               INTEGER,
           rs232AsyncPortParity
               INTEGER,
           rs232AsyncPortAutobaud
               INTEGER,
           rs232AsyncPortParityErrs
               Counter32,
           rs232AsyncPortFramingErrs
               Counter32,
           rs232AsyncPortOverrunErrs
               Counter32

       }

   rs232AsyncPortIndex OBJECT-TYPE
       SYNTAX InterfaceIndex
       MAX-ACCESS read-only
       STATUS current
       DESCRIPTION
           "A unique value for each port.  Its value is the
           same as rs232PortIndex for the port."
       ::= { rs232AsyncPortEntry 1 }

   rs232AsyncPortBits OBJECT-TYPE
       SYNTAX INTEGER (5..8)
       MAX-ACCESS read-write
       STATUS current
       DESCRIPTION
           "The port's number of bits in a character."
       ::= { rs232AsyncPortEntry 2 }

   rs232AsyncPortStopBits OBJECT-TYPE
       SYNTAX INTEGER { one(1), two(2),
                        oneAndHalf(3), dynamic(4) }
       MAX-ACCESS read-write
       STATUS current
       DESCRIPTION
           "The port's number of stop bits."
       ::= { rs232AsyncPortEntry 3 }

   rs232AsyncPortParity OBJECT-TYPE
       SYNTAX INTEGER { none(1), odd(2), even(3),
                        mark(4), space(5) }
       MAX-ACCESS read-write
       STATUS current
       DESCRIPTION
           "The port's sense of a character parity bit."
       ::= { rs232AsyncPortEntry 4 }

   rs232AsyncPortAutobaud OBJECT-TYPE
       SYNTAX INTEGER { enabled(1), disabled(2) }
       MAX-ACCESS read-write
       STATUS current
       DESCRIPTION
           "A control for the port's ability to automatically
           sense input speed.

           When rs232PortAutoBaud is 'enabled', a port may
           autobaud to values different from the set values for
           speed, parity, and character size.  As a result a
           network management system may temporarily observe
           values different from what was previously set."
       ::= { rs232AsyncPortEntry 5 }

   rs232AsyncPortParityErrs OBJECT-TYPE
       SYNTAX Counter32
       MAX-ACCESS read-only
       STATUS current
       DESCRIPTION
           "Total number of characters with a parity error,
           input from the port since system re-initialization
           and while the port state was 'up' or 'test'."
       ::= { rs232AsyncPortEntry 6 }

   rs232AsyncPortFramingErrs OBJECT-TYPE
       SYNTAX Counter32
       MAX-ACCESS read-only
       STATUS current
       DESCRIPTION
           "Total number of characters with a framing error,
           input from the port since system re-initialization
           and while the port state was 'up' or 'test'."
       ::= { rs232AsyncPortEntry 7 }

   rs232AsyncPortOverrunErrs OBJECT-TYPE
       SYNTAX Counter32
       MAX-ACCESS read-only
       STATUS current
       DESCRIPTION
           "Total number of characters with an overrun error,
           input from the port since system re-initialization
           and while the port state was 'up' or 'test'."
       ::= { rs232AsyncPortEntry 8 }


   -- RS-232-like Synchronous Port Table

   rs232SyncPortTable OBJECT-TYPE
       SYNTAX SEQUENCE OF Rs232SyncPortEntry
       MAX-ACCESS not-accessible
       STATUS current
       DESCRIPTION
           "A list of asynchronous port entries.  Entries need
           not exist for synchronous ports."
       ::= { rs232 4 }

   rs232SyncPortEntry OBJECT-TYPE
       SYNTAX Rs232SyncPortEntry
       MAX-ACCESS not-accessible
       STATUS current
       DESCRIPTION
           "Status and parameter values for a synchronous
           port."
       INDEX { rs232SyncPortIndex }
       ::= { rs232SyncPortTable 1 }

   Rs232SyncPortEntry ::=
       SEQUENCE {
           rs232SyncPortIndex
               InterfaceIndex,
           rs232SyncPortClockSource
               INTEGER,
           rs232SyncPortFrameCheckErrs
               Counter32,
           rs232SyncPortTransmitUnderrunErrs
               Counter32,
           rs232SyncPortReceiveOverrunErrs
               Counter32,
           rs232SyncPortInterruptedFrames
               Counter32,
           rs232SyncPortAbortedFrames
               Counter32,
           rs232SyncPortRole
               INTEGER,
           rs232SyncPortEncoding
               INTEGER,
           rs232SyncPortRTSControl
               INTEGER,
           rs232SyncPortRTSCTSDelay
               Integer32,
           rs232SyncPortMode
               INTEGER,
           rs232SyncPortIdlePattern
               INTEGER,
           rs232SyncPortMinFlags
               Integer32
       }

   rs232SyncPortIndex OBJECT-TYPE
       SYNTAX InterfaceIndex
       MAX-ACCESS read-only
       STATUS current
       DESCRIPTION
           "A unique value for each port.  Its value is the
           same as rs232PortIndex for the port."
       ::= { rs232SyncPortEntry 1 }


   rs232SyncPortClockSource OBJECT-TYPE
       SYNTAX INTEGER { internal(1), external(2), split(3) }
       MAX-ACCESS read-write
       STATUS current
       DESCRIPTION
           "Source of the port's bit rate clock. 'split' means
           the tranmit clock is internal and the receive clock
           is external."
       ::= { rs232SyncPortEntry 2 }

   rs232SyncPortFrameCheckErrs OBJECT-TYPE
       SYNTAX Counter32
       MAX-ACCESS read-only
       STATUS current
       DESCRIPTION
           "Total number of frames with an invalid frame check
           sequence, input from the port since system
           re-initialization and while the port state was 'up'
           or 'test'."
       ::= { rs232SyncPortEntry 3 }

   rs232SyncPortTransmitUnderrunErrs OBJECT-TYPE
       SYNTAX Counter32
       MAX-ACCESS read-only
       STATUS current
       DESCRIPTION
           "Total number of frames that failed to be
           transmitted on the port since system
           re-initialization and while the port state was 'up'
           or 'test' because data was not available to the
           transmitter in time."
       ::= { rs232SyncPortEntry 4 }

   rs232SyncPortReceiveOverrunErrs OBJECT-TYPE
       SYNTAX Counter32
       MAX-ACCESS read-only
       STATUS current
       DESCRIPTION
           "Total number of frames that failed to be received
           on the port since system re-initialization and while
           the port state was 'up' or 'test' because the
           receiver did not accept the data in time."
       ::= { rs232SyncPortEntry 5 }

   rs232SyncPortInterruptedFrames OBJECT-TYPE
       SYNTAX Counter32
       MAX-ACCESS read-only
       STATUS current
       DESCRIPTION
           "Total number of frames that failed to be received
           or transmitted on the port due to loss of modem
           signals since system re-initialization and while the
           port state was 'up' or 'test'."
       ::= { rs232SyncPortEntry 6 }

   rs232SyncPortAbortedFrames OBJECT-TYPE
       SYNTAX Counter32
       MAX-ACCESS read-only
       STATUS current
       DESCRIPTION
           "Number of frames aborted on the port due to
           receiving an abort sequence since system
           re-initialization and while the port state was 'up'
           or 'test'."
       ::= { rs232SyncPortEntry 7 }

   rs232SyncPortRole OBJECT-TYPE
       SYNTAX INTEGER  { dte(1), dce(2) }
       MAX-ACCESS read-write
       STATUS current
       DESCRIPTION
           "The role the device is playing that is using this port.
              dte    means the device is performing the role of
                     data terminal equipment
              dce    means the device is performing the role of
                     data circuit-terminating equipment."
       DEFVAL { dce }
       ::= { rs232SyncPortEntry 8 }

   rs232SyncPortEncoding OBJECT-TYPE
       SYNTAX INTEGER  { nrz(1), nrzi(2) }
       MAX-ACCESS read-write
       STATUS current
       DESCRIPTION
           "The bit stream encoding technique that is in effect
            for this port.
              nrz    for Non-Return to Zero encoding
              nrzi   for Non-Return to Zero Inverted encoding."
       DEFVAL { nrz }
       ::= { rs232SyncPortEntry 9 }

   rs232SyncPortRTSControl OBJECT-TYPE
       SYNTAX INTEGER  { controlled(1), constant(2) }
       MAX-ACCESS read-write
       STATUS current
       DESCRIPTION
           "The method used to control the Request To Send (RTS)
            signal.

              controlled  when the DTE is asserts RTS each time
                          data needs to be transmitted and drops
                          RTS at some point after data
                          transmission begins.

                          If rs232SyncPortRole is 'dte', the
                          RTS is an output signal. The device
                          will issue a RTS and wait for a CTS
                          from the DCE before starting to
                          transmit.

                          If rs232SyncPortRole is 'dce', the
                          RTS is an input signal. The device
                          will issue a CTS only after having
                          received RTS and waiting the
                          rs232SyncPortRTSCTSDelay interval.

              constant    when the DTE constantly asserts RTS."
       DEFVAL { constant }
       ::= { rs232SyncPortEntry 10 }

   rs232SyncPortRTSCTSDelay OBJECT-TYPE
       SYNTAX Integer32
       MAX-ACCESS read-write
       STATUS current
       DESCRIPTION
           "The interval (in milliseconds) that the DCE must wait
            after it sees RTS asserted before asserting CTS.  This
            object exists in support of older synchronous devices
            that cannot recognize CTS within a certain interval
            after it asserts RTS."
       DEFVAL { 0 }
       ::= { rs232SyncPortEntry 11 }

   rs232SyncPortMode OBJECT-TYPE
       SYNTAX INTEGER  { fdx(1), hdx(2), simplex-receive(3),
                         simplex-send(4) }
       MAX-ACCESS read-write
       STATUS current
       DESCRIPTION
           "The mode of operation of the port with respect to the
            direction and simultaneity of data transfer.



              fdx              when frames on the data link can be
                               transmitted and received at the same
                               time

              hdx              when frames can either be received
                               from the data link or transmitted
                               onto the data link but not at the
                               same time.

              simplex-receive  when frames can only be received on
                               this data link.

              simplex-send     when frames can only be sent on this
                               data link."
       DEFVAL { fdx }
       ::= { rs232SyncPortEntry 12 }

   rs232SyncPortIdlePattern OBJECT-TYPE
       SYNTAX INTEGER  { mark(1), space(2) }
       MAX-ACCESS read-write
       STATUS current
       DESCRIPTION
           "The bit pattern used to indicate an idle line."
       DEFVAL { space }
       ::= { rs232SyncPortEntry 13 }

   rs232SyncPortMinFlags OBJECT-TYPE
       SYNTAX Integer32
       MAX-ACCESS read-write
       STATUS current
       DESCRIPTION
           "The minimum number of flag patterns this port needs in
            order to recognize the end of one frame and the start
            of the next.  Plausible values are 1 and 2."
       DEFVAL { 2 }
       ::= { rs232SyncPortEntry 14 }


   -- Input Signal Table

   rs232InSigTable OBJECT-TYPE
       SYNTAX SEQUENCE OF Rs232InSigEntry
       MAX-ACCESS not-accessible
       STATUS current
       DESCRIPTION
           "A list of port input control signal entries
           implemented and visible to the software on the port,
           and useful to monitor."
       ::= { rs232 5 }

   rs232InSigEntry OBJECT-TYPE
       SYNTAX Rs232InSigEntry
       MAX-ACCESS not-accessible
       STATUS current
       DESCRIPTION
           "Input control signal status for a hardware port."
       INDEX { rs232InSigPortIndex, rs232InSigName }
       ::= { rs232InSigTable 1 }

   Rs232InSigEntry ::=
       SEQUENCE {
           rs232InSigPortIndex
               InterfaceIndex,
           rs232InSigName
               INTEGER,
           rs232InSigState
               INTEGER,
           rs232InSigChanges
               Counter32
       }

   rs232InSigPortIndex OBJECT-TYPE
       SYNTAX InterfaceIndex
       MAX-ACCESS read-only
       STATUS current
       DESCRIPTION
           "The value of rs232PortIndex for the port to which
           this entry belongs."
       ::= { rs232InSigEntry 1 }

   rs232InSigName OBJECT-TYPE
       SYNTAX INTEGER { rts(1), cts(2), dsr(3), dtr(4), ri(5),
                        dcd(6), sq(7), srs(8), srts(9),
                        scts(10), sdcd(11) }
       MAX-ACCESS read-only
       STATUS current
       DESCRIPTION
           "Identification of a hardware signal, as follows:

               rts    Request to Send
               cts    Clear to Send
               dsr    Data Set Ready
               dtr    Data Terminal Ready
               ri     Ring Indicator
               dcd    Received Line Signal Detector
               sq     Signal Quality Detector
               srs    Data Signaling Rate Selector
               srts   Secondary Request to Send
               scts   Secondary Clear to Send
               sdcd   Secondary Received Line Signal Detector
           "
       REFERENCE
           "EIA Standard RS-232-C, August 1969."
       ::= { rs232InSigEntry 2 }

   rs232InSigState OBJECT-TYPE
       SYNTAX INTEGER { none(1), on(2), off(3) }
       MAX-ACCESS read-only
       STATUS current
       DESCRIPTION
           "The current signal state."
       ::= { rs232InSigEntry 3 }

   rs232InSigChanges OBJECT-TYPE
       SYNTAX Counter32
       MAX-ACCESS read-only
       STATUS current
       DESCRIPTION
           "The number of times the signal has changed from
           'on' to 'off' or from 'off' to 'on'."
       ::= { rs232InSigEntry 4 }


   -- Output Signal Table

   rs232OutSigTable OBJECT-TYPE
       SYNTAX SEQUENCE OF Rs232OutSigEntry
       MAX-ACCESS not-accessible
       STATUS current
       DESCRIPTION
           "A list of port output control signal entries
           implemented and visible to the software on the port,
           and useful to monitor."
       ::= { rs232 6 }

   rs232OutSigEntry OBJECT-TYPE
       SYNTAX Rs232OutSigEntry
       MAX-ACCESS not-accessible
       STATUS current
       DESCRIPTION
           "Output control signal status for a hardware port."
       INDEX { rs232OutSigPortIndex, rs232OutSigName }
       ::= { rs232OutSigTable 1 }

   Rs232OutSigEntry ::=
       SEQUENCE {
           rs232OutSigPortIndex
               InterfaceIndex,
           rs232OutSigName
               INTEGER,
           rs232OutSigState
               INTEGER,
           rs232OutSigChanges
               Counter32
       }

   rs232OutSigPortIndex OBJECT-TYPE
       SYNTAX InterfaceIndex
       MAX-ACCESS read-only
       STATUS current
       DESCRIPTION
           "The value of rs232PortIndex for the port to which
           this entry belongs."
       ::= { rs232OutSigEntry 1 }

   rs232OutSigName OBJECT-TYPE
       SYNTAX INTEGER { rts(1), cts(2), dsr(3), dtr(4), ri(5),
                        dcd(6), sq(7), srs(8), srts(9),
                        scts(10), sdcd(11) }
       MAX-ACCESS read-only
       STATUS current
       DESCRIPTION
           "Identification of a hardware signal, as follows:

               rts    Request to Send
               cts    Clear to Send
               dsr    Data Set Ready
               dtr    Data Terminal Ready
               ri     Ring Indicator
               dcd    Received Line Signal Detector
               sq     Signal Quality Detector
               srs    Data Signaling Rate Selector
               srts   Secondary Request to Send
               scts   Secondary Clear to Send
               sdcd   Secondary Received Line Signal Detector
           "
       REFERENCE
           "EIA Standard RS-232-C, August 1969."
       ::= { rs232OutSigEntry 2 }

   rs232OutSigState OBJECT-TYPE
       SYNTAX INTEGER { none(1), on(2), off(3) }
       MAX-ACCESS read-only
       STATUS current
       DESCRIPTION
           "The current signal state."
       ::= { rs232OutSigEntry 3 }

   rs232OutSigChanges OBJECT-TYPE
       SYNTAX Counter32
       MAX-ACCESS read-only
       STATUS current
       DESCRIPTION
           "The number of times the signal has changed from
           'on' to 'off' or from 'off' to 'on'."
       ::= { rs232OutSigEntry 4 }


   -- conformance information

   rs232Conformance OBJECT IDENTIFIER ::= { rs232 7 }

   rs232Groups      OBJECT IDENTIFIER ::= { rs232Conformance 1 }
   rs232Compliances OBJECT IDENTIFIER ::= { rs232Conformance 2 }


   -- compliance statements

   rs232Compliance MODULE-COMPLIANCE
       STATUS  current
       DESCRIPTION
               "The compliance statement for SNMPv2 entities
               which have RS-232-like hardware interfaces."

       MODULE  -- this module
           MANDATORY-GROUPS { rs232Group }

           GROUP   rs232AsyncGroup
           DESCRIPTION
               "The Asynch group is mandatory only for those
                SNMPv2 entities which have asynchronous
                interfaces Rs-232-like."

           GROUP   rs232SyncGroup
           DESCRIPTION
               "The Synch group is mandatory only for those
                SNMPv2 entities which have synchronous
                interfaces Rs-232-like."
       ::= { rs232Compliances 1 }

   -- units of conformance

   rs232Group    OBJECT-GROUP
       OBJECTS { rs232Number, rs232PortIndex, rs232PortType,
                 rs232PortInSigNumber, rs232PortOutSigNumber,
                 rs232PortInSpeed, rs232PortOutSpeed,
                 rs232PortInFlowType, rs232PortOutFlowType,
                 rs232InSigPortIndex, rs232InSigName,
                 rs232InSigState, rs232InSigChanges,
                 rs232OutSigPortIndex, rs232OutSigName,
                 rs232OutSigState, rs232OutSigChanges }
       STATUS  current
       DESCRIPTION
               "A collection of objects providing information
                applicable to all RS-232-like interfaces."
       ::= { rs232Groups 1 }

   rs232AsyncGroup OBJECT-GROUP
       OBJECTS { rs232AsyncPortIndex, rs232AsyncPortBits,
                 rs232AsyncPortStopBits, rs232AsyncPortParity,
                 rs232AsyncPortAutobaud, rs232AsyncPortParityErrs,
                 rs232AsyncPortFramingErrs, rs232AsyncPortOverrunErrs }
       STATUS  current
       DESCRIPTION
               "A collection of objects providing information
                applicable to asynchronous RS-232-like interfaces."
       ::= { rs232Groups 2 }

   rs232SyncGroup OBJECT-GROUP
       OBJECTS { rs232SyncPortIndex, rs232SyncPortClockSource,
                 rs232SyncPortFrameCheckErrs,
                 rs232SyncPortTransmitUnderrunErrs,
                 rs232SyncPortReceiveOverrunErrs,
                 rs232SyncPortInterruptedFrames,
                 rs232SyncPortAbortedFrames }
       STATUS  current
       DESCRIPTION
               "A collection of objects providing information
                applicable to synchronous RS-232-like interfaces."
       ::= { rs232Groups 3 }

   rs232SyncSDLCGroup OBJECT-GROUP
       OBJECTS { rs232SyncPortRole,
                 rs232SyncPortEncoding,
                 rs232SyncPortRTSControl,
                 rs232SyncPortRTSCTSDelay,
                 rs232SyncPortMode,
                 rs232SyncPortIdlePattern,
                 rs232SyncPortMinFlags }
       STATUS  current
       DESCRIPTION
               "A collection of objects providing information
                applicable to synchronous RS-232-like interfaces
                running SDLC."
       ::= { rs232Groups 4 }

END

IP-FORWARD-MIB DEFINITIONS ::= BEGIN

IMPORTS
    MODULE-IDENTITY, OBJECT-TYPE, IpAddress, Integer32, Gauge32
        FROM SNMPv2-SMI
    RowStatus
        FROM SNMPv2-TC
    ip
        FROM RFC1213-MIB
    MODULE-COMPLIANCE, OBJECT-GROUP
        FROM SNMPv2-CONF;

ipForward MODULE-IDENTITY
    LAST-UPDATED "9609190000Z"     -- Thu Sep 26 16:34:47 PDT 1996
    ORGANIZATION "IETF OSPF Working Group"
    CONTACT-INFO
     "        Fred Baker
      Postal: Cisco Systems
              519 Lado Drive
              Santa Barbara, California 93111

      Phone:  +1 805 681 0115
      Email:  fred@cisco.com
      "
    DESCRIPTION
            "The MIB module for the display of CIDR multipath IP Routes."
    REVISION      "9609190000Z"
    DESCRIPTION
            "Revisions made by the OSPF WG."
    ::= { ip 24 }

ipCidrRouteNumber OBJECT-TYPE
    SYNTAX   Gauge32
    MAX-ACCESS read-only
    STATUS   current
    DESCRIPTION
       "The number of current ipCidrRouteTable entries
       that are not invalid."
    ::= { ipForward 3 }

--  IP CIDR Route Table

--  The IP CIDR Route Table obsoletes and replaces the ipRoute
--  Table current in MIB-I and MIB-II and the IP Forwarding Table.
--  It adds knowledge of the autonomous system of the next hop,
--  multiple next hops, and policy routing, and Classless
--  Inter-Domain Routing.

ipCidrRouteTable OBJECT-TYPE
    SYNTAX   SEQUENCE OF IpCidrRouteEntry
    MAX-ACCESS not-accessible
    STATUS   current
    DESCRIPTION
       "This entity's IP Routing table."
    REFERENCE
       "RFC 1213 Section 6.6, The IP Group"
    ::= { ipForward 4 }

ipCidrRouteEntry OBJECT-TYPE
    SYNTAX   IpCidrRouteEntry
    MAX-ACCESS not-accessible
    STATUS   current
    DESCRIPTION
       "A particular route to  a  particular  destina-
       tion, under a particular policy."
    INDEX {
        ipCidrRouteDest,
        ipCidrRouteMask,
        ipCidrRouteTos,
        ipCidrRouteNextHop
        }
    ::= { ipCidrRouteTable 1 }

IpCidrRouteEntry ::=
    SEQUENCE {
        ipCidrRouteDest
            IpAddress,
        ipCidrRouteMask
            IpAddress,
        ipCidrRouteTos
             Integer32,
        ipCidrRouteNextHop
            IpAddress,
        ipCidrRouteIfIndex
            Integer32,
        ipCidrRouteType
            INTEGER,
        ipCidrRouteProto
            INTEGER,
        ipCidrRouteAge
            Integer32,
        ipCidrRouteInfo
            OBJECT IDENTIFIER,
        ipCidrRouteNextHopAS
            Integer32,
        ipCidrRouteMetric1
            Integer32,
        ipCidrRouteMetric2
            Integer32,
        ipCidrRouteMetric3
            Integer32,
        ipCidrRouteMetric4
            Integer32,
        ipCidrRouteMetric5
            Integer32,
        ipCidrRouteStatus
            RowStatus
    }

ipCidrRouteDest OBJECT-TYPE
    SYNTAX   IpAddress
    MAX-ACCESS read-only
    STATUS   current
    DESCRIPTION
       "The destination IP address of this route.

       This object may not take a Multicast (Class  D)
       address value.

       Any assignment (implicit or  otherwise)  of  an
       instance  of  this  object to a value x must be
       rejected if the bitwise logical-AND of  x  with
       the  value of the corresponding instance of the
       ipCidrRouteMask object is not equal to x."
    ::= { ipCidrRouteEntry 1 }

ipCidrRouteMask OBJECT-TYPE
    SYNTAX   IpAddress
    MAX-ACCESS read-only
    STATUS   current
    DESCRIPTION
       "Indicate the mask to be logical-ANDed with the
       destination  address  before  being compared to
       the value  in  the  ipCidrRouteDest  field.   For
       those  systems  that  do  not support arbitrary
       subnet masks, an agent constructs the value  of
       the  ipCidrRouteMask  by  reference to the IP Ad-
       dress Class.

       Any assignment (implicit or  otherwise)  of  an
       instance  of  this  object to a value x must be
       rejected if the bitwise logical-AND of  x  with
       the  value of the corresponding instance of the
       ipCidrRouteDest object is not equal to ipCidrRoute-
       Dest."
    ::= { ipCidrRouteEntry 2 }

-- The following convention is included for specification
-- of TOS Field contents.  At this time, the Host Requirements
-- and the Router Requirements documents disagree on the width
-- of the TOS field.  This mapping describes the Router
-- Requirements mapping, and leaves room to widen the TOS field
-- without impact to fielded systems.

ipCidrRouteTos OBJECT-TYPE
    SYNTAX   Integer32
    MAX-ACCESS read-only
    STATUS   current
    DESCRIPTION
       "The policy specifier is the IP TOS Field.  The encoding
       of IP TOS is as specified  by  the  following convention.
       Zero indicates the default path if no more  specific
       policy applies.

       +-----+-----+-----+-----+-----+-----+-----+-----+
       |                 |                       |     |
       |   PRECEDENCE    |    TYPE OF SERVICE    |  0  |
       |                 |                       |     |
       +-----+-----+-----+-----+-----+-----+-----+-----+

                IP TOS                IP TOS
           Field     Policy      Field     Policy
           Contents    Code      Contents    Code
           0 0 0 0  ==&gt;   0      0 0 0 1  ==&gt;   2
           0 0 1 0  ==&gt;   4      0 0 1 1  ==&gt;   6
           0 1 0 0  ==&gt;   8      0 1 0 1  ==&gt;  10
           0 1 1 0  ==&gt;  12      0 1 1 1  ==&gt;  14
           1 0 0 0  ==&gt;  16      1 0 0 1  ==&gt;  18
           1 0 1 0  ==&gt;  20      1 0 1 1  ==&gt;  22
           1 1 0 0  ==&gt;  24      1 1 0 1  ==&gt;  26
           1 1 1 0  ==&gt;  28      1 1 1 1  ==&gt;  30"
    ::= { ipCidrRouteEntry 3 }

ipCidrRouteNextHop OBJECT-TYPE
    SYNTAX   IpAddress
    MAX-ACCESS read-only
    STATUS   current
    DESCRIPTION
       "On remote routes, the address of the next sys-
       tem en route; Otherwise, 0.0.0.0."
    ::= { ipCidrRouteEntry 4 }

ipCidrRouteIfIndex OBJECT-TYPE
    SYNTAX   Integer32
    MAX-ACCESS read-create
    STATUS   current
    DESCRIPTION
       "The ifIndex value which identifies  the  local
       interface  through  which  the next hop of this
       route should be reached."
    DEFVAL { 0 }
    ::= { ipCidrRouteEntry 5 }

ipCidrRouteType OBJECT-TYPE
    SYNTAX   INTEGER {
                other    (1), -- not specified by this MIB
                reject   (2), -- route which discards traffic
                local    (3), -- local interface
                remote   (4)  -- remote destination
             }
    MAX-ACCESS read-create
    STATUS   current
    DESCRIPTION
       "The type of route.  Note that local(3)  refers
       to  a route for which the next hop is the final
       destination; remote(4) refers to  a  route  for
       which  the  next  hop is not the final destina-
       tion.

       Routes which do not result in traffic forwarding or
       rejection should not be displayed even if the
       implementation keeps them stored internally.


       reject (2) refers to a route which, if matched, discards
       the message as unreachable. This is used in some
       protocols as a means of correctly aggregating routes."
    ::= { ipCidrRouteEntry 6 }

ipCidrRouteProto OBJECT-TYPE
    SYNTAX   INTEGER {
                other     (1),  -- not specified
                local     (2),  -- local interface
                netmgmt   (3),  -- static route
                icmp      (4),  -- result of ICMP Redirect

                        -- the following are all dynamic
                        -- routing protocols
                egp        (5),  -- Exterior Gateway Protocol
                ggp        (6),  -- Gateway-Gateway Protocol
                hello      (7),  -- FuzzBall HelloSpeak
                rip        (8),  -- Berkeley RIP or RIP-II
                isIs       (9),  -- Dual IS-IS
                esIs       (10), -- ISO 9542
                ciscoIgrp  (11), -- Cisco IGRP
                bbnSpfIgp  (12), -- BBN SPF IGP
                ospf       (13), -- Open Shortest Path First
                bgp        (14), -- Border Gateway Protocol
                idpr       (15), -- InterDomain Policy Routing
                ciscoEigrp (16)  -- Cisco EIGRP
             }
    MAX-ACCESS read-only
    STATUS   current
    DESCRIPTION
       "The routing mechanism via which this route was
       learned.  Inclusion of values for gateway rout-
       ing protocols is not  intended  to  imply  that
       hosts should support those protocols."
    ::= { ipCidrRouteEntry 7 }

ipCidrRouteAge OBJECT-TYPE
    SYNTAX   Integer32
    MAX-ACCESS read-only
    STATUS   current
    DESCRIPTION
       "The number of seconds  since  this  route  was
       last  updated  or  otherwise  determined  to be
       correct.  Note that no semantics of  `too  old'
       can  be implied except through knowledge of the
       routing  protocol  by  which  the   route   was
       learned."
    DEFVAL  { 0 }
    ::= { ipCidrRouteEntry 8 }

ipCidrRouteInfo OBJECT-TYPE
    SYNTAX   OBJECT IDENTIFIER
    MAX-ACCESS read-create
    STATUS   current
    DESCRIPTION
       "A reference to MIB definitions specific to the
       particular  routing protocol which is responsi-
       ble for this route, as determined by the  value
       specified  in the route's ipCidrRouteProto value.
       If this information is not present,  its  value
       should be set to the OBJECT IDENTIFIER { 0 0 },
       which is a syntactically valid object  identif-
       ier, and any implementation conforming to ASN.1
       and the Basic Encoding Rules must  be  able  to
       generate and recognize this value."
    ::= { ipCidrRouteEntry 9 }

ipCidrRouteNextHopAS OBJECT-TYPE
    SYNTAX   Integer32
    MAX-ACCESS read-create
    STATUS   current
    DESCRIPTION
       "The Autonomous System Number of the Next  Hop.
       The  semantics of this object are determined by
       the routing-protocol specified in  the  route's
       ipCidrRouteProto  value. When  this object is
       unknown or not relevant its value should be set
       to zero."
    DEFVAL { 0 }
    ::= { ipCidrRouteEntry 10 }

ipCidrRouteMetric1 OBJECT-TYPE
    SYNTAX   Integer32
    MAX-ACCESS read-create
    STATUS   current
    DESCRIPTION
       "The primary routing  metric  for  this  route.
       The  semantics of this metric are determined by
       the routing-protocol specified in  the  route's
       ipCidrRouteProto  value.   If  this metric is not
       used, its value should be set to -1."
    DEFVAL { -1 }
    ::= { ipCidrRouteEntry 11 }

ipCidrRouteMetric2 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { ipCidrRouteEntry 12 }

ipCidrRouteMetric3 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { ipCidrRouteEntry 13 }

ipCidrRouteMetric4 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { ipCidrRouteEntry 14 }

ipCidrRouteMetric5 OBJECT-TYPE
    SYNTAX   Integer32
    MAX-ACCESS read-create
    STATUS   current
    DESCRIPTION
       "An alternate routing metric  for  this  route.
       The  semantics of this metric are determined by
       the routing-protocol specified in  the  route's
       ipCidrRouteProto  value.   If  this metric is not
       used, its value should be set to -1."
    DEFVAL { -1 }
    ::= { ipCidrRouteEntry 15 }

ipCidrRouteStatus OBJECT-TYPE
    SYNTAX   RowStatus
    MAX-ACCESS read-create
    STATUS   current
    DESCRIPTION
       "The row status variable, used according to
       row installation and removal conventions."
    ::= { ipCidrRouteEntry 16 }

-- conformance information

ipForwardConformance OBJECT IDENTIFIER ::= { ipForward 5 }
ipForwardGroups      OBJECT IDENTIFIER ::= { ipForwardConformance 1 }
ipForwardCompliances OBJECT IDENTIFIER ::= { ipForwardConformance 2 }

-- compliance statements

ipForwardCompliance MODULE-COMPLIANCE
   STATUS  current
   DESCRIPTION
       "The compliance statement for SNMPv2 entities
       which implement the ipForward MIB."

   MODULE  -- this module
   MANDATORY-GROUPS { ipForwardCidrRouteGroup }

   ::= { ipForwardCompliances 1 }

-- units of conformance

ipForwardCidrRouteGroup OBJECT-GROUP
    OBJECTS { ipCidrRouteNumber,
              ipCidrRouteDest, ipCidrRouteMask, ipCidrRouteTos,
              ipCidrRouteNextHop, ipCidrRouteIfIndex, ipCidrRouteType,
              ipCidrRouteProto, ipCidrRouteAge, ipCidrRouteInfo,
              ipCidrRouteNextHopAS, ipCidrRouteMetric1,
              ipCidrRouteMetric2, ipCidrRouteMetric3,
              ipCidrRouteMetric4, ipCidrRouteMetric5, ipCidrRouteStatus
        }
    STATUS  current
    DESCRIPTION
       "The CIDR Route Table."
    ::= { ipForwardGroups 3 }

-- Obsoleted Definitions - Objects

ipForwardNumber OBJECT-TYPE
    SYNTAX   Gauge32
    MAX-ACCESS read-only
    STATUS   obsolete
    DESCRIPTION
       "The number of current  ipForwardTable  entries
       that are not invalid."
    ::= { ipForward 1 }

--  IP Forwarding Table

--  The IP Forwarding Table obsoletes and replaces the ipRoute
--  Table current in MIB-I and MIB-II.  It adds knowledge of
--  the autonomous system of the next hop, multiple next hop
--  support, and policy routing support.

ipForwardTable OBJECT-TYPE
    SYNTAX   SEQUENCE OF IpForwardEntry
    MAX-ACCESS not-accessible
    STATUS   obsolete
    DESCRIPTION
       "This entity's IP Routing table."
    REFERENCE
       "RFC 1213 Section 6.6, The IP Group"
    ::= { ipForward 2 }

ipForwardEntry OBJECT-TYPE
    SYNTAX   IpForwardEntry
    MAX-ACCESS not-accessible
    STATUS   obsolete
    DESCRIPTION
       "A particular route to  a  particular  destina-
       tion, under a particular policy."
    INDEX {
        ipForwardDest,
        ipForwardProto,
        ipForwardPolicy,
        ipForwardNextHop
        }
    ::= { ipForwardTable 1 }

IpForwardEntry ::=
    SEQUENCE {
        ipForwardDest
            IpAddress,
        ipForwardMask
            IpAddress,
        ipForwardPolicy
             Integer32,
        ipForwardNextHop
            IpAddress,
        ipForwardIfIndex
            Integer32,
        ipForwardType
            INTEGER,
        ipForwardProto
            INTEGER,
        ipForwardAge
            Integer32,
        ipForwardInfo
            OBJECT IDENTIFIER,
        ipForwardNextHopAS
            Integer32,
        ipForwardMetric1
            Integer32,
        ipForwardMetric2
            Integer32,
        ipForwardMetric3
            Integer32,
        ipForwardMetric4
            Integer32,
        ipForwardMetric5
            Integer32
    }

ipForwardDest OBJECT-TYPE
    SYNTAX   IpAddress
    MAX-ACCESS read-only
    STATUS   obsolete
    DESCRIPTION
       "The destination IP address of this route.   An
       entry  with  a value of 0.0.0.0 is considered a
       default route.

       This object may not take a Multicast (Class  D)
       address value.

       Any assignment (implicit or  otherwise)  of  an
       instance  of  this  object to a value x must be
       rejected if the bitwise logical-AND of  x  with
       the  value of the corresponding instance of the
       ipForwardMask object is not equal to x."
    ::= { ipForwardEntry 1 }

ipForwardMask OBJECT-TYPE
    SYNTAX   IpAddress
    MAX-ACCESS read-create
    STATUS   obsolete
    DESCRIPTION
       "Indicate the mask to be logical-ANDed with the
       destination  address  before  being compared to
       the value  in  the  ipForwardDest  field.   For
       those  systems  that  do  not support arbitrary
       subnet masks, an agent constructs the value  of
       the  ipForwardMask  by  reference to the IP Ad-
       dress Class.

       Any assignment (implicit or  otherwise)  of  an
       instance  of  this  object to a value x must be
       rejected if the bitwise logical-AND of  x  with
       the  value of the corresponding instance of the
       ipForwardDest object is not equal to ipForward-
       Dest."
    DEFVAL { '00000000'h }      -- 0.0.0.0
    ::= { ipForwardEntry 2 }

-- The following convention is included for specification
-- of TOS Field contents.  At this time, the Host Requirements
-- and the Router Requirements documents disagree on the width
-- of the TOS field.  This mapping describes the Router
-- Requirements mapping, and leaves room to widen the TOS field
-- without impact to fielded systems.

ipForwardPolicy OBJECT-TYPE
    SYNTAX   Integer32
    MAX-ACCESS read-only
    STATUS   obsolete
    DESCRIPTION
       "The general set of conditions that would cause
       the  selection  of  one multipath route (set of
       next hops for a given destination) is  referred
       to as 'policy'.

       Unless the mechanism indicated by ipForwardPro-
       to specifies otherwise, the policy specifier is
       the IP TOS Field.  The encoding of IP TOS is as
        specified  by  the  following convention.  Zero
       indicates the default path if no more  specific
       policy applies.

       +-----+-----+-----+-----+-----+-----+-----+-----+
       |                 |                       |     |
       |   PRECEDENCE    |    TYPE OF SERVICE    |  0  |
       |                 |                       |     |
       +-----+-----+-----+-----+-----+-----+-----+-----+

                IP TOS                IP TOS
           Field     Policy      Field     Policy
           Contents    Code      Contents    Code
           0 0 0 0  ==&gt;   0      0 0 0 1  ==&gt;   2
           0 0 1 0  ==&gt;   4      0 0 1 1  ==&gt;   6
           0 1 0 0  ==&gt;   8      0 1 0 1  ==&gt;  10
           0 1 1 0  ==&gt;  12      0 1 1 1  ==&gt;  14
           1 0 0 0  ==&gt;  16      1 0 0 1  ==&gt;  18
           1 0 1 0  ==&gt;  20      1 0 1 1  ==&gt;  22
           1 1 0 0  ==&gt;  24      1 1 0 1  ==&gt;  26
           1 1 1 0  ==&gt;  28      1 1 1 1  ==&gt;  30

       Protocols defining 'policy' otherwise must  ei-
       ther define a set of values which are valid for
       this  object  or  must  implement  an  integer-
       instanced  policy table for which this object's
       value acts as an index."
    ::= { ipForwardEntry 3 }

ipForwardNextHop OBJECT-TYPE
    SYNTAX   IpAddress
    MAX-ACCESS read-only
    STATUS   obsolete
    DESCRIPTION
       "On remote routes, the address of the next sys-
       tem en route; Otherwise, 0.0.0.0."
    ::= { ipForwardEntry 4 }

ipForwardIfIndex OBJECT-TYPE
    SYNTAX   Integer32
    MAX-ACCESS read-create
    STATUS   obsolete
    DESCRIPTION
       "The ifIndex value which identifies  the  local
       interface  through  which  the next hop of this
       route should be reached."
    DEFVAL { 0 }
    ::= { ipForwardEntry 5 }

ipForwardType OBJECT-TYPE
    SYNTAX   INTEGER {
                other    (1), -- not specified by this MIB
                invalid  (2), -- logically deleted
                local    (3), -- local interface
                remote   (4)  -- remote destination
             }
    MAX-ACCESS read-create
    STATUS   obsolete
    DESCRIPTION
       "The type of route.  Note that local(3)  refers
       to  a route for which the next hop is the final
       destination; remote(4) refers to  a  route  for
       which  the  next  hop is not the final destina-
       tion.

       Setting this object to the value invalid(2) has
       the  effect  of  invalidating the corresponding
       entry in the ipForwardTable object.   That  is,
       it  effectively  disassociates  the destination
       identified with said entry from the route iden-
       tified    with    said   entry.    It   is   an
       implementation-specific matter  as  to  whether
       the agent removes an invalidated entry from the
       table.  Accordingly, management  stations  must
       be prepared to receive tabular information from
       agents that corresponds to entries not current-
       ly  in  use.  Proper interpretation of such en-
       tries requires examination of the relevant  ip-
       ForwardType object."
    DEFVAL { invalid }
    ::= { ipForwardEntry 6 }

ipForwardProto OBJECT-TYPE
    SYNTAX   INTEGER {
                other     (1),  -- not specified
                local     (2),  -- local interface
                netmgmt   (3),  -- static route
                icmp      (4),  -- result of ICMP Redirect

                        -- the following are all dynamic
                        -- routing protocols
                egp       (5),  -- Exterior Gateway Protocol
                ggp       (6),  -- Gateway-Gateway Protocol
                hello     (7),  -- FuzzBall HelloSpeak
                rip       (8),  -- Berkeley RIP or RIP-II
                is-is     (9),  -- Dual IS-IS
                es-is     (10), -- ISO 9542
                ciscoIgrp (11), -- Cisco IGRP
                bbnSpfIgp (12), -- BBN SPF IGP
                ospf      (13), -- Open Shortest Path First
                bgp       (14), -- Border Gateway Protocol
                idpr      (15)  -- InterDomain Policy Routing
             }
    MAX-ACCESS read-only
    STATUS   obsolete
    DESCRIPTION
       "The routing mechanism via which this route was
       learned.  Inclusion of values for gateway rout-
       ing protocols is not  intended  to  imply  that
       hosts should support those protocols."
    ::= { ipForwardEntry 7 }

ipForwardAge OBJECT-TYPE
    SYNTAX   Integer32
    MAX-ACCESS read-only
    STATUS   obsolete
    DESCRIPTION
       "The number of seconds  since  this  route  was
       last  updated  or  otherwise  determined  to be
       correct.  Note that no semantics of  `too  old'
       can  be implied except through knowledge of the
       routing  protocol  by  which  the   route   was
       learned."
    DEFVAL  { 0 }
    ::= { ipForwardEntry 8 }

ipForwardInfo OBJECT-TYPE
    SYNTAX   OBJECT IDENTIFIER
    MAX-ACCESS read-create
    STATUS   obsolete
    DESCRIPTION
       "A reference to MIB definitions specific to the
       particular  routing protocol which is responsi-
       ble for this route, as determined by the  value
       specified  in the route's ipForwardProto value.
       If this information is not present,  its  value
       should be set to the OBJECT IDENTIFIER { 0 0 },
       which is a syntactically valid object  identif-
       ier, and any implementation conforming to ASN.1
       and the Basic Encoding Rules must  be  able  to
       generate and recognize this value."
    ::= { ipForwardEntry 9 }

ipForwardNextHopAS OBJECT-TYPE
    SYNTAX   Integer32
    MAX-ACCESS read-create
    STATUS   obsolete
    DESCRIPTION
       "The Autonomous System Number of the Next  Hop.
       When  this  is  unknown  or not relevant to the
       protocol indicated by ipForwardProto, zero."
    DEFVAL { 0 }
    ::= { ipForwardEntry 10 }

ipForwardMetric1 OBJECT-TYPE
    SYNTAX   Integer32
    MAX-ACCESS read-create
    STATUS   obsolete
    DESCRIPTION
       "The primary routing  metric  for  this  route.
       The  semantics of this metric are determined by
       the routing-protocol specified in  the  route's
       ipForwardProto  value.   If  this metric is not
       used, its value should be set to -1."
    DEFVAL { -1 }
    ::= { ipForwardEntry 11 }
ipForwardMetric2 OBJECT-TYPE
    SYNTAX   Integer32
    MAX-ACCESS read-create
    STATUS   obsolete
    DESCRIPTION
       "An alternate routing metric  for  this  route.
       The  semantics of this metric are determined by
       the routing-protocol specified in  the  route's
       ipForwardProto  value.   If  this metric is not
       used, its value should be set to -1."

    DEFVAL { -1 }
    ::= { ipForwardEntry 12 }

ipForwardMetric3 OBJECT-TYPE
    SYNTAX   Integer32
    MAX-ACCESS read-create
    STATUS   obsolete
    DESCRIPTION
       "An alternate routing metric  for  this  route.
       The  semantics of this metric are determined by
       the routing-protocol specified in  the  route's
       ipForwardProto  value.   If  this metric is not
       used, its value should be set to -1."
    DEFVAL { -1 }
    ::= { ipForwardEntry 13 }

ipForwardMetric4 OBJECT-TYPE
    SYNTAX   Integer32
    MAX-ACCESS read-create
    STATUS   obsolete
    DESCRIPTION
       "An alternate routing metric  for  this  route.
       The  semantics of this metric are determined by
       the routing-protocol specified in  the  route's
       ipForwardProto  value.   If  this metric is not
       used, its value should be set to -1."
    DEFVAL { -1 }
    ::= { ipForwardEntry 14 }

ipForwardMetric5 OBJECT-TYPE
    SYNTAX   Integer32
    MAX-ACCESS read-create
    STATUS   obsolete
    DESCRIPTION
       "An alternate routing metric  for  this  route.
       The  semantics of this metric are determined by
       the routing-protocol specified in  the  route's
       ipForwardProto  value.   If  this metric is not
       used, its value should be set to -1."
    DEFVAL { -1 }
    ::= { ipForwardEntry 15 }

-- Obsoleted Definitions - Groups
-- compliance statements

ipForwardOldCompliance MODULE-COMPLIANCE
   STATUS  obsolete
   DESCRIPTION
       "The compliance statement for SNMP entities
       which implement the ipForward MIB."

   MODULE  -- this module
   MANDATORY-GROUPS { ipForwardMultiPathGroup }

   ::= { ipForwardCompliances 2 }

ipForwardMultiPathGroup OBJECT-GROUP
    OBJECTS { ipForwardNumber,
              ipForwardDest, ipForwardMask, ipForwardPolicy,
              ipForwardNextHop, ipForwardIfIndex, ipForwardType,
              ipForwardProto, ipForwardAge, ipForwardInfo,
              ipForwardNextHopAS,
              ipForwardMetric1, ipForwardMetric2, ipForwardMetric3,
              ipForwardMetric4, ipForwardMetric5
        }
    STATUS  obsolete
    DESCRIPTION
       "IP Multipath Route Table."
    ::= { ipForwardGroups 2 }

END

PerfHist-TC-MIB DEFINITIONS ::= BEGIN

     IMPORTS
        MODULE-IDENTITY,
        Gauge32, mib-2
            FROM SNMPv2-SMI
        TEXTUAL-CONVENTION
            FROM SNMPv2-TC;

     perfHistTCMIB MODULE-IDENTITY


          LAST-UPDATED "9811071100Z"
          ORGANIZATION "IETF AToMMIB and TrunkMIB WGs"
          CONTACT-INFO
                       "Kaj Tesink
              Postal:  Bellcore
                       331 Newman Springs Road
                       Red Bank, NJ 07701
                       USA
              Tel:     +1 732 758 5254
              Fax:     +1 732 758 2269
              E-mail:  kaj@bellcore.com"
          DESCRIPTION
           "This MIB Module provides Textual Conventions
             to be used by systems supporting 15 minute
             based performance history counts."
          ::= { mib-2 58 }

     -- The Textual Conventions defined below are organized
     -- alphabetically

     -- Use of these TCs assumes the following:
     -- 0  The agent supports 15 minute based history
     --    counters.
     -- 0  The agent is capable of keeping a history of n
     --    intervals of 15 minute performance data. The
     --    value of n is defined by the specific MIB
     --    module but shall be 0 &lt; n =&lt; 96.
     -- 0  The agent may optionally support performance
     --    data aggregating the history intervals.
     -- 0  The agent will keep separate tables for the
     --    current interval, the history intervals, and
     --    the total aggregates.
     -- 0  The agent will keep the following objects.
     --    If performance data is kept for multiple instances
     --    of a measured entity, then
     --    these objects are applied to each instance of
     --    the measured entity (e.g., interfaces).
     --

     -- xyzTimeElapsed OBJECT-TYPE
     --       SYNTAX  INTEGER (0..899)
     --       MAX-ACCESS  read-only
     --       STATUS  current
     --       DESCRIPTION


     --       "The number of seconds that have elapsed since
     --       the beginning of the current measurement period.
     --       If, for some reason, such as an adjustment in the
     --       system's time-of-day clock, the current interval
     --       exceeds the maximum value, the agent will return
     --       the maximum value."
     --       ::= { xxx }

     -- xyzValidIntervals OBJECT-TYPE
     --       SYNTAX  INTEGER (0..&lt;n&gt;)
     --       MAX-ACCESS  read-only
     --       STATUS  current
     --       DESCRIPTION
     --       "The number of previous near end intervals
     --       for which data was collected.
     --          [ The overall constraint on &lt;n&gt; is 1 =&lt; n =&lt; 96; ]
     --          [ Define any additional constraints on &lt;n&gt; here. ]
     --       The value will be &lt;n&gt; unless the measurement was
     --       (re-)started within the last (&lt;n&gt;*15) minutes, in which
     --       case the value will be the number of complete 15
     --       minute intervals for which the agent has at least
     --       some data. In certain cases (e.g., in the case
     --       where the agent is a proxy) it is possible that some
     --       intervals are unavailable.  In this case, this
     --       interval is the maximum interval number for
     --       which data is available."
     --       ::= { xxx }

     -- xyzInvalidIntervals OBJECT-TYPE
     --     SYNTAX  INTEGER (0..&lt;n&gt;)
     --     MAX-ACCESS  read-only
     --     STATUS  current
     --     DESCRIPTION
     --       "The number of intervals in the range from
     --        0 to xyzValidIntervals for which no
     --        data is available. This object will typically
     --        be zero except in cases where the data for some
     --        intervals are not available (e.g., in proxy
     --        situations)."
     --       ::= { xxx }

     PerfCurrentCount ::= TEXTUAL-CONVENTION
           STATUS  current
           DESCRIPTION
              "A counter associated with a
               performance measurement in a current 15
               minute measurement interval. The value
               of this counter starts from zero and is


               increased when associated events occur,
               until the end of the 15 minute interval.
               At that time the value of the counter is
               stored in the first 15 minute history
               interval, and the CurrentCount is
               restarted at zero. In the
               case where the agent has no valid data
               available for the current interval the
               corresponding object instance is not
               available and upon a retrieval request
               a corresponding error message shall be
               returned to indicate that this instance
               does not exist (for example, a noSuchName
               error for SNMPv1 and a noSuchInstance for
               SNMPv2 GET operation)."
            SYNTAX  Gauge32

     PerfIntervalCount ::= TEXTUAL-CONVENTION
           STATUS  current
           DESCRIPTION
              "A counter associated with a
               performance measurement in a previous
               15 minute measurement interval. In the
               case where the agent has no valid data
               available for a particular interval the
               corresponding object instance is not
               available and upon a retrieval request
               a corresponding error message shall be
               returned to indicate that this instance
               does not exist (for example, a noSuchName
               error for SNMPv1 and a noSuchInstance for
               SNMPv2 GET operation).
               In a system supporting
               a history of n intervals with
               IntervalCount(1) and IntervalCount(n) the
               most and least recent intervals
               respectively, the following applies at
               the end of a 15 minute interval:
               - discard the value of IntervalCount(n)
               - the value of IntervalCount(i) becomes that
                 of IntervalCount(i-1) for n &gt;= i &gt; 1
               - the value of IntervalCount(1) becomes that
                 of CurrentCount
               - the TotalCount, if supported, is adjusted."
            SYNTAX  Gauge32

     PerfTotalCount ::= TEXTUAL-CONVENTION
           STATUS  current


           DESCRIPTION
              "A counter associated with a
               performance measurements aggregating the
               previous valid 15 minute measurement
               intervals. (Intervals for which no valid
               data was available are not counted)"
            SYNTAX  Gauge32

END

DS1-MIB DEFINITIONS ::= BEGIN

     IMPORTS
          MODULE-IDENTITY, OBJECT-TYPE,
          NOTIFICATION-TYPE, transmission         FROM SNMPv2-SMI
          DisplayString, TimeStamp, TruthValue    FROM SNMPv2-TC
          MODULE-COMPLIANCE, OBJECT-GROUP,
          NOTIFICATION-GROUP                      FROM SNMPv2-CONF
          InterfaceIndex, ifIndex                 FROM IF-MIB
          PerfCurrentCount, PerfIntervalCount,
          PerfTotalCount                          FROM PerfHist-TC-MIB;

     ds1 MODULE-IDENTITY
         LAST-UPDATED "9808011830Z"
         ORGANIZATION "IETF Trunk MIB Working Group"
         CONTACT-INFO
           "        David Fowler

            Postal: Newbridge Networks Corporation
                    600 March Road
                    Kanata, Ontario, Canada K2K 2E6

                    Tel: +1 613 591 3600


                    Fax: +1 613 599 3667

            E-mail: davef@newbridge.com"
         DESCRIPTION
              "The MIB module to describe DS1, E1, DS2, and
               E2 interfaces objects."

         ::= { transmission 18 }

     -- note that this subsumes cept (19) and g703at2mb (67)
     -- there is no separate CEPT or G703AT2MB MIB

     -- The DS1 Near End Group

     -- The DS1 Near End Group consists of five tables:
     --    DS1 Configuration
     --    DS1 Current
     --    DS1 Interval
     --    DS1 Total
     --    DS1 Channel Table

     -- The DS1 Configuration Table

     dsx1ConfigTable OBJECT-TYPE
          SYNTAX  SEQUENCE OF Dsx1ConfigEntry
          MAX-ACCESS  not-accessible
          STATUS  current
          DESCRIPTION
                 "The DS1 Configuration table."
          ::= { ds1 6 }

     dsx1ConfigEntry OBJECT-TYPE
          SYNTAX  Dsx1ConfigEntry
          MAX-ACCESS  not-accessible
          STATUS  current
          DESCRIPTION
                 "An entry in the DS1 Configuration table."
          INDEX   { dsx1LineIndex }
          ::= { dsx1ConfigTable 1 }

     Dsx1ConfigEntry ::=
          SEQUENCE {
              dsx1LineIndex                        InterfaceIndex,
              dsx1IfIndex                          InterfaceIndex,
              dsx1TimeElapsed                      INTEGER,
              dsx1ValidIntervals                   INTEGER,
              dsx1LineType                         INTEGER,
              dsx1LineCoding                       INTEGER,


              dsx1SendCode                         INTEGER,
              dsx1CircuitIdentifier                DisplayString,
              dsx1LoopbackConfig                   INTEGER,
              dsx1LineStatus                       INTEGER,
              dsx1SignalMode                       INTEGER,
              dsx1TransmitClockSource              INTEGER,
              dsx1Fdl                              INTEGER,
              dsx1InvalidIntervals                 INTEGER,
              dsx1LineLength                       INTEGER,
              dsx1LineStatusLastChange             TimeStamp,
              dsx1LineStatusChangeTrapEnable       INTEGER,
              dsx1LoopbackStatus                   INTEGER,
              dsx1Ds1ChannelNumber                 INTEGER,
              dsx1Channelization                   INTEGER
     }

     dsx1LineIndex OBJECT-TYPE
          SYNTAX  InterfaceIndex
          MAX-ACCESS  read-only
          STATUS  current
          DESCRIPTION
                 "This object should be made equal to ifIndex.  The
                 next paragraph describes its previous usage.
                 Making the object equal to ifIndex allows proper
                 use of ifStackTable and ds0/ds0bundle mibs.

                 Previously, this object is the identifier of a DS1
                 Interface on a managed device.  If there is an
                 ifEntry that is directly associated with this and
                 only this DS1 interface, it should have the same
                 value as ifIndex.  Otherwise, number the
                 dsx1LineIndices with an unique identifier
                 following the rules of choosing a number that is
                 greater than ifNumber and numbering the inside
                 interfaces (e.g., equipment side) with even
                 numbers and outside interfaces (e.g, network side)
                 with odd numbers."
          ::= { dsx1ConfigEntry 1 }

     dsx1IfIndex OBJECT-TYPE
          SYNTAX  InterfaceIndex
          MAX-ACCESS  read-only
          STATUS  deprecated
          DESCRIPTION
                 "This value for this object is equal to the value
                 of ifIndex from the Interfaces table of MIB II
                 (RFC 1213)."
          ::= { dsx1ConfigEntry 2 }


     dsx1TimeElapsed OBJECT-TYPE
          SYNTAX  INTEGER (0..899)
          MAX-ACCESS  read-only
          STATUS  current
          DESCRIPTION
                   "The number of seconds that have elapsed since
                        the beginning of the near end current error-
                   measurement period.  If, for some reason, such
                        as an adjustment in the system's time-of-day
                        clock, the current interval exceeds the maximum
                        value, the agent will return the maximum value."

          ::= { dsx1ConfigEntry 3 }

     dsx1ValidIntervals OBJECT-TYPE
          SYNTAX  INTEGER (0..96)
          MAX-ACCESS  read-only
          STATUS  current
          DESCRIPTION
                 "The number of previous near end intervals for
                 which data was collected.  The value will be
                 96 unless the interface was brought online within
                 the last 24 hours, in which case the value will be
                 the number of complete 15 minute near end
                 intervals since the interface has been online.  In
                 the case where the agent is a proxy, it is
                 possible that some intervals are unavailable.  In
                 this case, this interval is the maximum interval
                 number for which data is available."
          ::= { dsx1ConfigEntry 4 }

     dsx1LineType OBJECT-TYPE
          SYNTAX  INTEGER {
                     other(1),
                     dsx1ESF(2),
                     dsx1D4(3),
                     dsx1E1(4),
                     dsx1E1CRC(5),
                     dsx1E1MF(6),
                     dsx1E1CRCMF(7),
                     dsx1Unframed(8),
                     dsx1E1Unframed(9),
                     dsx1DS2M12(10),
                     dsx2E2(11)
                 }
          MAX-ACCESS  read-write
          STATUS  current
          DESCRIPTION


                 "This variable indicates  the  variety  of  DS1
                 Line  implementing  this  circuit.  The type of
                 circuit affects the number of bits  per  second
                 that  the circuit can reasonably carry, as well
                 as the interpretation of the  usage  and  error
                 statistics.  The values, in sequence, describe:

                 TITLE:         SPECIFICATION:
                 dsx1ESF         Extended SuperFrame DS1 (T1.107)
                 dsx1D4          AT&amp;T D4 format DS1 (T1.107)
                 dsx1E1          ITU-T Recommendation G.704
                                  (Table 4a)
                 dsx1E1-CRC      ITU-T Recommendation G.704
                                  (Table 4b)
                 dsxE1-MF        G.704 (Table 4a) with TS16
                                  multiframing enabled
                 dsx1E1-CRC-MF   G.704 (Table 4b) with TS16
                                  multiframing enabled
                 dsx1Unframed    DS1 with No Framing
                 dsx1E1Unframed  E1 with No Framing (G.703)
                 dsx1DS2M12      DS2 frame format (T1.107)
                 dsx1E2          E2 frame format (G.704)

                 For clarification, the capacity for each E1 type
                 is as listed below:
                 dsx1E1Unframed - E1, no framing = 32 x 64k = 2048k
                 dsx1E1 or dsx1E1CRC - E1, with framing,
                    no signalling = 31 x 64k = 1984k
                 dsx1E1MF or dsx1E1CRCMF - E1, with framing,
                    signalling = 30 x 64k = 1920k

                 For further information See ITU-T Recomm G.704"
          ::= { dsx1ConfigEntry 5 }

     dsx1LineCoding OBJECT-TYPE
          SYNTAX  INTEGER {
                     dsx1JBZS (1),
                     dsx1B8ZS (2),
                     dsx1HDB3 (3),
                     dsx1ZBTSI (4),
                     dsx1AMI (5),
                     other(6),
                     dsx1B6ZS(7)
                 }
          MAX-ACCESS  read-write
          STATUS  current
          DESCRIPTION
                 "This variable describes the variety of Zero Code


                 Suppression used on this interface, which in turn
                 affects a number of its characteristics.

                 dsx1JBZS refers the Jammed Bit Zero Suppression,
                 in which the AT&amp;T specification of at least one
                 pulse every 8 bit periods is literally implemented
                 by forcing a pulse in bit 8 of each channel.
                 Thus, only seven bits per channel, or 1.344 Mbps,
                 is available for data.

                 dsx1B8ZS refers to the use of a specified pattern
                 of normal bits and bipolar violations which are
                 used to replace a sequence of eight zero bits.

                 ANSI Clear Channels may use dsx1ZBTSI, or Zero
                 Byte Time Slot Interchange.

                 E1 links, with or without CRC, use dsx1HDB3 or
                 dsx1AMI.

                 dsx1AMI refers to a mode wherein no zero code
                 suppression is present and the line encoding does
                 not solve the problem directly.  In this
                 application, the higher layer must provide data
                 which meets or exceeds the pulse density
                 requirements, such as inverting HDLC data.

                 dsx1B6ZS refers to the user of a specifed pattern
                 of normal bits and bipolar violations which are
                 used to replace a sequence of six zero bits.  Used
                 for DS2."

          ::= { dsx1ConfigEntry 6 }

     dsx1SendCode OBJECT-TYPE
          SYNTAX  INTEGER {
                    dsx1SendNoCode(1),
                    dsx1SendLineCode(2),
                    dsx1SendPayloadCode(3),
                    dsx1SendResetCode(4),
                    dsx1SendQRS(5),
                    dsx1Send511Pattern(6),
                    dsx1Send3in24Pattern(7),
                    dsx1SendOtherTestPattern(8)
                    }
          MAX-ACCESS  read-write
          STATUS  current
          DESCRIPTION


                 "This variable indicates what type of code is
                 being sent across the DS1 interface by the device.
                 Setting this variable causes the interface to send
                 the code requested.  The values mean:
           dsx1SendNoCode
                sending looped or normal data

           dsx1SendLineCode
                sending a request for a line loopback

           dsx1SendPayloadCode
                sending a request for a payload loopback

           dsx1SendResetCode
                sending a loopback termination request

           dsx1SendQRS
                sending a Quasi-Random Signal  (QRS)  test
                pattern

           dsx1Send511Pattern
                sending a 511 bit fixed test pattern

           dsx1Send3in24Pattern
                sending a fixed test pattern of 3 bits set
                in 24

           dsx1SendOtherTestPattern
                sending a test pattern  other  than  those
                described by this object"
::= { dsx1ConfigEntry 7 }

     dsx1CircuitIdentifier OBJECT-TYPE
          SYNTAX  DisplayString (SIZE (0..255))
          MAX-ACCESS  read-write
          STATUS  current
          DESCRIPTION
                 "This variable contains the transmission vendor's
                 circuit identifier, for the purpose of
                 facilitating troubleshooting."
          ::= { dsx1ConfigEntry 8 }

     dsx1LoopbackConfig OBJECT-TYPE
          SYNTAX  INTEGER {
                      dsx1NoLoop(1),
                      dsx1PayloadLoop(2),
                      dsx1LineLoop(3),
                      dsx1OtherLoop(4),


                      dsx1InwardLoop(5),
                      dsx1DualLoop(6)
                    }
          MAX-ACCESS  read-write
          STATUS  current
          DESCRIPTION
                 "This variable represents the desired loopback
                 configuration of the DS1 interface.  Agents
                 supporting read/write access should return
                 inconsistentValue in response to a requested
                 loopback state that the interface does not
                 support.  The values mean:

                 dsx1NoLoop
                  Not in the loopback state.  A device that is not
                 capable of performing a loopback on the interface
                 shall always return this as its value.

                 dsx1PayloadLoop
                  The received signal at this interface is looped
                 through the device.  Typically the received signal
                 is looped back for retransmission after it has
                 passed through the device's framing function.

                 dsx1LineLoop
                  The received signal at this interface does not go
                 through the device (minimum penetration) but is
                 looped back out.

                 dsx1OtherLoop
                  Loopbacks that are not defined here.

                 dsx1InwardLoop
                  The transmitted signal at this interface is
                 looped back and received by the same interface.
                 What is transmitted onto the line is product
                 dependent.

                 dsx1DualLoop
                  Both dsx1LineLoop and dsx1InwardLoop will be
                 active simultaneously."
          ::= { dsx1ConfigEntry 9 }

     dsx1LineStatus OBJECT-TYPE
          SYNTAX  INTEGER (1..131071)
          MAX-ACCESS  read-only
          STATUS  current
          DESCRIPTION


                 "This variable indicates the Line Status of the
                 interface.  It contains loopback, failure,
                 received 'alarm' and transmitted 'alarms
                 information.

                 The dsx1LineStatus is a bit map represented as a
                 sum, therefore, it can represent multiple failures
                 (alarms) and a LoopbackState simultaneously.

                 dsx1NoAlarm must be set if and only if no other
                 flag is set.

                 If the dsx1loopbackState bit is set, the loopback
                 in effect can be determined from the
                 dsx1loopbackConfig object.
       The various bit positions are:
      1     dsx1NoAlarm           No alarm present
      2     dsx1RcvFarEndLOF      Far end LOF (a.k.a., Yellow Alarm)
      4     dsx1XmtFarEndLOF      Near end sending LOF Indication
      8     dsx1RcvAIS            Far end sending AIS
     16     dsx1XmtAIS            Near end sending AIS
     32     dsx1LossOfFrame       Near end LOF (a.k.a., Red Alarm)
     64     dsx1LossOfSignal      Near end Loss Of Signal
    128     dsx1LoopbackState     Near end is looped
    256     dsx1T16AIS            E1 TS16 AIS
    512     dsx1RcvFarEndLOMF     Far End Sending TS16 LOMF
   1024     dsx1XmtFarEndLOMF     Near End Sending TS16 LOMF
   2048     dsx1RcvTestCode       Near End detects a test code
   4096     dsx1OtherFailure      any line status not defined here
   8192     dsx1UnavailSigState   Near End in Unavailable Signal
                                  State
  16384     dsx1NetEquipOOS       Carrier Equipment Out of Service
  32768     dsx1RcvPayloadAIS     DS2 Payload AIS
  65536     dsx1Ds2PerfThreshold  DS2 Performance Threshold
                                  Exceeded"
     ::= { dsx1ConfigEntry 10 }

     dsx1SignalMode OBJECT-TYPE
          SYNTAX  INTEGER {
                     none (1),
                     robbedBit (2),
                     bitOriented (3),
                     messageOriented (4),
                     other (5)
                 }
          MAX-ACCESS  read-write
          STATUS  current
          DESCRIPTION


            "'none' indicates that no bits are reserved for
            signaling on this channel.

            'robbedBit' indicates that DS1 Robbed Bit  Sig-
            naling is in use.

            'bitOriented' indicates that E1 Channel  Asso-
            ciated Signaling is in use.

            'messageOriented' indicates that Common  Chan-
            nel Signaling is in use either on channel 16 of
            an E1 link or channel 24 of a DS1."
          ::= { dsx1ConfigEntry 11 }

     dsx1TransmitClockSource OBJECT-TYPE
          SYNTAX  INTEGER {
                     loopTiming(1),
                     localTiming(2),
                     throughTiming(3)
                 }
          MAX-ACCESS  read-write
          STATUS  current
          DESCRIPTION
            "The source of Transmit Clock.
             'loopTiming' indicates that the recovered re-
            ceive clock is used as the transmit clock.

             'localTiming' indicates that a local clock
            source is used or when an external clock is
            attached to the box containing the interface.

             'throughTiming' indicates that recovered re-
            ceive clock from another interface is used as
            the transmit clock."
          ::= { dsx1ConfigEntry 12 }

     dsx1Fdl OBJECT-TYPE
          SYNTAX  INTEGER (1..15)
          MAX-ACCESS  read-write
          STATUS  current
          DESCRIPTION
            "This bitmap describes the use of  the  facili-
            ties data link, and is the sum of the capabili-
            ties.  Set any bits that are appropriate:

            other(1),
            dsx1AnsiT1403(2),
            dsx1Att54016(4),


            dsx1FdlNone(8)

             'other' indicates that a protocol  other  than
            one following is used.

             'dsx1AnsiT1403' refers to the  FDL  exchange
            recommended by ANSI.

             'dsx1Att54016' refers to ESF FDL exchanges.

             'dsx1FdlNone' indicates that the device  does
            not use the FDL."
          ::= { dsx1ConfigEntry 13 }

     dsx1InvalidIntervals OBJECT-TYPE
          SYNTAX  INTEGER (0..96)
          MAX-ACCESS  read-only
          STATUS  current
          DESCRIPTION
                 "The number of intervals in the range from 0 to
                 dsx1ValidIntervals for which no data is
                 available.  This object will typically be zero
                 except in cases where the data for some intervals
                 are not available (e.g., in proxy situations)."
          ::= { dsx1ConfigEntry 14 }

     dsx1LineLength OBJECT-TYPE
          SYNTAX  INTEGER (0..64000)
          UNITS  "meters"
          MAX-ACCESS  read-write
          STATUS  current
          DESCRIPTION
                 "The length of the ds1 line in meters. This
                 objects provides information for line build out
                 circuitry.  This object is only useful if the
                 interface has configurable line build out
                 circuitry."

          ::= { dsx1ConfigEntry 15 }

     dsx1LineStatusLastChange OBJECT-TYPE
          SYNTAX  TimeStamp
          MAX-ACCESS  read-only
          STATUS  current
          DESCRIPTION
                 "The value of MIB II's sysUpTime object at the
                 time this DS1 entered its current line status
                 state.  If the current state was entered prior to


                 the last re-initialization of the proxy-agent,
                 then this object contains a zero value."
          ::= { dsx1ConfigEntry 16 }

     dsx1LineStatusChangeTrapEnable  OBJECT-TYPE
          SYNTAX      INTEGER {
                         enabled(1),
                         disabled(2)
                      }
          MAX-ACCESS  read-write
          STATUS      current
          DESCRIPTION
                 "Indicates whether dsx1LineStatusChange traps
                 should be generated for this interface."
          DEFVAL { disabled }
          ::= { dsx1ConfigEntry 17 }

     dsx1LoopbackStatus  OBJECT-TYPE
          SYNTAX      INTEGER (1..127)
          MAX-ACCESS  read-only
          STATUS      current
          DESCRIPTION
                 "This variable represents the current state of the
                 loopback on the DS1 interface.  It contains
                 information about loopbacks established by a
                 manager and remotely from the far end.

                 The dsx1LoopbackStatus is a bit map represented as
                 a sum, therefore is can represent multiple
                 loopbacks simultaneously.

                 The various bit positions are:
                  1  dsx1NoLoopback
                  2  dsx1NearEndPayloadLoopback
                  4  dsx1NearEndLineLoopback
                  8  dsx1NearEndOtherLoopback
                 16  dsx1NearEndInwardLoopback
                 32  dsx1FarEndPayloadLoopback
                 64  dsx1FarEndLineLoopback"

     ::= { dsx1ConfigEntry 18 }

     dsx1Ds1ChannelNumber  OBJECT-TYPE
          SYNTAX      INTEGER (0..28)
          MAX-ACCESS  read-only
          STATUS      current
          DESCRIPTION
                 "This variable represents the channel number of


                 the DS1/E1 on its parent Ds2/E2 or DS3/E3.  A
                 value of 0 indicated this DS1/E1 does not have a
                 parent DS3/E3."

     ::= { dsx1ConfigEntry 19 }

     dsx1Channelization  OBJECT-TYPE
          SYNTAX      INTEGER {
                         disabled(1),
                         enabledDs0(2),
                         enabledDs1(3)
                      }
          MAX-ACCESS  read-write
          STATUS      current
          DESCRIPTION
                 "Indicates whether this ds1/e1 is channelized or
                 unchannelized.  The value of enabledDs0 indicates
                 that this is a DS1 channelized into DS0s.  The
                 value of enabledDs1 indicated that this is a DS2
                 channelized into DS1s.  Setting this value will
                 cause the creation or deletion of entries in the
                 ifTable for the DS0s that are within the DS1."
     ::= { dsx1ConfigEntry 20 }

     -- The DS1 Current Table
     dsx1CurrentTable OBJECT-TYPE
          SYNTAX  SEQUENCE OF Dsx1CurrentEntry
          MAX-ACCESS  not-accessible
          STATUS  current
          DESCRIPTION
                 "The DS1 current table contains various statistics
                 being collected for the current 15 minute
                 interval."
          ::= { ds1 7 }

     dsx1CurrentEntry OBJECT-TYPE
          SYNTAX  Dsx1CurrentEntry
          MAX-ACCESS  not-accessible
          STATUS  current
          DESCRIPTION
                 "An entry in the DS1 Current table."
                      INDEX   { dsx1CurrentIndex }
                      ::= { dsx1CurrentTable 1 }

     Dsx1CurrentEntry ::=
          SEQUENCE {
              dsx1CurrentIndex            InterfaceIndex,
              dsx1CurrentESs              PerfCurrentCount,


              dsx1CurrentSESs             PerfCurrentCount,
              dsx1CurrentSEFSs            PerfCurrentCount,
              dsx1CurrentUASs             PerfCurrentCount,
              dsx1CurrentCSSs             PerfCurrentCount,
              dsx1CurrentPCVs             PerfCurrentCount,
              dsx1CurrentLESs             PerfCurrentCount,
              dsx1CurrentBESs             PerfCurrentCount,
              dsx1CurrentDMs              PerfCurrentCount,
              dsx1CurrentLCVs             PerfCurrentCount
     }

     dsx1CurrentIndex OBJECT-TYPE
          SYNTAX  InterfaceIndex
          MAX-ACCESS  read-only
          STATUS  current
          DESCRIPTION
                 "The index value which uniquely identifies  the
                 DS1 interface to which this entry is applicable.
                 The interface identified by a particular value of
                 this index is the same interface as identified by
                 the same value as a dsx1LineIndex object
                 instance."
          ::= { dsx1CurrentEntry 1 }

     dsx1CurrentESs OBJECT-TYPE
          SYNTAX  PerfCurrentCount
          MAX-ACCESS  read-only
          STATUS  current
          DESCRIPTION
                 "The number of Errored Seconds."
          ::= { dsx1CurrentEntry 2 }

     dsx1CurrentSESs OBJECT-TYPE
          SYNTAX  PerfCurrentCount
          MAX-ACCESS  read-only
          STATUS  current
          DESCRIPTION
                 "The number of Severely Errored Seconds."
          ::= { dsx1CurrentEntry 3 }

     dsx1CurrentSEFSs OBJECT-TYPE
          SYNTAX  PerfCurrentCount
          MAX-ACCESS  read-only
          STATUS  current
          DESCRIPTION
                 "The number of Severely Errored Framing Seconds."
          ::= { dsx1CurrentEntry 4 }


     dsx1CurrentUASs OBJECT-TYPE
          SYNTAX  PerfCurrentCount
          MAX-ACCESS  read-only
          STATUS  current
          DESCRIPTION
                 "The number of Unavailable Seconds."
          ::= { dsx1CurrentEntry 5 }

     dsx1CurrentCSSs OBJECT-TYPE
          SYNTAX  PerfCurrentCount
          MAX-ACCESS  read-only
          STATUS  current
          DESCRIPTION
                 "The number of Controlled Slip Seconds."
          ::= { dsx1CurrentEntry 6 }

     dsx1CurrentPCVs OBJECT-TYPE
          SYNTAX  PerfCurrentCount
          MAX-ACCESS  read-only
          STATUS  current
          DESCRIPTION
                 "The number of Path Coding Violations."
          ::= { dsx1CurrentEntry 7 }

     dsx1CurrentLESs OBJECT-TYPE
          SYNTAX  PerfCurrentCount
          MAX-ACCESS  read-only
          STATUS  current
          DESCRIPTION
                 "The number of Line Errored Seconds."
          ::= { dsx1CurrentEntry 8 }

     dsx1CurrentBESs OBJECT-TYPE
          SYNTAX PerfCurrentCount
          MAX-ACCESS read-only
          STATUS current
          DESCRIPTION
                 "The number of Bursty Errored Seconds."
          ::= { dsx1CurrentEntry 9 }

     dsx1CurrentDMs OBJECT-TYPE
          SYNTAX PerfCurrentCount
          MAX-ACCESS read-only
          STATUS current
          DESCRIPTION
                 "The number of Degraded Minutes."
          ::= { dsx1CurrentEntry 10 }


     dsx1CurrentLCVs OBJECT-TYPE
          SYNTAX PerfCurrentCount
          MAX-ACCESS read-only
          STATUS current
          DESCRIPTION
                 "The number of Line Code Violations (LCVs)."
          ::= { dsx1CurrentEntry 11 }

     -- The DS1 Interval Table
     dsx1IntervalTable OBJECT-TYPE
          SYNTAX  SEQUENCE OF Dsx1IntervalEntry
          MAX-ACCESS  not-accessible
          STATUS  current
          DESCRIPTION
                 "The DS1 Interval Table contains various
                 statistics collected by each DS1 Interface over
                 the previous 24 hours of operation.  The past 24
                 hours are broken into 96 completed 15 minute
                 intervals.  Each row in this table represents one
                 such interval (identified by dsx1IntervalNumber)
                 for one specific instance (identified by
                 dsx1IntervalIndex)."
          ::= { ds1 8 }

     dsx1IntervalEntry OBJECT-TYPE
          SYNTAX  Dsx1IntervalEntry
          MAX-ACCESS  not-accessible
          STATUS  current
          DESCRIPTION
                 "An entry in the DS1 Interval table."
          INDEX   { dsx1IntervalIndex, dsx1IntervalNumber }
          ::= { dsx1IntervalTable 1 }

     Dsx1IntervalEntry ::=
          SEQUENCE {
              dsx1IntervalIndex             InterfaceIndex,
              dsx1IntervalNumber            INTEGER,
              dsx1IntervalESs               PerfIntervalCount,
              dsx1IntervalSESs              PerfIntervalCount,
              dsx1IntervalSEFSs             PerfIntervalCount,
              dsx1IntervalUASs              PerfIntervalCount,
              dsx1IntervalCSSs              PerfIntervalCount,
              dsx1IntervalPCVs              PerfIntervalCount,
              dsx1IntervalLESs              PerfIntervalCount,
              dsx1IntervalBESs              PerfIntervalCount,
              dsx1IntervalDMs               PerfIntervalCount,
              dsx1IntervalLCVs              PerfIntervalCount,


              dsx1IntervalValidData         TruthValue
     }

     dsx1IntervalIndex OBJECT-TYPE
          SYNTAX  InterfaceIndex
          MAX-ACCESS  read-only
          STATUS  current
          DESCRIPTION
                 "The index value which uniquely identifies the DS1
                 interface to which this entry is applicable.  The
                 interface identified by a particular value of this
                 index is the same interface as identified by the
                 same value as a dsx1LineIndex object instance."
          ::= { dsx1IntervalEntry 1 }

     dsx1IntervalNumber OBJECT-TYPE
          SYNTAX  INTEGER (1..96)
          MAX-ACCESS  read-only
          STATUS  current
          DESCRIPTION
                 "A number between 1 and 96, where 1 is the most
                 recently completed 15 minute interval and 96 is
                 the 15 minutes interval completed 23 hours and 45
                 minutes prior to interval 1."
          ::= { dsx1IntervalEntry 2 }

     dsx1IntervalESs OBJECT-TYPE
          SYNTAX  PerfIntervalCount
          MAX-ACCESS  read-only
          STATUS  current
          DESCRIPTION
                 "The number of Errored Seconds."
          ::= { dsx1IntervalEntry 3 }

     dsx1IntervalSESs OBJECT-TYPE
          SYNTAX  PerfIntervalCount
          MAX-ACCESS  read-only
          STATUS  current
          DESCRIPTION
                 "The number of Severely Errored Seconds."
          ::= { dsx1IntervalEntry 4 }

     dsx1IntervalSEFSs OBJECT-TYPE
          SYNTAX  PerfIntervalCount
          MAX-ACCESS  read-only
          STATUS  current
          DESCRIPTION
                 "The number of Severely Errored Framing Seconds."


          ::= { dsx1IntervalEntry 5 }

     dsx1IntervalUASs OBJECT-TYPE
          SYNTAX  PerfIntervalCount
          MAX-ACCESS  read-only
          STATUS  current
          DESCRIPTION
                 "The number of Unavailable Seconds.  This object
                 may decrease if the occurance of unavailable
                 seconds occurs across an inteval boundary."
          ::= { dsx1IntervalEntry 6 }

     dsx1IntervalCSSs OBJECT-TYPE
          SYNTAX  PerfIntervalCount
          MAX-ACCESS  read-only
          STATUS  current
          DESCRIPTION
                 "The number of Controlled Slip Seconds."
          ::= { dsx1IntervalEntry 7 }

     dsx1IntervalPCVs OBJECT-TYPE
          SYNTAX  PerfIntervalCount
          MAX-ACCESS  read-only
          STATUS  current
          DESCRIPTION
                 "The number of Path Coding Violations."
          ::= { dsx1IntervalEntry 8 }

     dsx1IntervalLESs OBJECT-TYPE
          SYNTAX  PerfIntervalCount
          MAX-ACCESS  read-only
          STATUS  current
          DESCRIPTION
                 "The number of Line Errored Seconds."
          ::= { dsx1IntervalEntry 9 }

     dsx1IntervalBESs OBJECT-TYPE
          SYNTAX PerfIntervalCount
          MAX-ACCESS read-only
          STATUS current
          DESCRIPTION
                 "The number of Bursty Errored Seconds."
          ::= { dsx1IntervalEntry 10 }

     dsx1IntervalDMs OBJECT-TYPE
          SYNTAX PerfIntervalCount
          MAX-ACCESS read-only
          STATUS current


          DESCRIPTION
                 "The number of Degraded Minutes."
          ::= { dsx1IntervalEntry 11 }

     dsx1IntervalLCVs OBJECT-TYPE
          SYNTAX PerfIntervalCount
          MAX-ACCESS read-only
          STATUS current
          DESCRIPTION
                 "The number of Line Code Violations."
          ::= { dsx1IntervalEntry 12 }

     dsx1IntervalValidData OBJECT-TYPE
          SYNTAX TruthValue
          MAX-ACCESS read-only
          STATUS current
          DESCRIPTION
                 "This variable indicates if the data for this
                 interval is valid."
          ::= { dsx1IntervalEntry 13 }

     -- The DS1 Total Table
     dsx1TotalTable OBJECT-TYPE
          SYNTAX  SEQUENCE OF Dsx1TotalEntry
          MAX-ACCESS  not-accessible
          STATUS  current
          DESCRIPTION
                 "The DS1 Total Table contains the cumulative sum
                 of the various statistics for the 24 hour period
                 preceding the current interval."
          ::= { ds1 9 }

     dsx1TotalEntry OBJECT-TYPE
          SYNTAX  Dsx1TotalEntry
          MAX-ACCESS  not-accessible
          STATUS  current
          DESCRIPTION
                 "An entry in the DS1 Total table."
          INDEX   { dsx1TotalIndex }
          ::= { dsx1TotalTable 1 }

     Dsx1TotalEntry ::=
          SEQUENCE {
              dsx1TotalIndex                InterfaceIndex,
              dsx1TotalESs                  PerfTotalCount,
              dsx1TotalSESs                 PerfTotalCount,
              dsx1TotalSEFSs                PerfTotalCount,
              dsx1TotalUASs                 PerfTotalCount,


              dsx1TotalCSSs                 PerfTotalCount,
              dsx1TotalPCVs                 PerfTotalCount,
              dsx1TotalLESs                 PerfTotalCount,
              dsx1TotalBESs                 PerfTotalCount,
              dsx1TotalDMs                  PerfTotalCount,
              dsx1TotalLCVs                 PerfTotalCount
     }

     dsx1TotalIndex OBJECT-TYPE
          SYNTAX  InterfaceIndex
          MAX-ACCESS  read-only
          STATUS  current
          DESCRIPTION
                 "The index value which uniquely identifies the DS1
                 interface to which this entry is applicable.  The
                 interface identified by a particular value of this
                 index is the same interface as identified by the
                 same value as a dsx1LineIndex object instance."

          ::= { dsx1TotalEntry 1 }

     dsx1TotalESs OBJECT-TYPE
          SYNTAX  PerfTotalCount
          MAX-ACCESS  read-only
          STATUS  current
          DESCRIPTION
                 "The sum of Errored Seconds encountered by a DS1
                 interface in the previous 24 hour interval.
                 Invalid 15 minute intervals count as 0."
          ::= { dsx1TotalEntry 2 }

     dsx1TotalSESs OBJECT-TYPE
          SYNTAX  PerfTotalCount
          MAX-ACCESS  read-only
          STATUS  current
          DESCRIPTION
                 "The number of Severely Errored Seconds
                 encountered by a DS1 interface in the previous 24
                 hour interval.  Invalid 15 minute intervals count
                 as 0."
          ::= { dsx1TotalEntry 3 }

     dsx1TotalSEFSs OBJECT-TYPE
          SYNTAX  PerfTotalCount
          MAX-ACCESS  read-only
          STATUS  current
          DESCRIPTION
                 "The number of Severely Errored Framing Seconds


                 encountered by a DS1 interface in the previous 24
                 hour interval.  Invalid 15 minute intervals count
                 as 0."
          ::= { dsx1TotalEntry 4 }

     dsx1TotalUASs OBJECT-TYPE
          SYNTAX  PerfTotalCount
          MAX-ACCESS  read-only
          STATUS  current
          DESCRIPTION
                 "The number of Unavailable Seconds encountered by
                 a DS1 interface in the previous 24 hour interval.
                 Invalid 15 minute intervals count as 0."
          ::= { dsx1TotalEntry 5 }

     dsx1TotalCSSs OBJECT-TYPE
          SYNTAX  PerfTotalCount
          MAX-ACCESS  read-only
          STATUS  current
          DESCRIPTION
                 "The number of Controlled Slip Seconds encountered
                 by a DS1 interface in the previous 24 hour
                 interval.  Invalid 15 minute intervals count as
                 0."
          ::= { dsx1TotalEntry 6 }

     dsx1TotalPCVs OBJECT-TYPE
          SYNTAX  PerfTotalCount
          MAX-ACCESS  read-only
          STATUS  current
          DESCRIPTION
                 "The number of Path Coding Violations encountered
                 by a DS1 interface in the previous 24 hour
                 interval.  Invalid 15 minute intervals count as
                 0."
          ::= { dsx1TotalEntry 7 }

     dsx1TotalLESs OBJECT-TYPE
          SYNTAX  PerfTotalCount
          MAX-ACCESS  read-only
          STATUS  current
          DESCRIPTION
                 "The number of Line Errored Seconds encountered by
                 a DS1 interface in the previous 24 hour interval.
                 Invalid 15 minute intervals count as 0."
          ::= { dsx1TotalEntry 8 }

     dsx1TotalBESs OBJECT-TYPE


          SYNTAX PerfTotalCount
          MAX-ACCESS read-only
          STATUS current
          DESCRIPTION
                 "The number of Bursty Errored Seconds (BESs)
                 encountered by a DS1 interface in the previous 24
                 hour interval. Invalid 15 minute intervals count
                 as 0."
          ::= { dsx1TotalEntry 9 }

     dsx1TotalDMs OBJECT-TYPE
          SYNTAX PerfTotalCount
          MAX-ACCESS read-only
          STATUS current
          DESCRIPTION
                 "The number of Degraded Minutes (DMs) encountered
                 by a DS1 interface in the previous 24 hour
                 interval.  Invalid 15 minute intervals count as
                 0."
          ::= { dsx1TotalEntry 10 }

     dsx1TotalLCVs OBJECT-TYPE
          SYNTAX PerfTotalCount
          MAX-ACCESS read-only
          STATUS current
          DESCRIPTION
                 "The number of Line Code Violations (LCVs)
                 encountered by a DS1 interface in the current 15
                 minute interval.  Invalid 15 minute intervals
                 count as 0."
          ::= { dsx1TotalEntry 11 }

     -- The DS1 Channel Table
     dsx1ChanMappingTable OBJECT-TYPE
          SYNTAX  SEQUENCE OF Dsx1ChanMappingEntry
          MAX-ACCESS  not-accessible
          STATUS  current
          DESCRIPTION
                 "The DS1 Channel Mapping table.  This table maps a
                 DS1 channel number on a particular DS3 into an
                 ifIndex.  In the presence of DS2s, this table can
                 be used to map a DS2 channel number on a DS3 into
                 an ifIndex, or used to map a DS1 channel number on
                 a DS2 onto an ifIndex."
          ::= { ds1 16 }

     dsx1ChanMappingEntry OBJECT-TYPE
          SYNTAX  Dsx1ChanMappingEntry


          MAX-ACCESS  not-accessible
          STATUS  current
          DESCRIPTION
                 "An entry in the DS1 Channel Mapping table.  There
                 is an entry in this table corresponding to each
                 ds1 ifEntry within any interface that is
                 channelized to the individual ds1 ifEntry level.

                 This table is intended to facilitate mapping from
                 channelized interface / channel number to DS1
                 ifEntry.  (e.g. mapping (DS3 ifIndex, DS1 Channel
                 Number) -&gt; ifIndex)

                 While this table provides information that can
                 also be found in the ifStackTable and
                 dsx1ConfigTable, it provides this same information
                 with a single table lookup, rather than by walking
                 the ifStackTable to find the various constituent
                 ds1 ifTable entries, and testing various
                 dsx1ConfigTable entries to check for the entry
                 with the applicable DS1 channel number."
          INDEX   { ifIndex, dsx1Ds1ChannelNumber }
          ::= { dsx1ChanMappingTable 1 }

     Dsx1ChanMappingEntry ::=
          SEQUENCE {
              dsx1ChanMappedIfIndex  InterfaceIndex
     }

     dsx1ChanMappedIfIndex OBJECT-TYPE
          SYNTAX  InterfaceIndex
          MAX-ACCESS  read-only
          STATUS  current
          DESCRIPTION
                 "This object indicates the ifIndex value assigned
                 by the agent for the individual ds1 ifEntry that
                 corresponds to the given DS1 channel number
                 (specified by the INDEX element
                 dsx1Ds1ChannelNumber) of the given channelized
                 interface (specified by INDEX element ifIndex)."
          ::= { dsx1ChanMappingEntry 1 }

     -- The DS1 Far End Current Table

     dsx1FarEndCurrentTable OBJECT-TYPE
          SYNTAX  SEQUENCE OF Dsx1FarEndCurrentEntry
          MAX-ACCESS  not-accessible


          STATUS  current
          DESCRIPTION
                 "The DS1 Far End Current table contains various
                 statistics being collected for the current 15
                 minute interval.  The statistics are collected
                 from the far end messages on the Facilities Data
                 Link.  The definitions are the same as described
                 for the near-end information."
          ::= { ds1 10 }

     dsx1FarEndCurrentEntry OBJECT-TYPE
          SYNTAX  Dsx1FarEndCurrentEntry
          MAX-ACCESS  not-accessible
          STATUS  current
          DESCRIPTION
                 "An entry in the DS1 Far End Current table."
          INDEX   { dsx1FarEndCurrentIndex }
          ::= { dsx1FarEndCurrentTable 1 }

     Dsx1FarEndCurrentEntry ::=
          SEQUENCE {
              dsx1FarEndCurrentIndex      InterfaceIndex,
              dsx1FarEndTimeElapsed       INTEGER,
              dsx1FarEndValidIntervals    INTEGER,
              dsx1FarEndCurrentESs        PerfCurrentCount,
              dsx1FarEndCurrentSESs       PerfCurrentCount,
              dsx1FarEndCurrentSEFSs      PerfCurrentCount,
              dsx1FarEndCurrentUASs       PerfCurrentCount,
              dsx1FarEndCurrentCSSs       PerfCurrentCount,
              dsx1FarEndCurrentLESs       PerfCurrentCount,
              dsx1FarEndCurrentPCVs       PerfCurrentCount,
              dsx1FarEndCurrentBESs       PerfCurrentCount,
              dsx1FarEndCurrentDMs        PerfCurrentCount,
              dsx1FarEndInvalidIntervals  INTEGER
     }

     dsx1FarEndCurrentIndex OBJECT-TYPE
          SYNTAX  InterfaceIndex
          MAX-ACCESS  read-only
          STATUS  current
          DESCRIPTION
                 "The index value which uniquely identifies the DS1
                 interface to which this entry is applicable.  The
                 interface identified by a particular value of this
                 index is identical to the interface identified by
                 the same value of dsx1LineIndex."
          ::= { dsx1FarEndCurrentEntry 1 }


     dsx1FarEndTimeElapsed OBJECT-TYPE
          SYNTAX  INTEGER (0..899)
          MAX-ACCESS  read-only
          STATUS  current
          DESCRIPTION
                      "The number of seconds that have elapsed since the
                 beginning of the far end current error-measurement
                 period.  If, for some reason, such as an
                 adjustment in the system's time-of-day clock, the
                 current interval exceeds the maximum value, the
                 agent will return the maximum value."
          ::= { dsx1FarEndCurrentEntry 2 }

     dsx1FarEndValidIntervals OBJECT-TYPE
          SYNTAX  INTEGER (0..96)
          MAX-ACCESS  read-only
          STATUS  current
          DESCRIPTION
                      "The number of previous far end intervals for
                 which data was collected.  The value will be
                 96 unless the interface was brought online within
                 the last 24 hours, in which case the value will be
                 the number of complete 15 minute far end intervals
                 since the interface has been online."
          ::= { dsx1FarEndCurrentEntry 3 }

     dsx1FarEndCurrentESs OBJECT-TYPE
          SYNTAX  PerfCurrentCount
          MAX-ACCESS  read-only
          STATUS  current
          DESCRIPTION
                 "The number of Far End Errored Seconds."
          ::= { dsx1FarEndCurrentEntry 4 }

     dsx1FarEndCurrentSESs OBJECT-TYPE
          SYNTAX  PerfCurrentCount
          MAX-ACCESS  read-only
          STATUS  current
          DESCRIPTION
                 "The number of Far End Severely Errored Seconds."

          ::= { dsx1FarEndCurrentEntry 5 }

     dsx1FarEndCurrentSEFSs OBJECT-TYPE
          SYNTAX  PerfCurrentCount
          MAX-ACCESS  read-only
          STATUS  current
          DESCRIPTION


                 "The number of Far End Severely Errored Framing
                 Seconds."
          ::= { dsx1FarEndCurrentEntry 6 }

     dsx1FarEndCurrentUASs OBJECT-TYPE
          SYNTAX  PerfCurrentCount
          MAX-ACCESS  read-only
          STATUS  current
          DESCRIPTION
                 "The number of Unavailable Seconds."
          ::= { dsx1FarEndCurrentEntry 7 }

     dsx1FarEndCurrentCSSs OBJECT-TYPE
          SYNTAX  PerfCurrentCount
          MAX-ACCESS  read-only
          STATUS  current
          DESCRIPTION
                 "The number of Far End Controlled Slip Seconds."
          ::= { dsx1FarEndCurrentEntry 8 }

     dsx1FarEndCurrentLESs OBJECT-TYPE
          SYNTAX  PerfCurrentCount
          MAX-ACCESS  read-only
          STATUS  current
          DESCRIPTION
                 "The number of Far End Line Errored Seconds."
          ::= { dsx1FarEndCurrentEntry 9 }

     dsx1FarEndCurrentPCVs OBJECT-TYPE
          SYNTAX  PerfCurrentCount
          MAX-ACCESS  read-only
          STATUS  current
          DESCRIPTION
                 "The number of Far End Path Coding Violations."
          ::= { dsx1FarEndCurrentEntry 10 }

     dsx1FarEndCurrentBESs OBJECT-TYPE
          SYNTAX PerfCurrentCount
          MAX-ACCESS read-only
          STATUS current
          DESCRIPTION
                 "The number of Far End Bursty Errored Seconds."
          ::= { dsx1FarEndCurrentEntry 11 }

     dsx1FarEndCurrentDMs OBJECT-TYPE
          SYNTAX PerfCurrentCount
          MAX-ACCESS read-only
          STATUS current


          DESCRIPTION
                 "The number of Far End Degraded Minutes."
          ::= { dsx1FarEndCurrentEntry 12 }

     dsx1FarEndInvalidIntervals OBJECT-TYPE
          SYNTAX  INTEGER (0..96)
          MAX-ACCESS  read-only
          STATUS  current
          DESCRIPTION
                 "The number of intervals in the range from 0 to
                 dsx1FarEndValidIntervals for which no data is
                 available.  This object will typically be zero
                 except in cases where the data for some intervals
                 are not available (e.g., in proxy situations)."
          ::= { dsx1FarEndCurrentEntry 13 }

     -- The DS1 Far End Interval Table
     dsx1FarEndIntervalTable OBJECT-TYPE
          SYNTAX  SEQUENCE OF Dsx1FarEndIntervalEntry
          MAX-ACCESS  not-accessible
          STATUS  current
          DESCRIPTION
                 "The DS1 Far End Interval Table contains various
                 statistics collected by each DS1 interface over
                 the previous 24 hours of operation.  The past 24
                 hours are broken into 96 completed 15 minute
                 intervals. Each row in this table represents one
                 such interval (identified by
                 dsx1FarEndIntervalNumber) for one specific
                 instance (identified by dsx1FarEndIntervalIndex)."
          ::= { ds1 11 }

     dsx1FarEndIntervalEntry OBJECT-TYPE
          SYNTAX  Dsx1FarEndIntervalEntry
          MAX-ACCESS  not-accessible
          STATUS  current
          DESCRIPTION
                 "An entry in the DS1 Far End Interval table."

          INDEX   { dsx1FarEndIntervalIndex,
                    dsx1FarEndIntervalNumber }
          ::= { dsx1FarEndIntervalTable 1 }

     Dsx1FarEndIntervalEntry ::=
          SEQUENCE {
              dsx1FarEndIntervalIndex       InterfaceIndex,
              dsx1FarEndIntervalNumber      INTEGER,
              dsx1FarEndIntervalESs         PerfIntervalCount,


              dsx1FarEndIntervalSESs        PerfIntervalCount,
              dsx1FarEndIntervalSEFSs       PerfIntervalCount,
              dsx1FarEndIntervalUASs        PerfIntervalCount,
              dsx1FarEndIntervalCSSs        PerfIntervalCount,
              dsx1FarEndIntervalLESs        PerfIntervalCount,
              dsx1FarEndIntervalPCVs        PerfIntervalCount,
              dsx1FarEndIntervalBESs        PerfIntervalCount,
              dsx1FarEndIntervalDMs         PerfIntervalCount,
              dsx1FarEndIntervalValidData   TruthValue
     }

     dsx1FarEndIntervalIndex OBJECT-TYPE
          SYNTAX  InterfaceIndex
          MAX-ACCESS  read-only
          STATUS  current
          DESCRIPTION
                 "The index value which uniquely identifies the DS1
                 interface to which this entry is applicable.  The
                 interface identified by a particular value of this
                 index is identical to the interface identified by
                 the same value of dsx1LineIndex."
          ::= { dsx1FarEndIntervalEntry 1 }

     dsx1FarEndIntervalNumber OBJECT-TYPE
          SYNTAX  INTEGER (1..96)
          MAX-ACCESS  read-only
          STATUS  current
          DESCRIPTION
                 "A number between 1 and 96, where 1 is the most
                 recently completed 15 minute interval and 96 is
                 the 15 minutes interval completed 23 hours and 45
                 minutes prior to interval 1."
          ::= { dsx1FarEndIntervalEntry 2 }

     dsx1FarEndIntervalESs OBJECT-TYPE
          SYNTAX  PerfIntervalCount
          MAX-ACCESS  read-only
          STATUS  current
          DESCRIPTION
                 "The number of Far End Errored Seconds."
          ::= { dsx1FarEndIntervalEntry 3 }

     dsx1FarEndIntervalSESs OBJECT-TYPE
          SYNTAX  PerfIntervalCount
          MAX-ACCESS  read-only
          STATUS  current
          DESCRIPTION
                 "The number of Far End Severely Errored Seconds."


          ::= { dsx1FarEndIntervalEntry 4 }

     dsx1FarEndIntervalSEFSs OBJECT-TYPE
          SYNTAX  PerfIntervalCount
          MAX-ACCESS  read-only
          STATUS  current
          DESCRIPTION
                 "The number of Far End Severely Errored Framing
                 Seconds."
          ::= { dsx1FarEndIntervalEntry 5 }

     dsx1FarEndIntervalUASs OBJECT-TYPE
          SYNTAX  PerfIntervalCount
          MAX-ACCESS  read-only
          STATUS  current
          DESCRIPTION
                 "The number of Unavailable Seconds."
          ::= { dsx1FarEndIntervalEntry 6 }

     dsx1FarEndIntervalCSSs OBJECT-TYPE
          SYNTAX  PerfIntervalCount
          MAX-ACCESS  read-only
          STATUS  current
          DESCRIPTION
                 "The number of Far End Controlled Slip Seconds."
          ::= { dsx1FarEndIntervalEntry 7 }

     dsx1FarEndIntervalLESs OBJECT-TYPE
          SYNTAX  PerfIntervalCount
          MAX-ACCESS  read-only
          STATUS  current
          DESCRIPTION
                 "The number of Far End Line Errored Seconds."

          ::= { dsx1FarEndIntervalEntry 8 }

     dsx1FarEndIntervalPCVs OBJECT-TYPE
          SYNTAX  PerfIntervalCount
          MAX-ACCESS  read-only
          STATUS  current
          DESCRIPTION
                 "The number of Far End Path Coding Violations."
          ::= { dsx1FarEndIntervalEntry 9 }

     dsx1FarEndIntervalBESs OBJECT-TYPE
          SYNTAX PerfIntervalCount
          MAX-ACCESS read-only
          STATUS current


          DESCRIPTION
                 "The number of Far End Bursty Errored Seconds."
          ::= { dsx1FarEndIntervalEntry 10 }

     dsx1FarEndIntervalDMs OBJECT-TYPE
          SYNTAX PerfIntervalCount
          MAX-ACCESS read-only
          STATUS current
          DESCRIPTION
                 "The number of Far End Degraded Minutes."
          ::= { dsx1FarEndIntervalEntry 11 }

     dsx1FarEndIntervalValidData OBJECT-TYPE
          SYNTAX TruthValue
          MAX-ACCESS read-only
          STATUS current
          DESCRIPTION
                      "This variable indicates if the data for this
                 interval is valid."
          ::= { dsx1FarEndIntervalEntry 12 }

     -- The DS1 Far End Total Table

     dsx1FarEndTotalTable OBJECT-TYPE
          SYNTAX  SEQUENCE OF Dsx1FarEndTotalEntry
          MAX-ACCESS  not-accessible
          STATUS  current
          DESCRIPTION
                 "The DS1 Far End Total Table contains the
                 cumulative sum of the various statistics for the
                 24 hour period preceding the current interval."
          ::= { ds1 12 }

     dsx1FarEndTotalEntry OBJECT-TYPE
          SYNTAX  Dsx1FarEndTotalEntry
          MAX-ACCESS  not-accessible
          STATUS  current
          DESCRIPTION
                 "An entry in the DS1 Far End Total table."
          INDEX   { dsx1FarEndTotalIndex }
          ::= { dsx1FarEndTotalTable 1 }

     Dsx1FarEndTotalEntry ::=
          SEQUENCE {
              dsx1FarEndTotalIndex          InterfaceIndex,
              dsx1FarEndTotalESs            PerfTotalCount,
              dsx1FarEndTotalSESs           PerfTotalCount,
              dsx1FarEndTotalSEFSs          PerfTotalCount,


              dsx1FarEndTotalUASs           PerfTotalCount,
              dsx1FarEndTotalCSSs           PerfTotalCount,
              dsx1FarEndTotalLESs           PerfTotalCount,
              dsx1FarEndTotalPCVs           PerfTotalCount,
              dsx1FarEndTotalBESs           PerfTotalCount,
              dsx1FarEndTotalDMs            PerfTotalCount
     }

     dsx1FarEndTotalIndex OBJECT-TYPE
          SYNTAX  InterfaceIndex
          MAX-ACCESS  read-only
          STATUS  current
          DESCRIPTION
                 "The index value which uniquely identifies the DS1
                 interface to which this entry is applicable.  The
                 interface identified by a particular value of this
                 index is identical to the interface identified by
                 the same value of dsx1LineIndex."

          ::= { dsx1FarEndTotalEntry 1 }

     dsx1FarEndTotalESs OBJECT-TYPE
          SYNTAX  PerfTotalCount
          MAX-ACCESS  read-only
          STATUS  current
          DESCRIPTION
                 "The number of Far End Errored Seconds encountered
                 by a DS1 interface in the previous 24 hour
                 interval.  Invalid 15 minute intervals count as
                 0."
          ::= { dsx1FarEndTotalEntry 2 }

     dsx1FarEndTotalSESs OBJECT-TYPE
          SYNTAX  PerfTotalCount
          MAX-ACCESS  read-only
          STATUS  current
          DESCRIPTION
                 "The number of Far End Severely Errored Seconds
                 encountered by a DS1 interface in the previous 24
                 hour interval.  Invalid 15 minute intervals count
                 as 0."
          ::= { dsx1FarEndTotalEntry 3 }

     dsx1FarEndTotalSEFSs OBJECT-TYPE
          SYNTAX  PerfTotalCount
          MAX-ACCESS  read-only
          STATUS  current
          DESCRIPTION


                 "The number of Far End Severely Errored Framing
                 Seconds encountered by a DS1 interface in the
                 previous 24 hour interval. Invalid 15 minute
                 intervals count as 0."
          ::= { dsx1FarEndTotalEntry 4 }

     dsx1FarEndTotalUASs OBJECT-TYPE
          SYNTAX  PerfTotalCount
          MAX-ACCESS  read-only
          STATUS  current
          DESCRIPTION
                 "The number of Unavailable Seconds encountered by
                 a DS1 interface in the previous 24 hour interval.
                 Invalid 15 minute intervals count as 0."
          ::= { dsx1FarEndTotalEntry 5 }

     dsx1FarEndTotalCSSs OBJECT-TYPE
          SYNTAX  PerfTotalCount
          MAX-ACCESS  read-only
          STATUS  current
          DESCRIPTION
                 "The number of Far End Controlled Slip Seconds
                 encountered by a DS1 interface in the previous 24
                 hour interval.  Invalid 15 minute intervals count
                 as 0."
          ::= { dsx1FarEndTotalEntry 6 }

     dsx1FarEndTotalLESs OBJECT-TYPE
          SYNTAX  PerfTotalCount
          MAX-ACCESS  read-only
          STATUS  current
          DESCRIPTION
                 "The number of Far End Line Errored Seconds
                 encountered by a DS1 interface in the previous 24
                 hour interval.  Invalid 15 minute intervals count
                 as 0."
          ::= { dsx1FarEndTotalEntry 7 }

     dsx1FarEndTotalPCVs OBJECT-TYPE
          SYNTAX  PerfTotalCount
          MAX-ACCESS  read-only
          STATUS  current
          DESCRIPTION
                 "The number of Far End Path Coding Violations
                 reported via the far end block error count
                 encountered by a DS1 interface in the previous 24
                 hour interval.  Invalid 15 minute intervals count
                 as 0."


          ::= { dsx1FarEndTotalEntry 8 }

     dsx1FarEndTotalBESs OBJECT-TYPE
          SYNTAX PerfTotalCount
          MAX-ACCESS read-only
          STATUS current
          DESCRIPTION
                 "The number of Bursty Errored Seconds (BESs)
                 encountered by a DS1 interface in the previous 24
                 hour interval. Invalid 15 minute intervals count
                 as 0."
          ::= { dsx1FarEndTotalEntry 9 }

     dsx1FarEndTotalDMs OBJECT-TYPE
          SYNTAX PerfTotalCount
          MAX-ACCESS read-only
          STATUS current
          DESCRIPTION
                 "The number of Degraded Minutes (DMs) encountered
                 by a DS1 interface in the previous 24 hour
                 interval.  Invalid 15 minute intervals count as
                 0."
          ::= { dsx1FarEndTotalEntry 10 }

     -- The DS1 Fractional Table
     dsx1FracTable OBJECT-TYPE
          SYNTAX  SEQUENCE OF Dsx1FracEntry
          MAX-ACCESS  not-accessible
          STATUS  deprecated
          DESCRIPTION
                 "This table is deprecated in favour of using
                 ifStackTable.

                 The table was mandatory for systems dividing a DS1
                 into channels containing different data streams
                 that are of local interest.  Systems which are
                 indifferent to data content, such as CSUs, need
                 not implement it.

                 The DS1 fractional table identifies which DS1
                 channels associated with a CSU are being used to
                 support a logical interface, i.e., an entry in the
                 interfaces table from the Internet-standard MIB.

                 For example, consider an application managing a
                 North American ISDN Primary Rate link whose
                 division is a 384 kbit/s H1 _B_ Channel for Video,


                 a second H1 for data to a primary routing peer,
                 and 12 64 kbit/s H0 _B_ Channels. Consider that
                 some subset of the H0 channels are used for voice
                 and the remainder are available for dynamic data
                 calls.

                 We count a total of 14 interfaces multiplexed onto
                 the DS1 interface. Six DS1 channels (for the sake
                 of the example, channels 1..6) are used for Video,
                 six more (7..11 and 13) are used for data, and the
                 remaining 12 are are in channels 12 and 14..24.

                 Let us further imagine that ifIndex 2 is of type
                 DS1 and refers to the DS1 interface, and that the
                 interfaces layered onto it are numbered 3..16.

                 We might describe the allocation of channels, in
                 the dsx1FracTable, as follows:
               dsx1FracIfIndex.2. 1 = 3  dsx1FracIfIndex.2.13 = 4
               dsx1FracIfIndex.2. 2 = 3  dsx1FracIfIndex.2.14 = 6
               dsx1FracIfIndex.2. 3 = 3  dsx1FracIfIndex.2.15 = 7
               dsx1FracIfIndex.2. 4 = 3  dsx1FracIfIndex.2.16 = 8
               dsx1FracIfIndex.2. 5 = 3  dsx1FracIfIndex.2.17 = 9
               dsx1FracIfIndex.2. 6 = 3  dsx1FracIfIndex.2.18 = 10
               dsx1FracIfIndex.2. 7 = 4  dsx1FracIfIndex.2.19 = 11
               dsx1FracIfIndex.2. 8 = 4  dsx1FracIfIndex.2.20 = 12
               dsx1FracIfIndex.2. 9 = 4  dsx1FracIfIndex.2.21 = 13
               dsx1FracIfIndex.2.10 = 4  dsx1FracIfIndex.2.22 = 14
               dsx1FracIfIndex.2.11 = 4  dsx1FracIfIndex.2.23 = 15
               dsx1FracIfIndex.2.12 = 5  dsx1FracIfIndex.2.24 = 16

                 For North American (DS1) interfaces, there are 24
                 legal channels, numbered 1 through 24.

                 For G.704 interfaces, there are 31 legal channels,
                 numbered 1 through 31.  The channels (1..31)
                 correspond directly to the equivalently numbered
                 time-slots."
          ::= { ds1 13 }

     dsx1FracEntry OBJECT-TYPE
          SYNTAX  Dsx1FracEntry
          MAX-ACCESS  not-accessible
          STATUS  deprecated
          DESCRIPTION
             "An entry in the DS1 Fractional table."
         INDEX   { dsx1FracIndex, dsx1FracNumber }
         ::= { dsx1FracTable 1 }


     Dsx1FracEntry ::=
         SEQUENCE {
             dsx1FracIndex        INTEGER,
             dsx1FracNumber       INTEGER,
             dsx1FracIfIndex      INTEGER
         }

     dsx1FracIndex OBJECT-TYPE
         SYNTAX  INTEGER (1..'7fffffff'h)
         MAX-ACCESS  read-only
         STATUS  deprecated
         DESCRIPTION
            "The index value which uniquely identifies  the
            DS1  interface  to which this entry is applicable
            The interface identified by a  particular
            value  of  this  index is the same interface as
            identified by the same value  an  dsx1LineIndex
            object instance."
        ::= { dsx1FracEntry 1 }

     dsx1FracNumber OBJECT-TYPE
         SYNTAX  INTEGER (1..31)
         MAX-ACCESS  read-only
         STATUS  deprecated
         DESCRIPTION
            "The channel number for this entry."
        ::= { dsx1FracEntry 2 }

     dsx1FracIfIndex OBJECT-TYPE
         SYNTAX  INTEGER (1..'7fffffff'h)
         MAX-ACCESS  read-write
         STATUS  deprecated
         DESCRIPTION
            "An index value that uniquely identifies an
            interface.  The interface identified by a particular
            value of this index is the same  interface
            as  identified by the same value an ifIndex
            object instance. If no interface is currently using
            a channel, the value should be zero.  If a
            single interface occupies more  than  one  time
            slot,  that ifIndex value will be found in multiple
            time slots."
        ::= { dsx1FracEntry 3 }

      -- Ds1 TRAPS

     ds1Traps OBJECT IDENTIFIER ::= { ds1 15 }


     dsx1LineStatusChange NOTIFICATION-TYPE
         OBJECTS { dsx1LineStatus,
                   dsx1LineStatusLastChange }
         STATUS  current
         DESCRIPTION
                 "A dsx1LineStatusChange trap is sent when the
                 value of an instance dsx1LineStatus changes. It
                 can be utilized by an NMS to trigger polls.  When
                 the line status change results from a higher level
                 line status change (i.e. ds3), then no traps for
                 the ds1 are sent."
          ::= { ds1Traps 0 1 }

     -- conformance information
     ds1Conformance OBJECT IDENTIFIER ::= { ds1 14 }

     ds1Groups      OBJECT IDENTIFIER ::= { ds1Conformance 1 }
     ds1Compliances OBJECT IDENTIFIER ::= { ds1Conformance 2 }

     -- compliance statements

     ds1Compliance MODULE-COMPLIANCE
         STATUS  current
         DESCRIPTION
                 "The compliance statement for T1 and E1
                 interfaces."
         MODULE  -- this module
             MANDATORY-GROUPS { ds1NearEndConfigGroup,
                                ds1NearEndStatisticsGroup }

             GROUP       ds1FarEndGroup
             DESCRIPTION
                 "Implementation of this group is optional for all
                 systems that attach to a DS1 Interface."

             GROUP       ds1NearEndOptionalConfigGroup
             DESCRIPTION
                 "Implementation of this group is optional for all
                 systems that attach to a DS1 Interface."

             GROUP       ds1DS2Group
             DESCRIPTION
                 "Implementation of this group is mandatory for all
                 systems that attach to a DS2 Interface."

             GROUP       ds1TransStatsGroup


             DESCRIPTION
                 "This group is the set of statistics appropriate
                 for all systems which attach to a DS1 Interface
                 running transparent or unFramed lineType."

             GROUP       ds1ChanMappingGroup
             DESCRIPTION
                 "This group is the set of objects for mapping a
                 DS3 Channel (ds1ChannelNumber) to ifIndex.

                 Implementation of this group is mandatory for
                 systems which support the channelization of DS3s
                 into DS1s."

             OBJECT dsx1LineType
             MIN-ACCESS read-only
             DESCRIPTION
                 "The ability to set the line type is not
                 required."

             OBJECT dsx1LineCoding
             MIN-ACCESS read-only
             DESCRIPTION
                 "The ability to set the line coding is not
                 required."

             OBJECT dsx1SendCode
             MIN-ACCESS read-only
             DESCRIPTION
                 "The ability to set the send code is not
                 required."

             OBJECT dsx1LoopbackConfig
             MIN-ACCESS read-only
             DESCRIPTION
                 "The ability to set loopbacks is not required."

             OBJECT dsx1SignalMode
             MIN-ACCESS read-only
             DESCRIPTION
                 "The ability to set the signal mode is not
                 required."

             OBJECT dsx1TransmitClockSource
             MIN-ACCESS read-only
             DESCRIPTION
                 "The ability to set the transmit clock source is


                 not required."

             OBJECT dsx1Fdl
             MIN-ACCESS read-only
             DESCRIPTION
                 "The ability to set the FDL is not required."

             OBJECT dsx1LineLength
             MIN-ACCESS read-only
             DESCRIPTION
                 "The ability to set the line length is not
                 required."

             OBJECT dsx1Channelization
             MIN-ACCESS read-only
             DESCRIPTION
                 "The ability to set the channelization is not
                 required."
         ::= { ds1Compliances 1 }

     ds1MibT1PriCompliance MODULE-COMPLIANCE
         STATUS current
         DESCRIPTION
                 "Compliance statement for using this MIB for ISDN
                 Primary Rate interfaces on T1 lines."
         MODULE
             MANDATORY-GROUPS { ds1NearEndConfigGroup,
                                ds1NearEndStatisticsGroup }
             OBJECT dsx1LineType
                 SYNTAX INTEGER {
                     dsx1ESF(2)   -- Intl Spec would be G704(2)
                                  -- or I.431(4)
                 }
                 MIN-ACCESS read-only
                 DESCRIPTION
                     "Line type for T1 ISDN Primary Rate
                      interfaces."

             OBJECT dsx1LineCoding
                 SYNTAX INTEGER {
                     dsx1B8ZS(2)
                 }
                 MIN-ACCESS read-only
                 DESCRIPTION
                     "Type of Zero Code Suppression for
                      T1 ISDN Primary Rate interfaces."

             OBJECT dsx1SignalMode


                 SYNTAX INTEGER {
                     none(1), -- if there is no signaling channel
                     messageOriented(4)
                 }
                 MIN-ACCESS read-only
                 DESCRIPTION
                     "Possible signaling modes for
                      T1 ISDN Primary Rate interfaces."

             OBJECT dsx1TransmitClockSource
                 SYNTAX INTEGER {
                     loopTiming(1)
                 }
                 MIN-ACCESS read-only
                 DESCRIPTION
                     "The transmit clock is derived from
                      received clock on ISDN Primary Rate
                      interfaces."

             OBJECT dsx1Fdl
                 MIN-ACCESS read-only
                 DESCRIPTION
                     "Facilities Data Link usage on T1 ISDN
                      Primary Rate interfaces.
                      Note: Eventually dsx1Att-54016(4) is to be
                            used here since the line type is ESF."

             OBJECT dsx1Channelization
                 MIN-ACCESS read-only
                 DESCRIPTION
                     "The ability to set the channelization
                      is not required."
         ::= { ds1Compliances 2 }

     ds1MibE1PriCompliance MODULE-COMPLIANCE
         STATUS current
         DESCRIPTION
                 "Compliance statement for using this MIB for ISDN
                 Primary Rate interfaces on E1 lines."
         MODULE
             MANDATORY-GROUPS { ds1NearEndConfigGroup,
                                ds1NearEndStatisticsGroup }
             OBJECT dsx1LineType
                 SYNTAX INTEGER {
                     dsx1E1CRC(5)
                 }
                 MIN-ACCESS read-only


                 DESCRIPTION
                     "Line type for E1 ISDN Primary Rate
                      interfaces."

             OBJECT dsx1LineCoding
                 SYNTAX INTEGER {
                     dsx1HDB3(3)
                 }
                 MIN-ACCESS read-only
                 DESCRIPTION
                     "Type of Zero Code Suppression for
                      E1 ISDN Primary Rate interfaces."

             OBJECT dsx1SignalMode
                 SYNTAX INTEGER {
                     messageOriented(4)
                 }
                 MIN-ACCESS read-only
                 DESCRIPTION
                     "Signaling on E1 ISDN Primary Rate interfaces
                      is always message oriented."

             OBJECT dsx1TransmitClockSource
                 SYNTAX INTEGER {
                     loopTiming(1)
                 }
                 MIN-ACCESS read-only
                 DESCRIPTION
                     "The transmit clock is derived from received
                      clock on ISDN Primary Rate interfaces."

             OBJECT dsx1Fdl
                 MIN-ACCESS read-only
                 DESCRIPTION
                     "Facilities Data Link usage on E1 ISDN
                      Primary Rate interfaces.
                      Note: There is a 'M-Channel' in E1,
                            using National Bit Sa4 (G704,
                            Table 4a). It is used to implement
                            management features between ET
                            and NT.  This is different to
                            FDL in T1, which is used to carry
                            control signals and performance
                            data.  In E1, control and status
                            signals are carried using National
                            Bits Sa5, Sa6 and A (RAI Ind.).
                      This indicates that only the other(1) or
                      eventually the dsx1Fdl-none(8) bits should


                      be set in this object for E1 PRI."

             OBJECT dsx1Channelization
                 MIN-ACCESS read-only
                 DESCRIPTION
                 "The ability to set the channelization is not
                 required."
         ::= { ds1Compliances 3 }

     ds1Ds2Compliance MODULE-COMPLIANCE
         STATUS current
         DESCRIPTION
                 "Compliance statement for using this MIB for DS2
                 interfaces."
         MODULE
             MANDATORY-GROUPS { ds1DS2Group }

             OBJECT dsx1Channelization
                 MIN-ACCESS read-only
                 DESCRIPTION
                 "The ability to set the channelization is not
                 required."
         ::= { ds1Compliances 4 }

     -- units of conformance

     ds1NearEndConfigGroup  OBJECT-GROUP
         OBJECTS { dsx1LineIndex,
                   dsx1TimeElapsed,
                   dsx1ValidIntervals,
                   dsx1LineType,
                   dsx1LineCoding,
                   dsx1SendCode,
                   dsx1CircuitIdentifier,
                   dsx1LoopbackConfig,
                   dsx1LineStatus,
                   dsx1SignalMode,
                   dsx1TransmitClockSource,
                   dsx1Fdl,
                   dsx1InvalidIntervals,
                   dsx1LineLength,
                   dsx1LoopbackStatus,
                   dsx1Ds1ChannelNumber,
                   dsx1Channelization }
         STATUS  current
         DESCRIPTION
                 "A collection of objects providing configuration


                 information applicable to all DS1 interfaces."
         ::= { ds1Groups 1 }

     ds1NearEndStatisticsGroup OBJECT-GROUP
         OBJECTS { dsx1CurrentIndex,
                   dsx1CurrentESs,
                   dsx1CurrentSESs,
                   dsx1CurrentSEFSs,
                   dsx1CurrentUASs,
                   dsx1CurrentCSSs,
                   dsx1CurrentPCVs,
                   dsx1CurrentLESs,
                   dsx1CurrentBESs,
                   dsx1CurrentDMs,
                   dsx1CurrentLCVs,
                   dsx1IntervalIndex,
                   dsx1IntervalNumber,
                   dsx1IntervalESs,
                   dsx1IntervalSESs,
                   dsx1IntervalSEFSs,
                   dsx1IntervalUASs,
                   dsx1IntervalCSSs,
                   dsx1IntervalPCVs,
                   dsx1IntervalLESs,
                   dsx1IntervalBESs,
                   dsx1IntervalDMs,
                   dsx1IntervalLCVs,
                   dsx1IntervalValidData,
                   dsx1TotalIndex,
                   dsx1TotalESs,
                   dsx1TotalSESs,
                   dsx1TotalSEFSs,
                   dsx1TotalUASs,
                   dsx1TotalCSSs,
                   dsx1TotalPCVs,
                   dsx1TotalLESs,
                   dsx1TotalBESs,
                   dsx1TotalDMs,
                   dsx1TotalLCVs }
         STATUS  current
         DESCRIPTION
                 "A collection of objects providing statistics
                 information applicable to all DS1 interfaces."
         ::= { ds1Groups 2 }

     ds1FarEndGroup  OBJECT-GROUP
         OBJECTS { dsx1FarEndCurrentIndex,
                   dsx1FarEndTimeElapsed,


                   dsx1FarEndValidIntervals,
                   dsx1FarEndCurrentESs,
                   dsx1FarEndCurrentSESs,
                   dsx1FarEndCurrentSEFSs,
                   dsx1FarEndCurrentUASs,
                   dsx1FarEndCurrentCSSs,
                   dsx1FarEndCurrentLESs,
                   dsx1FarEndCurrentPCVs,
                   dsx1FarEndCurrentBESs,
                   dsx1FarEndCurrentDMs,
                   dsx1FarEndInvalidIntervals,
                   dsx1FarEndIntervalIndex,
                   dsx1FarEndIntervalNumber,
                   dsx1FarEndIntervalESs,
                   dsx1FarEndIntervalSESs,
                   dsx1FarEndIntervalSEFSs,
                   dsx1FarEndIntervalUASs,
                   dsx1FarEndIntervalCSSs,
                   dsx1FarEndIntervalLESs,
                   dsx1FarEndIntervalPCVs,
                   dsx1FarEndIntervalBESs,
                   dsx1FarEndIntervalDMs,
                   dsx1FarEndIntervalValidData,
                   dsx1FarEndTotalIndex,
                   dsx1FarEndTotalESs,
                   dsx1FarEndTotalSESs,
                   dsx1FarEndTotalSEFSs,
                   dsx1FarEndTotalUASs,
                   dsx1FarEndTotalCSSs,
                   dsx1FarEndTotalLESs,
                   dsx1FarEndTotalPCVs,
                   dsx1FarEndTotalBESs,
                   dsx1FarEndTotalDMs }
         STATUS  current
         DESCRIPTION
                 "A collection of objects providing remote
                 configuration and statistics information."
         ::= { ds1Groups 3 }

     ds1DeprecatedGroup OBJECT-GROUP
         OBJECTS { dsx1IfIndex,
                   dsx1FracIndex,
                   dsx1FracNumber,
                   dsx1FracIfIndex }
         STATUS  deprecated
         DESCRIPTION
                 "A collection of obsolete objects that may be
                 implemented for backwards compatibility."


         ::= { ds1Groups 4 }

     ds1NearEndOptionalConfigGroup OBJECT-GROUP
         OBJECTS { dsx1LineStatusLastChange,
                   dsx1LineStatusChangeTrapEnable }

         STATUS    current
         DESCRIPTION
                 "A collection of objects that may be implemented
                 on DS1 and DS2 interfaces."
         ::= { ds1Groups 5 }

     ds1DS2Group OBJECT-GROUP
         OBJECTS { dsx1LineIndex,
                   dsx1LineType,
                   dsx1LineCoding,
                   dsx1SendCode,
                   dsx1LineStatus,
                   dsx1SignalMode,
                   dsx1TransmitClockSource,
                   dsx1Channelization }
         STATUS   current
         DESCRIPTION
                 "A collection of objects providing information
                 about DS2 (6,312 kbps) and E2 (8,448 kbps)
                 systems."
         ::= { ds1Groups 6 }

     ds1TransStatsGroup OBJECT-GROUP
         OBJECTS { dsx1CurrentESs,
                   dsx1CurrentSESs,
                   dsx1CurrentUASs,
                   dsx1IntervalESs,
                   dsx1IntervalSESs,
                   dsx1IntervalUASs,
                   dsx1TotalESs,
                   dsx1TotalSESs,
                   dsx1TotalUASs }
         STATUS   current
         DESCRIPTION
                      "A collection of objects which are the
                 statistics which can be collected from a ds1
                 interface that is running transparent or unframed
                 lineType.  Statistics not in this list should
                 return noSuchInstance."
         ::= { ds1Groups 7 }

     ds1NearEndOptionalTrapGroup NOTIFICATION-GROUP


         NOTIFICATIONS { dsx1LineStatusChange }
         STATUS    current
         DESCRIPTION
                 "A collection of notifications that may be
                 implemented on DS1 and DS2 interfaces."
         ::= { ds1Groups 8 }

     ds1ChanMappingGroup OBJECT-GROUP
         OBJECTS { dsx1ChanMappedIfIndex }
         STATUS    current
         DESCRIPTION
                 "A collection of objects that give an mapping of
                 DS3 Channel (ds1ChannelNumber) to ifIndex."
         ::= { ds1Groups 9 }

END

ATM-TC-MIB DEFINITIONS ::= BEGIN

     IMPORTS
        MODULE-IDENTITY, OBJECT-IDENTITY,
        TimeTicks, mib-2
            FROM SNMPv2-SMI
        TEXTUAL-CONVENTION
            FROM SNMPv2-TC;

     atmTCMIB MODULE-IDENTITY
          LAST-UPDATED "9810190200Z"
          ORGANIZATION "IETF AToMMIB Working Group"
          CONTACT-INFO
            "          Michael Noto
              Postal:  3Com Corporation
                       5400 Bayfront Plaza, M/S 3109
                       Santa Clara, CA 95052
                       USA
              Tel:     +1 408 326 2218
              E-mail:  mike_noto@3com.com

                       Ethan Mickey Spiegel


              Postal:  Cisco Systems
                       170 W. Tasman Dr.
                       San Jose, CA 95134
                       USA
              Tel:     +1 408 526 6408
              E-mail:  mspiegel@cisco.com

                       Kaj Tesink
              Postal:  Bellcore
                       331 Newman Springs Road
                       Red Bank, NJ 07701
                       USA
              Tel:     +1 732 758 5254
              Fax:     +1 732 758 4177
              E-mail:  kaj@bellcore.com"
          DESCRIPTION
           "This MIB Module provides Textual Conventions
           and OBJECT-IDENTITY Objects to be used by
           ATM systems."
          ::= { mib-2 37 3 } -- atmMIB 3 (see [3])

     -- The Textual Conventions defined below are organized
     -- alphabetically

     AtmAddr ::= TEXTUAL-CONVENTION
             DISPLAY-HINT "1x"
             STATUS  current
             DESCRIPTION
                 "An ATM address. The semantics are implied by
                 the length. The address types are: - no
                 address (0 octets) - E.164 (8 octets) - NSAP
                 (20 octets) In addition, when subaddresses
                 are used the AtmAddr may represent the
                 concatenation of address and subaddress. The
                 associated address types are: - E.164, E.164
                 (16 octets) - E.164, NSAP (28 octets) - NSAP,
                 NSAP (40 octets) Address lengths other than
                 defined in this definition imply address
                 types defined elsewhere.  Note: The E.164
                 address is encoded in BCD format."
            SYNTAX   OCTET STRING (SIZE(0..40))

    AtmConnCastType ::= TEXTUAL-CONVENTION
            STATUS  current
            DESCRIPTION
              "The type of topology of a connection (point-


              to-point, point-to-multipoint). In the case
              of point-to-multipoint, the orientation of
              this VPL or VCL in the connection.
              On a host:
              - p2mpRoot indicates that the host
                is the root of the p2mp connection.
              - p2mpLeaf indicates that the host
                is a leaf of the p2mp connection.
              On a switch interface:
              - p2mpRoot indicates that cells received
                by the switching fabric from the interface
                are from the root of the p2mp connection.
              - p2mpLeaf indicates that cells transmitted
                to the interface from the switching fabric
                are to the leaf of the p2mp connection."
            SYNTAX   INTEGER {
               p2p(1),
               p2mpRoot(2),
               p2mpLeaf(3)
               }

    AtmConnKind ::= TEXTUAL-CONVENTION
            STATUS  current
            DESCRIPTION
                "The type of call control used for an ATM
                connection at a particular interface. The use
                is as follows:
                   pvc(1)
                      Virtual link of a PVC. Should not be
                      used for an PVC/SVC (i.e., Soft PVC)
                      crossconnect.
                   svcIncoming(2)
                      Virtual link established after a
                      received signaling request to setup
                      an SVC.
                   svcOutgoing(3)
                      Virtual link established after a
                      transmitted or forwarded signaling
                      request to setup an SVC.
                   spvcInitiator(4)
                      Virtual link at the PVC side of an
                      SVC/PVC crossconnect, where the
                      switch is the initiator of the Soft PVC
                      setup.
                   spvcTarget(5)
                      Virtual link at the PVC side of an
                      SVC/PVC crossconnect, where the
                      switch is the target of the Soft PVC


                      setup.

                For PVCs, a pvc virtual link is always cross-
                connected to a pvc virtual link.

                For SVCs, an svcIncoming virtual link is always cross-
                connected to an svcOutgoing virtual link.

For Soft PVCs, an spvcInitiator is either cross-connected to
an svcOutgoing or an spvcTarget, and an spvcTarget is either
cross-connected to an svcIncoming or an spvcInitiator."
        SYNTAX   INTEGER {
           pvc(1),
           svcIncoming(2),
           svcOutgoing(3),
           spvcInitiator(4),
           spvcTarget(5)
           }

    AtmIlmiNetworkPrefix ::= TEXTUAL-CONVENTION
        STATUS   current
        DESCRIPTION
            "A network prefix used for ILMI address
            registration.  In the case of ATM endsystem
            addresses (AESAs), the network prefix is the first
            13 octets of the address which includes the AFI,
            IDI, and HO-DSP fields.  In the case of native
            E.164 addresses, the network prefix is the entire
            E.164 address encoded in 8 octets, as if it were
            an E.164 IDP in an ATM endsystem address
            structure."
        REFERENCE
            "ATM Forum, Integrated Local Management Interface
               (ILMI) Specification, Version 4.0,
               af-ilmi-0065.000, September 1996, Section 9
             ATM Forum, ATM User-Network Interface Signalling
               Specification, Version 4.0 (UNI 4.0),
               af-sig-0061.000, June 1996, Section 3"
        SYNTAX   OCTET STRING (SIZE(8|13))

AtmInterfaceType ::= TEXTUAL-CONVENTION
        STATUS       current
        DESCRIPTION
            "The connection setup procedures used for the
            identified interface.

            Other: Connection setup procedures other than
               those listed below.


            Auto-configuration:
               Indicates that the connection setup
               procedures are to be determined dynamically,
               or that determination has not yet been
               completed. One such mechanism is via ATM
               Forum ILMI auto-configuration procedures.

            ITU-T DSS2:
            -  ITU-T Recommendation Q.2931, Broadband
               Integrated Service Digital Network (B-ISDN)
               Digital Subscriber Signalling System No.2
               (DSS2) User-Network Interface (UNI) Layer 3
               Specification for Basic Call/Connection
               Control (September 1994)
            -  ITU-T Draft Recommendation Q.2961,
               B-ISDN DSS 2 Support of Additional Traffic
               Parameters (May 1995)

            -  ITU-T Draft Recommendation Q.2971,
               B-ISDN DSS 2 User Network Interface Layer 3
               Specification for Point-to-multipoint
               Call/connection Control (May 1995)

            ATM Forum UNI 3.0:
               ATM Forum, ATM User-Network Interface,
               Version 3.0 (UNI 3.0) Specification,
               (1994).

            ATM Forum UNI 3.1:
               ATM Forum, ATM User-Network Interface,
               Version 3.1 (UNI 3.1) Specification,
               (November 1994).

            ATM Forum UNI Signalling 4.0:
               ATM Forum, ATM User-Network Interface (UNI)
               Signalling Specification Version 4.0,
               af-sig-0061.000 (June 1996).

            ATM Forum IISP (based on UNI 3.0 or UNI 3.1) :
               Interim Inter-switch Signaling Protocol
               (IISP) Specification, Version 1.0,
               af-pnni-0026.000, (December 1994).

            ATM Forum PNNI 1.0 :
               ATM Forum, Private Network-Network Interface
               Specification, Version 1.0, af-pnni-0055.000,
               (March 1996).


            ATM Forum B-ICI:
               ATM Forum, B-ICI Specification, Version 2.0,
               af-bici-0013.002, (November 1995).

            ATM Forum UNI PVC Only:
               An ATM Forum compliant UNI with the
               signalling disabled.
            ATM Forum NNI PVC Only:
               An ATM Forum compliant NNI with the
               signalling disabled."
        SYNTAX  INTEGER  {
                  other(1),
                  autoConfig(2),
                  ituDss2(3),
                  atmfUni3Dot0(4),
                  atmfUni3Dot1(5),
                  atmfUni4Dot0(6),
                  atmfIispUni3Dot0(7),
                  atmfIispUni3Dot1(8),
                  atmfIispUni4Dot0(9),
        atmfPnni1Dot0(10),
        atmfBici2Dot0(11),
        atmfUniPvcOnly(12),
        atmfNniPvcOnly(13)  }

AtmServiceCategory ::= TEXTUAL-CONVENTION
        STATUS  current
        DESCRIPTION
            "The service category for a connection."
        REFERENCE
            "ATM Forum Traffic Management Specification,
            Version 4.0, af-tm-0056.000, June 1996."
        SYNTAX   INTEGER {
           other(1),   -- none of the following
           cbr(2),     -- constant bit rate
           rtVbr(3),   -- real-time variable bit rate
           nrtVbr(4),  -- non real-time variable bit rate
           abr(5),     -- available bit rate
           ubr(6)      -- unspecified bit rate
           }

AtmSigDescrParamIndex ::= TEXTUAL-CONVENTION
        STATUS  current
        DESCRIPTION
            "The value of this object identifies a row in the
            atmSigDescrParamTable. The value 0 signifies that
            none of the signalling parameters defined in the
            atmSigDescrParamTable are applicable."


        SYNTAX  INTEGER (0..2147483647)

AtmTrafficDescrParamIndex ::= TEXTUAL-CONVENTION
        STATUS  current
        DESCRIPTION
            "The value of this object identifies a row in the
            atmTrafficDescrParamTable.  The value 0 signifies
            that no row has been identified."
        SYNTAX  INTEGER (0..2147483647)

AtmVcIdentifier ::= TEXTUAL-CONVENTION
        STATUS  current
        DESCRIPTION
            "The VCI value for a VCL. The maximum VCI value
            cannot exceed the value allowable by
            atmInterfaceMaxVciBits defined in ATM-MIB."
        SYNTAX   INTEGER (0..65535)

AtmVpIdentifier ::= TEXTUAL-CONVENTION
        STATUS  current
        DESCRIPTION
            "The VPI value for a VPL or VCL. The value VPI=0
            is only allowed for a VCL. For ATM UNIs supporting
            VPCs the VPI value ranges from 0 to 255.  The VPI
            value 0 is supported for ATM UNIs conforming to
            the ATM Forum UNI 4.0 Annex 8 (Virtual UNIs)
            specification. For ATM UNIs supporting VCCs the
            VPI value ranges from 0 to 255.  For ATM NNIs the
            VPI value ranges from 0 to 4095.  The maximum VPI
            value cannot exceed the value allowable by
            atmInterfaceMaxVpiBits defined in ATM-MIB."
        SYNTAX    INTEGER (0..4095)

AtmVorXAdminStatus ::= TEXTUAL-CONVENTION
        STATUS  current
        DESCRIPTION
            "The value determines the desired administrative
            status of a virtual link or cross-connect. The up
            and down states indicate that the traffic flow is
            enabled or disabled respectively on the virtual
            link or cross-connect."
        SYNTAX   INTEGER {
           up(1),
           down(2)
            }

AtmVorXLastChange ::= TEXTUAL-CONVENTION
        STATUS  current


        DESCRIPTION
            "The value of MIB II's sysUpTime at the time a
            virtual link or cross-connect entered its current
            operational state. If the current state was
            entered prior to the last re-initialization of the
            agent then this object contains a zero value."
        SYNTAX   TimeTicks

AtmVorXOperStatus ::= TEXTUAL-CONVENTION
        STATUS  current
        DESCRIPTION
            "The value determines the operational status of a
            virtual link or cross-connect. The up and down
            states indicate that the traffic flow is enabled
            or disabled respectively on the virtual link or
            cross-connect. The unknown state indicates that
            the state of it cannot be determined. The state
            will be down or unknown if the supporting ATM
            interface(s) is down or unknown respectively."
        SYNTAX   INTEGER {
           up(1),
           down(2),
           unknown(3)
           }

-- OBJECT-IDENTITIES:

-- The following atmTrafficDescriptorTypes has been moved
-- from RFC1695 and no longer appear in the revision of
-- RFC1695[3].

atmTrafficDescriptorTypes OBJECT IDENTIFIER ::= {mib-2 37 1 1}
                                            -- atmMIBObjects
                                            -- See [3].

-- All other and new OBJECT IDENTITIES
-- are defined under the following subtree:

    atmObjectIdentities OBJECT IDENTIFIER ::= {atmTCMIB 1}

-- The following values are defined for use as
-- possible values of the ATM traffic descriptor type.

atmNoTrafficDescriptor  OBJECT-IDENTITY
    STATUS  deprecated


    DESCRIPTION
        "This identifies the no ATM traffic
        descriptor type.  Parameters 1, 2, 3, 4,
        and 5 are not used.  This traffic descriptor
        type can be used for best effort traffic."
    ::= {atmTrafficDescriptorTypes 1}

atmNoClpNoScr  OBJECT-IDENTITY
    STATUS  current
    DESCRIPTION
        "This traffic descriptor type is for no CLP
        and no Sustained Cell Rate.  The use of the
        parameter vector for this type:
        Parameter 1: peak cell rate in cells/second
                     for CLP=0+1 traffic
        Parameter 2: not used
        Parameter 3: not used
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 2}

atmClpNoTaggingNoScr  OBJECT-IDENTITY
    STATUS  deprecated
    DESCRIPTION
        "This traffic descriptor is for CLP without
        tagging and no Sustained Cell Rate.  The use
        of the parameter vector for this type:
        Parameter 1: peak cell rate in cells/second
                     for CLP=0+1 traffic
        Parameter 2: peak cell rate in cells/second
                     for CLP=0 traffic
        Parameter 3: not used
        Parameter 4: not used
        Parameter 5: not used."
    ::= {atmTrafficDescriptorTypes 3}

atmClpTaggingNoScr  OBJECT-IDENTITY
    STATUS  deprecated
    DESCRIPTION
        "This traffic descriptor is for CLP with
        tagging and no Sustained Cell Rate.  The use
        of the parameter vector for this type:


        Parameter 1: peak cell rate in cells/second
                     for CLP=0+1 traffic
        Parameter 2: peak cell rate in cells/second
                     for CLP=0 traffic, excess
                     tagged as CLP=1
        Parameter 3: not used
        Parameter 4: not used
        Parameter 5: not used."
    ::= {atmTrafficDescriptorTypes 4}

atmNoClpScr  OBJECT-IDENTITY
    STATUS  current
    DESCRIPTION
        "This traffic descriptor type is for no CLP
        with Sustained Cell Rate.  The use of the
        parameter vector for this type:
        Parameter 1: peak cell rate in cells/second
                     for CLP=0+1 traffic
        Parameter 2: sustainable cell rate in cells/second
                     for CLP=0+1 traffic
        Parameter 3: maximum burst size in cells
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 5}

atmClpNoTaggingScr  OBJECT-IDENTITY
    STATUS  current
    DESCRIPTION
        "This traffic descriptor type is for CLP with
        Sustained Cell Rate and no tagging.  The use
        of the parameter vector for this type:
        Parameter 1: peak cell rate in cells/second
                     for CLP=0+1 traffic
        Parameter 2: sustainable cell rate in cells/second
                     for CLP=0 traffic
        Parameter 3: maximum burst size in cells
        Parameter 4: not used
        Parameter 5: not used."
    REFERENCE
        "ATM Forum,ATM User-Network Interface,
           Version 3.0 (UNI 3.0) Specification, 1994.
         ATM Forum, ATM User-Network Interface,


           Version 3.1 (UNI 3.1) Specification,
           November 1994."
    ::= {atmTrafficDescriptorTypes 6}

atmClpTaggingScr  OBJECT-IDENTITY
    STATUS  current
    DESCRIPTION
        "This traffic descriptor type is for CLP with
        tagging and Sustained Cell Rate.  The use of
        the parameter vector for this type:
        Parameter 1: peak cell rate in cells/second
                     for CLP=0+1 traffic
        Parameter 2: sustainable cell rate in cells/second
                     for CLP=0 traffic, excess tagged as
                     CLP=1
        Parameter 3: maximum burst size in cells
        Parameter 4: not used
        Parameter 5: not used."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 7}

atmClpNoTaggingMcr  OBJECT-IDENTITY
    STATUS  current
    DESCRIPTION
        "This traffic descriptor type is for CLP with
        Minimum Cell Rate and no tagging.  The use of
        the parameter vector for this type:
        Parameter 1: peak cell rate in cells/second
                     for CLP=0+1 traffic
        Parameter 2: CDVT in tenths of microseconds
        Parameter 3: minimum cell rate in cells/second
        Parameter 4: unused
        Parameter 5: unused."
    REFERENCE
        "ATM Forum,ATM User-Network Interface,
           Version 3.0 (UNI 3.0) Specification, 1994.
         ATM Forum, ATM User-Network Interface,
           Version 3.1 (UNI 3.1) Specification,
           November 1994."
    ::= {atmTrafficDescriptorTypes 8}

atmClpTransparentNoScr  OBJECT-IDENTITY
    STATUS  current


    DESCRIPTION
        "This traffic descriptor type is for the CLP-
        transparent model and no Sustained Cell Rate.
        The use of the parameter vector for this type:
        Parameter 1: peak cell rate in cells/second
                     for CLP=0+1 traffic
        Parameter 2: CDVT in tenths of microseconds
        Parameter 3: not used
        Parameter 4: not used
        Parameter 5: not used.

        This traffic descriptor type is applicable to
        connections following the CBR.1 conformance
        definition.

        Connections specifying this traffic descriptor
        type will be rejected at UNI 3.0 or UNI 3.1
        interfaces.  For a similar traffic descriptor
        type that can be accepted at UNI 3.0 and
        UNI 3.1 interfaces, see atmNoClpNoScr."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 9}

atmClpTransparentScr  OBJECT-IDENTITY
    STATUS  current
    DESCRIPTION
        "This traffic descriptor type is for the CLP-
        transparent model with Sustained Cell Rate.
        The use of the parameter vector for this type:
        Parameter 1: peak cell rate in cells/second
                     for CLP=0+1 traffic
        Parameter 2: sustainable cell rate in cells/second
                     for CLP=0+1 traffic
        Parameter 3: maximum burst size in cells
        Parameter 4: CDVT in tenths of microseconds
        Parameter 5: not used.

        This traffic descriptor type is applicable to
        connections following the VBR.1 conformance
        definition.


        Connections specifying this traffic descriptor
        type will be rejected at UNI 3.0 or UNI 3.1
        interfaces.  For a similar traffic descriptor
        type that can be accepted at UNI 3.0 and
        UNI 3.1 interfaces, see atmNoClpScr."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 10}

atmNoClpTaggingNoScr  OBJECT-IDENTITY
    STATUS  current
    DESCRIPTION
        "This traffic descriptor type is for no CLP
        with tagging and no Sustained Cell Rate.  The
        use of the parameter vector for this type:
        Parameter 1: peak cell rate in cells/second
                     for CLP=0+1 traffic
        Parameter 2: CDVT in tenths of microseconds
        Parameter 3: not used
        Parameter 4: not used
        Parameter 5: not used.

        This traffic descriptor type is applicable to
        connections following the UBR.2 conformance
        definition ."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 11}

atmNoClpNoScrCdvt  OBJECT-IDENTITY
    STATUS  current
    DESCRIPTION
        "This traffic descriptor type is for no CLP
        and no Sustained Cell Rate.  The use of the
        parameter vector for this type:
        Parameter 1: peak cell rate in cells/second


                     for CLP=0+1 traffic
        Parameter 2: CDVT in tenths of microseconds
        Parameter 3: not used
        Parameter 4: not used
        Parameter 5: not used.

        This traffic descriptor type is applicable to
        CBR connections following the UNI 3.0/3.1
        conformance definition for PCR CLP=0+1.
        These CBR connections differ from CBR.1
        connections in that the CLR objective
        applies only to the CLP=0 cell flow.

        This traffic descriptor type is also
        applicable to connections following the UBR.1
        conformance definition."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 12}

atmNoClpScrCdvt  OBJECT-IDENTITY
    STATUS  current
    DESCRIPTION
        "This traffic descriptor type is for no CLP
        with Sustained Cell Rate.  The use of the
        parameter vector for this type:
        Parameter 1: peak cell rate in cells/second
                     for CLP=0+1 traffic
        Parameter 2: sustainable cell rate in cells/second
                     for CLP=0+1 traffic
        Parameter 3: maximum burst size in cells
        Parameter 4: CDVT in tenths of microseconds
        Parameter 5: not used.

        This traffic descriptor type is applicable
        to VBR connections following the UNI 3.0/3.1
        conformance definition for PCR CLP=0+1 and
        SCR CLP=0+1.  These VBR connections
        differ from VBR.1 connections in that
        the CLR objective applies only to the CLP=0
        cell flow."
    REFERENCE


        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 13}

atmClpNoTaggingScrCdvt  OBJECT-IDENTITY
    STATUS  current
    DESCRIPTION
        "This traffic descriptor type is for CLP with
        Sustained Cell Rate and no tagging.  The use
        of the parameter vector for this type:
        Parameter 1: peak cell rate in cells/second
                     for CLP=0+1 traffic
        Parameter 2: sustainable cell rate in cells/second
                     for CLP=0 traffic
        Parameter 3: maximum burst size in cells
        Parameter 4: CDVT in tenths of microseconds
        Parameter 5: not used.

        This traffic descriptor type is applicable to
        connections following the VBR.2 conformance
        definition."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 14}

atmClpTaggingScrCdvt  OBJECT-IDENTITY
    STATUS  current
    DESCRIPTION
        "This traffic descriptor type is for CLP with
        tagging and Sustained Cell Rate.  The use of
        the parameter vector for this type:
        Parameter 1: peak cell rate in cells/second
                     for CLP=0+1 traffic
        Parameter 2: sustainable cell rate in cells/second
                     for CLP=0 traffic, excess tagged as
                     CLP=1
        Parameter 3: maximum burst size in cells


        Parameter 4: CDVT in tenths of microseconds
        Parameter 5: not used.

        This traffic descriptor type is applicable to
        connections following the VBR.3 conformance
        definition."
    REFERENCE
        "ATM Forum,ATM User-Network Interface,
           Version 3.0 (UNI 3.0) Specification, 1994.
         ATM Forum, ATM User-Network Interface,
           Version 3.1 (UNI 3.1) Specification,
           November 1994.
         ATM Forum, Traffic Management Specification,
           Version 4.0, af-tm-0056.000, June 1996."
    ::= {atmTrafficDescriptorTypes 15}

END

ATM-MIB DEFINITIONS ::= BEGIN

     IMPORTS
        MODULE-IDENTITY, OBJECT-TYPE,
        Counter32, Integer32, IpAddress, mib-2
            FROM SNMPv2-SMI
        DisplayString, RowStatus, TruthValue
            FROM SNMPv2-TC
        MODULE-COMPLIANCE, OBJECT-GROUP
            FROM SNMPv2-CONF
        InterfaceIndex, ifIndex
            FROM IF-MIB
        AtmAddr, AtmConnKind, AtmConnCastType,
        AtmServiceCategory, AtmTrafficDescrParamIndex,
        AtmVpIdentifier, AtmVcIdentifier,
        AtmVorXAdminStatus, AtmVorXLastChange,
        AtmVorXOperStatus, atmNoClpNoScr
            FROM ATM-TC-MIB;

     atmMIB MODULE-IDENTITY
          LAST-UPDATED "9810191200Z"
          ORGANIZATION "IETF AToM MIB Working Group"
          CONTACT-INFO
            "          Kaj Tesink
              Postal:  Bellcore
                       331 Newman Springs Road
                       Red Bank, NJ 07701
              Tel:     732-758-5254
              Fax:     732-758-2269
              E-mail:  kaj@bellcore.com"
          DESCRIPTION
           "This is the MIB Module for ATM and AAL5-related
            objects for managing ATM interfaces, ATM virtual


            links, ATM cross-connects, AAL5 entities, and
            and AAL5 connections."
          REVISION      "9810191200Z"
          DESCRIPTION
           "The initial revision of this module was published
            as RFC 1695. Key revisions include:
            o  Textual Conventions and OBJECT IDENTITIES have
               been moved to a separate MIB module.
            o  Applicability of objects to PVCs, SVCs and Soft
               PVCs has been clarified.
            o  DEFVAL clauses have been added.
            o  The relationship of ifIndex values with different
               layers and sublayers related to ATM has been
               clarified.
            o  atmTrafficQosClass has been deprecated
               and replaced with atmServiceCategory.
            o  atmInterfaceCurrentMaxVpiBits and
               atmInterfaceCurrentMaxVciBits have been added with
               a description on their relationship with other
               objects.
            o  atmInterfaceAddressType and atmInterfaceAdminAddress
               have been deprecated and replaced by
               atmInterfaceSubscrAddress.
            o  atmInterfaceTCAlarmState has been clarified.
            o  atmTrafficDescrParamIndexNext has been introduced
               in order to provide a manager a free
               atmTrafficDescrParamIndex value.
            o  The atmTrafficFrameDiscard capability has been added.
            o  A connection topology type (atmVpl/VclCastType) and
               a call control type (atmVpl/VclConnKind) have been
               added.
            o  aal2 has been added to atmVccAalType."
          REVISION      "9406072245Z"
          DESCRIPTION
           "The RFC1695 version of this MIB module."
          ::= { mib-2 37 }

     atmMIBObjects  OBJECT IDENTIFIER ::= {atmMIB 1}

     -- {atmMIBObjects 1} has been moved to a separate
     -- specification [19].

     -- This ATM MIB Module consists of the following tables:
     -- (1) ATM Interface configuration table
     -- (2) ATM Interface DS3 PLCP table
     -- (3) ATM Interface TC Sublayer table


     -- (4) Atm Traffic Descriptor table
     -- (5) ATM Interface VPL configuration table
     -- (6) ATM Interface VCL configuration table
     -- (7) ATM VP Cross Connect table (for PVCs)
     -- (8) ATM VC Cross Connect table (for PVCs)
     -- (9) ATM Interface AAL5 VCC performance statistics
     --     table

     --    ATM Interface Configuration Parameters Table

     -- This table contains ATM specific
     -- configuration information associated with
     -- an ATM interface beyond those
     -- supported using the ifTable.

     atmInterfaceConfTable  OBJECT-TYPE
          SYNTAX         SEQUENCE OF AtmInterfaceConfEntry
          MAX-ACCESS     not-accessible
          STATUS         current
          DESCRIPTION
           "This table contains ATM local interface
            configuration parameters, one entry per ATM
            interface port."
          ::= { atmMIBObjects 2 }

     atmInterfaceConfEntry    OBJECT-TYPE
          SYNTAX         AtmInterfaceConfEntry
          MAX-ACCESS     not-accessible
          STATUS         current
          DESCRIPTION
           "This list contains ATM interface configuration
            parameters and state variables and is indexed
            by ifIndex values of ATM interfaces."
          INDEX { ifIndex }
          ::= { atmInterfaceConfTable  1}

     AtmInterfaceConfEntry    ::= SEQUENCE  {
          atmInterfaceMaxVpcs             INTEGER,
          atmInterfaceMaxVccs             INTEGER,
          atmInterfaceConfVpcs            INTEGER,
          atmInterfaceConfVccs            INTEGER,
          atmInterfaceMaxActiveVpiBits    INTEGER,
          atmInterfaceMaxActiveVciBits    INTEGER,
          atmInterfaceIlmiVpi             AtmVpIdentifier,
          atmInterfaceIlmiVci             AtmVcIdentifier,


          atmInterfaceAddressType         INTEGER,
          atmInterfaceAdminAddress        AtmAddr,
          atmInterfaceMyNeighborIpAddress IpAddress,
          atmInterfaceMyNeighborIfName    DisplayString,
          atmInterfaceCurrentMaxVpiBits   INTEGER,
          atmInterfaceCurrentMaxVciBits   INTEGER,
          atmInterfaceSubscrAddress       AtmAddr
               }

     atmInterfaceMaxVpcs OBJECT-TYPE
          SYNTAX         INTEGER  (0..4096)
          MAX-ACCESS     read-write
          STATUS         current
          DESCRIPTION
           "The maximum number of VPCs (PVPCs and SVPCs)
            supported at this ATM interface. At the ATM UNI,
            the maximum number of VPCs (PVPCs and SVPCs)
            ranges from 0 to 256 only."
          ::= { atmInterfaceConfEntry 1}

     atmInterfaceMaxVccs OBJECT-TYPE
          SYNTAX         INTEGER  (0..65536)
          MAX-ACCESS     read-write
          STATUS         current
          DESCRIPTION
           "The maximum number of VCCs (PVCCs and SVCCs)
            supported at this ATM interface."
          ::= { atmInterfaceConfEntry 2}

     atmInterfaceConfVpcs  OBJECT-TYPE
          SYNTAX         INTEGER  (0..4096)
          MAX-ACCESS     read-only
          STATUS         current
          DESCRIPTION
           "The number of VPCs (PVPC, Soft PVPC and SVPC)
            currently in use at this ATM interface.  It includes
            the number of PVPCs and Soft PVPCs that are configured
            at the interface, plus the number of SVPCs
            that are currently  established at the
            interface.

            At the ATM UNI, the configured number of
            VPCs (PVPCs and SVPCs) can range from
            0 to 256 only."
          ::= { atmInterfaceConfEntry 3}

     atmInterfaceConfVccs  OBJECT-TYPE


          SYNTAX         INTEGER  (0..65536)
          MAX-ACCESS     read-only
          STATUS         current
          DESCRIPTION
           "The number of VCCs (PVCC, Soft PVCC and SVCC)
            currently in use at this ATM interface.  It includes
            the number of PVCCs and Soft PVCCs that are configured
            at the interface, plus the number of SVCCs
            that are currently  established at the
            interface."
          ::= { atmInterfaceConfEntry 4}

     atmInterfaceMaxActiveVpiBits  OBJECT-TYPE
          SYNTAX         INTEGER (0..12)
          MAX-ACCESS     read-write
          STATUS         current
          DESCRIPTION
           "The  maximum number of active VPI bits
            configured for use at the ATM interface.
            At the ATM UNI, the maximum number of active
            VPI bits configured for use ranges from
            0 to 8 only."
          ::= { atmInterfaceConfEntry 5}

     atmInterfaceMaxActiveVciBits  OBJECT-TYPE
          SYNTAX         INTEGER (0..16)
          MAX-ACCESS     read-write
          STATUS         current
          DESCRIPTION
           "The maximum number of active VCI bits
            configured for use at this ATM interface."
          ::= { atmInterfaceConfEntry 6}

     atmInterfaceIlmiVpi OBJECT-TYPE
          SYNTAX         AtmVpIdentifier
          MAX-ACCESS     read-write
          STATUS         current
          DESCRIPTION
           "The VPI value of the VCC supporting
            the ILMI at this ATM interface.  If the values of
            atmInterfaceIlmiVpi and atmInterfaceIlmiVci are
            both equal to zero then the ILMI is not
            supported at this ATM interface."
          DEFVAL { 0 }
          ::= { atmInterfaceConfEntry 7}

     atmInterfaceIlmiVci OBJECT-TYPE
          SYNTAX         AtmVcIdentifier


          MAX-ACCESS     read-write
          STATUS         current
          DESCRIPTION
           "The VCI value of the VCC supporting
            the ILMI at this ATM interface.  If the values of
            atmInterfaceIlmiVpi and atmInterfaceIlmiVci are
            both equal to zero then the ILMI is not
            supported at this ATM interface."
          DEFVAL { 16 }
          ::= { atmInterfaceConfEntry 8}

     atmInterfaceAddressType  OBJECT-TYPE
          SYNTAX         INTEGER {
                            private(1),
                            nsapE164(2),
                            nativeE164(3),
                            other(4)
                              }
          MAX-ACCESS     read-only
          STATUS         deprecated
          DESCRIPTION
           "The type of primary ATM address configured
            for use at this ATM interface."
          ::= { atmInterfaceConfEntry 9 }

     --  The atmInterfaceAdminAddress object has been replaced by
     --  atmInterfaceSubscrAddress.

     atmInterfaceAdminAddress OBJECT-TYPE
          SYNTAX         AtmAddr
          MAX-ACCESS     read-only
          STATUS         deprecated
          DESCRIPTION
           "The primary address assigned for administrative purposes,
            for example, an address associated with the
            service provider side of a public network UNI
            (thus, the value of this address corresponds
            with the value of ifPhysAddress at the host side).
            If this interface has no assigned administrative
            address, or when the address used for
            administrative purposes is the same as that used
            for ifPhysAddress, then this is an octet string of
            zero length."
          ::= { atmInterfaceConfEntry 10 }

     atmInterfaceMyNeighborIpAddress OBJECT-TYPE
          SYNTAX         IpAddress
          MAX-ACCESS     read-write


          STATUS         current
          DESCRIPTION
           "The IP address of the neighbor system connected to
            the  far end of this interface, to which a Network
            Management Station can send SNMP messages, as IP
            datagrams sent to UDP port 161, in order to access
            network management information concerning the
            operation of that system.  Note that the value
            of this object may be obtained in different ways,
            e.g., by manual configuration, or through ILMI
            interaction with the neighbor system."
          ::= { atmInterfaceConfEntry 11 }

     atmInterfaceMyNeighborIfName OBJECT-TYPE
          SYNTAX         DisplayString
          MAX-ACCESS     read-write
          STATUS         current
          DESCRIPTION
           "The textual name of the interface on the neighbor
            system on the far end of this interface, and to
            which this interface connects.  If the neighbor
            system is manageable through SNMP and supports
            the object ifName, the value of this object must
            be identical with that of ifName for the ifEntry
            of the lowest level physical interface
            for this port.  If this interface does not have a
            textual name, the value of this object is a zero
            length string.  Note that the value of this object
            may be obtained in different ways, e.g., by manual
            configuration, or through ILMI interaction with
            the neighbor system."
          ::= { atmInterfaceConfEntry 12 }

     atmInterfaceCurrentMaxVpiBits    OBJECT-TYPE
          SYNTAX         INTEGER  (0..12)
          MAX-ACCESS     read-only
          STATUS         current
          DESCRIPTION
           "The maximum number of VPI Bits that may
            currently be used at this ATM interface.
            The value is the minimum of
            atmInterfaceMaxActiveVpiBits, and the
            atmInterfaceMaxActiveVpiBits of the interface's
            UNI/NNI peer.

            If the interface does not negotiate with
            its peer to determine the number of VPI Bits
            that can be used on the interface, then the


            value of this object must equal
            atmInterfaceMaxActiveVpiBits."
          ::= { atmInterfaceConfEntry 13 }

     atmInterfaceCurrentMaxVciBits    OBJECT-TYPE
          SYNTAX         INTEGER  (0..16)
          MAX-ACCESS     read-only
          STATUS         current
          DESCRIPTION
           "The maximum number of VCI Bits that may
            currently be used at this ATM interface.
            The value is the minimum of
            atmInterfaceMaxActiveVciBits, and the
            atmInterfaceMaxActiveVciBits of the interface's
            UNI/NNI peer.

            If the interface does not negotiate with
            its peer to determine the number of VCI Bits
            that can be used on the interface, then the
            value of this object must equal
            atmInterfaceMaxActiveVciBits."
          ::= { atmInterfaceConfEntry 14 }

     atmInterfaceSubscrAddress OBJECT-TYPE
          SYNTAX         AtmAddr
          MAX-ACCESS     read-write
          STATUS         current
          DESCRIPTION
           "The identifier assigned by a service provider
            to the network side of a public network UNI.
            If this interface has no assigned service provider
            address, or for other interfaces this is an octet string
            of zero length."
          ::= { atmInterfaceConfEntry 15 }

     -- The ATM Interface DS3 PLCP Table

     -- This table contains the DS3 PLCP configuration and
     -- state parameters of those ATM interfaces
     -- which use DS3 PLCP for carrying ATM cells over DS3.

     atmInterfaceDs3PlcpTable  OBJECT-TYPE
          SYNTAX       SEQUENCE OF AtmInterfaceDs3PlcpEntry
          MAX-ACCESS   not-accessible
          STATUS       current
          DESCRIPTION
           "This table contains ATM interface DS3 PLCP
            parameters and state variables, one entry per


            ATM interface port."
          ::= { atmMIBObjects 3}

     atmInterfaceDs3PlcpEntry OBJECT-TYPE
          SYNTAX         AtmInterfaceDs3PlcpEntry
          MAX-ACCESS     not-accessible
          STATUS         current
          DESCRIPTION
           "This list contains DS3 PLCP parameters and
            state variables at the ATM interface and is
            indexed by the ifIndex value of the ATM interface."
          INDEX    { ifIndex }
          ::= { atmInterfaceDs3PlcpTable 1}

     AtmInterfaceDs3PlcpEntry    ::= SEQUENCE  {
          atmInterfaceDs3PlcpSEFSs       Counter32,
          atmInterfaceDs3PlcpAlarmState  INTEGER,
          atmInterfaceDs3PlcpUASs        Counter32
            }

     atmInterfaceDs3PlcpSEFSs  OBJECT-TYPE
          SYNTAX         Counter32
          MAX-ACCESS     read-only
          STATUS         current
          DESCRIPTION
           "The number of DS3 PLCP Severely Errored Framing
            Seconds (SEFS). Each SEFS represents a
            one-second interval which contains
            one or more SEF events."
          ::= { atmInterfaceDs3PlcpEntry 1}

     atmInterfaceDs3PlcpAlarmState    OBJECT-TYPE
          SYNTAX         INTEGER {
                            noAlarm(1),
                            receivedFarEndAlarm(2),
                            incomingLOF(3)
                                 }
          MAX-ACCESS     read-only
          STATUS         current
          DESCRIPTION
           "This variable indicates if there is an
            alarm present for the DS3 PLCP.  The value
            receivedFarEndAlarm means that the DS3 PLCP
            has received an incoming Yellow
            Signal, the value incomingLOF means that
            the DS3 PLCP has declared a loss of frame (LOF)
            failure condition, and the value noAlarm


            means that there are no alarms present.
            Transition from the failure to the no alarm state
            occurs when no defects (e.g., LOF) are received
            for more than 10 seconds."
          ::= { atmInterfaceDs3PlcpEntry 2}

     atmInterfaceDs3PlcpUASs  OBJECT-TYPE
          SYNTAX         Counter32
          MAX-ACCESS     read-only
          STATUS         current
          DESCRIPTION
           "The counter associated with the number of
            Unavailable Seconds encountered by the PLCP."
          ::= { atmInterfaceDs3PlcpEntry 3}

     -- The ATM Interface TC Sublayer Table

     -- This table contains TC sublayer configuration and
     -- state parameters of those ATM interfaces
     -- which use TC sublayer for carrying ATM cells over
     -- SONET/SDH or DS3.

     atmInterfaceTCTable  OBJECT-TYPE
          SYNTAX         SEQUENCE OF AtmInterfaceTCEntry
          MAX-ACCESS     not-accessible
          STATUS         current
          DESCRIPTION
           "This table contains ATM interface TC
            Sublayer parameters and state variables,
            one entry per ATM interface port."
          ::= { atmMIBObjects 4}

     atmInterfaceTCEntry OBJECT-TYPE
          SYNTAX         AtmInterfaceTCEntry
          MAX-ACCESS     not-accessible
          STATUS         current
          DESCRIPTION
           "This list contains TC Sublayer parameters
            and state variables at the ATM interface and is
            indexed by the ifIndex value of the ATM interface."
          INDEX  {ifIndex }
          ::= { atmInterfaceTCTable 1}

     AtmInterfaceTCEntry    ::= SEQUENCE  {
          atmInterfaceOCDEvents      Counter32,
          atmInterfaceTCAlarmState   INTEGER


            }

     atmInterfaceOCDEvents  OBJECT-TYPE
          SYNTAX         Counter32
          MAX-ACCESS     read-only
          STATUS         current
          DESCRIPTION
           "The number of times the Out of Cell
            Delineation (OCD) events occur.  If seven
            consecutive ATM cells have Header Error
            Control (HEC) violations, an OCD event occurs.
            A high number of OCD events may indicate a
            problem with the TC Sublayer."
          ::= { atmInterfaceTCEntry 1}

     atmInterfaceTCAlarmState    OBJECT-TYPE
          SYNTAX         INTEGER {
                            noAlarm(1),
                            lcdFailure(2)
                                  }
          MAX-ACCESS     read-only
          STATUS         current
          DESCRIPTION
           "This variable indicates if there is an
            alarm present for the TC Sublayer.  The value
            lcdFailure(2) indicates that the TC Sublayer
            is currently in the Loss of Cell Delineation
            (LCD) defect maintenance state.  The value
            noAlarm(1) indicates that the TC Sublayer
            is currently not in the LCD defect
            maintenance state."
           ::= { atmInterfaceTCEntry 2}

     --  ATM Traffic Descriptor Parameter Table

     -- This table contains a set of self-consistent
     -- ATM traffic parameters including the
     -- ATM traffic service category.

     -- The ATM virtual link tables (i.e., VPL and VCL tables)
     -- will use this ATM Traffic Descriptor table
     -- to assign traffic parameters and service category
     -- to the receive and transmit directions of
     -- the ATM virtual links (i.e., VPLs and VCLs).
     -- The ATM VPL or VCL table will indicate a row
     -- in the atmTrafficDescrParamTable
     -- using its atmTrafficDescrParamIndex value.


     -- The management application can then compare a set of
     -- ATM traffic parameters with a single value.

     -- If no suitable row(s) in the atmTrafficDescrParamTable
     -- exists, the manager must create a new row(s) in this
     -- table. If such a row is created, agent checks the
     -- sanity of that set of ATM traffic parameter values.

     -- The manager may use atmTrafficDescrParamIndexNext
     -- in order to obtain a free atmTrafficDescrParamIndex
     -- value.

     -- When creating a new row, the parameter values
     -- will be checked for self-consistency.
     -- Predefined/template rows may be supported.

     -- A row in the atmTrafficDescrParamTable is deleted
     -- by setting the atmTrafficDescrRowStatus to destroy(6).
     -- The agent will check whether this row is still in use
     -- by any entry of the atmVplTable or atmVclTable.
     -- The agent denies the request if the row is still in
     -- use.

     --  The ATM Traffic Descriptor Parameter Table

     atmTrafficDescrParamTable    OBJECT-TYPE
          SYNTAX       SEQUENCE OF AtmTrafficDescrParamEntry
          MAX-ACCESS   not-accessible
          STATUS       current
          DESCRIPTION
           "This table contains information on ATM traffic
            descriptor type and the associated parameters."
          ::= { atmMIBObjects 5}

     atmTrafficDescrParamEntry    OBJECT-TYPE
          SYNTAX         AtmTrafficDescrParamEntry
          MAX-ACCESS     not-accessible
          STATUS         current
          DESCRIPTION
           "This list contains ATM traffic descriptor
            type and the associated parameters."
          INDEX  {atmTrafficDescrParamIndex}
          ::= { atmTrafficDescrParamTable 1}

     AtmTrafficDescrParamEntry   ::= SEQUENCE  {
       atmTrafficDescrParamIndex  AtmTrafficDescrParamIndex,
       atmTrafficDescrType        OBJECT IDENTIFIER,


       atmTrafficDescrParam1      Integer32,
       atmTrafficDescrParam2      Integer32,
       atmTrafficDescrParam3      Integer32,
       atmTrafficDescrParam4      Integer32,
       atmTrafficDescrParam5      Integer32,
       atmTrafficQoSClass         INTEGER,
       atmTrafficDescrRowStatus   RowStatus,
       atmServiceCategory         AtmServiceCategory,
       atmTrafficFrameDiscard     TruthValue
                    }

     atmTrafficDescrParamIndex OBJECT-TYPE
          SYNTAX  AtmTrafficDescrParamIndex (1..2147483647)
          MAX-ACCESS     not-accessible
          STATUS         current
          DESCRIPTION
           "This object is used by the virtual link
            table (i.e., VPL or VCL table)
            to identify the row of this table.
            When creating a new row in the table
            the value of this index may be obtained
            by retrieving the value of
            atmTrafficDescrParamIndexNext."
          ::= { atmTrafficDescrParamEntry  1}

     atmTrafficDescrType OBJECT-TYPE
          SYNTAX         OBJECT IDENTIFIER
          MAX-ACCESS     read-create
          STATUS         current
          DESCRIPTION
           "The value of this object identifies the type
            of ATM traffic descriptor.
            The type may indicate no traffic descriptor or
            traffic descriptor with one or more parameters.
            These parameters are specified as a parameter
            vector, in the corresponding instances of the
            objects:
                atmTrafficDescrParam1
                atmTrafficDescrParam2
                atmTrafficDescrParam3
                atmTrafficDescrParam4
                atmTrafficDescrParam5."
           DEFVAL  { atmNoClpNoScr }
           ::= { atmTrafficDescrParamEntry 2}

     atmTrafficDescrParam1 OBJECT-TYPE
          SYNTAX         Integer32
          MAX-ACCESS     read-create


          STATUS         current
          DESCRIPTION
           "The first parameter of the ATM traffic descriptor
            used according to the value of
            atmTrafficDescrType."
          DEFVAL  { 0 }
          ::= { atmTrafficDescrParamEntry 3}

     atmTrafficDescrParam2 OBJECT-TYPE
          SYNTAX         Integer32
          MAX-ACCESS     read-create
          STATUS         current
          DESCRIPTION
           "The second parameter of the ATM traffic descriptor
            used according to the value of
            atmTrafficDescrType."
          DEFVAL  { 0 }
          ::= { atmTrafficDescrParamEntry 4}

     atmTrafficDescrParam3 OBJECT-TYPE
          SYNTAX         Integer32
          MAX-ACCESS     read-create
          STATUS         current
          DESCRIPTION
           "The third parameter of the ATM traffic descriptor
            used according to the value of
            atmTrafficDescrType."
          DEFVAL  { 0 }
          ::= { atmTrafficDescrParamEntry 5}

     atmTrafficDescrParam4 OBJECT-TYPE
          SYNTAX         Integer32
          MAX-ACCESS     read-create
          STATUS         current
          DESCRIPTION
           "The fourth parameter of the ATM traffic descriptor
            used according to the value of
            atmTrafficDescrType."
          DEFVAL  { 0 }
          ::= { atmTrafficDescrParamEntry 6}

     atmTrafficDescrParam5 OBJECT-TYPE
          SYNTAX         Integer32
          MAX-ACCESS     read-create
          STATUS         current
          DESCRIPTION
           "The fifth parameter of the ATM traffic descriptor
            used according to the value of


            atmTrafficDescrType."
          DEFVAL  { 0 }
          ::= { atmTrafficDescrParamEntry 7}

     atmTrafficQoSClass  OBJECT-TYPE
          SYNTAX         INTEGER (0..255)
          MAX-ACCESS     read-create
          STATUS         deprecated
          DESCRIPTION
           "The value of this object identifies the QoS Class.
            Four Service classes have been
            specified in the ATM Forum UNI Specification:
            Service Class A: Constant bit rate video and
                             Circuit emulation
            Service Class B: Variable bit rate video/audio
            Service Class C: Connection-oriented data
            Service Class D: Connectionless data
            Four QoS classes numbered 1, 2, 3, and 4 have
            been specified with the aim to support service
            classes A, B, C, and D respectively.
            An unspecified QoS Class numbered `0' is used
            for best effort traffic."
          DEFVAL  { 0 }
          ::= { atmTrafficDescrParamEntry 8}

     atmTrafficDescrRowStatus  OBJECT-TYPE
          SYNTAX         RowStatus
          MAX-ACCESS     read-create
          STATUS         current
          DESCRIPTION
           "This object is used to create
            a new row or modify or delete an
            existing row in this table."
          DEFVAL  { active }
          ::= {atmTrafficDescrParamEntry 9}

     atmServiceCategory  OBJECT-TYPE
          SYNTAX         AtmServiceCategory
          MAX-ACCESS     read-create
          STATUS         current
          DESCRIPTION
           "The ATM service category."
          DEFVAL  { ubr }
          ::= { atmTrafficDescrParamEntry 10}

     atmTrafficFrameDiscard    OBJECT-TYPE
          SYNTAX       TruthValue


          MAX-ACCESS   read-create
          STATUS       current
          DESCRIPTION
           "If set to 'true', this object indicates that the network
            is requested to treat data for this connection, in the
            given direction, as frames (e.g. AAL5 CPCS_PDU's) rather
            than as individual cells.  While the precise
            implementation is network-specific, this treatment may
            for example involve discarding entire frames during
            congestion, rather than a few cells from many frames."
          DEFVAL { true }
          ::= { atmTrafficDescrParamEntry 11 }

     --  ATM Interface Virtual Path Link (VPL) Table

     -- This table contains configuration and state
     -- information of a bi-directional Virtual Path Link
     -- (VPL)

     -- This table can be used to create, delete or modify
     -- a VPL that is terminated in an ATM host or switch.
     -- This table can also be used to create, delete or
     -- modify a VPL which is cross-connected to another
     -- VPL.

     -- In the example below, the traffic flows on the receive
     -- and transmit directions of the VPLs are characterized
     -- by atmVplReceiveTrafficDescrIndex and
     -- atmVplTransmitTrafficDescrIndex respectively.
     -- The cross-connected VPLs are identified by
     -- atmVplCrossConnectIdentifier.

     --           ________________________________
     --           |                              |
     --  VPL      | ATM Host, Switch, or Network |   VPL
     -- receive   |                              |  receive
     -- ========&gt; X                              X &lt;=======
     -- &lt;======== X                              X ========&gt;
     -- transmit  |                              |  transmit
     --           |______________________________|

     --  The ATM Interface VPL Table


     atmVplTable         OBJECT-TYPE
          SYNTAX         SEQUENCE OF AtmVplEntry
          MAX-ACCESS     not-accessible
          STATUS         current
          DESCRIPTION
           "The Virtual Path Link (VPL) table.  A
            bi-directional VPL is modeled as one entry
            in this table. This table can be used for
            PVCs, SVCs and Soft PVCs.
            Entries are not present in this table for
            the VPIs used by entries in the atmVclTable."
          ::= { atmMIBObjects 6}

     atmVplEntry         OBJECT-TYPE
          SYNTAX         AtmVplEntry
          MAX-ACCESS     not-accessible
          STATUS         current
          DESCRIPTION
           "An entry in the VPL table.  This entry is
            used to model a bi-directional VPL.
            To create a VPL at an ATM interface,
            either of the following procedures are used:

            Negotiated VPL establishment

          (1) The management application creates
              a VPL entry in the atmVplTable
              by setting atmVplRowStatus to createAndWait(5).
              This may fail for the following reasons:
              - The selected VPI value is unavailable,
              - The selected VPI value is in use.
              Otherwise, the agent creates a row and
              reserves the VPI value on that port.

          (2) The manager selects an existing row(s) in the
              atmTrafficDescrParamTable,
              thereby, selecting a set of self-consistent
              ATM traffic parameters and the service category
              for receive and transmit directions of the VPL.

         (2a) If no suitable row(s) in the
              atmTrafficDescrParamTable exists,
              the manager must create a new row(s)
              in that table.

         (2b) The manager characterizes the VPL's traffic
              parameters through setting the
              atmVplReceiveTrafficDescrIndex and the


              atmVplTransmitTrafficDescrIndex values
              in the VPL table, which point to the rows
              containing desired ATM traffic parameter values
              in the atmTrafficDescrParamTable.  The agent
              will check the availability of resources and
              may refuse the request.
              If the transmit and receive service categories
              are inconsistent, the agent should refuse the
              request.

          (3) The manager activates the VPL by setting the
              the atmVplRowStatus to active(1).
              If this set is successful, the agent has
              reserved the resources to satisfy the requested
              traffic parameter values and the service category
              for that VPL.

          (4) If the VPL terminates a VPC in the ATM host
              or switch, the manager turns on the
              atmVplAdminStatus to up(1) to turn the VPL
              traffic flow on.  Otherwise, the
              atmVpCrossConnectTable  must be used
              to cross-connect the VPL to another VPL(s)
              in an ATM switch or network.

            One-Shot VPL Establishment

            A VPL may also be established in one step by a
            set-request with all necessary VPL parameter
            values and atmVplRowStatus set to createAndGo(4).

            In contrast to the negotiated VPL establishment
            which allows for detailed error checking
            (i.e., set errors are explicitly linked to
            particular resource acquisition failures),
            the one-shot VPL establishment
            performs the setup on one operation but
            does not have the advantage of step-wise
            error checking.

            VPL Retirement

            A VPL is released by setting atmVplRowStatus to
            destroy(6), and the agent may release all
            associated resources."
          INDEX  {ifIndex, atmVplVpi }
          ::= { atmVplTable  1}


     AtmVplEntry    ::= SEQUENCE  {
          atmVplVpi          AtmVpIdentifier,
          atmVplAdminStatus  AtmVorXAdminStatus,
          atmVplOperStatus   AtmVorXOperStatus,
          atmVplLastChange   AtmVorXLastChange,
          atmVplReceiveTrafficDescrIndex
                         AtmTrafficDescrParamIndex,
          atmVplTransmitTrafficDescrIndex
                         AtmTrafficDescrParamIndex,
          atmVplCrossConnectIdentifier INTEGER,
          atmVplRowStatus    RowStatus,
          atmVplCastType     AtmConnCastType,
          atmVplConnKind     AtmConnKind
             }

     atmVplVpi           OBJECT-TYPE
          SYNTAX         AtmVpIdentifier
          MAX-ACCESS     not-accessible
          STATUS         current
          DESCRIPTION
           "The VPI value of the VPL."
          ::= { atmVplEntry 1}

     atmVplAdminStatus   OBJECT-TYPE
          SYNTAX         AtmVorXAdminStatus
          MAX-ACCESS     read-create
          STATUS         current
          DESCRIPTION
           "This object is instanciated only for a VPL
            which terminates a VPC (i.e., one which is
            NOT cross-connected to other VPLs).
            Its value specifies the desired
            administrative state of the VPL."
          DEFVAL { down }
          ::= { atmVplEntry 2}

     atmVplOperStatus    OBJECT-TYPE
          SYNTAX         AtmVorXOperStatus
          MAX-ACCESS     read-only
          STATUS         current
          DESCRIPTION
           "The current operational status of the VPL."
          ::= { atmVplEntry 3}

     atmVplLastChange    OBJECT-TYPE
          SYNTAX         AtmVorXLastChange
          MAX-ACCESS     read-only


          STATUS         current
          DESCRIPTION
           "The value of sysUpTime at the time this
            VPL entered its current operational state."
          ::= { atmVplEntry 4 }

     atmVplReceiveTrafficDescrIndex  OBJECT-TYPE
          SYNTAX         AtmTrafficDescrParamIndex
          MAX-ACCESS     read-create
          STATUS         current
          DESCRIPTION
           "The value of this object identifies the row
            in the atmTrafficDescrParamTable which
            applies to the receive direction of the VPL."
          DEFVAL { 0 }
           ::= { atmVplEntry 5}

     atmVplTransmitTrafficDescrIndex  OBJECT-TYPE
          SYNTAX         AtmTrafficDescrParamIndex
          MAX-ACCESS     read-create
          STATUS         current
          DESCRIPTION
           "The value of this object identifies the row
            in the atmTrafficDescrParamTable which
            applies to the transmit direction of the VPL."
          DEFVAL { 0 }
           ::= { atmVplEntry 6}

     atmVplCrossConnectIdentifier   OBJECT-TYPE
          SYNTAX         INTEGER (0..2147483647)
          MAX-ACCESS     read-only
          STATUS         current
          DESCRIPTION
           "This object is instantiated only for a VPL
            which is cross-connected to other VPLs
            that belong to the same VPC.  All such
            associated VPLs have the same value of this
            object, and all their cross-connections are
            identified either by entries that are indexed
            by the same value of atmVpCrossConnectIndex in
            the atmVpCrossConnectTable of this MIB module or by
            the same value of the cross-connect index in
            the cross-connect table for SVCs and Soft PVCs
            (defined in a separate MIB module).
            At no time should entries in these respective
            cross-connect tables exist simultaneously
            with the same cross-connect index value.


            The value of this object is initialized by the
            agent after the associated entries in the
            atmVpCrossConnectTable have been created."
          ::= {atmVplEntry 7}

     atmVplRowStatus     OBJECT-TYPE
          SYNTAX         RowStatus
          MAX-ACCESS     read-create
          STATUS         current
          DESCRIPTION
           "This object is used to create, delete
            or modify a row in this table.
            To create a new VCL, this object is
            initially set to 'createAndWait' or
            'createAndGo'.  This object should not be
            set to 'active' unless the following columnar
            objects have been set to their desired value
            in this row:
            atmVplReceiveTrafficDescrIndex and
            atmVplTransmitTrafficDescrIndex.
            The DESCRIPTION of atmVplEntry provides
            further guidance to row treatment in this table."
          DEFVAL { createAndWait }
          ::= {atmVplEntry 8}

     atmVplCastType      OBJECT-TYPE
          SYNTAX         AtmConnCastType
          MAX-ACCESS     read-create
          STATUS         current
          DESCRIPTION
           "The connection topology type."
          DEFVAL { p2p }
          ::= {atmVplEntry 9}

     atmVplConnKind      OBJECT-TYPE
          SYNTAX         AtmConnKind
          MAX-ACCESS     read-create
          STATUS         current
          DESCRIPTION
           "The use of call control."
          DEFVAL { pvc }
          ::= {atmVplEntry 10}

     --  ATM Interface Virtual Channel Link (VCL) Table

     -- This table contains configuration and state
     -- information of a bi-directional Virtual Channel
     -- Link (VCL) at an ATM interface.


     -- This table can be used to create, delete or modify
     -- a VCL that is terminated in an ATM host or switch.
     -- This table can also be
     -- used to create, delete or modify a VCL that is
     -- cross-connected to another VCL.

     --  The ATM Interface VCL Table

     atmVclTable         OBJECT-TYPE
          SYNTAX         SEQUENCE OF AtmVclEntry
          MAX-ACCESS     not-accessible
          STATUS         current
          DESCRIPTION
           "The Virtual Channel Link (VCL) table.  A
            bi-directional VCL is modeled as one entry
            in this table. This table can be used for
            PVCs, SVCs and Soft PVCs."
          ::= { atmMIBObjects 7}

     atmVclEntry         OBJECT-TYPE
          SYNTAX         AtmVclEntry
          MAX-ACCESS     not-accessible
          STATUS         current
          DESCRIPTION
           "An entry in the VCL table. This entry is
            used to model a bi-directional VCL.
            To create a VCL at an ATM interface,
            either of the following procedures are used:

            Negotiated VCL establishment

          (1) The management application creates
              a VCL entry in the atmVclTable
              by setting atmVclRowStatus to createAndWait(5).
              This may fail for the following reasons:
              - The selected VPI/VCI values are unavailable,
              - The selected VPI/VCI values are in use.
              Otherwise, the agent creates a row and
              reserves the VPI/VCI values on that port.

          (2) The manager selects an existing row(s) in the
              atmTrafficDescrParamTable,
              thereby, selecting a set of self-consistent
              ATM traffic parameters and the service category
              for receive and transmit directions of the VCL.


         (2a) If no suitable row(s) in the
              atmTrafficDescrParamTable exists,
              the manager must create a new row(s)
              in that table.

         (2b) The manager characterizes the VCL's traffic
              parameters through setting the
              atmVclReceiveTrafficDescrIndex and the
              atmVclTransmitTrafficDescrIndex values
              in the VCL table, which point to the rows
              containing desired ATM traffic parameter values
              in the atmTrafficDescrParamTable.  The agent
              will check the availability of resources and
              may refuse the request.
              If the transmit and receive service categories
              are inconsistent, the agent should refuse the
              request.

          (3) The manager activates the VCL by setting the
              the atmVclRowStatus to active(1) (for
              requirements on this activation see the
              description of atmVclRowStatus).
              If this set is successful, the agent has
              reserved the resources to satisfy the requested
              traffic parameter values and the service category
              for that VCL.
          (4) If the VCL terminates a VCC in the ATM host
              or switch, the manager turns on the
              atmVclAdminStatus to up(1) to turn the VCL
              traffic flow on.  Otherwise, the
              atmVcCrossConnectTable  must be used
              to cross-connect the VCL to another VCL(s)
              in an ATM switch or network.

           One-Shot VCL Establishment

           A VCL may also be established in one step by a
           set-request with all necessary VCL parameter
           values and atmVclRowStatus set to createAndGo(4).

           In contrast to the negotiated VCL establishment
           which allows for detailed error checking
           (i.e., set errors are explicitly linked to
           particular resource acquisition failures),
           the one-shot VCL establishment
           performs the setup on one operation but
           does not have the advantage of step-wise
           error checking.


           VCL Retirement

           A VCL is released by setting atmVclRowStatus to
           destroy(6), and the agent may release all
           associated resources."
          INDEX  {ifIndex, atmVclVpi, atmVclVci }
          ::= { atmVclTable  1}

     AtmVclEntry    ::= SEQUENCE  {
          atmVclVpi                     AtmVpIdentifier,
          atmVclVci                     AtmVcIdentifier,
          atmVclAdminStatus             AtmVorXAdminStatus,
          atmVclOperStatus              AtmVorXOperStatus,
          atmVclLastChange              AtmVorXLastChange,
          atmVclReceiveTrafficDescrIndex
                                AtmTrafficDescrParamIndex,
          atmVclTransmitTrafficDescrIndex
                                AtmTrafficDescrParamIndex,
          atmVccAalType                 INTEGER,
          atmVccAal5CpcsTransmitSduSize INTEGER,
          atmVccAal5CpcsReceiveSduSize  INTEGER,
          atmVccAal5EncapsType          INTEGER,
          atmVclCrossConnectIdentifier  INTEGER,
          atmVclRowStatus               RowStatus,
          atmVclCastType                AtmConnCastType,
          atmVclConnKind                AtmConnKind
                 }

     atmVclVpi           OBJECT-TYPE
          SYNTAX         AtmVpIdentifier
          MAX-ACCESS     not-accessible
          STATUS         current
          DESCRIPTION
           "The VPI value of the VCL."
          ::= { atmVclEntry 1}

     atmVclVci           OBJECT-TYPE
          SYNTAX         AtmVcIdentifier
          MAX-ACCESS     not-accessible
          STATUS         current
          DESCRIPTION
           "The VCI value of the VCL."
          ::= { atmVclEntry 2}

     atmVclAdminStatus   OBJECT-TYPE
          SYNTAX         AtmVorXAdminStatus
          MAX-ACCESS     read-create
          STATUS         current


          DESCRIPTION
           "This object is instanciated only for a VCL which
            terminates a VCC (i.e., one which is NOT
            cross-connected to other VCLs). Its value
            specifies the desired administrative state of
            the VCL."
          DEFVAL { down }
          ::= { atmVclEntry 3}

     atmVclOperStatus    OBJECT-TYPE
          SYNTAX         AtmVorXOperStatus
          MAX-ACCESS     read-only
          STATUS         current
          DESCRIPTION
           "The current operational status of the VCL."
          ::= { atmVclEntry 4}

     atmVclLastChange    OBJECT-TYPE
          SYNTAX         AtmVorXLastChange
          MAX-ACCESS     read-only
          STATUS         current
          DESCRIPTION
           "The value of sysUpTime at the time this VCL
            entered its current operational state."
          ::= { atmVclEntry 5 }

     atmVclReceiveTrafficDescrIndex  OBJECT-TYPE
          SYNTAX         AtmTrafficDescrParamIndex
          MAX-ACCESS     read-create
          STATUS         current
          DESCRIPTION
           "The value of this object identifies the row
            in the ATM Traffic Descriptor Table which
            applies to the receive direction of this VCL."
          DEFVAL { 0 }
           ::= { atmVclEntry 6}

     atmVclTransmitTrafficDescrIndex  OBJECT-TYPE
          SYNTAX         AtmTrafficDescrParamIndex
          MAX-ACCESS     read-create
          STATUS         current
          DESCRIPTION
           "The value of this object identifies the row
            of the ATM Traffic Descriptor Table which applies
            to the transmit direction of this VCL."
          DEFVAL { 0 }
           ::= { atmVclEntry 7}


     atmVccAalType       OBJECT-TYPE
          SYNTAX         INTEGER {
                            aal1(1),
                            aal34(2),
                            aal5(3),
                            other(4),
                            unknown(5),
                            aal2(6)
                              }
          MAX-ACCESS    read-create
          STATUS        current
          DESCRIPTION
           "An instance of this object only exists when the
            local VCL end-point is also the VCC end-point,
            and AAL is in use.
            The type of AAL used on this VCC.
            The AAL type includes AAL1, AAL2, AAL3/4,
            and AAL5. The other(4) may be user-defined
            AAL type.  The unknown type indicates that
            the AAL type cannot be determined."
          DEFVAL { aal5 }
          ::= { atmVclEntry 8 }

     atmVccAal5CpcsTransmitSduSize OBJECT-TYPE
          SYNTAX         INTEGER (1..65535)
          MAX-ACCESS     read-create
          STATUS         current
          DESCRIPTION
           "An instance of this object only exists when the
            local VCL end-point is also the VCC end-point,
            and AAL5 is in use.
            The maximum AAL5 CPCS SDU size in octets that is
            supported on the transmit direction of this VCC."
          DEFVAL { 9188 }
                ::= { atmVclEntry 9 }

     atmVccAal5CpcsReceiveSduSize OBJECT-TYPE
          SYNTAX         INTEGER (1..65535)
          MAX-ACCESS     read-create
          STATUS         current
          DESCRIPTION
           "An instance of this object only exists when the
            local VCL end-point is also the VCC end-point,
            and AAL5 is in use.
            The maximum AAL5 CPCS SDU size in octets that is
            supported on the receive direction of this VCC."
          DEFVAL { 9188 }
                ::= { atmVclEntry 10 }


     atmVccAal5EncapsType  OBJECT-TYPE
          SYNTAX         INTEGER {
                         vcMultiplexRoutedProtocol(1),
                         vcMultiplexBridgedProtocol8023(2),
                         vcMultiplexBridgedProtocol8025(3),
                         vcMultiplexBridgedProtocol8026(4),
                         vcMultiplexLANemulation8023(5),
                         vcMultiplexLANemulation8025(6),
                         llcEncapsulation(7),
                         multiprotocolFrameRelaySscs(8),
                         other(9),
                         unknown(10)
                            }
          MAX-ACCESS     read-create
          STATUS         current
          DESCRIPTION
           "An instance of this object only exists when the
            local VCL end-point is also the VCC end-point,
            and AAL5 is in use.
            The type of data encapsulation used over
            the AAL5 SSCS layer. The definitions reference
            RFC 1483 Multiprotocol Encapsulation
            over ATM AAL5 and to the ATM Forum
            LAN Emulation specification."
          DEFVAL { llcEncapsulation }
                ::= { atmVclEntry 11 }

     atmVclCrossConnectIdentifier   OBJECT-TYPE
          SYNTAX         INTEGER (0..2147483647)
          MAX-ACCESS     read-only
          STATUS         current
          DESCRIPTION
           "This object is instantiated only for a VCL
            which is cross-connected to other VCLs
            that belong to the same VCC.  All such
            associated VCLs have the same value of this
            object, and all their cross-connections are
            identified either by entries that are indexed
            by the same value of atmVcCrossConnectIndex in
            the atmVcCrossConnectTable of this MIB module or by
            the same value of the cross-connect index in
            the cross-connect table for SVCs and Soft PVCs
            (defined in a separate MIB module).

            At no time should entries in these respective
            cross-connect tables exist simultaneously
            with the same cross-connect index value.


            The value of this object is initialized by the
            agent after the associated entries in the
            atmVcCrossConnectTable have been created."
          ::= {atmVclEntry 12}

     atmVclRowStatus     OBJECT-TYPE
          SYNTAX         RowStatus
          MAX-ACCESS     read-create
          STATUS         current
          DESCRIPTION
           "This object is used to create, delete or
            modify a row in this table.  To create
            a new VCL, this object is initially set
            to 'createAndWait' or 'createAndGo'.
            This object should not be
            set to 'active' unless the following columnar
            objects have been set to their desired value
            in this row:
            atmVclReceiveTrafficDescrIndex,
            atmVclTransmitTrafficDescrIndex.
            In addition, if the local VCL end-point
            is also the VCC end-point:
            atmVccAalType.
            In addition, for AAL5 connections only:
            atmVccAal5CpcsTransmitSduSize,
            atmVccAal5CpcsReceiveSduSize, and
            atmVccAal5EncapsType. (The existence
            of these objects imply the AAL connection type.).
            The DESCRIPTION of atmVclEntry provides
            further guidance to row treatment in this table."
          DEFVAL { createAndWait }
                ::= {atmVclEntry 13}

     atmVclCastType      OBJECT-TYPE
          SYNTAX         AtmConnCastType
          MAX-ACCESS     read-create
          STATUS         current
          DESCRIPTION
           "The connection topology type."
          DEFVAL { p2p }
                ::= {atmVclEntry 14}

     atmVclConnKind      OBJECT-TYPE
          SYNTAX         AtmConnKind
          MAX-ACCESS     read-create
          STATUS         current
          DESCRIPTION


           "The use of call control."
          DEFVAL { pvc }
          ::= {atmVclEntry 15}

     --     ATM Virtual Path (VP) Cross Connect Table

     -- This table contains configuration and state
     -- information of point-to-point,
     -- point-to-multipoint, or multipoint-to-multipoint
     -- VP cross-connects for PVCs.

     -- This table has read-create access and can be used
     -- to cross-connect the VPLs together in an ATM switch
     -- or network. The atmVpCrossConnectIndex
     -- is used to associate the related
     -- VPLs that are cross-connected together.

     -- The ATM VP Cross Connect Table
     -- models each bi-directional VPC
     -- cross-connect as a set of entries in
     -- the atmVpCrossConnectTable. A
     -- point-to-point VPC cross-connect is modeled
     -- as one entry; a point-to-multipoint (N leafs) VPC
     -- cross-connect as N entries in this table; and
     -- a multipoint-to-multipoint (N parties) VPC cross-
     -- connect as N(N-1)/2 entries in this table.
     -- In the latter cases, all the N (or N(N-1)/2) entries
     -- are associated with a single VPC cross-connect by
     -- having the same value of atmVpCrossConnectIndex.

     --      _________________________________________
     --      |                                       |
     --  Low |         ATM Switch or Network         | High
     --  port|                                       | port
     -- _____|&gt;&gt; from low to high VPC traffic flow &gt;&gt;|______
     --      |&lt;&lt; from high to low VPC traffic flow &lt;&lt;|
     --      |                                       |
     --      |_______________________________________|
     --

     -- The terms low and high are chosen to represent
     -- numerical ordering of the two interfaces associated
     -- with a VPC cross-connect. That is, the ATM interface
     -- with the lower value of ifIndex is termed 'low',
     -- while the other ATM interface associated with the
     -- VPC cross-connect is termed 'high'. This terminology


     -- is used to provide directional information; for
     -- example, the atmVpCrossConnectL2HOperStatus applies
     -- to the low-&gt;high direction, and
     -- atmVpCrossConnectH2LOperStatus applies to the
     -- high-&gt;low  direction, as illustrated above.

     atmVpCrossConnectIndexNext  OBJECT-TYPE
          SYNTAX         INTEGER (0..2147483647)
          MAX-ACCESS     read-only
          STATUS         current
          DESCRIPTION
           "This object contains an appropriate value to
            be used for atmVpCrossConnectIndex when creating
            entries in the atmVpCrossConnectTable.  The value
            0 indicates that no unassigned entries are
            available. To obtain the atmVpCrossConnectIndex
            value for a new entry, the manager issues a
            management protocol retrieval operation to obtain
            the current value of this object.  After each
            retrieval, the agent should modify the value to
            the next unassigned index.
            After a manager retrieves a value the agent will
            determine through its local policy when this index
            value will be made available for reuse."
          ::= { atmMIBObjects 8 }

     --  The ATM VP Cross Connect Table

     atmVpCrossConnectTable OBJECT-TYPE
          SYNTAX         SEQUENCE OF AtmVpCrossConnectEntry
          MAX-ACCESS     not-accessible
          STATUS         current
          DESCRIPTION
           "The ATM VP Cross Connect table for PVCs.
            An entry in this table models two
            cross-connected VPLs.
            Each VPL must have its atmConnKind set
            to pvc(1)."
          ::= { atmMIBObjects 9 }

     atmVpCrossConnectEntry OBJECT-TYPE
          SYNTAX         AtmVpCrossConnectEntry


          MAX-ACCESS     not-accessible
          STATUS         current
          DESCRIPTION
           "An entry in the ATM VP Cross Connect table.
            This entry is used to model a bi-directional
            ATM VP cross-connect which cross-connects
            two VPLs.

            Step-wise Procedures to set up a VP Cross-connect

            Once the entries in the atmVplTable are created,
            the following procedures are used
            to cross-connect the VPLs together.

           (1) The manager obtains a unique
               atmVpCrossConnectIndex by reading the
               atmVpCrossConnectIndexNext object.

           (2) Next, the manager creates a set of one
               or more rows in the ATM VP Cross Connect
               Table, one for each cross-connection between
               two VPLs.  Each row is indexed by the ATM
               interface port numbers and VPI values of the
               two ends of that cross-connection.
               This set of rows specifies the topology of the
               VPC cross-connect and is identified by a single
               value of atmVpCrossConnectIndex.

            Negotiated VP Cross-Connect Establishment

          (2a) The manager creates a row in this table by
               setting atmVpCrossConnectRowStatus to
               createAndWait(5).  The agent checks the
               requested topology and the mutual sanity of
               the ATM traffic parameters and
               service categories, i.e., the row creation
               fails if:
               - the requested topology is incompatible with
                 associated values of atmVplCastType,
               - the requested topology is not supported
                 by the agent,
               - the traffic/service category parameter values
                 associated with the requested row are
                 incompatible with those of already existing
                 rows for this VP cross-connect.
               [For example, for setting up
               a point-to-point VP cross-connect, the
               ATM traffic parameters in the receive direction


               of a VPL at the low end of the cross-connect
               must equal to the traffic parameters in the
               transmit direction of the other VPL at the
               high end of the cross-connect,
               otherwise, the row creation fails.]
               The agent also checks for internal errors
               in building the cross-connect.

               The atmVpCrossConnectIndex values in the
               corresponding atmVplTable rows are filled
               in by the agent at this point.

          (2b) The manager promotes the row in the
               atmVpCrossConnectTable by setting
               atmVpCrossConnectRowStatus to active(1).  If
               this set is successful, the agent has reserved
               the resources specified by the ATM traffic
               parameter and Service category values
               for each direction of the VP cross-connect
               in an ATM switch or network.

           (3) The manager sets the
               atmVpCrossConnectAdminStatus to up(1) in all
               rows of this VP cross-connect to turn the
               traffic flow on.

            One-Shot VP Cross-Connect Establishment

            A VP cross-connect may also be established in
            one step by a set-request with all necessary
            parameter values and atmVpCrossConnectRowStatus
            set to createAndGo(4).

            In contrast to the negotiated VP cross-connect
            establishment which allows for detailed error
            checking (i.e., set errors are explicitly linked
            to particular resource acquisition failures),
            the one-shot VP cross-connect establishment
            performs the setup on one operation but does not
            have the advantage of step-wise error checking.

            VP Cross-Connect Retirement

            A VP cross-connect identified by a particular
            value of atmVpCrossConnectIndex is released by:

           (1) Setting atmVpCrossConnectRowStatus of all


               rows identified by this value of
               atmVpCrossConnectIndex to destroy(6).
               The agent may release all
               associated resources, and the
               atmVpCrossConnectIndex values in the
               corresponding atmVplTable row are removed.
               Note that a situation when only a subset of
               the associated rows are deleted corresponds
               to a VP topology change.

           (2) After deletion of the appropriate
               atmVpCrossConnectEntries, the manager may
               set atmVplRowStatus to destroy(6) the
               associated VPLs.  The agent releases
               the resources and removes the associated
               rows in the atmVplTable.

            VP Cross-connect Reconfiguration

            At the discretion of the agent, a VP
            cross-connect may be reconfigured by
            adding and/or deleting leafs to/from
            the VP topology as per the VP cross-connect
            establishment/retirement procedures.
            Reconfiguration of traffic/service category parameter
            values requires release of the VP cross-connect
            before those parameter values may by changed
            for individual VPLs."
          INDEX { atmVpCrossConnectIndex,
                atmVpCrossConnectLowIfIndex,
                atmVpCrossConnectLowVpi,
                atmVpCrossConnectHighIfIndex,
                atmVpCrossConnectHighVpi }
          ::= { atmVpCrossConnectTable 1 }

     AtmVpCrossConnectEntry ::= SEQUENCE {
          atmVpCrossConnectIndex          INTEGER,
          atmVpCrossConnectLowIfIndex     InterfaceIndex,
          atmVpCrossConnectLowVpi         AtmVpIdentifier,
          atmVpCrossConnectHighIfIndex    InterfaceIndex,
          atmVpCrossConnectHighVpi        AtmVpIdentifier,
          atmVpCrossConnectAdminStatus    AtmVorXAdminStatus,
          atmVpCrossConnectL2HOperStatus  AtmVorXOperStatus,
          atmVpCrossConnectH2LOperStatus  AtmVorXOperStatus,
          atmVpCrossConnectL2HLastChange  AtmVorXLastChange,
          atmVpCrossConnectH2LLastChange  AtmVorXLastChange,
          atmVpCrossConnectRowStatus      RowStatus
                  }


     atmVpCrossConnectIndex OBJECT-TYPE
          SYNTAX         INTEGER (1..2147483647)
          MAX-ACCESS     not-accessible
          STATUS         current
          DESCRIPTION
           "A unique value to identify this VP cross-connect.
            For each VPL associated with this cross-connect,
            the agent reports this cross-connect index value
            in the atmVplCrossConnectIdentifier attribute of
            the corresponding atmVplTable entries."
          ::= { atmVpCrossConnectEntry 1 }

     atmVpCrossConnectLowIfIndex OBJECT-TYPE
          SYNTAX         InterfaceIndex
          MAX-ACCESS     not-accessible
          STATUS         current
          DESCRIPTION
           "The ifIndex value of the ATM interface for
            this VP cross-connect. The term low implies
            that this ATM interface has the numerically lower
            ifIndex value than the other ATM interface
            identified in the same atmVpCrossConnectEntry."
          ::= { atmVpCrossConnectEntry 2 }

     atmVpCrossConnectLowVpi OBJECT-TYPE
          SYNTAX         AtmVpIdentifier
          MAX-ACCESS     not-accessible
          STATUS         current
          DESCRIPTION
           "The VPI value at the ATM interface
            associated with the VP cross-connect that is
            identified by atmVpCrossConnectLowIfIndex."
          ::= { atmVpCrossConnectEntry 3 }

     atmVpCrossConnectHighIfIndex OBJECT-TYPE
          SYNTAX         InterfaceIndex
          MAX-ACCESS     not-accessible
          STATUS  current
          DESCRIPTION
           "The ifIndex value of the ATM interface for
            this VP cross-connect. The term high implies that
            this ATM interface has the numerically higher
            ifIndex value than the  other ATM interface
            identified in the same atmVpCrossConnectEntry."
          ::= { atmVpCrossConnectEntry 4 }

     atmVpCrossConnectHighVpi OBJECT-TYPE
          SYNTAX         AtmVpIdentifier


          MAX-ACCESS     not-accessible
          STATUS         current
          DESCRIPTION
           "The VPI value at the ATM interface
            associated with the VP cross-connect that is
            identified by atmVpCrossConnectHighIfIndex."
          ::= { atmVpCrossConnectEntry 5 }

     atmVpCrossConnectAdminStatus OBJECT-TYPE
          SYNTAX         AtmVorXAdminStatus
          MAX-ACCESS     read-create
          STATUS         current
          DESCRIPTION
           "The desired administrative status of this
            bi-directional VP cross-connect."
          DEFVAL { down }
          ::= { atmVpCrossConnectEntry 6 }

     atmVpCrossConnectL2HOperStatus OBJECT-TYPE
          SYNTAX         AtmVorXOperStatus
          MAX-ACCESS     read-only
          STATUS         current
          DESCRIPTION
           "The operational status of the VP cross-connect
            in one direction; (i.e., from the low to
            high direction)."
          ::= { atmVpCrossConnectEntry 7 }

     atmVpCrossConnectH2LOperStatus OBJECT-TYPE
          SYNTAX         AtmVorXOperStatus
          MAX-ACCESS     read-only
          STATUS         current
          DESCRIPTION
           "The operational status of the VP cross-connect
            in one direction; (i.e., from the high to
            low direction)."
          ::= { atmVpCrossConnectEntry 8 }

     atmVpCrossConnectL2HLastChange OBJECT-TYPE
          SYNTAX         AtmVorXLastChange
          MAX-ACCESS     read-only
          STATUS         current
          DESCRIPTION
           "The value of sysUpTime at the time this
            VP cross-connect entered its current operational
            state in the low to high direction."
          ::= { atmVpCrossConnectEntry 9 }


     atmVpCrossConnectH2LLastChange OBJECT-TYPE
          SYNTAX         AtmVorXLastChange
          MAX-ACCESS     read-only
          STATUS         current
          DESCRIPTION
            "The value of sysUpTime at the time this
            VP cross-connect entered its current operational
            in the high to low direction."
          ::= { atmVpCrossConnectEntry 10 }

     atmVpCrossConnectRowStatus OBJECT-TYPE
          SYNTAX         RowStatus
          MAX-ACCESS     read-create
          STATUS         current
          DESCRIPTION
           "The status of this entry in the
            atmVpCrossConnectTable.  This object is used to
            create a cross-connect for cross-connecting
            VPLs which are created using the atmVplTable
            or to change or delete an existing cross-connect.
            This object must be initially set
            to `createAndWait' or 'createAndGo'.
            To turn on a VP cross-connect,
            the atmVpCrossConnectAdminStatus
            is set to `up'."
          DEFVAL { createAndWait }
          ::= { atmVpCrossConnectEntry 11 }

     --     ATM Virtual Channel (VC) Cross Connect Table

     -- This table contains configuration and state
     -- information of point-to-point,
     -- point-to-multipoint or multipoint-to-multipoint
     -- VC cross-connects for PVCs.

     -- This table has read-create access and is used
     -- to cross-connect the VCLs together in an ATM switch
     -- or network that belong to a VC connection.
     -- The atmVcCrossConnectIndex is used to associate
     -- the related VCLs that are cross-connected together.

     -- The model using step-wise procedures described for setting
     -- up a VP cross-connect is also used for setting up
     -- a VC cross-connect.


     atmVcCrossConnectIndexNext  OBJECT-TYPE
          SYNTAX         INTEGER (0..2147483647)
          MAX-ACCESS     read-only
          STATUS         current
          DESCRIPTION
           "This object contains an appropriate value to
            be used for atmVcCrossConnectIndex when creating
            entries in the atmVcCrossConnectTable.  The value
            0 indicates that no unassigned entries are
            available. To obtain the atmVcCrossConnectIndex
            value for a new entry, the manager issues a
            management protocol retrieval operation to obtain
            the current value of this object.  After each
            retrieval, the agent should modify the value to
            the next unassigned index.
            After a manager retrieves a value the agent will
            determine through its local policy when this index
            value will be made available for reuse."
          ::= { atmMIBObjects 10 }

     --  The ATM VC Cross Connect Table

     atmVcCrossConnectTable OBJECT-TYPE
          SYNTAX         SEQUENCE OF AtmVcCrossConnectEntry
          MAX-ACCESS     not-accessible
          STATUS         current
          DESCRIPTION
           "The ATM VC Cross Connect table for PVCs.
            An entry in this table models two
            cross-connected VCLs.
            Each VCL must have its atmConnKind set
            to pvc(1)."
          ::= { atmMIBObjects 11 }

     atmVcCrossConnectEntry OBJECT-TYPE
          SYNTAX       AtmVcCrossConnectEntry
          MAX-ACCESS   not-accessible
          STATUS       current
          DESCRIPTION
           "An entry in the ATM VC Cross Connect table.
            This entry is used to model a bi-directional ATM
            VC cross-connect cross-connecting two end points.

            Step-wise Procedures to set up a VC Cross-connect


            Once the entries in the atmVclTable are created,
            the following procedures are used
            to cross-connect the VCLs together to
            form a VCC segment.

           (1) The manager obtains a unique
               atmVcCrossConnectIndex by reading the
               atmVcCrossConnectIndexNext object.

           (2) Next, the manager creates a set of one
               or more rows in the ATM VC Cross Connect
               Table, one for each cross-connection between
               two VCLs.  Each row is indexed by the ATM
               interface port numbers and VPI/VCI values of
               the two ends of that cross-connection.
               This set of rows specifies the topology of the
               VCC cross-connect and is identified by a single
               value of atmVcCrossConnectIndex.

            Negotiated VC Cross-Connect Establishment

          (2a) The manager creates a row in this table by
               setting atmVcCrossConnectRowStatus to
               createAndWait(5).  The agent checks the
               requested topology and the mutual sanity of
               the ATM traffic parameters and
               service categories, i.e., the row creation
               fails if:
               - the requested topology is incompatible with
                 associated values of atmVclCastType,
               - the requested topology is not supported
                 by the agent,
               - the traffic/service category parameter values
                 associated with the requested row are
                 incompatible with those of already existing
                 rows for this VC cross-connect.
               [For example, for setting up
               a point-to-point VC cross-connect, the
               ATM traffic parameters in the receive direction
               of a VCL at the low end of the cross-connect
               must equal to the traffic parameters in the
               transmit direction of the other VCL at the
               high end of the cross-connect,
               otherwise, the row creation fails.]
               The agent also checks for internal errors
               in building the cross-connect.

               The atmVcCrossConnectIndex values in the


               corresponding atmVclTable rows are filled
               in by the agent at this point.

          (2b) The manager promotes the row in the
               atmVcCrossConnectTable by setting
               atmVcCrossConnectRowStatus to active(1).  If
               this set is successful, the agent has reserved
               the resources specified by the ATM traffic
               parameter and Service category values
               for each direction of the VC cross-connect
               in an ATM switch or network.

           (3) The manager sets the
               atmVcCrossConnectAdminStatus to up(1)
               in all rows of this VC cross-connect to
               turn the traffic flow on.

            One-Shot VC Cross-Connect Establishment

            A VC cross-connect may also be established in
            one step by a set-request with all necessary
            parameter values and atmVcCrossConnectRowStatus
            set to createAndGo(4).

            In contrast to the negotiated VC cross-connect
            establishment which allows for detailed error
            checking i.e., set errors are explicitly linked to
            particular resource acquisition failures), the
            one-shot VC cross-connect establishment
            performs the setup on one operation but does
            not have the advantage of step-wise error
            checking.

            VC Cross-Connect Retirement

            A VC cross-connect identified by a particular
            value of atmVcCrossConnectIndex is released by:

           (1) Setting atmVcCrossConnectRowStatus of all rows
               identified by this value of
               atmVcCrossConnectIndex to destroy(6).
               The agent may release all
               associated resources, and the
               atmVcCrossConnectIndex values in the
               corresponding atmVclTable row are removed.
               Note that a situation when only a subset of
               the associated rows are deleted corresponds


               to a VC topology change.

           (2) After deletion of the appropriate
               atmVcCrossConnectEntries, the manager may
               set atmVclRowStatus to destroy(6) the
               associated VCLs.  The agent releases
               the resources and removes the associated
               rows in the atmVclTable.

            VC Cross-Connect Reconfiguration

            At the discretion of the agent, a VC
            cross-connect may be reconfigured by
            adding and/or deleting leafs to/from
            the VC topology as per the VC cross-connect
            establishment/retirement procedures.
            Reconfiguration of traffic/service category parameter
            values requires release of the VC cross-connect
            before those parameter values may by changed
            for individual VCLs."
          INDEX { atmVcCrossConnectIndex,
                atmVcCrossConnectLowIfIndex,
                atmVcCrossConnectLowVpi,
                atmVcCrossConnectLowVci,
                atmVcCrossConnectHighIfIndex,
                atmVcCrossConnectHighVpi,
                atmVcCrossConnectHighVci }
          ::= { atmVcCrossConnectTable 1 }

     AtmVcCrossConnectEntry ::= SEQUENCE {
          atmVcCrossConnectIndex          INTEGER,
          atmVcCrossConnectLowIfIndex     InterfaceIndex,
          atmVcCrossConnectLowVpi         AtmVpIdentifier,
          atmVcCrossConnectLowVci         AtmVcIdentifier,
          atmVcCrossConnectHighIfIndex    InterfaceIndex,
          atmVcCrossConnectHighVpi        AtmVpIdentifier,
          atmVcCrossConnectHighVci        AtmVcIdentifier,
          atmVcCrossConnectAdminStatus    AtmVorXAdminStatus,
          atmVcCrossConnectL2HOperStatus  AtmVorXOperStatus,
          atmVcCrossConnectH2LOperStatus  AtmVorXOperStatus,
          atmVcCrossConnectL2HLastChange  AtmVorXLastChange,
          atmVcCrossConnectH2LLastChange  AtmVorXLastChange,
          atmVcCrossConnectRowStatus      RowStatus
                  }

     atmVcCrossConnectIndex OBJECT-TYPE
          SYNTAX         INTEGER (1..2147483647)
          MAX-ACCESS     not-accessible


          STATUS         current
          DESCRIPTION
           "A unique value to identify this VC cross-connect.
            For each VCL associated with this cross-connect,
            the agent reports this cross-connect index value
            in the atmVclCrossConnectIdentifier attribute of
            the corresponding atmVclTable entries."
          ::= { atmVcCrossConnectEntry 1 }

     atmVcCrossConnectLowIfIndex OBJECT-TYPE
          SYNTAX         InterfaceIndex
          MAX-ACCESS     not-accessible
          STATUS         current
          DESCRIPTION
           "The ifIndex value of the ATM interface for this
            VC cross-connect. The term low implies
            that this ATM interface has the numerically lower
            ifIndex value than the other ATM interface
            identified in the same atmVcCrossConnectEntry."
          ::= { atmVcCrossConnectEntry 2 }

     atmVcCrossConnectLowVpi OBJECT-TYPE
          SYNTAX         AtmVpIdentifier
          MAX-ACCESS     not-accessible
          STATUS         current
          DESCRIPTION
           "The VPI value at the ATM interface
            associated with the VC cross-connect that is
            identified by atmVcCrossConnectLowIfIndex."
          ::= { atmVcCrossConnectEntry 3 }

     atmVcCrossConnectLowVci OBJECT-TYPE
          SYNTAX         AtmVcIdentifier
          MAX-ACCESS     not-accessible
          STATUS         current
          DESCRIPTION
           "The VCI value at the ATM interface
            associated with this VC cross-connect that is
            identified by atmVcCrossConnectLowIfIndex."
          ::= { atmVcCrossConnectEntry 4 }

     atmVcCrossConnectHighIfIndex OBJECT-TYPE
          SYNTAX         InterfaceIndex
          MAX-ACCESS     not-accessible
          STATUS         current
          DESCRIPTION
           "The ifIndex value for the ATM interface for
            this VC cross-connect. The term high implies


            that this ATM interface has the numerically higher
            ifIndex value than the other ATM interface
            identified in the same atmVcCrossConnectEntry."
          ::= { atmVcCrossConnectEntry 5 }

     atmVcCrossConnectHighVpi OBJECT-TYPE
          SYNTAX         AtmVpIdentifier
          MAX-ACCESS     not-accessible
          STATUS         current
          DESCRIPTION
           "The VPI value at the ATM interface
            associated with the VC cross-connect that is
            identified by atmVcCrossConnectHighIfIndex."
          ::= { atmVcCrossConnectEntry 6 }

     atmVcCrossConnectHighVci OBJECT-TYPE
          SYNTAX         AtmVcIdentifier
          MAX-ACCESS     not-accessible
          STATUS         current
          DESCRIPTION
           "The VCI value at the ATM interface
            associated with the VC cross-connect that is
            identified by atmVcCrossConnectHighIfIndex."
          ::= { atmVcCrossConnectEntry 7 }

     atmVcCrossConnectAdminStatus OBJECT-TYPE
          SYNTAX         AtmVorXAdminStatus
          MAX-ACCESS     read-create
          STATUS         current
          DESCRIPTION
           "The desired administrative status of this
            bi-directional VC cross-connect."
          DEFVAL { down }
          ::= { atmVcCrossConnectEntry 8 }

     atmVcCrossConnectL2HOperStatus OBJECT-TYPE
          SYNTAX         AtmVorXOperStatus
          MAX-ACCESS     read-only
          STATUS         current
          DESCRIPTION
           "The current operational status of the
            VC cross-connect in one direction; (i.e.,
            from the low to high direction)."
          ::= { atmVcCrossConnectEntry 9 }

     atmVcCrossConnectH2LOperStatus OBJECT-TYPE
          SYNTAX         AtmVorXOperStatus


          MAX-ACCESS     read-only
          STATUS         current
          DESCRIPTION
           "The current operational status of the
            VC cross-connect in one direction; (i.e.,
            from the high to low direction)."
          ::= { atmVcCrossConnectEntry 10 }

     atmVcCrossConnectL2HLastChange OBJECT-TYPE
          SYNTAX         AtmVorXLastChange
          MAX-ACCESS     read-only
          STATUS         current
          DESCRIPTION
           "The value of sysUpTime at the time this
            VC cross-connect entered its current
            operational state in low to high direction."
          ::= { atmVcCrossConnectEntry 11 }

     atmVcCrossConnectH2LLastChange OBJECT-TYPE
          SYNTAX         AtmVorXLastChange
          MAX-ACCESS     read-only
          STATUS         current
          DESCRIPTION
           "The value of sysUpTime at the time this
            VC cross-connect entered its current
            operational state in high to low direction."
          ::= { atmVcCrossConnectEntry 12 }

     atmVcCrossConnectRowStatus OBJECT-TYPE
          SYNTAX         RowStatus
          MAX-ACCESS     read-create
          STATUS         current
          DESCRIPTION
           "The status of this entry in the
            atmVcCrossConnectTable.  This object is used to
            create a new cross-connect for cross-connecting
            VCLs which are created using the atmVclTable
            or to change or delete existing cross-connect.
            This object must be initially set to
            `createAndWait' or 'createAndGo'.
            To turn on a VC cross-connect,
            the atmVcCrossConnectAdminStatus
            is set to `up'."
          DEFVAL { createAndWait }
          ::= { atmVcCrossConnectEntry 13 }

     -- AAL5 Virtual Channel Connection Performance Statistics


     -- Table

     -- This table contains the AAL5
     -- performance statistics of a VCC at the
     -- interface associated with an AAL5 entity in an ATM
     -- host or ATM switch.

     aal5VccTable        OBJECT-TYPE
          SYNTAX         SEQUENCE OF Aal5VccEntry
          MAX-ACCESS     not-accessible
          STATUS         current
          DESCRIPTION
           "This table contains AAL5 VCC performance
            parameters."
          ::= { atmMIBObjects 12 }

     aal5VccEntry        OBJECT-TYPE
          SYNTAX         Aal5VccEntry
          MAX-ACCESS     not-accessible
          STATUS         current
          DESCRIPTION
           "This list contains the AAL5 VCC
            performance parameters and is indexed
            by ifIndex values of AAL5 interfaces
            and the associated VPI/VCI values."
          INDEX { ifIndex, aal5VccVpi, aal5VccVci }
          ::= { aal5VccTable 1 }

     Aal5VccEntry    ::= SEQUENCE  {
          aal5VccVpi             AtmVpIdentifier,
          aal5VccVci             AtmVcIdentifier,
          aal5VccCrcErrors       Counter32,
          aal5VccSarTimeOuts     Counter32,
          aal5VccOverSizedSDUs   Counter32
               }

     aal5VccVpi          OBJECT-TYPE
          SYNTAX         AtmVpIdentifier
          MAX-ACCESS     not-accessible
          STATUS         current
          DESCRIPTION
           "The VPI value of the AAL5 VCC at the
            interface identified by the ifIndex."
          ::= { aal5VccEntry 1 }

     aal5VccVci          OBJECT-TYPE


          SYNTAX         AtmVcIdentifier
          MAX-ACCESS     not-accessible
          STATUS         current
          DESCRIPTION
           "The VCI value of the AAL5 VCC at the
            interface identified by the ifIndex."
          ::= { aal5VccEntry 2 }

     aal5VccCrcErrors    OBJECT-TYPE
          SYNTAX         Counter32
          MAX-ACCESS     read-only
          STATUS         current
          DESCRIPTION
           "The number of AAL5 CPCS PDUs received with
            CRC-32 errors on this AAL5 VCC at the
            interface associated with an AAL5 entity."
          ::= { aal5VccEntry 3 }

     aal5VccSarTimeOuts  OBJECT-TYPE
          SYNTAX         Counter32
          MAX-ACCESS     read-only
          STATUS         current
          DESCRIPTION
           "The number of partially re-assembled AAL5
            CPCS PDUs which were discarded
            on this AAL5 VCC at the interface associated
            with an AAL5 entity because they
            were not fully re-assembled within the
            required time period.  If the re-assembly
            timer is not supported, then this object
            contains a zero value."
          ::= { aal5VccEntry 4 }

     aal5VccOverSizedSDUs OBJECT-TYPE
          SYNTAX         Counter32
          MAX-ACCESS     read-only
          STATUS         current
          DESCRIPTION
           "The number of AAL5 CPCS PDUs discarded
            on this AAL5 VCC at the interface
            associated with an AAL5 entity because the
            AAL5 SDUs were too large."
          ::= { aal5VccEntry 5 }

     --
     -- The following object may be used in conjunction with
     -- the atmTrafficDescrParamTable for the creation of


     -- new table entries.
     --

     atmTrafficDescrParamIndexNext  OBJECT-TYPE
          SYNTAX         INTEGER (0..2147483647)
          MAX-ACCESS     read-only
          STATUS         current
          DESCRIPTION
           "This object contains an appropriate value to
            be used for atmTrafficDescrParamIndex when
            creating entries in the
            atmTrafficDescrParamTable.
            The value 0 indicates that no unassigned
            entries are available. To obtain the
            atmTrafficDescrParamIndex value for a new
            entry, the manager issues a management
            protocol retrieval operation to obtain the
            current value of this object.  After each
            retrieval, the agent should modify the value
            to the next unassigned index.
            After a manager retrieves a value the agent will
            determine through its local policy when this index
            value will be made available for reuse."
          ::= { atmMIBObjects 13 }

     -- Conformance Information

     atmMIBConformance   OBJECT IDENTIFIER ::= { atmMIB 2 }

     atmMIBGroups        OBJECT IDENTIFIER
                                ::= { atmMIBConformance 1 }
     atmMIBCompliances   OBJECT IDENTIFIER
                                ::= { atmMIBConformance 2 }

     -- Compliance Statements

     atmMIBCompliance2    MODULE-COMPLIANCE
          STATUS         current
          DESCRIPTION
            "The compliance statement for SNMP entities
             including networks which have ATM and
             AAL5 interfaces."

          MODULE -- this module
     --
     -- ****** Interface and Traffic Descriptor Support ***


     --
            MANDATORY-GROUPS  {atmInterfaceConfGroup2,
                               atmTrafficDescrGroup2 }

            OBJECT         atmInterfaceMaxVpcs
            MIN-ACCESS     read-only
            DESCRIPTION
              "Write access is not required."

            OBJECT         atmInterfaceMaxVccs
            MIN-ACCESS     read-only
            DESCRIPTION
              "Write access is not required."

            OBJECT         atmInterfaceMaxActiveVpiBits
            MIN-ACCESS     read-only
            DESCRIPTION
              "Write access is not required.
               At the ATM UNI the maximum number of
               active VPI bits configured for use ranges
               from 0 to 8 only.
               Implementations may support smaller ranges."
            OBJECT         atmInterfaceMaxActiveVciBits
            MIN-ACCESS     read-only
            DESCRIPTION
              "Write access is not required.
               Implementations may support smaller ranges."

            OBJECT         atmInterfaceIlmiVpi
            MIN-ACCESS     read-only
            DESCRIPTION
              "Write access is not required."

            OBJECT         atmInterfaceIlmiVci
            MIN-ACCESS     read-only
            DESCRIPTION
              "Write access is not required."

            OBJECT         atmInterfaceMyNeighborIpAddress
            MIN-ACCESS     read-only
            DESCRIPTION
              "Write access is not required."

            OBJECT         atmInterfaceMyNeighborIfName
            MIN-ACCESS     read-only
            DESCRIPTION
              "Write access is not required."


            OBJECT         atmInterfaceSubscrAddress
            MIN-ACCESS     read-only
            DESCRIPTION
              "Write access is not required."

            OBJECT         atmTrafficDescrParamIndexNext
            DESCRIPTION
              "This object is only required for systems
               that support the creation of entries in
               the atmTrafficDescrParamTable."

            OBJECT         atmTrafficDescrType
            MIN-ACCESS     read-only
            DESCRIPTION
              "Write access is not required."

            OBJECT         atmTrafficDescrParam1
            MIN-ACCESS     read-only
            DESCRIPTION
              "Write access is not required."

            OBJECT         atmTrafficDescrParam2
            MIN-ACCESS     read-only
            DESCRIPTION
              "Write access is not required."

            OBJECT         atmTrafficDescrParam3
            MIN-ACCESS     read-only
            DESCRIPTION
              "Write access is not required."

            OBJECT         atmTrafficDescrParam4
            MIN-ACCESS     read-only
            DESCRIPTION
              "Write access is not required."

            OBJECT         atmTrafficDescrParam5
            MIN-ACCESS     read-only
            DESCRIPTION
              "Write access is not required."

            OBJECT         atmServiceCategory
            MIN-ACCESS     read-only
            DESCRIPTION
              "Write access is not required."

            OBJECT         atmTrafficDescrRowStatus
            SYNTAX         INTEGER {active(1)}


                             -- subset of RowStatus
            MIN-ACCESS     read-only
            DESCRIPTION
              "Write access is not required, and only one
               of the six enumerated values for the
               RowStatus textual convention need be
               supported, specifically: active(1)."

            OBJECT         atmTrafficFrameDiscard
            MIN-ACCESS     read-only
            DESCRIPTION
              "Write access is not required."

     --
     -- ****** DS3 PLCP Support **************************
     --
            GROUP          atmInterfaceDs3PlcpGroup
            DESCRIPTION
              "This group is mandatory only for those
               ATM interfaces which implement the
               DS3 PLCP layer."
     --
     -- ****** TC Sublayer Support ********************************
     --
            GROUP          atmInterfaceTCGroup
            DESCRIPTION
              "This group is mandatory only for those
               ATM interfaces which implement the
               TC Sublayer."

     --
     -- ****** VPC Support *******************************
     --
            GROUP          atmVpcTerminationGroup2
            DESCRIPTION
              "This group is mandatory only for those
               ATM interfaces which implement ATM
               VPLs that terminate VPCs (i.e., ones which
               are NOT cross-connected to other VPLs)."

            GROUP          atmVplCrossConnectGroup
            DESCRIPTION
              "This group is mandatory only for those
               ATM interfaces which implement ATM
               VPLs that are not associated with VCLs
               and are cross-connected to other VPLs
               for VPCs."


            GROUP          atmVpPvcCrossConnectGroup
            DESCRIPTION
              "This group is mandatory only for those
               ATM interfaces which implement ATM
               VPLs that are not associated with VCLs
               and are cross-connected to other VPLs
               for permanent VPCs (i.e., PVCs).
               This group is not used to crossconnect
               a PVC with an SVC to form a Soft PVC."

            OBJECT         atmVplAdminStatus
            MIN-ACCESS     read-only
            DESCRIPTION
              "Write access is not required."

            OBJECT         atmVplReceiveTrafficDescrIndex
            MIN-ACCESS     read-only
            DESCRIPTION
              "Write access is not required."

            OBJECT         atmVplTransmitTrafficDescrIndex
            MIN-ACCESS     read-only
            DESCRIPTION
              "Write access is not required."

            OBJECT         atmVplRowStatus
            SYNTAX         INTEGER {active(1)}
                             -- subset of RowStatus
            MIN-ACCESS      read-only
            DESCRIPTION
              "Write access is not required, and only one
               of the six enumerated values for the
               RowStatus textual convention need be
               supported, specifically: active(1)."

            OBJECT         atmVplCastType
            MIN-ACCESS     read-only
            DESCRIPTION
              "Write access is not required."

            OBJECT         atmVplConnKind
            MIN-ACCESS     read-only
            DESCRIPTION
              "Write access is not required."

            OBJECT         atmVpCrossConnectAdminStatus
            MIN-ACCESS     read-only
            DESCRIPTION


              "Write access is not required."

            OBJECT         atmVpCrossConnectRowStatus
            SYNTAX         INTEGER {active(1)}
                             -- subset of RowStatus
            MIN-ACCESS     read-only
            DESCRIPTION
              "Write access is not required, and only one
               of the six enumerated values for the
               RowStatus textual convention need be
               supported, specifically: active(1)."

     --
     -- ****** VCC Support *******************************
     --
            GROUP          atmVccTerminationGroup2
            DESCRIPTION
              "This group is mandatory only for those
               ATM interfaces which implement ATM
               VCLs that terminate VCCs (i.e., ones which
               are NOT cross-connected to other VCLs)."

            GROUP          atmVclCrossConnectGroup
            DESCRIPTION
              "This group is mandatory only for those
               ATM interfaces which implement ATM
               VCLs that are cross-connected to other VCLs
               for VCCs."

            GROUP          atmVcPvcCrossConnectGroup
            DESCRIPTION
              "This group is mandatory only for those
               ATM interfaces which implement ATM
               VCLs that are cross-connected to other
               VCLs for permanent VCCs (i.e., PVCs).
               This group is not used to crossconnect
               a PVC with an SVC to form a Soft PVC."

            OBJECT         atmVclAdminStatus
            MIN-ACCESS     read-only
            DESCRIPTION
              "Write access is not required."

            OBJECT         atmVclReceiveTrafficDescrIndex
            MIN-ACCESS     read-only
            DESCRIPTION
              "Write access is not required."


            OBJECT         atmVclTransmitTrafficDescrIndex
            MIN-ACCESS     read-only
            DESCRIPTION
              "Write access is not required."

            OBJECT         atmVccAalType
            MIN-ACCESS     read-only
            DESCRIPTION
              "Write access is not required."

            OBJECT         atmVclRowStatus
            SYNTAX         INTEGER {active(1)}
                             -- subset of RowStatus
            MIN-ACCESS     read-only
            DESCRIPTION
              "Write access is not required, and only one
               of the six enumerated values for the
               RowStatus textual convention need be
               supported, specifically: active(1)."

            OBJECT         atmVclCastType
            MIN-ACCESS     read-only
            DESCRIPTION
              "Write access is not required."

            OBJECT         atmVclConnKind
            MIN-ACCESS     read-only
            DESCRIPTION
              "Write access is not required."

            OBJECT         atmVcCrossConnectAdminStatus
            MIN-ACCESS     read-only
            DESCRIPTION
              "Write access is not required."

            OBJECT         atmVcCrossConnectRowStatus
            SYNTAX         INTEGER { active(1)}
                             -- subset of RowStatus
            MIN-ACCESS     read-only
            DESCRIPTION
              "Write access is not required, and only one
               of the six enumerated values for the
               RowStatus textual convention need be
               supported, specifically: active(1)."
     --
     -- ****** AAL5 Support ******************************
     --
            GROUP          aal5VccGroup


            DESCRIPTION
              "This group is mandatory for the
               AAL5 virtual connections only."
            OBJECT         atmVccAal5CpcsTransmitSduSize
            MIN-ACCESS     read-only
            DESCRIPTION
              "Write access is not required."

            OBJECT         atmVccAal5CpcsReceiveSduSize
            MIN-ACCESS     read-only
            DESCRIPTION
              "Write access is not required."

            OBJECT         atmVccAal5EncapsType
            MIN-ACCESS     read-only
            DESCRIPTION
              "Write access is not required."
             ::= { atmMIBCompliances 2 }

     -- Units of Conformance

     atmInterfaceDs3PlcpGroup    OBJECT-GROUP
            OBJECTS {atmInterfaceDs3PlcpSEFSs,
                atmInterfaceDs3PlcpAlarmState,
                atmInterfaceDs3PlcpUASs}
            STATUS     current
            DESCRIPTION
               "A collection of objects providing information
                about DS3 PLCP layer at an ATM interface."
            ::= { atmMIBGroups 3 }

     atmInterfaceTCGroup    OBJECT-GROUP
            OBJECTS { atmInterfaceOCDEvents,
                atmInterfaceTCAlarmState }
            STATUS     current
            DESCRIPTION
               "A collection of objects providing information
                about TC sublayer at an ATM interface."
            ::= { atmMIBGroups 4 }

     aal5VccGroup    OBJECT-GROUP
            OBJECTS {atmVccAal5CpcsTransmitSduSize,
                atmVccAal5CpcsReceiveSduSize,
                atmVccAal5EncapsType,
                aal5VccCrcErrors, aal5VccSarTimeOuts,
                aal5VccOverSizedSDUs }
            STATUS     current


            DESCRIPTION
               "A collection of objects providing
                AAL5 configuration and performance statistics
                of a VCC."
            ::= { atmMIBGroups 9 }

     atmInterfaceConfGroup2    OBJECT-GROUP
            OBJECTS {
                  atmInterfaceMaxVpcs, atmInterfaceMaxVccs,
                  atmInterfaceConfVpcs, atmInterfaceConfVccs,
                  atmInterfaceMaxActiveVpiBits,
                  atmInterfaceMaxActiveVciBits,
                  atmInterfaceIlmiVpi,
                  atmInterfaceIlmiVci,
                  atmInterfaceMyNeighborIpAddress,
                  atmInterfaceMyNeighborIfName,
                  atmInterfaceCurrentMaxVpiBits,
                  atmInterfaceCurrentMaxVciBits,
                  atmInterfaceSubscrAddress }
            STATUS     current
            DESCRIPTION
              "A collection of objects providing configuration
               information about an ATM interface."
            ::= { atmMIBGroups 10 }

     atmTrafficDescrGroup2    OBJECT-GROUP
            OBJECTS {
                atmTrafficDescrType, atmTrafficDescrParam1,
                atmTrafficDescrParam2, atmTrafficDescrParam3,
                atmTrafficDescrParam4, atmTrafficDescrParam5,
                atmTrafficDescrRowStatus, atmServiceCategory,
                atmTrafficFrameDiscard,
                atmTrafficDescrParamIndexNext }
            STATUS     current
            DESCRIPTION
               "A collection of objects providing information
                about ATM traffic descriptor type and
                the associated parameters."
            ::= { atmMIBGroups 11 }

     atmVpcTerminationGroup2    OBJECT-GROUP
            OBJECTS  {atmVplOperStatus, atmVplAdminStatus,
                atmVplLastChange,
                atmVplReceiveTrafficDescrIndex,
                atmVplTransmitTrafficDescrIndex,
                atmVplRowStatus, atmVplCastType,
                atmVplConnKind }
            STATUS     current


            DESCRIPTION
               "A collection of objects providing information
                about a VPL at an ATM interface which
                terminates a VPC (i.e., one which is NOT
                cross-connected to other VPLs)."
            ::= { atmMIBGroups 12 }

     atmVccTerminationGroup2    OBJECT-GROUP
            OBJECTS {atmVclOperStatus, atmVclAdminStatus,
                 atmVclLastChange,
                 atmVclReceiveTrafficDescrIndex,
                 atmVclTransmitTrafficDescrIndex,
                 atmVccAalType, atmVclRowStatus,
                 atmVclCastType, atmVclConnKind }
            STATUS     current
            DESCRIPTION
               "A collection of objects providing information
                about a VCL at an ATM interface
                which terminates a VCC (i.e., one which is
                NOT cross-connected to other VCLs)."
            ::= { atmMIBGroups 13 }

     atmVplCrossConnectGroup    OBJECT-GROUP
            OBJECTS { atmVplReceiveTrafficDescrIndex,
                atmVplTransmitTrafficDescrIndex,
                atmVplOperStatus, atmVplLastChange,
                atmVplRowStatus,
                atmVplCastType, atmVplConnKind }
            STATUS     current
            DESCRIPTION
               "A collection of objects providing
                information about the VPLs that
                are cross-connected together."
            ::= { atmMIBGroups 14 }

     atmVpPvcCrossConnectGroup    OBJECT-GROUP
            OBJECTS { atmVpCrossConnectAdminStatus,
                atmVpCrossConnectL2HOperStatus,
                atmVpCrossConnectH2LOperStatus,
                atmVpCrossConnectL2HLastChange,
                atmVpCrossConnectH2LLastChange,
                atmVpCrossConnectRowStatus,
                atmVplCrossConnectIdentifier,
                atmVpCrossConnectIndexNext }
            STATUS     current
            DESCRIPTION
               "A collection of objects providing
                information about a VP cross-connect


                for PVCs. These objects are not used
                for Soft PVCs or SVCs."
            ::= { atmMIBGroups 15 }

     atmVclCrossConnectGroup    OBJECT-GROUP
            OBJECTS { atmVclReceiveTrafficDescrIndex,
                atmVclTransmitTrafficDescrIndex,
                atmVclOperStatus, atmVclLastChange,
                atmVclRowStatus,
                atmVclCastType, atmVclConnKind }
            STATUS     current
            DESCRIPTION
               "A collection of objects providing
                information about the VCLs that
                are cross-connected together."
            ::= { atmMIBGroups 16 }

     atmVcPvcCrossConnectGroup    OBJECT-GROUP
            OBJECTS { atmVcCrossConnectAdminStatus,
                atmVcCrossConnectL2HOperStatus,
                atmVcCrossConnectH2LOperStatus,
                atmVcCrossConnectL2HLastChange,
                atmVcCrossConnectH2LLastChange,
                atmVcCrossConnectRowStatus,
                atmVclCrossConnectIdentifier,
                atmVcCrossConnectIndexNext }
            STATUS     current
            DESCRIPTION
               "A collection of objects providing
                information about a VC cross-connect
                for PVCs. These objects are not used
                for Soft PVCs or SVCs."
            ::= { atmMIBGroups 17 }

     -- Deprecated Definitions - Objects

     -- atmInterfaceAddressType
     -- atmTrafficQoSClass

     -- Deprecated Definitions - Compliance

     atmMIBCompliance    MODULE-COMPLIANCE
          STATUS         deprecated
          DESCRIPTION
            "The compliance statement for SNMP entities
             including networks which have ATM and


             AAL5 interfaces."

          MODULE -- this module
            MANDATORY-GROUPS  {atmInterfaceConfGroup,
                               atmTrafficDescrGroup}

            OBJECT         atmInterfaceMaxVpcs
            MIN-ACCESS     read-only
            DESCRIPTION
              "Write access is not required."

            OBJECT         atmInterfaceMaxVccs
            MIN-ACCESS     read-only
            DESCRIPTION
              "Write access is not required."

            OBJECT         atmInterfaceMaxActiveVpiBits
            MIN-ACCESS     read-only
            DESCRIPTION
              "Write access is not required."

            OBJECT         atmInterfaceMaxActiveVciBits
            MIN-ACCESS     read-only
            DESCRIPTION
              "Write access is not required."

            OBJECT         atmInterfaceIlmiVpi
            MIN-ACCESS     read-only
            DESCRIPTION
              "Write access is not required."

            OBJECT         atmInterfaceIlmiVci
            MIN-ACCESS     read-only
            DESCRIPTION
              "Write access is not required."

            OBJECT         atmInterfaceMyNeighborIpAddress
            MIN-ACCESS     read-only
            DESCRIPTION
              "Write access is not required."

            OBJECT         atmInterfaceMyNeighborIfName
            MIN-ACCESS     read-only
            DESCRIPTION
              "Write access is not required."

            OBJECT         atmTrafficDescrType
            MIN-ACCESS     read-only


            DESCRIPTION
              "Write access is not required."

            OBJECT         atmTrafficDescrParam1
            MIN-ACCESS     read-only
            DESCRIPTION
              "Write access is not required."

            OBJECT         atmTrafficDescrParam2
            MIN-ACCESS     read-only
            DESCRIPTION
              "Write access is not required."

            OBJECT         atmTrafficDescrParam3
            MIN-ACCESS     read-only
            DESCRIPTION
              "Write access is not required."

            OBJECT         atmTrafficDescrParam4
            MIN-ACCESS     read-only
            DESCRIPTION
              "Write access is not required."

            OBJECT         atmTrafficDescrParam5
            MIN-ACCESS     read-only
            DESCRIPTION
              "Write access is not required."

            OBJECT         atmTrafficQoSClass
            MIN-ACCESS     read-only
            DESCRIPTION
              "Write access is not required."

            OBJECT         atmTrafficDescrRowStatus
            SYNTAX         INTEGER {active(1)}
                             -- subset of RowStatus
            MIN-ACCESS     read-only
            DESCRIPTION
              "Write access is not required, and only one
               of the six enumerated values for the
               RowStatus textual convention need be
               supported, specifically: active(1)."

            GROUP          atmInterfaceDs3PlcpGroup
            DESCRIPTION
              "This group is mandatory only for those
               ATM interfaces which implement the
               DS3 PLCP layer."


            GROUP          atmInterfaceTCGroup
            DESCRIPTION
              "This group is mandatory only for those
               ATM interfaces which implement the
               TC Sublayer."

            GROUP          atmVpcTerminationGroup
            DESCRIPTION
              "This group is mandatory only for those
               ATM interfaces which implement ATM
               VPLs that terminate VPCs (i.e., ones which
               are NOT cross-connected to other VPLs)."

            GROUP          atmVpCrossConnectGroup
            DESCRIPTION
              "This group is mandatory only for those
               ATM interfaces which implement ATM
               VPLs that are not associated with VCLs
               and are cross-connected to other VPLs."

            OBJECT         atmVplAdminStatus
            MIN-ACCESS     read-only
            DESCRIPTION
              "Write access is not required."

            OBJECT         atmVplReceiveTrafficDescrIndex
            MIN-ACCESS     read-only
            DESCRIPTION
              "Write access is not required."

            OBJECT         atmVplTransmitTrafficDescrIndex
            MIN-ACCESS     read-only
            DESCRIPTION
              "Write access is not required."

            OBJECT         atmVplRowStatus
            SYNTAX         INTEGER {active(1)}
                             -- subset of RowStatus
            MIN-ACCESS      read-only
            DESCRIPTION
              "Write access is not required, and only one
               of the six enumerated values for the
               RowStatus textual convention need be
               supported, specifically: active(1)."

            OBJECT         atmVpCrossConnectAdminStatus
            MIN-ACCESS     read-only
            DESCRIPTION


              "Write access is not required."

            OBJECT         atmVpCrossConnectRowStatus
            SYNTAX         INTEGER {active(1)}
                             -- subset of RowStatus
            MIN-ACCESS     read-only
            DESCRIPTION
              "Write access is not required, and only one
               of the six enumerated values for the
               RowStatus textual convention need be
               supported, specifically: active(1)."

            GROUP          atmVccTerminationGroup
            DESCRIPTION
              "This group is mandatory only for those
               ATM interfaces which implement ATM
               VCLs that terminate VCCs (i.e., ones which
               are NOT cross-connected to other VCLs)."

            GROUP          atmVcCrossConnectGroup
            DESCRIPTION
              "This group is mandatory only for those
               ATM interfaces which implement ATM
               VCLs that are cross-connected to
               other VCLs."

            OBJECT         atmVclAdminStatus
            MIN-ACCESS     read-only
            DESCRIPTION
              "Write access is not required."

            OBJECT         atmVclReceiveTrafficDescrIndex
            MIN-ACCESS     read-only
            DESCRIPTION
              "Write access is not required."

            OBJECT         atmVclTransmitTrafficDescrIndex
            MIN-ACCESS     read-only
            DESCRIPTION
              "Write access is not required."

            OBJECT         atmVccAalType
            MIN-ACCESS     read-only
            DESCRIPTION
              "Write access is not required."

            OBJECT         atmVclRowStatus
            SYNTAX         INTEGER {active(1)}


                             -- subset of RowStatus
            MIN-ACCESS     read-only
            DESCRIPTION
              "Write access is not required, and only one
               of the six enumerated values for the
               RowStatus textual convention need be
               supported, specifically: active(1)."

            OBJECT         atmVcCrossConnectAdminStatus
            MIN-ACCESS     read-only
            DESCRIPTION
              "Write access is not required."

            OBJECT         atmVcCrossConnectRowStatus
            SYNTAX         INTEGER { active(1)}
                             -- subset of RowStatus
            MIN-ACCESS     read-only
            DESCRIPTION
              "Write access is not required, and only one
               of the six enumerated values for the
               RowStatus textual convention need be
               supported, specifically: active(1)."

            GROUP          aal5VccGroup
            DESCRIPTION
              "This group is mandatory for the
               AAL5 virtual connections only."

            OBJECT         atmVccAal5CpcsTransmitSduSize
            MIN-ACCESS     read-only
            DESCRIPTION
              "Write access is not required."

            OBJECT         atmVccAal5CpcsReceiveSduSize
            MIN-ACCESS     read-only
            DESCRIPTION
              "Write access is not required."

            OBJECT         atmVccAal5EncapsType
            MIN-ACCESS     read-only
            DESCRIPTION
              "Write access is not required."
             ::= { atmMIBCompliances 1 }

     -- Deprecated Definitions - Groups


     atmInterfaceConfGroup    OBJECT-GROUP
            OBJECTS {
                  atmInterfaceMaxVpcs, atmInterfaceMaxVccs,
                  atmInterfaceConfVpcs, atmInterfaceConfVccs,
                  atmInterfaceMaxActiveVpiBits,
                  atmInterfaceMaxActiveVciBits,
                  atmInterfaceIlmiVpi,
                  atmInterfaceIlmiVci,
                  atmInterfaceAddressType,
                  atmInterfaceAdminAddress,
                  atmInterfaceMyNeighborIpAddress,
                  atmInterfaceMyNeighborIfName }
            STATUS     deprecated
            DESCRIPTION
              "A collection of objects providing configuration
               information about an ATM interface."
            ::= { atmMIBGroups 1 }

     atmTrafficDescrGroup    OBJECT-GROUP
            OBJECTS {
                atmTrafficDescrType, atmTrafficDescrParam1,
                atmTrafficDescrParam2, atmTrafficDescrParam3,
                atmTrafficDescrParam4, atmTrafficDescrParam5,
                atmTrafficQoSClass, atmTrafficDescrRowStatus}
            STATUS     deprecated
            DESCRIPTION
               "A collection of objects providing information
                about ATM traffic descriptor type and
                the associated parameters."
            ::= { atmMIBGroups 2 }

     atmVpcTerminationGroup    OBJECT-GROUP
            OBJECTS  {atmVplOperStatus, atmVplAdminStatus,
                atmVplLastChange,
                atmVplReceiveTrafficDescrIndex,
                atmVplTransmitTrafficDescrIndex,
                atmVplRowStatus }
            STATUS     deprecated
            DESCRIPTION
               "A collection of objects providing
                information about a VPL at an ATM interface
                which terminates a VPC
                (i.e., one which is NOT cross-connected
                to other VPLs)."
            ::= { atmMIBGroups 5 }

     atmVccTerminationGroup    OBJECT-GROUP
            OBJECTS {atmVclOperStatus, atmVclAdminStatus,


                atmVclLastChange,
                 atmVclReceiveTrafficDescrIndex,
                 atmVclTransmitTrafficDescrIndex,
                 atmVccAalType, atmVclRowStatus }
            STATUS     deprecated
            DESCRIPTION
               "A collection of objects providing information
                about a VCL at an ATM interface
                which terminates a VCC (i.e., one which is
                NOT cross-connected to other VCLs)."
            ::= { atmMIBGroups 6 }

     atmVpCrossConnectGroup    OBJECT-GROUP
            OBJECTS { atmVplReceiveTrafficDescrIndex,
                atmVplTransmitTrafficDescrIndex,
                atmVplOperStatus, atmVplRowStatus,
                atmVpCrossConnectAdminStatus,
                atmVpCrossConnectL2HOperStatus,
                atmVpCrossConnectH2LOperStatus,
                atmVpCrossConnectL2HLastChange,
                atmVpCrossConnectH2LLastChange,
                atmVpCrossConnectRowStatus,
                atmVplCrossConnectIdentifier,
                atmVpCrossConnectIndexNext }
            STATUS     deprecated
            DESCRIPTION
               "A collection of objects providing
                information about a VP cross-connect
                and the associated VPLs that are
                cross-connected together."
            ::= { atmMIBGroups 7 }

     atmVcCrossConnectGroup    OBJECT-GROUP
            OBJECTS { atmVclReceiveTrafficDescrIndex,
                atmVclTransmitTrafficDescrIndex,
                atmVclOperStatus, atmVclRowStatus,
                atmVcCrossConnectAdminStatus,
                atmVcCrossConnectL2HOperStatus,
                atmVcCrossConnectH2LOperStatus,
                atmVcCrossConnectL2HLastChange,
                atmVcCrossConnectH2LLastChange,
                atmVcCrossConnectRowStatus,
                atmVclCrossConnectIdentifier,
                atmVcCrossConnectIndexNext }
            STATUS     deprecated
            DESCRIPTION
               "A collection of objects providing
                information about a VC cross-connect


                and the associated VCLs that are
                cross-connected together."
            ::= { atmMIBGroups 8 }

     -- {atmMIB 3} has been used by [19].

END

SONET-MIB DEFINITIONS ::= BEGIN

IMPORTS
    MODULE-IDENTITY, OBJECT-TYPE,
    Integer32, transmission
          FROM SNMPv2-SMI
    DisplayString, TruthValue
          FROM SNMPv2-TC
    MODULE-COMPLIANCE, OBJECT-GROUP
          FROM SNMPv2-CONF
    ifIndex
          FROM IF-MIB
    PerfCurrentCount, PerfIntervalCount
          FROM PerfHist-TC-MIB;

--  This is the MIB module for the SONET/SDH Interface objects.

sonetMIB MODULE-IDENTITY
    LAST-UPDATED "9810190000Z"
    ORGANIZATION "IETF AToM MIB Working Group"
    CONTACT-INFO
      "Kaj Tesink
       Telcordia Technologies
       Tel: (732) 758-5254
       Fax: (732) 758-2269
       E-mail: kaj@research.telcordia.com."
    DESCRIPTION
         "The MIB module to describe
         SONET/SDH interfaces objects."


    REVISION      "9810190000Z"
    DESCRIPTION
        "The key changes made to this MIB module
        since its initial publication in RFC 1595
        are as follows.

        (1) The MODULE-IDENTITY has been updated to reflect the
            changes to the MIB.

        (2) Where applicable, the textual conventions
            PerfCurrentCount and PerfIntervalCount from
            PerfHist-TC-MIB have been used in place of Gauge32.

        (3) An agent now has the option to delay updates to
            the various performance counts in lieu of performing
            retroactive adjustments upon entering into or exiting
            from unavailable time. This implementation option is
            described in Appendix A of this memo.

        (4) In order to make the SONET-MIB more useful for
            circuit provisioning, the formerly read-only objects
            sonetMediumType, sonetMediumLineCoding,
            sonetMediumLineType, and sonetMediumCircuitIdentifier
            have been given a MAX-ACCESS of read-write. The
            MIN-ACCESS remains read-only.

        (5) The DESCRIPTION clause for sonetMediumTimeElapsed has
            been updated to describe its behaviour if the duration
            of the current interval exceeds the maximum value.

        (6) The DESCRIPTION clause for sonetMediumValidIntervals
            has been updated to describe its behaviour when some
            intervals may be unavailable, and the object
            sonetMediumInvalidIntervals has been added to keep
            count of the number of missing intervals (if any).

        (7) The object sonetMediumLoopbackConfig has been added
            to enable or disable loopback configurations.

        (8) Because the error count thresholds for declaring
            severely errored seconds that are specified in ANSI
            T1.231-1993, ITU-T G.826-1995, and ANSI T1.231-1997
            are all different from each other and from the thresholds
            specified in RFC 1595, an enumerated INTEGER object
            sonetSESthresholdSet has been added to allow an agent
            to specify which threshold set is in use. Text has
            been added to Section 3 stating that if this object is
            not implemented the thresholds specified in RFC 1595


            should be assumed, and the table containing those
            thresholds has been moved to Appendix B of this memo.

        (9) A column with SYNTAX TruthValue has been added to each
            interval table.  The purpose of the additional column
            is to indicate, for each interval, whether the data
            is valid in the sense intended by ANSI T1.231 clause
            9.1.2.2 [31][35]. The objects in question are:

                sonetSectionIntervalValidData
                sonetLineIntervalValidData
                sonetFarEndLineIntervalValidData
                sonetPathIntervalValidData
                sonetFarEndPathIntervalValidData
                sonetVTIntervalValidData
                sonetFarEndVTIntervalValidData

       (10) The ranges for sonetPathCurrentStatus and
            sonetVTCurrentStatus have been made consistent
            with the DESCRIPTION clauses.

       (11) The conformance information has been updated. Previous
            conformance information from RFC 1595 has been
            deprecated. Some typographical errors in the deprecated
            section have been corrected in order to prevent
            MIB compilation errors."

    REVISION      "9401030000Z"
    DESCRIPTION
        "The RFC1595 version of this MIB module."

    ::= { transmission 39 }

--  This is the MIB module for the SONET/SDH objects

sonetObjects      OBJECT IDENTIFIER ::= { sonetMIB 1 }

sonetObjectsPath  OBJECT IDENTIFIER ::= { sonetMIB 2 }

sonetObjectsVT    OBJECT IDENTIFIER ::= { sonetMIB 3 }

-- groups in the SONET/SDH MIB module

sonetMedium        OBJECT IDENTIFIER ::= { sonetObjects 1 }

sonetSection       OBJECT IDENTIFIER ::= { sonetObjects 2 }


sonetLine          OBJECT IDENTIFIER ::= { sonetObjects 3 }

sonetFarEndLine    OBJECT IDENTIFIER ::= { sonetObjects 4 }

sonetPath          OBJECT IDENTIFIER ::= { sonetObjectsPath 1 }

sonetFarEndPath    OBJECT IDENTIFIER ::= { sonetObjectsPath 2 }

sonetVT            OBJECT IDENTIFIER ::= { sonetObjectsVT 1 }

sonetFarEndVT      OBJECT IDENTIFIER ::= { sonetObjectsVT 2 }

-- the SONET/SDH Medium group

-- SONET/SDH interfaces for some applications may be electrical
-- interfaces and not optical interfaces.  This group handles
-- the configuration information for both optical SONET/SDH
-- interfaces and electrical SONET/SDH interfaces.

sonetMediumTable OBJECT-TYPE
    SYNTAX  SEQUENCE OF SonetMediumEntry
    MAX-ACCESS  not-accessible
    STATUS  current
    DESCRIPTION
       "The SONET/SDH Medium table."
     ::= { sonetMedium 1 }

sonetMediumEntry OBJECT-TYPE
    SYNTAX  SonetMediumEntry
    MAX-ACCESS  not-accessible
    STATUS  current
    DESCRIPTION
       "An entry in the SONET/SDH Medium table."
    INDEX   { ifIndex }
     ::= { sonetMediumTable 1 }

SonetMediumEntry ::=
    SEQUENCE {
         sonetMediumType               INTEGER,
         sonetMediumTimeElapsed        Integer32,
         sonetMediumValidIntervals     Integer32,
         sonetMediumLineCoding         INTEGER,
         sonetMediumLineType           INTEGER,
         sonetMediumCircuitIdentifier  DisplayString,
         sonetMediumInvalidIntervals   Integer32,
         sonetMediumLoopbackConfig     BITS
    }


sonetMediumType OBJECT-TYPE
    SYNTAX  INTEGER  {
               sonet(1),
               sdh(2)
            }
    MAX-ACCESS  read-write
    STATUS  current
    DESCRIPTION
       "This variable identifies whether a SONET
       or a SDH signal is used across this interface."
    ::= { sonetMediumEntry 1 }

sonetMediumTimeElapsed OBJECT-TYPE
    SYNTAX  Integer32 (1..900)
    MAX-ACCESS  read-only
    STATUS  current
    DESCRIPTION
       "The number of seconds, including partial seconds,
       that have elapsed since the beginning of the current
       measurement period. If, for some reason, such as an
       adjustment in the system's time-of-day clock, the
       current interval exceeds the maximum value, the
       agent will return the maximum value."
    ::= { sonetMediumEntry 2 }

sonetMediumValidIntervals OBJECT-TYPE
    SYNTAX  Integer32 (0..96)
    MAX-ACCESS  read-only
    STATUS  current
    DESCRIPTION
       "The number of previous 15-minute intervals
       for which data was collected.
       A SONET/SDH interface must be capable
       of supporting at least n intervals.
       The minimum value of n is 4.
       The default of n is 32.
       The maximum value of n is 96.
       The value will be &lt;n&gt; unless the measurement was
       (re-)started within the last (&lt;n&gt;*15) minutes, in which
       case the value will be the number of complete 15
       minute intervals for which the agent has at least
       some data. In certain cases (e.g., in the case
       where the agent is a proxy) it is possible that some
       intervals are unavailable.  In this case, this
       interval is the maximum interval number for
       which data is available. "
    ::= { sonetMediumEntry 3 }


sonetMediumLineCoding OBJECT-TYPE
    SYNTAX  INTEGER {
                sonetMediumOther(1),
                sonetMediumB3ZS(2),
                sonetMediumCMI(3),
                sonetMediumNRZ(4),
                sonetMediumRZ(5)
            }
    MAX-ACCESS  read-write
    STATUS  current
    DESCRIPTION
       "This variable describes the line coding for
       this interface. The B3ZS and CMI are used for
       electrical SONET/SDH signals (STS-1 and STS-3).
       The Non-Return to Zero (NRZ) and the Return
       to Zero are used for optical SONET/SDH signals."
    ::= { sonetMediumEntry 4 }

sonetMediumLineType OBJECT-TYPE
    SYNTAX  INTEGER {
                sonetOther(1),
                sonetShortSingleMode(2),
                sonetLongSingleMode(3),
                sonetMultiMode(4),
                sonetCoax(5),
                sonetUTP(6)
            }
    MAX-ACCESS  read-write
    STATUS  current
    DESCRIPTION
       "This variable describes the line type for
       this interface. The line types are
       Short and Long Range
       Single Mode fiber or Multi-Mode fiber interfaces,
       and coax and UTP for electrical interfaces.  The
       value sonetOther should be used when the Line Type is
       not one of the listed values."
    ::= { sonetMediumEntry 5 }

sonetMediumCircuitIdentifier OBJECT-TYPE
    SYNTAX  DisplayString (SIZE (0..255))
    MAX-ACCESS  read-write
    STATUS  current
    DESCRIPTION
       "This variable contains the transmission
       vendor's circuit identifier, for the
       purpose of facilitating troubleshooting.
       Note that the circuit identifier, if available,


       is also represented by ifPhysAddress."
    ::= { sonetMediumEntry 6 }
sonetMediumInvalidIntervals OBJECT-TYPE
    SYNTAX  Integer32 (0..96)
    MAX-ACCESS  read-only
    STATUS  current
    DESCRIPTION
        "The number of intervals in the range from
        0 to sonetMediumValidIntervals for which no
        data is available. This object will typically
        be zero except in cases where the data for some
        intervals are not available (e.g., in proxy
        situations)."
    ::= { sonetMediumEntry 7 }

sonetMediumLoopbackConfig OBJECT-TYPE
    SYNTAX      BITS {
                  sonetNoLoop(0),
                  sonetFacilityLoop(1),
                  sonetTerminalLoop(2),
                  sonetOtherLoop(3) }
    MAX-ACCESS  read-write
    STATUS      current
    DESCRIPTION
       "The current loopback state of the SONET/SDH interface.  The
        values mean:

          sonetNoLoop
             Not in the loopback state. A device that is not
             capable of performing a loopback on this interface
             shall always return this value.

          sonetFacilityLoop
             The received signal at this interface is looped back
             out through the corresponding transmitter in the return
             direction.

          sonetTerminalLoop
             The signal that is about to be transmitted is connected
             to the associated incoming receiver.

          sonetOtherLoop
             Loopbacks that are not defined here."

    ::= { sonetMediumEntry 8 }

sonetSESthresholdSet    OBJECT-TYPE
    SYNTAX   INTEGER {


               other(1),
               Bellcore1991(2),
               ansi1993(3),
               itu1995(4),
               ansi1997(5)
                      }
    MAX-ACCESS      read-write
    STATUS          current
    DESCRIPTION
      "An enumerated integer indicating which
       recognized set of SES thresholds that
       the agent uses for determining severely
       errored seconds and unavailable time.

       other(1)
         None of the following.

       Bellcore1991(2)
         Bellcore TR-NWT-000253, 1991 [32], or
         ANSI T1M1.3/93-005R2, 1993 [22].
         See also Appendix B.

       ansi1993(3)
         ANSI T1.231, 1993 [31], or
         Bellcore GR-253-CORE, Issue 2, 1995 [34]

       itu1995(4)
         ITU Recommendation G.826, 1995 [33]

       ansi1997(5)
         ANSI T1.231, 1997 [35]

       If a manager changes the value of this
       object then the SES statistics collected
       prior to this change must be invalidated."
     ::= { sonetMedium 2 }

-- the SONET/SDH Section group

-- this group consists of 2 tables:
-- - the SONET/SDH Section Current Table
-- - the SONET/SDH Section Interval Table

-- the SONET/SDH Section Current Table

-- The SONET/SDH Section


-- current table contains various statistics
-- being collected for the current 15 minute interval.

sonetSectionCurrentTable OBJECT-TYPE
    SYNTAX  SEQUENCE OF SonetSectionCurrentEntry
    MAX-ACCESS  not-accessible
    STATUS  current
    DESCRIPTION
       "The SONET/SDH Section Current table."
     ::= { sonetSection 1 }

sonetSectionCurrentEntry OBJECT-TYPE
    SYNTAX  SonetSectionCurrentEntry
    MAX-ACCESS  not-accessible
    STATUS  current
    DESCRIPTION
       "An entry in the SONET/SDH Section Current table."
    INDEX   { ifIndex }
     ::= { sonetSectionCurrentTable 1 }

SonetSectionCurrentEntry ::=
    SEQUENCE {
        sonetSectionCurrentStatus   Integer32,
        sonetSectionCurrentESs      PerfCurrentCount,
        sonetSectionCurrentSESs     PerfCurrentCount,
        sonetSectionCurrentSEFSs    PerfCurrentCount,
        sonetSectionCurrentCVs      PerfCurrentCount
    }

sonetSectionCurrentStatus OBJECT-TYPE
    SYNTAX  Integer32 (1..6)
    MAX-ACCESS  read-only
    STATUS  current
    DESCRIPTION
       "This variable indicates the
       status of the interface.
       The sonetSectionCurrentStatus
       is a bit map represented
       as a sum, therefore,
       it can represent multiple defects
       simultaneously.
       The sonetSectionNoDefect should be
       set if and only if
       no other flag is set.

       The various bit positions are:
             1   sonetSectionNoDefect


             2   sonetSectionLOS
             4   sonetSectionLOF"
     ::= { sonetSectionCurrentEntry 1 }

sonetSectionCurrentESs OBJECT-TYPE
    SYNTAX  PerfCurrentCount
    MAX-ACCESS  read-only
    STATUS  current
    DESCRIPTION
       "The counter associated with the number of Errored
       Seconds encountered by a SONET/SDH
       Section in the current 15 minute interval."
     ::= { sonetSectionCurrentEntry 2 }

sonetSectionCurrentSESs OBJECT-TYPE
    SYNTAX  PerfCurrentCount
    MAX-ACCESS  read-only
    STATUS  current
    DESCRIPTION
       "The counter associated with the number of
       Severely Errored Seconds
       encountered by a SONET/SDH Section in the current 15
       minute interval."
     ::= { sonetSectionCurrentEntry 3 }

sonetSectionCurrentSEFSs OBJECT-TYPE
    SYNTAX  PerfCurrentCount
    MAX-ACCESS  read-only
    STATUS  current
    DESCRIPTION
       "The counter associated with the number of
       Severely Errored Framing Seconds
       encountered by a SONET/SDH Section in the current
       15 minute interval."
    ::= { sonetSectionCurrentEntry 4 }

sonetSectionCurrentCVs OBJECT-TYPE
    SYNTAX  PerfCurrentCount
    MAX-ACCESS  read-only
    STATUS  current
    DESCRIPTION
       "The counter associated with the number of Coding
       Violations encountered by a
       SONET/SDH Section in the current 15 minute interval."
     ::= { sonetSectionCurrentEntry 5 }

-- the SONET/SDH Section Interval Table


-- The SONET/SDH Section Interval Table
-- contains various statistics
-- collected by each system over a maximum
-- of the previous 24 hours of
-- operation.  The past 24 hours may be broken into 96
-- completed 15 minute intervals.
-- A system is required to store at
-- least 4 completed 15 minute interval.
-- The default value is 32 intervals.

sonetSectionIntervalTable OBJECT-TYPE
    SYNTAX  SEQUENCE OF SonetSectionIntervalEntry
    MAX-ACCESS  not-accessible
    STATUS  current
    DESCRIPTION
       "The SONET/SDH Section Interval table."
     ::= { sonetSection 2 }

sonetSectionIntervalEntry OBJECT-TYPE
    SYNTAX  SonetSectionIntervalEntry
    MAX-ACCESS  not-accessible
    STATUS  current
    DESCRIPTION
       "An entry in the SONET/SDH Section Interval table."
    INDEX   { ifIndex,
              sonetSectionIntervalNumber }
     ::= { sonetSectionIntervalTable 1 }

SonetSectionIntervalEntry ::=
    SEQUENCE {
         sonetSectionIntervalNumber  Integer32,
         sonetSectionIntervalESs     PerfIntervalCount,
         sonetSectionIntervalSESs    PerfIntervalCount,
         sonetSectionIntervalSEFSs   PerfIntervalCount,
         sonetSectionIntervalCVs     PerfIntervalCount,
         sonetSectionIntervalValidData  TruthValue
    }

sonetSectionIntervalNumber OBJECT-TYPE
    SYNTAX  Integer32 (1..96)
    MAX-ACCESS  not-accessible
    STATUS  current
    DESCRIPTION
      "A number between 1 and 96, which identifies the
      interval for which the set of statistics is available.
      The interval identified by 1 is the most recently
      completed 15 minute interval,


      and the interval identified
      by N is the interval immediately preceding the
      one identified
      by N-1."
     ::= { sonetSectionIntervalEntry 1 }

sonetSectionIntervalESs OBJECT-TYPE
    SYNTAX  PerfIntervalCount
    MAX-ACCESS  read-only
    STATUS  current
    DESCRIPTION
       "The counter associated with the number of
       Errored Seconds encountered
       by a SONET/SDH Section in a
       particular 15-minute interval
       in the past 24 hours."
     ::= { sonetSectionIntervalEntry 2 }

sonetSectionIntervalSESs OBJECT-TYPE
    SYNTAX  PerfIntervalCount
    MAX-ACCESS  read-only
    STATUS  current
    DESCRIPTION
       "The counter associated with the number of
       Severely Errored Seconds
       encountered by a SONET/SDH Section in a
       particular 15-minute interval
       in the past 24 hours."
    ::= { sonetSectionIntervalEntry 3 }

sonetSectionIntervalSEFSs OBJECT-TYPE
    SYNTAX  PerfIntervalCount
    MAX-ACCESS  read-only
    STATUS  current
    DESCRIPTION
       "The counter associated with the number of
       Severely Errored Framing Seconds
       encountered by a SONET/SDH Section in a
       particular 15-minute interval
       in the past 24 hours."
    ::= { sonetSectionIntervalEntry 4 }

sonetSectionIntervalCVs OBJECT-TYPE
    SYNTAX  PerfIntervalCount
    MAX-ACCESS  read-only
    STATUS  current
    DESCRIPTION
       "The counter associated with the number of Coding


       Violations encountered by a
       SONET/SDH Section in a particular 15-minute interval
       in the past 24 hours."
    ::= { sonetSectionIntervalEntry 5 }

sonetSectionIntervalValidData OBJECT-TYPE
    SYNTAX  TruthValue
    MAX-ACCESS  read-only
    STATUS  current
    DESCRIPTION
       "This variable indicates if the data for this
        interval is valid."
    ::= { sonetSectionIntervalEntry 6 }

-- the SONET/SDH Line group

-- this group consists of 2 tables:
-- - the SONET/SDH Line Current Table
-- - the SONET/SDH Line Interval Table

-- the SONET/SDH Line Current Table

-- The SONET/SDH Line
-- current table contains various statistics
-- being collected for the current 15 minute interval.

sonetLineCurrentTable OBJECT-TYPE
    SYNTAX  SEQUENCE OF SonetLineCurrentEntry
    MAX-ACCESS  not-accessible
    STATUS  current
    DESCRIPTION
      "The SONET/SDH Line Current table."
    ::= { sonetLine 1 }

sonetLineCurrentEntry OBJECT-TYPE
    SYNTAX  SonetLineCurrentEntry
    MAX-ACCESS  not-accessible
    STATUS  current
    DESCRIPTION
      "An entry in the SONET/SDH Line Current table."
    INDEX   { ifIndex }
    ::= { sonetLineCurrentTable 1 }

SonetLineCurrentEntry ::=
    SEQUENCE {
         sonetLineCurrentStatus    Integer32,


         sonetLineCurrentESs       PerfCurrentCount,
         sonetLineCurrentSESs      PerfCurrentCount,
         sonetLineCurrentCVs       PerfCurrentCount,
         sonetLineCurrentUASs      PerfCurrentCount
     }

sonetLineCurrentStatus OBJECT-TYPE
    SYNTAX  Integer32 (1..6)
    MAX-ACCESS  read-only
    STATUS  current
    DESCRIPTION
       "This variable indicates the
       status of the interface.
       The sonetLineCurrentStatus
       is a bit map represented
       as a sum, therefore,
       it can represent multiple defects
       simultaneously.
       The sonetLineNoDefect should be
       set if and only if
       no other flag is set.

       The various bit positions are:
        1   sonetLineNoDefect
        2   sonetLineAIS
        4   sonetLineRDI"
     ::= { sonetLineCurrentEntry 1 }

sonetLineCurrentESs OBJECT-TYPE
    SYNTAX  PerfCurrentCount
    MAX-ACCESS  read-only
    STATUS  current
    DESCRIPTION
     "The counter associated with the number of Errored
     Seconds encountered by a SONET/SDH
     Line in the current 15 minute interval."
    ::= { sonetLineCurrentEntry 2 }

sonetLineCurrentSESs OBJECT-TYPE
    SYNTAX  PerfCurrentCount
    MAX-ACCESS  read-only
    STATUS  current
    DESCRIPTION
     "The counter associated with the number of
     Severely Errored Seconds
     encountered by a SONET/SDH Line in the current 15
     minute


     interval."
    ::= { sonetLineCurrentEntry 3 }

sonetLineCurrentCVs OBJECT-TYPE
    SYNTAX  PerfCurrentCount
    MAX-ACCESS  read-only
    STATUS  current
    DESCRIPTION
     "The counter associated with the number of Coding
     Violations encountered by a
     SONET/SDH Line in the current 15 minute interval."
    ::= { sonetLineCurrentEntry 4 }

sonetLineCurrentUASs OBJECT-TYPE
    SYNTAX  PerfCurrentCount
    MAX-ACCESS  read-only
    STATUS  current
    DESCRIPTION
     "The counter associated with the number of
     Unavailable Seconds
     encountered by a SONET/SDH Line in the current 15
     minute
     interval."
    ::= { sonetLineCurrentEntry 5 }

-- the SONET/SDH Line Interval Table

-- The SONET/SDH Line Interval Table
-- contains various statistics
-- collected by each system over a maximum
-- of the previous 24 hours of
-- operation.  The past 24 hours may be broken into 96
-- completed 15 minute intervals.
-- A system is required to store at
-- least 4 completed 15 minute interval.
-- The default value is 32 intervals.

sonetLineIntervalTable OBJECT-TYPE
    SYNTAX  SEQUENCE OF SonetLineIntervalEntry
    MAX-ACCESS  not-accessible
    STATUS  current
    DESCRIPTION
       "The SONET/SDH Line Interval table."
     ::= { sonetLine 2 }

sonetLineIntervalEntry OBJECT-TYPE
    SYNTAX  SonetLineIntervalEntry


    MAX-ACCESS  not-accessible
    STATUS  current
    DESCRIPTION
       "An entry in the SONET/SDH Line Interval table."
   INDEX   { ifIndex,
             sonetLineIntervalNumber }
   ::= { sonetLineIntervalTable 1 }

SonetLineIntervalEntry ::=
    SEQUENCE {
        sonetLineIntervalNumber    Integer32,
        sonetLineIntervalESs       PerfIntervalCount,
        sonetLineIntervalSESs      PerfIntervalCount,
        sonetLineIntervalCVs       PerfIntervalCount,
        sonetLineIntervalUASs      PerfIntervalCount,
        sonetLineIntervalValidData TruthValue
    }

sonetLineIntervalNumber OBJECT-TYPE
    SYNTAX  Integer32 (1..96)
    MAX-ACCESS  not-accessible
    STATUS  current
    DESCRIPTION
        "A number between 1 and 96, which identifies the
        interval for which the set of statistics is available.
        The interval identified by 1 is the most recently
        completed 15 minute interval,
        and the interval identified
        by N is the interval immediately preceding the
        one identified
        by N-1."
     ::= { sonetLineIntervalEntry 1 }

sonetLineIntervalESs OBJECT-TYPE
    SYNTAX  PerfIntervalCount
    MAX-ACCESS  read-only
    STATUS  current
    DESCRIPTION
       "The counter associated with the number of
       Errored Seconds encountered
       by a SONET/SDH Line in a
       particular 15-minute interval
       in the past 24 hours."
     ::= { sonetLineIntervalEntry 2 }

sonetLineIntervalSESs OBJECT-TYPE
    SYNTAX  PerfIntervalCount


    MAX-ACCESS  read-only
    STATUS  current
    DESCRIPTION
       "The counter associated with the number of
       Severely Errored Seconds
       encountered by a SONET/SDH Line in a
       particular 15-minute interval
       in the past 24 hours."
      ::= { sonetLineIntervalEntry 3 }

sonetLineIntervalCVs OBJECT-TYPE
    SYNTAX  PerfIntervalCount
    MAX-ACCESS  read-only
    STATUS  current
    DESCRIPTION
      "The counter associated with the number of Coding
      Violations encountered by a
      SONET/SDH Line in a
      particular 15-minute interval
      in the past 24 hours."
    ::= { sonetLineIntervalEntry 4 }

sonetLineIntervalUASs OBJECT-TYPE
    SYNTAX  PerfIntervalCount
    MAX-ACCESS  read-only
    STATUS  current
    DESCRIPTION
      "The counter associated with the
      number of Unavailable Seconds
      encountered by a SONET/SDH Line in
      a particular 15-minute interval
      in the past 24 hours."
    ::= { sonetLineIntervalEntry 5 }

sonetLineIntervalValidData OBJECT-TYPE
    SYNTAX  TruthValue
    MAX-ACCESS  read-only
    STATUS  current
    DESCRIPTION
       "This variable indicates if the data for this
        interval is valid."
    ::= { sonetLineIntervalEntry 6 }

-- The SONET/SDH Far End Line group.
-- This group may only be implemented by SONET/SDH (LTEs)
-- systems that provide for a far end block error (FEBE)
-- information at the SONET/SDH Line Layer.


-- This group consists of two tables:
--    SONET/SDH Far End Line Current Table
--    SONET/SDH Far End Line Interval Table

-- The SONET/SDH Far End Line Current Table

-- The SONET/SDH Far End Line Current table contains
-- various statistics being
-- collected for the current 15 minute interval.
-- The statistics are collected from the far end
-- block error code (FEBE)
-- within the third Z2 byte of the Line Overhead
-- in Broadband ISDN applications.
-- The definitions are the same as described for
-- the near-end information.

sonetFarEndLineCurrentTable OBJECT-TYPE
    SYNTAX  SEQUENCE OF SonetFarEndLineCurrentEntry
    MAX-ACCESS  not-accessible
    STATUS  current
    DESCRIPTION
      "The SONET/SDH Far End Line Current table."
    ::= { sonetFarEndLine 1 }

sonetFarEndLineCurrentEntry OBJECT-TYPE
    SYNTAX  SonetFarEndLineCurrentEntry
    MAX-ACCESS  not-accessible
    STATUS  current
    DESCRIPTION
      "An entry in the SONET/SDH Far End Line Current table."
    INDEX   { ifIndex }
    ::= { sonetFarEndLineCurrentTable 1 }

SonetFarEndLineCurrentEntry ::=
    SEQUENCE {
        sonetFarEndLineCurrentESs       PerfCurrentCount,
        sonetFarEndLineCurrentSESs      PerfCurrentCount,
        sonetFarEndLineCurrentCVs       PerfCurrentCount,
        sonetFarEndLineCurrentUASs      PerfCurrentCount
       }

sonetFarEndLineCurrentESs OBJECT-TYPE
   SYNTAX  PerfCurrentCount
   MAX-ACCESS  read-only
   STATUS  current
   DESCRIPTION


       "The counter associated with the number of Far
       End Errored Seconds encountered by a SONET/SDH
       interface in the current 15 minute interval."
   ::= { sonetFarEndLineCurrentEntry 1 }

sonetFarEndLineCurrentSESs OBJECT-TYPE
   SYNTAX  PerfCurrentCount
   MAX-ACCESS  read-only
   STATUS  current
   DESCRIPTION
       "The counter associated with the number of
       Far End Severely Errored Seconds
       encountered by a SONET/SDH Medium/Section/Line
       interface in the current 15 minute
       interval."
   ::= { sonetFarEndLineCurrentEntry 2 }

sonetFarEndLineCurrentCVs OBJECT-TYPE
   SYNTAX  PerfCurrentCount
   MAX-ACCESS  read-only
   STATUS  current
   DESCRIPTION
       "The counter associated with the number of
       Far End Coding Violations reported via
       the far end block error count
       encountered by a
       SONET/SDH Medium/Section/Line
       interface in the current 15 minute interval."
   ::= { sonetFarEndLineCurrentEntry 3 }

sonetFarEndLineCurrentUASs OBJECT-TYPE
   SYNTAX  PerfCurrentCount
   MAX-ACCESS  read-only
   STATUS  current
   DESCRIPTION
       "The counter associated with the number of
       Far End Unavailable Seconds
       encountered by a
       SONET/SDH Medium/Section/Line
       interface in the current 15 minute interval."
   ::= { sonetFarEndLineCurrentEntry 4 }

-- The SONET/SDH Far End Line Interval Table

-- The SONET/SDH Far End Line Interval Table
-- contains various statistics
-- collected by each system over a maximum


-- of the previous 24 hours of
-- operation.  The past 24 hours may be broken into 96
-- completed 15 minute intervals.
-- A system is required to store at
-- least 4 completed 15 minute interval.
-- The default value is 32 intervals.

sonetFarEndLineIntervalTable OBJECT-TYPE
   SYNTAX  SEQUENCE OF SonetFarEndLineIntervalEntry
   MAX-ACCESS  not-accessible
   STATUS  current
   DESCRIPTION
      "The SONET/SDH Far End Line Interval table."
   ::= { sonetFarEndLine 2 }

sonetFarEndLineIntervalEntry OBJECT-TYPE
   SYNTAX  SonetFarEndLineIntervalEntry
   MAX-ACCESS  not-accessible
   STATUS  current
   DESCRIPTION
     "An entry in the SONET/SDH Far
     End Line Interval table."
   INDEX   { ifIndex,
             sonetFarEndLineIntervalNumber }
   ::= { sonetFarEndLineIntervalTable 1 }

SonetFarEndLineIntervalEntry ::=
    SEQUENCE {
         sonetFarEndLineIntervalNumber    Integer32,
         sonetFarEndLineIntervalESs       PerfIntervalCount,
         sonetFarEndLineIntervalSESs      PerfIntervalCount,
         sonetFarEndLineIntervalCVs       PerfIntervalCount,
         sonetFarEndLineIntervalUASs      PerfIntervalCount,
         sonetFarEndLineIntervalValidData TruthValue
    }

sonetFarEndLineIntervalNumber OBJECT-TYPE
   SYNTAX  Integer32 (1..96)
   MAX-ACCESS  not-accessible
   STATUS  current
   DESCRIPTION
         "A number between 1 and 96, which identifies the
         interval for which the set of statistics is available.
         The interval identified by 1 is the most recently
         completed 15 minute interval,
         and the interval identified
         by N is the interval immediately preceding the


         one identified
         by N-1."
   ::= { sonetFarEndLineIntervalEntry 1 }

sonetFarEndLineIntervalESs OBJECT-TYPE
   SYNTAX  PerfIntervalCount
   MAX-ACCESS  read-only
   STATUS  current
   DESCRIPTION
        "The counter associated with the number of
        Far End Errored Seconds encountered
        by a SONET/SDH Line
        interface in a particular 15-minute interval
        in the past 24 hours."
  ::= { sonetFarEndLineIntervalEntry 2 }

sonetFarEndLineIntervalSESs OBJECT-TYPE
   SYNTAX  PerfIntervalCount
   MAX-ACCESS  read-only
   STATUS  current
   DESCRIPTION
        "The counter associated with the number of
        Far End Severely Errored Seconds
        encountered by a SONET/SDH Line
        interface in a particular 15-minute interval
        in the past 24 hours."
  ::= { sonetFarEndLineIntervalEntry 3 }

sonetFarEndLineIntervalCVs OBJECT-TYPE
    SYNTAX  PerfIntervalCount
    MAX-ACCESS  read-only
    STATUS  current
    DESCRIPTION
         "The counter associated with the number of
         Far End Coding Violations reported via
         the far end block error count
         encountered by a
         SONET/SDH Line
         interface in a particular 15-minute interval
         in the past 24 hours."
    ::= { sonetFarEndLineIntervalEntry 4 }

sonetFarEndLineIntervalUASs OBJECT-TYPE
   SYNTAX  PerfIntervalCount
   MAX-ACCESS  read-only
   STATUS  current
   DESCRIPTION
       "The counter associated with the number of


       Far End Unavailable Seconds
       encountered by a
       SONET/SDH Line
       interface in a particular 15-minute interval
       in the past 24 hours."
   ::= { sonetFarEndLineIntervalEntry 5 }

sonetFarEndLineIntervalValidData OBJECT-TYPE
    SYNTAX  TruthValue
    MAX-ACCESS  read-only
    STATUS  current
    DESCRIPTION
       "This variable indicates if the data for this
        interval is valid."
    ::= { sonetFarEndLineIntervalEntry 6 }

-- the SONET/SDH Path group

-- this group consists of 2 tables:
-- - the SONET/SDH Path Current Table
-- - the SONET/SDH Path Interval Table

-- the SONET/SDH Path Current Table

-- The SONET/SDH Path
-- current table contains various statistics
-- being collected for the current 15 minute interval.

sonetPathCurrentTable OBJECT-TYPE
    SYNTAX  SEQUENCE OF SonetPathCurrentEntry
    MAX-ACCESS  not-accessible
    STATUS  current
    DESCRIPTION
     "The SONET/SDH Path Current table."
::= { sonetPath 1 }

sonetPathCurrentEntry OBJECT-TYPE
    SYNTAX  SonetPathCurrentEntry
    MAX-ACCESS  not-accessible
    STATUS  current
    DESCRIPTION
     "An entry in the SONET/SDH Path Current table."
    INDEX   { ifIndex }
::= { sonetPathCurrentTable 1 }

SonetPathCurrentEntry ::=
    SEQUENCE {


        sonetPathCurrentWidth      INTEGER,
        sonetPathCurrentStatus     Integer32,
        sonetPathCurrentESs        PerfCurrentCount,
        sonetPathCurrentSESs       PerfCurrentCount,
        sonetPathCurrentCVs        PerfCurrentCount,
        sonetPathCurrentUASs       PerfCurrentCount
    }

sonetPathCurrentWidth OBJECT-TYPE
    SYNTAX  INTEGER  {
            sts1(1),
            sts3cSTM1(2),
            sts12cSTM4(3),
            sts24c(4),
            sts48cSTM16(5)
     }
    MAX-ACCESS  read-write
    STATUS  current
    DESCRIPTION
     "A value that indicates the type of the SONET/SDH
     Path.  For SONET, the assigned types are
     the STS-Nc SPEs, where N = 1, 3, 12, 24, and 48.
     STS-1 is equal to 51.84 Mbps.  For SDH, the assigned
     types are the STM-Nc VCs, where N = 1, 4, and 16."
::= { sonetPathCurrentEntry 1 }

sonetPathCurrentStatus OBJECT-TYPE
    SYNTAX  Integer32 (1..62)
    MAX-ACCESS  read-only
    STATUS  current
    DESCRIPTION
      "This variable indicates the
      status of the interface.
      The sonetPathCurrentStatus
      is a bit map represented
      as a sum, therefore,
      it can represent multiple defects
      simultaneously.
      The sonetPathNoDefect should be
      set if and only if
      no other flag is set.

      The various bit positions are:
         1   sonetPathNoDefect
         2   sonetPathSTSLOP
         4   sonetPathSTSAIS
         8   sonetPathSTSRDI


        16   sonetPathUnequipped
        32   sonetPathSignalLabelMismatch"
::= { sonetPathCurrentEntry 2 }

sonetPathCurrentESs OBJECT-TYPE
    SYNTAX  PerfCurrentCount
    MAX-ACCESS  read-only
    STATUS  current
    DESCRIPTION
     "The counter associated with the number of Errored
     Seconds encountered by a SONET/SDH
     Path in the current 15 minute interval."
::= { sonetPathCurrentEntry 3 }

sonetPathCurrentSESs OBJECT-TYPE
    SYNTAX  PerfCurrentCount
    MAX-ACCESS  read-only
    STATUS  current
    DESCRIPTION
     "The counter associated with the number of
     Severely Errored Seconds
     encountered by a SONET/SDH Path in the current 15
     minute
     interval."
::= { sonetPathCurrentEntry 4 }

sonetPathCurrentCVs OBJECT-TYPE
    SYNTAX  PerfCurrentCount
    MAX-ACCESS  read-only
    STATUS  current
    DESCRIPTION
     "The counter associated with the number of Coding
     Violations encountered by a
     SONET/SDH Path in the current 15 minute interval."
::= { sonetPathCurrentEntry 5 }

sonetPathCurrentUASs OBJECT-TYPE
    SYNTAX  PerfCurrentCount
    MAX-ACCESS  read-only
    STATUS  current
    DESCRIPTION
     "The counter associated with the number of
     Unavailable Seconds
     encountered by a Path in the current
     15 minute interval."
::= { sonetPathCurrentEntry 6 }

-- the SONET/SDH Path Interval Table


-- The SONET/SDH Path Interval Table
-- contains various statistics
-- collected by each system over a maximum
-- of the previous 24 hours of
-- operation.  The past 24 hours may be broken into 96
-- completed 15 minute intervals.
-- A system is required to store at
-- least 4 completed 15 minute interval.
-- The default value is 32 intervals.

sonetPathIntervalTable OBJECT-TYPE
    SYNTAX  SEQUENCE OF SonetPathIntervalEntry
    MAX-ACCESS  not-accessible
    STATUS  current
    DESCRIPTION
     "The SONET/SDH Path Interval table."
::= { sonetPath 2 }

sonetPathIntervalEntry OBJECT-TYPE
    SYNTAX  SonetPathIntervalEntry
    MAX-ACCESS  not-accessible
    STATUS  current
    DESCRIPTION
     "An entry in the SONET/SDH Path Interval table."
    INDEX   { ifIndex,
              sonetPathIntervalNumber }
::= { sonetPathIntervalTable 1 }

SonetPathIntervalEntry ::=
    SEQUENCE {
         sonetPathIntervalNumber     Integer32,
         sonetPathIntervalESs        PerfIntervalCount,
         sonetPathIntervalSESs       PerfIntervalCount,
         sonetPathIntervalCVs        PerfIntervalCount,
         sonetPathIntervalUASs       PerfIntervalCount,
         sonetPathIntervalValidData  TruthValue
    }

sonetPathIntervalNumber OBJECT-TYPE
    SYNTAX  Integer32 (1..96)
    MAX-ACCESS  not-accessible
    STATUS  current
    DESCRIPTION
       "A number between 1 and 96, which identifies the
       interval for which the set of statistics is available.
       The interval identified by 1 is the most recently


       completed 15 minute interval,
       and the interval identified
       by N is the interval immediately preceding the
       one identified
       by N-1."
::= { sonetPathIntervalEntry 1 }

sonetPathIntervalESs OBJECT-TYPE
    SYNTAX  PerfIntervalCount
    MAX-ACCESS  read-only
    STATUS  current
    DESCRIPTION
     "The counter associated with the number of
     Errored Seconds encountered
     by a SONET/SDH Path in a
     particular 15-minute interval
     in the past 24 hours."
::= { sonetPathIntervalEntry 2 }

sonetPathIntervalSESs OBJECT-TYPE
    SYNTAX  PerfIntervalCount
    MAX-ACCESS  read-only
    STATUS  current
    DESCRIPTION
     "The counter associated with the number of
     Severely Errored Seconds
     encountered by a SONET/SDH Path in
     a particular 15-minute interval
     in the past 24 hours."
::= { sonetPathIntervalEntry 3 }

sonetPathIntervalCVs OBJECT-TYPE
    SYNTAX  PerfIntervalCount
    MAX-ACCESS  read-only
    STATUS  current
    DESCRIPTION
     "The counter associated with the number of Coding
     Violations encountered by a
     SONET/SDH Path in a particular 15-minute interval
     in the past 24 hours."
::= { sonetPathIntervalEntry 4 }

sonetPathIntervalUASs OBJECT-TYPE
    SYNTAX  PerfIntervalCount
    MAX-ACCESS  read-only
    STATUS  current
    DESCRIPTION
     "The counter associated with the number of


     Unavailable Seconds
     encountered by a Path in a
     particular 15-minute interval
     in the past 24 hours."
::= { sonetPathIntervalEntry 5 }

sonetPathIntervalValidData OBJECT-TYPE
    SYNTAX  TruthValue
    MAX-ACCESS  read-only
    STATUS  current
    DESCRIPTION
       "This variable indicates if the data for this
        interval is valid."
    ::= { sonetPathIntervalEntry 6 }

-- The SONET/SDH Far End Path group

-- This group consists of two tables:
--  - SONET/SDH Far End Path Current Table
--  - SONET/SDH Far End Path Interval Table

-- The SONET/SDH Far End Path Current Table

-- The SONET/SDH Far End Path Current table
-- contains various statistics
-- being collected for the current 15 minute interval.
-- The statistics are collected from
-- the far end block error code
-- (FEBE) within the G1 byte of the Path Overhead.
-- The definitions are the same as described for
-- the near-end information.

sonetFarEndPathCurrentTable OBJECT-TYPE
    SYNTAX  SEQUENCE OF SonetFarEndPathCurrentEntry
    MAX-ACCESS  not-accessible
    STATUS  current
    DESCRIPTION
         "The SONET/SDH Far End Path Current table."
    ::= { sonetFarEndPath 1 }

sonetFarEndPathCurrentEntry OBJECT-TYPE
    SYNTAX  SonetFarEndPathCurrentEntry
    MAX-ACCESS  not-accessible
    STATUS  current
    DESCRIPTION
         "An entry in the SONET/SDH Far End Path Current table."
    INDEX   { ifIndex }
    ::= { sonetFarEndPathCurrentTable 1 }


SonetFarEndPathCurrentEntry ::=
    SEQUENCE {
        sonetFarEndPathCurrentESs       PerfCurrentCount,
        sonetFarEndPathCurrentSESs      PerfCurrentCount,
        sonetFarEndPathCurrentCVs       PerfCurrentCount,
        sonetFarEndPathCurrentUASs      PerfCurrentCount
    }

sonetFarEndPathCurrentESs OBJECT-TYPE
    SYNTAX  PerfCurrentCount
    MAX-ACCESS  read-only
    STATUS  current
    DESCRIPTION
         "The counter associated with the number of Far
         End Errored Seconds encountered by a SONET/SDH
         interface in the current 15 minute interval."
    ::= { sonetFarEndPathCurrentEntry 1 }

sonetFarEndPathCurrentSESs OBJECT-TYPE
    SYNTAX  PerfCurrentCount
    MAX-ACCESS  read-only
    STATUS  current
    DESCRIPTION
         "The counter associated with the number of
         Far End Severely Errored Seconds
         encountered by a SONET/SDH Path
         interface in the current 15 minute
         interval."
    ::= { sonetFarEndPathCurrentEntry 2 }

sonetFarEndPathCurrentCVs OBJECT-TYPE
    SYNTAX  PerfCurrentCount
    MAX-ACCESS  read-only
    STATUS  current
    DESCRIPTION
         "The counter associated with the number of
         Far End Coding Violations reported via
         the far end block error count
         encountered by a
         SONET/SDH Path interface in
         the current 15 minute interval."
    ::= { sonetFarEndPathCurrentEntry 3 }

sonetFarEndPathCurrentUASs OBJECT-TYPE
   SYNTAX  PerfCurrentCount
   MAX-ACCESS  read-only
   STATUS  current


   DESCRIPTION
       "The counter associated with the number of
       Far End Unavailable Seconds
       encountered by a
       SONET/SDH Path interface in
       the current 15 minute interval."
   ::= { sonetFarEndPathCurrentEntry 4 }

-- The SONET/SDH Far End Path Interval Table

-- The SONET/SDH Far End Path Interval Table
-- contains various statistics
-- collected by each system over a maximum
-- of the previous 24 hours of
-- operation.  The past 24 hours may be broken into 96
-- completed 15 minute intervals.
-- A system is required to store at
-- least 4 completed 15 minute interval.
-- The default value is 32 intervals.

sonetFarEndPathIntervalTable OBJECT-TYPE
    SYNTAX  SEQUENCE OF SonetFarEndPathIntervalEntry
    MAX-ACCESS  not-accessible
    STATUS  current
    DESCRIPTION
        "The SONET/SDH Far End Path Interval table."
    ::= { sonetFarEndPath 2 }

sonetFarEndPathIntervalEntry OBJECT-TYPE
    SYNTAX  SonetFarEndPathIntervalEntry
    MAX-ACCESS  not-accessible
    STATUS  current
    DESCRIPTION
       "An entry in the SONET/SDH Far
       End Path Interval table."
    INDEX   { ifIndex,
              sonetFarEndPathIntervalNumber }
    ::= { sonetFarEndPathIntervalTable 1 }

SonetFarEndPathIntervalEntry ::=
    SEQUENCE {
         sonetFarEndPathIntervalNumber     Integer32,
         sonetFarEndPathIntervalESs        PerfIntervalCount,
         sonetFarEndPathIntervalSESs       PerfIntervalCount,
         sonetFarEndPathIntervalCVs        PerfIntervalCount,
         sonetFarEndPathIntervalUASs       PerfIntervalCount,
         sonetFarEndPathIntervalValidData  TruthValue
    }


sonetFarEndPathIntervalNumber OBJECT-TYPE
   SYNTAX  Integer32 (1..96)
   MAX-ACCESS  not-accessible
   STATUS  current
   DESCRIPTION
        "A number between 1 and 96, which identifies the
        interval for which the set of statistics is available.
        The interval identified by 1 is the most recently
        completed 15 minute interval,
        and the interval identified
        by N is the interval immediately preceding the
        one identified
        by N-1."
   ::= { sonetFarEndPathIntervalEntry 1 }

sonetFarEndPathIntervalESs OBJECT-TYPE
   SYNTAX  PerfIntervalCount
   MAX-ACCESS  read-only
   STATUS  current
   DESCRIPTION
        "The counter associated with the number of
        Far End Errored Seconds encountered
        by a SONET/SDH Path interface in a
        particular 15-minute interval
        in the past 24 hours."
   ::= { sonetFarEndPathIntervalEntry 2 }

sonetFarEndPathIntervalSESs OBJECT-TYPE
   SYNTAX  PerfIntervalCount
   MAX-ACCESS  read-only
   STATUS  current
   DESCRIPTION
        "The counter associated with the number of
        Far End Severely Errored Seconds
        encountered by a SONET/SDH Path interface
        in a particular 15-minute interval
        in the past 24 hours."
   ::= { sonetFarEndPathIntervalEntry 3 }

sonetFarEndPathIntervalCVs OBJECT-TYPE
    SYNTAX  PerfIntervalCount
    MAX-ACCESS  read-only
    STATUS  current
    DESCRIPTION
         "The counter associated with the number of
         Far End Coding Violations reported via
         the far end block error count
         encountered by a


         SONET/SDH Path interface
         in a particular 15-minute interval
         in the past 24 hours."
    ::= { sonetFarEndPathIntervalEntry 4 }

sonetFarEndPathIntervalUASs OBJECT-TYPE
   SYNTAX  PerfIntervalCount
   MAX-ACCESS  read-only
   STATUS  current
   DESCRIPTION
       "The counter associated with the number of
       Far End Unavailable Seconds
       encountered by a
       SONET/SDH Path interface in
       a particular 15-minute interval
       in the past 24 hours."
   ::= { sonetFarEndPathIntervalEntry 5 }

sonetFarEndPathIntervalValidData OBJECT-TYPE
    SYNTAX  TruthValue
    MAX-ACCESS  read-only
    STATUS  current
    DESCRIPTION
       "This variable indicates if the data for this
        interval is valid."
    ::= { sonetFarEndPathIntervalEntry 6 }

-- the SONET/SDH Virtual Tributary group

-- this group consists of 2 tables:
-- - the SONET/SDH VT Current Table
-- - the SONET/SDH VT Interval Table

-- For SDH signals, virtual tributaries are
-- called VCs instead of VTs

-- A VT1.5 = VC11
-- A VT2 = VC12
-- A VT3 = none
-- A VT6 = VC3

-- the SONET/SDH VT Current Table

-- The SONET/SDH VT current table
-- contains various statistics
-- being collected for the
-- current 15 minute interval.


sonetVTCurrentTable OBJECT-TYPE
    SYNTAX  SEQUENCE OF SonetVTCurrentEntry
    MAX-ACCESS  not-accessible
    STATUS  current
    DESCRIPTION
     "The SONET/SDH VT Current table."
::= { sonetVT 1 }

sonetVTCurrentEntry OBJECT-TYPE
    SYNTAX  SonetVTCurrentEntry
    MAX-ACCESS  not-accessible
    STATUS  current
    DESCRIPTION
     "An entry in the SONET/SDH VT Current table."
    INDEX   { ifIndex }
::= { sonetVTCurrentTable 1 }

SonetVTCurrentEntry ::=
    SEQUENCE {
        sonetVTCurrentWidth      INTEGER,
        sonetVTCurrentStatus     Integer32,
        sonetVTCurrentESs        PerfCurrentCount,
        sonetVTCurrentSESs       PerfCurrentCount,
        sonetVTCurrentCVs        PerfCurrentCount,
        sonetVTCurrentUASs       PerfCurrentCount
    }

sonetVTCurrentWidth OBJECT-TYPE
    SYNTAX  INTEGER {
            vtWidth15VC11(1),
            vtWidth2VC12(2),
            vtWidth3(3),
            vtWidth6VC2(4),
            vtWidth6c(5)
         }
    MAX-ACCESS  read-write
    STATUS  current
    DESCRIPTION
    "A value that indicates the type of the SONET
     VT and SDH VC.  Assigned widths are
     VT1.5/VC11, VT2/VC12, VT3, VT6/VC2, and VT6c."
::= { sonetVTCurrentEntry 1 }

sonetVTCurrentStatus OBJECT-TYPE
    SYNTAX  Integer32 (1..126)
    MAX-ACCESS  read-only
    STATUS  current
    DESCRIPTION


      "This variable indicates the
      status of the interface.
      The sonetVTCurrentStatus
      is a bit map represented
      as a sum, therefore,
      it can represent multiple defects
      and failures
      simultaneously.
      The sonetVTNoDefect should be
      set if and only if
      no other flag is set.

      The various bit positions are:
         1   sonetVTNoDefect
         2   sonetVTLOP
         4   sonetVTPathAIS
         8   sonetVTPathRDI
        16   sonetVTPathRFI
        32   sonetVTUnequipped
        64   sonetVTSignalLabelMismatch"
::= { sonetVTCurrentEntry 2 }

sonetVTCurrentESs OBJECT-TYPE
    SYNTAX  PerfCurrentCount
    MAX-ACCESS  read-only
    STATUS  current
    DESCRIPTION
     "The counter associated with the number of Errored
     Seconds encountered by a SONET/SDH
     VT in the current 15 minute interval."
::= { sonetVTCurrentEntry 3 }

sonetVTCurrentSESs OBJECT-TYPE
    SYNTAX  PerfCurrentCount
    MAX-ACCESS  read-only
    STATUS  current
    DESCRIPTION
     "The counter associated with the number of
     Severely Errored Seconds
     encountered by a SONET/SDH VT in the current 15 minute
     interval."
::= { sonetVTCurrentEntry 4 }

sonetVTCurrentCVs OBJECT-TYPE
    SYNTAX  PerfCurrentCount
    MAX-ACCESS  read-only
    STATUS  current
    DESCRIPTION


     "The counter associated with the number of Coding
     Violations encountered by a
     SONET/SDH VT in the current 15 minute interval."
::= { sonetVTCurrentEntry 5 }

sonetVTCurrentUASs OBJECT-TYPE
    SYNTAX  PerfCurrentCount
    MAX-ACCESS  read-only
    STATUS  current
    DESCRIPTION
     "The counter associated with the number of
     Unavailable Seconds
     encountered by a VT in the current
     15 minute interval."
::= { sonetVTCurrentEntry 6 }

-- the SONET/SDH VT Interval Table

-- The SONET/SDH VT Interval Table
-- contains various statistics
-- collected by each system over a maximum
-- of the previous 24 hours of
-- operation.  The past 24 hours may be broken into 96
-- completed 15 minute intervals.
-- A system is required to store at
-- least 4 completed 15 minute interval.
-- The default value is 32 intervals.

sonetVTIntervalTable OBJECT-TYPE
    SYNTAX  SEQUENCE OF SonetVTIntervalEntry
    MAX-ACCESS  not-accessible
    STATUS  current
    DESCRIPTION
     "The SONET/SDH VT Interval table."
::= { sonetVT 2 }

sonetVTIntervalEntry OBJECT-TYPE
    SYNTAX  SonetVTIntervalEntry
    MAX-ACCESS  not-accessible
    STATUS  current
    DESCRIPTION
     "An entry in the SONET/SDH VT Interval table."
    INDEX   { ifIndex,
              sonetVTIntervalNumber }
::= { sonetVTIntervalTable 1 }

SonetVTIntervalEntry ::=


    SEQUENCE {
        sonetVTIntervalNumber     Integer32,
        sonetVTIntervalESs        PerfIntervalCount,
        sonetVTIntervalSESs       PerfIntervalCount,
        sonetVTIntervalCVs        PerfIntervalCount,
        sonetVTIntervalUASs       PerfIntervalCount,
        sonetVTIntervalValidData  TruthValue
    }

sonetVTIntervalNumber OBJECT-TYPE
    SYNTAX  Integer32 (1..96)
    MAX-ACCESS  not-accessible
    STATUS  current
    DESCRIPTION
      "A number between 1 and 96, which identifies the
      interval for which the set of statistics is available.
      The interval identified by 1 is the most recently
      completed 15 minute interval,
      and the interval identified
      by N is the interval immediately preceding the
      one identified
      by N-1."
::= { sonetVTIntervalEntry 1 }

sonetVTIntervalESs OBJECT-TYPE
    SYNTAX  PerfIntervalCount
    MAX-ACCESS  read-only
    STATUS  current
    DESCRIPTION
     "The counter associated with the number of
     Errored Seconds encountered
     by a SONET/SDH VT in a particular 15-minute interval
     in the past 24 hours."
::= { sonetVTIntervalEntry 2 }

sonetVTIntervalSESs OBJECT-TYPE
    SYNTAX  PerfIntervalCount
    MAX-ACCESS  read-only
    STATUS  current
    DESCRIPTION
     "The counter associated with the number of
     Severely Errored Seconds
     encountered by a SONET/SDH VT
     in a particular 15-minute interval
     in the past 24 hours."
::= { sonetVTIntervalEntry 3 }

sonetVTIntervalCVs OBJECT-TYPE


    SYNTAX  PerfIntervalCount
    MAX-ACCESS  read-only
    STATUS  current
    DESCRIPTION
     "The counter associated with the number of Coding
     Violations encountered by a
     SONET/SDH VT in a particular 15-minute interval
     in the past 24 hours."
::= { sonetVTIntervalEntry 4 }

sonetVTIntervalUASs OBJECT-TYPE
    SYNTAX  PerfIntervalCount
    MAX-ACCESS  read-only
    STATUS  current
    DESCRIPTION
     "The counter associated with the number of
     Unavailable Seconds
     encountered by a VT in a particular 15-minute interval
     in the past 24 hours."
::= { sonetVTIntervalEntry 5 }

sonetVTIntervalValidData OBJECT-TYPE
    SYNTAX  TruthValue
    MAX-ACCESS  read-only
    STATUS  current
    DESCRIPTION
       "This variable indicates if the data for this
        interval is valid."
    ::= { sonetVTIntervalEntry 6 }

-- The SONET/SDH Far End VT group

-- This group consists of two tables:
--    SONET/SDH Far End VT Current Table
--    SONET/SDH Far End VT Interval Table

-- The SONET/SDH Far End VT Current

-- The SONET/SDH Far End VT Current table
-- contains various statistics
-- being collected for the current 15 minute interval.
-- The statistics are collected from
-- the far end block error code
-- (FEBE) within the G1 byte of the VT Overhead.
-- The definitions are the same as described for
-- the near-end information.


sonetFarEndVTCurrentTable OBJECT-TYPE
    SYNTAX  SEQUENCE OF SonetFarEndVTCurrentEntry
    MAX-ACCESS  not-accessible
    STATUS  current
    DESCRIPTION
        "The SONET/SDH Far End VT Current table."
    ::= { sonetFarEndVT 1 }

sonetFarEndVTCurrentEntry OBJECT-TYPE
    SYNTAX  SonetFarEndVTCurrentEntry
    MAX-ACCESS  not-accessible
    STATUS  current
    DESCRIPTION
        "An entry in the SONET/SDH Far End VT Current table."
    INDEX   { ifIndex }
    ::= { sonetFarEndVTCurrentTable 1 }

SonetFarEndVTCurrentEntry ::=
    SEQUENCE {
        sonetFarEndVTCurrentESs       PerfCurrentCount,
        sonetFarEndVTCurrentSESs      PerfCurrentCount,
        sonetFarEndVTCurrentCVs       PerfCurrentCount,
        sonetFarEndVTCurrentUASs      PerfCurrentCount
    }

sonetFarEndVTCurrentESs OBJECT-TYPE
    SYNTAX  PerfCurrentCount
    MAX-ACCESS  read-only
    STATUS  current
    DESCRIPTION
        "The counter associated with the number of Far
        End Errored Seconds encountered by a SONET/SDH
        interface in the current 15 minute interval."
::= { sonetFarEndVTCurrentEntry 1 }

sonetFarEndVTCurrentSESs OBJECT-TYPE
    SYNTAX  PerfCurrentCount
    MAX-ACCESS  read-only
    STATUS  current
    DESCRIPTION
        "The counter associated with the number of
        Far End Severely Errored Seconds
        encountered by a SONET/SDH VT interface
        in the current 15 minute
        interval."
    ::= { sonetFarEndVTCurrentEntry 2 }


sonetFarEndVTCurrentCVs OBJECT-TYPE
    SYNTAX  PerfCurrentCount
    MAX-ACCESS  read-only
    STATUS  current
    DESCRIPTION
        "The counter associated with the number of
        Far End Coding Violations reported via
        the far end block error count
        encountered by a
        SONET/SDH VT interface
        in the current 15 minute interval."
    ::= { sonetFarEndVTCurrentEntry 3 }

sonetFarEndVTCurrentUASs OBJECT-TYPE
   SYNTAX  PerfCurrentCount
   MAX-ACCESS  read-only
   STATUS  current
   DESCRIPTION
      "The counter associated with the number of
      Far End Unavailable Seconds
      encountered by a
      SONET/SDH VT interface
      in the current 15 minute interval."
   ::= { sonetFarEndVTCurrentEntry 4 }

-- The SONET/SDH Far End VT Interval Table

-- The SONET/SDH Far End VT Interval Table
-- contains various statistics
-- collected by each system over a maximum
-- of the previous 24 hours of
-- operation.  The past 24 hours may be broken into 96
-- completed 15 minute intervals.
-- A system is required to store at
-- least 4 completed 15 minute interval.
-- The default value is 32 intervals.

sonetFarEndVTIntervalTable OBJECT-TYPE
    SYNTAX  SEQUENCE OF SonetFarEndVTIntervalEntry
    MAX-ACCESS  not-accessible
    STATUS  current
    DESCRIPTION
       "The SONET/SDH Far End VT Interval table."
    ::= { sonetFarEndVT 2 }

sonetFarEndVTIntervalEntry OBJECT-TYPE
    SYNTAX  SonetFarEndVTIntervalEntry
    MAX-ACCESS  not-accessible


    STATUS  current
    DESCRIPTION
      "An entry in the SONET/SDH Far
      End VT Interval table."
    INDEX   { ifIndex,
              sonetFarEndVTIntervalNumber }
    ::= { sonetFarEndVTIntervalTable 1 }

SonetFarEndVTIntervalEntry ::=
   SEQUENCE {
         sonetFarEndVTIntervalNumber     Integer32,
         sonetFarEndVTIntervalESs        PerfIntervalCount,
         sonetFarEndVTIntervalSESs       PerfIntervalCount,
         sonetFarEndVTIntervalCVs        PerfIntervalCount,
         sonetFarEndVTIntervalUASs       PerfIntervalCount,
         sonetFarEndVTIntervalValidData  TruthValue
    }

sonetFarEndVTIntervalNumber OBJECT-TYPE
    SYNTAX  Integer32 (1..96)
    MAX-ACCESS  not-accessible
    STATUS  current
    DESCRIPTION
       "A number between 1 and 96, which identifies the
       interval for which the set of statistics is available.
       The interval identified by 1 is the most recently
       completed 15 minute interval,
       and the interval identified
       by N is the interval immediately preceding the
       one identified
       by N-1."
    ::= { sonetFarEndVTIntervalEntry 1 }

sonetFarEndVTIntervalESs OBJECT-TYPE
    SYNTAX  PerfIntervalCount
    MAX-ACCESS  read-only
    STATUS  current
    DESCRIPTION
          "The counter associated with the number of
          Far End Errored Seconds encountered
          by a SONET/SDH VT interface
          in a particular 15-minute interval
          in the past 24 hours."
   ::= { sonetFarEndVTIntervalEntry 2 }

sonetFarEndVTIntervalSESs OBJECT-TYPE
    SYNTAX  PerfIntervalCount
    MAX-ACCESS  read-only


    STATUS  current
    DESCRIPTION
          "The counter associated with the number of
          Far End Severely Errored Seconds
          encountered by a SONET/SDH VT interface
          in a particular 15-minute interval
          in the past 24 hours."
    ::= { sonetFarEndVTIntervalEntry 3 }

sonetFarEndVTIntervalCVs OBJECT-TYPE
    SYNTAX  PerfIntervalCount
    MAX-ACCESS  read-only
    STATUS  current
    DESCRIPTION
         "The counter associated with the number of
         Far End Coding Violations reported via
         the far end block error count
         encountered by a
         SONET/SDH VT interface in a
         particular 15-minute interval
         in the past 24 hours."
    ::= { sonetFarEndVTIntervalEntry 4 }

sonetFarEndVTIntervalUASs OBJECT-TYPE
   SYNTAX  PerfIntervalCount
   MAX-ACCESS  read-only
   STATUS  current
   DESCRIPTION
       "The counter associated with the number of
       Far End Unavailable Seconds
       encountered by a
       SONET/SDH VT interface in a
       particular 15-minute interval
       in the past 24 hours."
   ::= { sonetFarEndVTIntervalEntry 5 }

sonetFarEndVTIntervalValidData OBJECT-TYPE
    SYNTAX  TruthValue
    MAX-ACCESS  read-only
    STATUS  current
    DESCRIPTION
       "This variable indicates if the data for this
        interval is valid."
    ::= { sonetFarEndVTIntervalEntry 6 }

-- conformance information

sonetConformance OBJECT IDENTIFIER ::= { sonetMIB 4 }


sonetGroups      OBJECT IDENTIFIER ::= { sonetConformance 1 }
sonetCompliances OBJECT IDENTIFIER ::= { sonetConformance 2 }

-- deprecated compliance statement

sonetCompliance MODULE-COMPLIANCE
    STATUS  deprecated
    DESCRIPTION
            "The compliance statement for SONET/SDH interfaces."

    MODULE  -- this module
        MANDATORY-GROUPS { sonetMediumStuff, sonetSectionStuff }

        GROUP       sonetLineStuff
        DESCRIPTION
            "Implementation of this group is mandatory for all
             SONET/SDH systems that terminate SONET/SDH Lines,
             Paths or Virtual Tributaries."

        GROUP       sonetFarEndLineStuff
        DESCRIPTION
            "Implementation of this group is optional for all
             SONET/SDH systems that terminate SONET/SDH Lines,
             Paths or Virtual Tributaries, and that
             provide for a far end block error (FEBE)
             information at the SONET/SDH Line Layer."

        GROUP       sonetPathStuff
        DESCRIPTION
            "Implementation of this group is mandatory for all
             SONET/SDH systems that terminate SONET/SDH
             Paths or Virtual Tributaries."

        OBJECT      sonetPathCurrentWidth
        MIN-ACCESS  read-only
        DESCRIPTION
            "Write access is not required."

        GROUP       sonetFarEndPathStuff
        DESCRIPTION
            "Implementation of this group is optional for all
             SONET/SDH systems that terminate SONET/SDH
             Paths or Virtual Tributaries, and that process
             Far End information."

        GROUP       sonetVTStuff
        DESCRIPTION
            "Implementation of this group is mandatory for all


             SONET/SDH systems that terminate SONET/SDH Virtual
             Tributaries."

        OBJECT      sonetVTCurrentWidth
        MIN-ACCESS  read-only
        DESCRIPTION
            "Write access is not required."

        GROUP       sonetFarEndVTStuff
        DESCRIPTION
            "Implementation of this group is optional for all
             SONET/SDH systems that terminate the SONET/SDH
             floating Virtual Tributaries, and that process
             Far End information."

    ::= { sonetCompliances 1 }

-- current compliance statements

sonetCompliance2 MODULE-COMPLIANCE
    STATUS  current
    DESCRIPTION
            "The compliance statement for SONET/SDH interfaces."

    MODULE  -- this module
        MANDATORY-GROUPS { sonetMediumStuff2, sonetSectionStuff2 }

        OBJECT      sonetMediumType
        MIN-ACCESS  read-only
        DESCRIPTION
            "Write access is not required."

        OBJECT      sonetMediumLineCoding
        MIN-ACCESS  read-only
        DESCRIPTION
            "Write access is not required."

        OBJECT      sonetMediumLineType
        MIN-ACCESS  read-only
        DESCRIPTION
            "Write access is not required."

        OBJECT      sonetMediumCircuitIdentifier
        MIN-ACCESS  read-only
        DESCRIPTION
            "Write access is not required."


        OBJECT      sonetMediumLoopbackConfig
        MIN-ACCESS  read-only
        DESCRIPTION
            "Write access is not required."

        OBJECT      sonetSESthresholdSet
        MIN-ACCESS  read-only
        DESCRIPTION
          "Write access is not required, and only one
          of the enumerated values need be supported."

        GROUP       sonetLineStuff2
        DESCRIPTION
            "Implementation of this group is mandatory for all
             SONET/SDH systems that terminate SONET/SDH Lines,
             Paths or Virtual Tributaries."

        GROUP       sonetFarEndLineStuff2
        DESCRIPTION
            "Implementation of this group is optional for all
             SONET/SDH systems that terminate SONET/SDH Lines,
             Paths or Virtual Tributaries, and that
             provide for a far end block error (FEBE)
             information at the SONET/SDH Line Layer."

        GROUP       sonetPathStuff2
        DESCRIPTION
            "Implementation of this group is mandatory for all
             SONET/SDH systems that terminate SONET/SDH
             Paths or Virtual Tributaries."

        OBJECT      sonetPathCurrentWidth
        MIN-ACCESS  read-only
        DESCRIPTION
            "Write access is not required."

        GROUP       sonetFarEndPathStuff2
        DESCRIPTION
            "Implementation of this group is optional for all
             SONET/SDH systems that terminate SONET/SDH
             Paths or Virtual Tributaries, and that process
             Far End information."

        GROUP       sonetVTStuff2
        DESCRIPTION
            "Implementation of this group is mandatory for all
             SONET/SDH systems that terminate SONET/SDH Virtual
             Tributaries."


        OBJECT      sonetVTCurrentWidth
        MIN-ACCESS  read-only
        DESCRIPTION
            "Write access is not required."

        GROUP       sonetFarEndVTStuff2
        DESCRIPTION
            "Implementation of this group is optional for all
             SONET/SDH systems that terminate the SONET/SDH
             floating Virtual Tributaries, and that process
             Far End information."

    ::= { sonetCompliances 2 }

-- units of conformance

-- deprecated groups

sonetMediumStuff    OBJECT-GROUP
    OBJECTS { sonetMediumType,
              sonetMediumTimeElapsed,
              sonetMediumValidIntervals,
              sonetMediumLineCoding,
              sonetMediumLineType,
              sonetMediumCircuitIdentifier }
    STATUS  deprecated
    DESCRIPTION
            "A collection of objects providing configuration
            information applicable to all SONET/SDH interfaces."
    ::= { sonetGroups 1 }

sonetSectionStuff    OBJECT-GROUP
    OBJECTS { sonetSectionCurrentStatus,
              sonetSectionCurrentESs,
              sonetSectionCurrentSESs,
              sonetSectionCurrentSEFSs,
              sonetSectionCurrentCVs,
              sonetSectionIntervalESs,
              sonetSectionIntervalSESs,
              sonetSectionIntervalSEFSs,
              sonetSectionIntervalCVs
 }
    STATUS  deprecated
    DESCRIPTION
            "A collection of objects providing information
            specific to SONET/SDH Section interfaces."
    ::= { sonetGroups 2 }


sonetLineStuff    OBJECT-GROUP
    OBJECTS { sonetLineCurrentStatus,
              sonetLineCurrentESs,
              sonetLineCurrentSESs,
              sonetLineCurrentCVs,
              sonetLineCurrentUASs,
              sonetLineIntervalESs,
              sonetLineIntervalSESs,
              sonetLineIntervalCVs,
              sonetLineIntervalUASs }
    STATUS  deprecated
    DESCRIPTION
            "A collection of objects providing information
            specific to SONET/SDH Line interfaces."
    ::= { sonetGroups 3 }

sonetFarEndLineStuff    OBJECT-GROUP
    OBJECTS { sonetFarEndLineCurrentESs,
              sonetFarEndLineCurrentSESs,
              sonetFarEndLineCurrentCVs,
              sonetFarEndLineCurrentUASs,
              sonetFarEndLineIntervalESs,
              sonetFarEndLineIntervalSESs,
              sonetFarEndLineIntervalCVs,
              sonetFarEndLineIntervalUASs }
    STATUS  deprecated
    DESCRIPTION
            "A collection of objects providing information
            specific to SONET/SDH Line interfaces,
            and maintaining Line Far End information."
    ::= { sonetGroups 4 }

sonetPathStuff    OBJECT-GROUP
    OBJECTS { sonetPathCurrentWidth,
              sonetPathCurrentStatus,
              sonetPathCurrentESs,
              sonetPathCurrentSESs,
              sonetPathCurrentCVs,
              sonetPathCurrentUASs,
              sonetPathIntervalESs,
              sonetPathIntervalSESs,
              sonetPathIntervalCVs,
              sonetPathIntervalUASs }
    STATUS  deprecated
    DESCRIPTION
            "A collection of objects providing information
            specific to SONET/SDH Path interfaces."
    ::= { sonetGroups 5 }


sonetFarEndPathStuff    OBJECT-GROUP
    OBJECTS { sonetFarEndPathCurrentESs,
              sonetFarEndPathCurrentSESs,
              sonetFarEndPathCurrentCVs,
              sonetFarEndPathCurrentUASs,
              sonetFarEndPathIntervalESs,
              sonetFarEndPathIntervalSESs,
              sonetFarEndPathIntervalCVs,
              sonetFarEndPathIntervalUASs }
    STATUS  deprecated
    DESCRIPTION
            "A collection of objects providing information
            specific to SONET/SDH Path interfaces,
            and maintaining Path Far End information."
    ::= { sonetGroups 6 }

sonetVTStuff    OBJECT-GROUP
    OBJECTS { sonetVTCurrentWidth,
              sonetVTCurrentStatus,
              sonetVTCurrentESs,
              sonetVTCurrentSESs,
              sonetVTCurrentCVs,
              sonetVTCurrentUASs,
              sonetVTIntervalESs,
              sonetVTIntervalSESs,
              sonetVTIntervalCVs,
              sonetVTIntervalUASs }
    STATUS  deprecated
    DESCRIPTION
            "A collection of objects providing information
            specific to SONET/SDH VT interfaces."
    ::= { sonetGroups 7 }

sonetFarEndVTStuff    OBJECT-GROUP
    OBJECTS { sonetFarEndVTCurrentESs,
              sonetFarEndVTCurrentSESs,
              sonetFarEndVTCurrentCVs,
              sonetFarEndVTCurrentUASs,
              sonetFarEndVTIntervalESs,
              sonetFarEndVTIntervalSESs,
              sonetFarEndVTIntervalCVs,
              sonetFarEndVTIntervalUASs }
    STATUS  deprecated
    DESCRIPTION
            "A collection of objects providing information
            specific to SONET/SDH VT interfaces,
            and maintaining VT Far End information."
    ::= { sonetGroups 8 }


-- current groups

sonetMediumStuff2    OBJECT-GROUP
    OBJECTS { sonetMediumType,
              sonetMediumTimeElapsed,
              sonetMediumValidIntervals,
              sonetMediumLineCoding,
              sonetMediumLineType,
              sonetMediumCircuitIdentifier,
              sonetMediumInvalidIntervals,
              sonetMediumLoopbackConfig,
              sonetSESthresholdSet }
    STATUS  current
    DESCRIPTION
            "A collection of objects providing configuration
            information applicable to all SONET/SDH interfaces."
    ::= { sonetGroups 9 }

sonetSectionStuff2    OBJECT-GROUP
    OBJECTS { sonetSectionCurrentStatus,
              sonetSectionCurrentESs,
              sonetSectionCurrentSESs,
              sonetSectionCurrentSEFSs,
              sonetSectionCurrentCVs,
              sonetSectionIntervalESs,
              sonetSectionIntervalSESs,
              sonetSectionIntervalSEFSs,
              sonetSectionIntervalCVs,
              sonetSectionIntervalValidData }
    STATUS  current
    DESCRIPTION
            "A collection of objects providing information
            specific to SONET/SDH Section interfaces."
    ::= { sonetGroups 10 }

sonetLineStuff2    OBJECT-GROUP
    OBJECTS { sonetLineCurrentStatus,
              sonetLineCurrentESs,
              sonetLineCurrentSESs,
              sonetLineCurrentCVs,
              sonetLineCurrentUASs,
              sonetLineIntervalESs,
              sonetLineIntervalSESs,
              sonetLineIntervalCVs,
              sonetLineIntervalUASs,
              sonetLineIntervalValidData }
    STATUS  current
    DESCRIPTION


            "A collection of objects providing information
            specific to SONET/SDH Line interfaces."
    ::= { sonetGroups 11 }

sonetPathStuff2    OBJECT-GROUP
    OBJECTS { sonetPathCurrentWidth,
              sonetPathCurrentStatus,
              sonetPathCurrentESs,
              sonetPathCurrentSESs,
              sonetPathCurrentCVs,
              sonetPathCurrentUASs,
              sonetPathIntervalESs,
              sonetPathIntervalSESs,
              sonetPathIntervalCVs,
              sonetPathIntervalUASs,
              sonetPathIntervalValidData }
    STATUS  current
    DESCRIPTION
            "A collection of objects providing information
            specific to SONET/SDH Path interfaces."
    ::= { sonetGroups 12 }

sonetVTStuff2    OBJECT-GROUP
    OBJECTS { sonetVTCurrentWidth,
              sonetVTCurrentStatus,
              sonetVTCurrentESs,
              sonetVTCurrentSESs,
              sonetVTCurrentCVs,
              sonetVTCurrentUASs,
              sonetVTIntervalESs,
              sonetVTIntervalSESs,
              sonetVTIntervalCVs,
              sonetVTIntervalUASs,
              sonetVTIntervalValidData }
    STATUS  current
    DESCRIPTION
            "A collection of objects providing information
            specific to SONET/SDH VT interfaces."
    ::= { sonetGroups 13 }

sonetFarEndLineStuff2    OBJECT-GROUP
    OBJECTS { sonetFarEndLineCurrentESs,
              sonetFarEndLineCurrentSESs,
              sonetFarEndLineCurrentCVs,
              sonetFarEndLineCurrentUASs,
              sonetFarEndLineIntervalESs,
              sonetFarEndLineIntervalSESs,
              sonetFarEndLineIntervalCVs,


              sonetFarEndLineIntervalUASs,
              sonetFarEndLineIntervalValidData }
    STATUS  current
    DESCRIPTION
            "A collection of objects providing information
            specific to SONET/SDH Line interfaces,
            and maintaining Line Far End information."
    ::= { sonetGroups 14 }

sonetFarEndPathStuff2    OBJECT-GROUP
    OBJECTS { sonetFarEndPathCurrentESs,
              sonetFarEndPathCurrentSESs,
              sonetFarEndPathCurrentCVs,
              sonetFarEndPathCurrentUASs,
              sonetFarEndPathIntervalESs,
              sonetFarEndPathIntervalSESs,
              sonetFarEndPathIntervalCVs,
              sonetFarEndPathIntervalUASs,
              sonetFarEndPathIntervalValidData }
    STATUS  current
    DESCRIPTION
            "A collection of objects providing information
            specific to SONET/SDH Path interfaces,
            and maintaining Path Far End information."
    ::= { sonetGroups 15 }

sonetFarEndVTStuff2    OBJECT-GROUP
    OBJECTS { sonetFarEndVTCurrentESs,
              sonetFarEndVTCurrentSESs,
              sonetFarEndVTCurrentCVs,
              sonetFarEndVTCurrentUASs,
              sonetFarEndVTIntervalESs,
              sonetFarEndVTIntervalSESs,
              sonetFarEndVTIntervalCVs,
              sonetFarEndVTIntervalUASs,
              sonetFarEndVTIntervalValidData }
    STATUS  current
    DESCRIPTION
            "A collection of objects providing information
            specific to SONET/SDH VT interfaces,
            and maintaining VT Far End information."
    ::= { sonetGroups 16 }

END

MAU-MIB DEFINITIONS ::= BEGIN

       IMPORTS
           Counter32, Integer32,
           OBJECT-TYPE, MODULE-IDENTITY, NOTIFICATION-TYPE,
           OBJECT-IDENTITY, mib-2
               FROM SNMPv2-SMI
           TruthValue, TEXTUAL-CONVENTION
               FROM SNMPv2-TC
           OBJECT-GROUP, MODULE-COMPLIANCE, NOTIFICATION-GROUP
               FROM SNMPv2-CONF;

       mauMod MODULE-IDENTITY
           LAST-UPDATED "9908240400Z"  -- August 24, 1999
           ORGANIZATION "IETF Ethernet Interfaces and Hub MIB
                        Working Group"
           CONTACT-INFO
               "WG E-mail: hubmib@hprnd.rose.hp.com
             To subscribe: hubmib-request@hprnd.rose.hp.com

                    Chair: Dan Romascanu
                   Postal: Lucent Technologies
                           Atidim Technology Park, Bldg. 3
                           Tel Aviv 61131
                           Israel
                      Tel: +972 3 645 8414, 6458458
                      Fax: +972 3 648 7146
                   E-mail: dromasca@lucent.com

                  Editors: Andrew Smith
                   Postal: Extreme Networks, Inc.
                           10460 Bandley Drive
                           Cupertino, CA 95014
                           USA
                      Tel: +1 408 579-2821
                   E-mail: andrew@extremenetworks.com

                           John Flick
                   Postal: Hewlett-Packard Company
                           8000 Foothills Blvd. M/S 5557
                          Roseville, CA 95747-5557
                          USA
                     Tel: +1 916 785 4018
                     Fax: +1 916 785 1199
                  E-mail: johnf@rose.hp.com


                          Kathryn de Graaf
                  Postal: Argon Networks
                          25 Porter Road
                          Littleton, MA  01460
                          USA
                     Tel: +1 978 486 0665 x163
                     Fax: +1 978 486 9379
                  E-mail: kdegraaf@argon.com"
          DESCRIPTION "Management information for 802.3 MAUs.

                      The following reference is used throughout
                      this MIB module:

                      [IEEE 802.3 Std] refers to
                         IEEE Std 802.3, 1998 Edition: 'Information
                         technology - Telecommunications and
                         information exchange between systems -
                         Local and metropolitan area networks -
                         Specific requirements - Part 3: Carrier
                         sense multiple access with collision
                         detection (CSMA/CD) access method and
                         physical layer specifications',
                         September 1998.

                      Of particular interest is Clause 30, '10Mb/s,
                      100Mb/s and 1000Mb/s Management'."

          REVISION    "9908240400Z" -- August 24, 1999
          DESCRIPTION "This version published as RFC 2668. Updated
                       to include support for 1000 Mb/sec
                       MAUs and flow control negotiation."

          REVISION    "9710310000Z" -- October 31, 1997
          DESCRIPTION "This version published as RFC 2239."

          REVISION    "9309300000Z" -- September 30, 1993
          DESCRIPTION "Initial version, published as RFC 1515."

          ::= { snmpDot3MauMgt 6 }

      snmpDot3MauMgt OBJECT IDENTIFIER ::= { mib-2 26 }

      -- textual conventions

      JackType ::= TEXTUAL-CONVENTION
          STATUS      current
          DESCRIPTION "Common enumeration values for repeater
                      and interface MAU jack types."


          SYNTAX      INTEGER {
                          other(1),
                          rj45(2),
                          rj45S(3), -- rj45 shielded
                          db9(4),
                          bnc(5),
                          fAUI(6),  -- female aui
                          mAUI(7),  -- male aui
                          fiberSC(8),
                          fiberMIC(9),
                          fiberST(10),
                          telco(11),
                          mtrj(12),  -- fiber MT-RJ
                          hssdc(13)  -- fiber channel style-2
                      }

      dot3RpMauBasicGroup
          OBJECT IDENTIFIER ::= { snmpDot3MauMgt 1 }
      dot3IfMauBasicGroup
          OBJECT IDENTIFIER ::= { snmpDot3MauMgt 2 }
      dot3BroadMauBasicGroup
          OBJECT IDENTIFIER ::= { snmpDot3MauMgt 3 }

      dot3IfMauAutoNegGroup
          OBJECT IDENTIFIER ::= { snmpDot3MauMgt 5 }

      -- object identities for MAU types
      --  (see rpMauType and ifMauType for usage)

      dot3MauType
          OBJECT IDENTIFIER ::= { snmpDot3MauMgt 4 }

      dot3MauTypeAUI OBJECT-IDENTITY
          STATUS      current
          DESCRIPTION "no internal MAU, view from AUI"
          ::= { dot3MauType 1 }

      dot3MauType10Base5 OBJECT-IDENTITY
          STATUS      current
          DESCRIPTION "thick coax MAU (per 802.3 section 8)"
          ::= { dot3MauType 2 }
      dot3MauTypeFoirl OBJECT-IDENTITY
          STATUS      current
          DESCRIPTION "FOIRL MAU (per 802.3 section 9.9)"
          ::= { dot3MauType 3 }

      dot3MauType10Base2 OBJECT-IDENTITY
          STATUS      current


          DESCRIPTION "thin coax MAU (per 802.3 section 10)"
          ::= { dot3MauType 4 }

      dot3MauType10BaseT OBJECT-IDENTITY
          STATUS      current
          DESCRIPTION "UTP MAU (per 802.3 section 14).
                      Note that it is strongly recommended that
                      agents return either dot3MauType10BaseTHD or
                      dot3MauType10BaseTFD if the duplex mode is
                      known.  However, management applications should
                      be prepared to receive this MAU type value from
                      older agent implementations."
          ::= { dot3MauType 5 }

      dot3MauType10BaseFP OBJECT-IDENTITY
          STATUS      current
          DESCRIPTION "passive fiber MAU (per 802.3 section 16)"
          ::= { dot3MauType 6 }

      dot3MauType10BaseFB OBJECT-IDENTITY
          STATUS      current
          DESCRIPTION "sync fiber MAU (per 802.3 section 17)"
          ::= { dot3MauType 7 }

      dot3MauType10BaseFL OBJECT-IDENTITY
          STATUS      current
          DESCRIPTION "async fiber MAU (per 802.3 section 18)
                      Note that it is strongly recommended that
                      agents return either dot3MauType10BaseFLHD or
                      dot3MauType10BaseFLFD if the duplex mode is
                      known.  However, management applications should
                      be prepared to receive this MAU type value from
                      older agent implementations."
          ::= { dot3MauType 8 }

      dot3MauType10Broad36 OBJECT-IDENTITY
          STATUS      current
          DESCRIPTION "broadband DTE MAU (per 802.3 section 11).
                      Note that 10BROAD36 MAUs can be attached to
                      interfaces but not to repeaters."
          ::= { dot3MauType 9 }
      ------ new since RFC 1515:
      dot3MauType10BaseTHD OBJECT-IDENTITY
          STATUS      current
          DESCRIPTION "UTP MAU (per 802.3 section 14), half duplex
                      mode"
          ::= { dot3MauType 10 }


      dot3MauType10BaseTFD OBJECT-IDENTITY
          STATUS      current
          DESCRIPTION "UTP MAU (per 802.3 section 14), full duplex
                      mode"
          ::= { dot3MauType 11 }

      dot3MauType10BaseFLHD OBJECT-IDENTITY
          STATUS      current
          DESCRIPTION "async fiber MAU (per 802.3 section 18), half
                      duplex mode"
          ::= { dot3MauType 12 }

      dot3MauType10BaseFLFD OBJECT-IDENTITY
          STATUS      current
          DESCRIPTION "async fiber MAU (per 802.3 section 18), full
                      duplex mode"
          ::= { dot3MauType 13 }

      dot3MauType100BaseT4 OBJECT-IDENTITY
          STATUS      current
          DESCRIPTION "4 pair categ. 3 UTP (per 802.3 section 23)"
          ::= { dot3MauType 14 }

      dot3MauType100BaseTXHD OBJECT-IDENTITY
          STATUS      current
          DESCRIPTION "2 pair categ. 5 UTP (per 802.3 section 25),
                      half duplex mode"
          ::= { dot3MauType 15 }

      dot3MauType100BaseTXFD OBJECT-IDENTITY
          STATUS      current
          DESCRIPTION "2 pair categ. 5 UTP (per 802.3 section 25),
                      full duplex mode"
          ::= { dot3MauType 16 }

      dot3MauType100BaseFXHD OBJECT-IDENTITY
          STATUS      current
          DESCRIPTION "X fiber over PMT (per 802.3 section 26), half
                      duplex mode"
          ::= { dot3MauType 17 }
      dot3MauType100BaseFXFD OBJECT-IDENTITY
          STATUS      current
          DESCRIPTION "X fiber over PMT (per 802.3 section 26), full
                      duplex mode"
          ::= { dot3MauType 18 }

      dot3MauType100BaseT2HD OBJECT-IDENTITY
          STATUS      current


          DESCRIPTION "2 pair categ. 3 UTP (per 802.3 section 32),
                      half duplex mode"
          ::= { dot3MauType 19 }

      dot3MauType100BaseT2FD OBJECT-IDENTITY
          STATUS      current
          DESCRIPTION "2 pair categ. 3 UTP (per 802.3 section 32),
                      full duplex mode"
          ::= { dot3MauType 20 }

      ------ new since RFC 2239:

      dot3MauType1000BaseXHD OBJECT-IDENTITY
          STATUS      current
          DESCRIPTION "PCS/PMA (per 802.3 section 36), unknown PMD,
                      half duplex mode"
          ::= { dot3MauType 21 }

      dot3MauType1000BaseXFD OBJECT-IDENTITY
          STATUS      current
          DESCRIPTION "PCS/PMA (per 802.3 section 36), unknown PMD,
                      full duplex mode"
          ::= { dot3MauType 22 }

      dot3MauType1000BaseLXHD OBJECT-IDENTITY
          STATUS      current
          DESCRIPTION "Fiber over long-wavelength laser (per 802.3
                      section 38), half duplex mode"
          ::= { dot3MauType 23 }

      dot3MauType1000BaseLXFD OBJECT-IDENTITY
          STATUS      current
          DESCRIPTION "Fiber over long-wavelength laser (per 802.3
                      section 38), full duplex mode"
          ::= { dot3MauType 24 }

      dot3MauType1000BaseSXHD OBJECT-IDENTITY
          STATUS      current
          DESCRIPTION "Fiber over short-wavelength laser (per 802.3
                      section 38), half duplex mode"
          ::= { dot3MauType 25 }

      dot3MauType1000BaseSXFD OBJECT-IDENTITY
          STATUS      current
          DESCRIPTION "Fiber over short-wavelength laser (per 802.3
                      section 38), full duplex mode"
          ::= { dot3MauType 26 }


      dot3MauType1000BaseCXHD OBJECT-IDENTITY
          STATUS      current
          DESCRIPTION "Copper over 150-Ohm balanced cable (per 802.3
                      section 39), half duplex mode"
          ::= { dot3MauType 27 }

      dot3MauType1000BaseCXFD OBJECT-IDENTITY
          STATUS      current
          DESCRIPTION "Copper over 150-Ohm balanced cable (per 802.3
                      section 39), full duplex mode"
          ::= { dot3MauType 28 }

      dot3MauType1000BaseTHD OBJECT-IDENTITY
          STATUS      current
          DESCRIPTION "Four-pair Category 5 UTP (per 802.3 section
                      40), half duplex mode"
          ::= { dot3MauType 29 }

      dot3MauType1000BaseTFD OBJECT-IDENTITY
          STATUS      current
          DESCRIPTION "Four-pair Category 5 UTP (per 802.3 section
                      40), full duplex mode"
          ::= { dot3MauType 30 }

      --
      -- The Basic Repeater MAU Table
      --

      rpMauTable OBJECT-TYPE
          SYNTAX      SEQUENCE OF RpMauEntry
          MAX-ACCESS  not-accessible
          STATUS      current
          DESCRIPTION "Table of descriptive and status information
                      about the MAU(s) attached to the ports of a
                      repeater."
          ::= { dot3RpMauBasicGroup 1 }

      rpMauEntry OBJECT-TYPE
          SYNTAX      RpMauEntry
          MAX-ACCESS  not-accessible
          STATUS      current
          DESCRIPTION "An entry in the table, containing information
                      about a single MAU."
          INDEX       { rpMauGroupIndex,
                        rpMauPortIndex,
                        rpMauIndex
                      }
          ::= { rpMauTable 1 }


      RpMauEntry ::=
          SEQUENCE {
              rpMauGroupIndex                     Integer32,
              rpMauPortIndex                      Integer32,
              rpMauIndex                          Integer32,
              rpMauType                           OBJECT IDENTIFIER,
              rpMauStatus                         INTEGER,
              rpMauMediaAvailable                 INTEGER,
              rpMauMediaAvailableStateExits       Counter32,
              rpMauJabberState                    INTEGER,
              rpMauJabberingStateEnters           Counter32,
              rpMauFalseCarriers                  Counter32
      }

      rpMauGroupIndex OBJECT-TYPE
          SYNTAX      Integer32 (1..2147483647)
          MAX-ACCESS  read-only
          STATUS      current
          DESCRIPTION "This variable uniquely identifies the group
                      containing the port to which the MAU described
                      by this entry is connected.

                      Note:  In practice, a group will generally be
                      a field-replaceable unit (i.e., module, card,
                      or board) that can fit in the physical system
                      enclosure, and the group number will correspond
                      to a number marked on the physical enclosure.

                      The group denoted by a particular value of this
                      object is the same as the group denoted by the
                      same value of rptrGroupIndex."
          REFERENCE   "Reference RFC 2108, rptrGroupIndex."
          ::= { rpMauEntry 1 }

      rpMauPortIndex OBJECT-TYPE
          SYNTAX      Integer32 (1..2147483647)
          MAX-ACCESS  read-only
          STATUS      current
          DESCRIPTION "This variable uniquely identifies the repeater
                      port within group rpMauGroupIndex to which the
                      MAU described by this entry is connected."
          REFERENCE   "Reference RFC 2108, rptrPortIndex."
          ::= { rpMauEntry 2 }

      rpMauIndex OBJECT-TYPE
          SYNTAX      Integer32 (1..2147483647)
          MAX-ACCESS  read-only
          STATUS      current


          DESCRIPTION "This variable uniquely identifies the MAU
                      described by this entry from among other
                      MAUs connected to the same port
                      (rpMauPortIndex)."
          REFERENCE   "[IEEE 802.3 Std], 30.5.1.1.1, aMAUID."
          ::= { rpMauEntry 3 }

      rpMauType OBJECT-TYPE
          SYNTAX      OBJECT IDENTIFIER
          MAX-ACCESS  read-only
          STATUS      current
          DESCRIPTION "This object identifies the MAU type.  An
                      initial set of MAU types are defined above.  The
                      assignment of OBJECT IDENTIFIERs to new types of
                      MAUs is managed by the IANA.  If the MAU type is
                      unknown, the object identifier

                      unknownMauType OBJECT IDENTIFIER ::= { 0 0 }

                      is returned.  Note that unknownMauType is a
                      syntactically valid object identifier, and any
                      conformant implementation of ASN.1 and the BER
                      must be able to generate and recognize this
                      value."
          REFERENCE   "[IEEE 802.3 Std], 30.5.1.1.2, aMAUType."
          ::= { rpMauEntry 4 }

      rpMauStatus OBJECT-TYPE
          SYNTAX      INTEGER {
                          other(1),
                          unknown(2),
                          operational(3),
                          standby(4),
                          shutdown(5),
                          reset(6)
                      }
          MAX-ACCESS  read-write
          STATUS      current
          DESCRIPTION "The current state of the MAU.  This object MAY
                      be implemented as a read-only object by those
                      agents and MAUs that do not implement software
                      control of the MAU state.  Some agents may not
                      support setting the value of this object to some
                      of the enumerated values.

                      The value other(1) is returned if the MAU is in
                      a state other than one of the states 2 through
                      6.


                      The value unknown(2) is returned when the MAU's
                      true state is unknown; for example, when it is
                      being initialized.

                      A MAU in the operational(3) state is fully
                      functional, operates, and passes signals to its
                      attached DTE or repeater port in accordance to
                      its specification.

                      A MAU in standby(4) state forces DI and CI to
                      idle and the media transmitter to idle or fault,
                      if supported.  Standby(4) mode only applies to
                      link type MAUs.  The state of
                      rpMauMediaAvailable is unaffected.

                      A MAU in shutdown(5) state assumes the same
                      condition on DI, CI, and the media transmitter
                      as though it were powered down or not connected.
                      The MAU MAY return other(1) value for the
                      rpMauJabberState and rpMauMediaAvailable objects
                      when it is in this state.  For an AUI, this
                      state will remove power from the AUI.

                      Setting this variable to the value reset(6)
                      resets the MAU in the same manner as a
                      power-off, power-on cycle of at least one-half
                      second would.  The agent is not required to
                      return the value reset (6).

                      Setting this variable to the value
                      operational(3), standby(4), or shutdown(5)
                      causes the MAU to assume the respective state
                      except that setting a mixing-type MAU or an AUI
                      to standby(4) will cause the MAU to enter the
                      shutdown state."
          REFERENCE   "[IEEE 802.3 Std], 30.5.1.1.7, aMAUAdminState,
                          30.5.1.2.2, acMAUAdminControl, and 30.5.1.2.1,
                      acResetMAU."
          ::= { rpMauEntry 5 }

      rpMauMediaAvailable OBJECT-TYPE
          SYNTAX      INTEGER {
                          other(1),
                          unknown(2),
                          available(3),
                          notAvailable(4),
                          remoteFault(5),
                          invalidSignal(6),


                          remoteJabber(7),
                          remoteLinkLoss(8),
                          remoteTest(9),
                          offline(10),
                          autoNegError(11)
                      }
          MAX-ACCESS  read-only
          STATUS      current
          DESCRIPTION "If the MAU is a link or fiber type (FOIRL,
                      10BASE-T, 10BASE-F) then this is equivalent to
                      the link test fail state/low light function.
                      For an AUI or a coax (including broadband) MAU
                      this indicates whether or not loopback is
                      detected on the DI circuit.  The value of this
                      attribute persists between packets for MAU types
                      AUI, 10BASE5, 10BASE2, 10BROAD36, and 10BASE-FP.

                      The value other(1) is returned if the
                      mediaAvailable state is not one of 2 through 11.

                      The value unknown(2) is returned when the MAU's
                      true state is unknown; for example, when it is
                      being initialized.  At power-up or following a
                      reset, the value of this attribute will be
                      unknown for AUI, coax, and 10BASE-FP MAUs.  For
                      these MAUs loopback will be tested on each
                      transmission during which no collision is
                      detected.  If DI is receiving input when DO
                      returns to IDL after a transmission and there
                      has been no collision during the transmission
                      then loopback will be detected.  The value of
                      this attribute will only change during
                      non-collided transmissions for AUI, coax, and
                      10BASE-FP MAUs.

                      For 100Mbps and 1000Mbps MAUs, the enumerations
                      match the states within the respective link
                      integrity state diagrams, fig 32-16, 23-12 and
                      24-15 of sections 32, 23 and 24 of [16].  Any
                      MAU which implements management of
                      auto-negotiation will map remote fault
                      indication to remote fault.

                      The value available(3) indicates that the link,
                      light, or loopback is normal.  The value
                      notAvailable(4) indicates link loss, low light,
                      or no loopback.


                      The value remoteFault(5) indicates that a fault
                      has been detected at the remote end of the link.
                      This value applies to 10BASE-FB, 100BASE-T4 Far
                      End Fault Indication and non-specified remote
                      faults from a system running auto-negotiation.
                      The values remoteJabber(7), remoteLinkLoss(8),
                      and remoteTest(9) SHOULD be used instead of
                      remoteFault(5) where the reason for remote fault
                      is identified in the remote signaling protocol.

                      The value invalidSignal(6) indicates that an
                      invalid signal has been received from the other
                      end of the link.  InvalidSignal(6) applies only
                      to MAUs of type 10BASE-FB.

                      Where an IEEE Std 802.3u-1995 clause 22 MII
                      is present, a logic one in the remote fault bit
                      (reference section 22.2.4.2.8 of that document)
                      maps to the value remoteFault(5), and a logic
                      zero in the link status bit (reference section
                      22.2.4.2.10 of that document) maps to the value
                      notAvailable(4).  The value notAvailable(4)
                      takes precedence over the value remoteFault(5).

                      Any MAU that implements management of clause 37
                      Auto-Negotiation will map the received Remote
                      Fault (RF1 and RF2) bit values for Offline to
                      offline(10), Link Failure to remoteFault(5) and
                      Auto-Negotiation Error to autoNegError(11)."

          REFERENCE   "[IEEE 802.3 Std], 30.5.1.1.4, aMediaAvailable."
          ::= { rpMauEntry 6 }

      rpMauMediaAvailableStateExits OBJECT-TYPE
          SYNTAX      Counter32
          MAX-ACCESS  read-only
          STATUS      current
          DESCRIPTION "A count of the number of times that
                      rpMauMediaAvailable for this MAU instance leaves
                      the state available(3).

                      Discontinuities in the value of this counter can
                      occur at re-initialization of the management
                      system, and at other times as indicated by the
                      value of rptrMonitorPortLastChange."
          REFERENCE   "[IEEE 802.3 Std], 30.5.1.1.5,
                      aLoseMediaCounter.
                      RFC 2108, rptrMonitorPortLastChange"


          ::= { rpMauEntry 7 }

      rpMauJabberState OBJECT-TYPE
          SYNTAX      INTEGER {
                          other(1),
                          unknown(2),
                          noJabber(3),
                          jabbering(4)
                      }
          MAX-ACCESS  read-only
          STATUS      current
          DESCRIPTION "The value other(1) is returned if the jabber
                      state is not 2, 3, or 4.  The agent MUST always
                      return other(1) for MAU type dot3MauTypeAUI.

                      The value unknown(2) is returned when the MAU's
                      true state is unknown; for example, when it is
                      being initialized.

                      If the MAU is not jabbering the agent returns
                      noJabber(3).  This is the 'normal' state.

                      If the MAU is in jabber state the agent returns
                      the jabbering(4) value."
          REFERENCE "[IEEE 802.3 Std], 30.5.1.1.6,
                    aJabber.jabberFlag."
          ::= { rpMauEntry 8 }

      rpMauJabberingStateEnters OBJECT-TYPE
          SYNTAX      Counter32
          MAX-ACCESS  read-only
          STATUS      current
          DESCRIPTION "A count of the number of times that
                      mauJabberState for this MAU instance enters the
                      state jabbering(4).  For MAUs of type
                      dot3MauTypeAUI, dot3MauType100BaseT4,
                      dot3MauType100BaseTX, dot3MauType100BaseFX and
                          all 1000Mbps types, this counter will always
                          indicate zero.

                          Discontinuities in the value of this counter
                          can occur at re-initialization of the
                          management system, and at other times as
                          indicated by the value of
                          rptrMonitorPortLastChange."
              REFERENCE   "[IEEE 802.3 Std], 30.5.1.1.6,
                          aJabber.jabberCounter.
                          RFC 2108, rptrMonitorPortLastChange"


          ::= { rpMauEntry 9 }

      rpMauFalseCarriers OBJECT-TYPE
          SYNTAX      Counter32
          MAX-ACCESS  read-only
          STATUS      current
          DESCRIPTION "A count of the number of false carrier events
                      during IDLE in 100BASE-X links.  This counter
                      does not increment at the symbol rate.  It can
                      increment after a valid carrier completion at a
                      maximum rate of once per 100 ms until the next
                      carrier event.

                      This counter increments only for MAUs of type
                      dot3MauType100BaseT4, dot3MauType100BaseTX, and
                      dot3MauType100BaseFX and all 1000Mbps types.
                      For all other MAU types, this counter will
                      always indicate zero.

                      The approximate minimum time for rollover of
                      this counter is 7.4 hours.

                      Discontinuities in the value of this counter can
                      occur at re-initialization of the management
                      system, and at other times as indicated by the
                      value of rptrMonitorPortLastChange."
          REFERENCE   "[IEEE 802.3 Std], 30.5.1.1.10, aFalseCarriers.
                      RFC 2108, rptrMonitorPortLastChange"
          ::= { rpMauEntry 10 }

      -- The rpJackTable applies to MAUs attached to repeaters
      -- which have one or more external jacks (connectors).

      rpJackTable OBJECT-TYPE
          SYNTAX      SEQUENCE OF RpJackEntry
          MAX-ACCESS  not-accessible
          STATUS      current
          DESCRIPTION "Information about the external jacks attached
                      to MAUs attached to the ports of a repeater."
          ::= { dot3RpMauBasicGroup 2 }

      rpJackEntry OBJECT-TYPE
          SYNTAX      RpJackEntry
          MAX-ACCESS  not-accessible
          STATUS      current
          DESCRIPTION "An entry in the table, containing information
                      about a particular jack."
          INDEX       { rpMauGroupIndex,


                        rpMauPortIndex,
                        rpMauIndex,
                        rpJackIndex
                      }
          ::= { rpJackTable 1 }

      RpJackEntry ::=
          SEQUENCE {
              rpJackIndex                         Integer32,
              rpJackType                          JackType
          }

      rpJackIndex OBJECT-TYPE
          SYNTAX      Integer32 (1..2147483647)
          MAX-ACCESS  not-accessible
          STATUS      current
          DESCRIPTION "This variable uniquely identifies the jack
                      described by this entry from among other jacks
                      attached to the same MAU (rpMauIndex)."
          ::= { rpJackEntry 1 }

      rpJackType OBJECT-TYPE
          SYNTAX      JackType
          MAX-ACCESS  read-only
          STATUS      current
          DESCRIPTION "The jack connector type, as it appears on the
                      outside of the system."
          ::= { rpJackEntry 2 }

      --
      -- The Basic Interface MAU Table
      --

      ifMauTable OBJECT-TYPE
          SYNTAX      SEQUENCE OF IfMauEntry
          MAX-ACCESS  not-accessible
          STATUS      current
          DESCRIPTION "Table of descriptive and status information
                      about MAU(s) attached to an interface."
          ::= { dot3IfMauBasicGroup 1 }

      ifMauEntry OBJECT-TYPE
          SYNTAX      IfMauEntry
          MAX-ACCESS  not-accessible
          STATUS      current
          DESCRIPTION "An entry in the table, containing information
                      about a single MAU."
          INDEX       { ifMauIfIndex,


                        ifMauIndex
                      }
          ::= { ifMauTable 1 }

      IfMauEntry ::=
          SEQUENCE {
              ifMauIfIndex                        Integer32,
              ifMauIndex                          Integer32,
              ifMauType                           OBJECT IDENTIFIER,
              ifMauStatus                         INTEGER,
              ifMauMediaAvailable                 INTEGER,
              ifMauMediaAvailableStateExits       Counter32,
              ifMauJabberState                    INTEGER,
              ifMauJabberingStateEnters           Counter32,
              ifMauFalseCarriers                  Counter32,
              ifMauTypeList                       Integer32,
              ifMauDefaultType                    OBJECT IDENTIFIER,
              ifMauAutoNegSupported               TruthValue,
              ifMauTypeListBits                   BITS
          }

      ifMauIfIndex OBJECT-TYPE
          SYNTAX      Integer32 (1..2147483647)
          MAX-ACCESS  read-only
          STATUS      current
          DESCRIPTION "This variable uniquely identifies the interface
                      to which the MAU described by this entry is
                      connected."
          REFERENCE   "RFC 1213, ifIndex"
          ::= { ifMauEntry 1 }

      ifMauIndex OBJECT-TYPE
          SYNTAX      Integer32 (1..2147483647)
          MAX-ACCESS  read-only
          STATUS      current
          DESCRIPTION "This variable uniquely identifies the MAU
                      described by this entry from among other MAUs
                      connected to the same interface (ifMauIfIndex)."
          REFERENCE   "[IEEE 802.3 Std], 30.5.1.1.1, aMAUID."
          ::= { ifMauEntry 2 }

      ifMauType OBJECT-TYPE
          SYNTAX      OBJECT IDENTIFIER
          MAX-ACCESS  read-only
          STATUS      current
          DESCRIPTION "This object identifies the MAU type.  An
                      initial set of MAU types are defined above.  The
                      assignment of OBJECT IDENTIFIERs to new types of


                      MAUs is managed by the IANA.  If the MAU type is
                      unknown, the object identifier

                      unknownMauType OBJECT IDENTIFIER ::= { 0 0 }

                      is returned.  Note that unknownMauType is a
                      syntactically valid object identifier, and any
                      conformant implementation of ASN.1 and the BER
                      must be able to generate and recognize this
                      value.

                      This object represents the operational type of
                      the MAU, as determined by either (1) the result
                      of the auto-negotiation function or (2) if
                      auto-negotiation is not enabled or is not
                      implemented for this MAU, by the value of the
                      object ifMauDefaultType.  In case (2), a set to
                      the object ifMauDefaultType will force the MAU
                      into the new operating mode."
          REFERENCE   "[IEEE 802.3 Std], 30.5.1.1.2, aMAUType."
          ::= { ifMauEntry 3 }

      ifMauStatus OBJECT-TYPE
          SYNTAX      INTEGER {
                          other(1),
                          unknown(2),
                          operational(3),
                          standby(4),
                          shutdown(5),
                          reset(6)
                      }
          MAX-ACCESS  read-write
          STATUS      current
          DESCRIPTION "The current state of the MAU.  This object MAY
                      be implemented as a read-only object by those
                      agents and MAUs that do not implement software
                      control of the MAU state.  Some agents may not
                      support setting the value of this object to some
                      of the enumerated values.

                      The value other(1) is returned if the MAU is in
                      a state other than one of the states 2 through
                      6.

                      The value unknown(2) is returned when the MAU's
                      true state is unknown; for example, when it is
                      being initialized.


                      A MAU in the operational(3) state is fully
                      functional, operates, and passes signals to its
                      attached DTE or repeater port in accordance to
                      its specification.

                      A MAU in standby(4) state forces DI and CI to
                      idle and the media transmitter to idle or fault,
                      if supported.  Standby(4) mode only applies to
                      link type MAUs.  The state of
                      ifMauMediaAvailable is unaffected.

                      A MAU in shutdown(5) state assumes the same
                      condition on DI, CI, and the media transmitter
                      as though it were powered down or not connected.
                      The MAU MAY return other(1) value for the
                      ifMauJabberState and ifMauMediaAvailable objects
                      when it is in this state.  For an AUI, this
                      state will remove power from the AUI.

                      Setting this variable to the value reset(6)
                      resets the MAU in the same manner as a
                      power-off, power-on cycle of at least one-half
                      second would.  The agent is not required to
                      return the value reset (6).

                      Setting this variable to the value
                      operational(3), standby(4), or shutdown(5)
                      causes the MAU to assume the respective state
                      except that setting a mixing-type MAU or an AUI
                      to standby(4) will cause the MAU to enter the
                      shutdown state."
          REFERENCE   "[IEEE 802.3 Std], 30.5.1.1.7, aMAUAdminState,
                      30.5.1.2.2, acMAUAdminControl, and 30.5.1.2.1,
                      acResetMAU."
          ::= { ifMauEntry 4 }
      ifMauMediaAvailable OBJECT-TYPE
          SYNTAX      INTEGER {
                          other(1),
                          unknown(2),
                          available(3),
                          notAvailable(4),
                          remoteFault(5),
                          invalidSignal(6),
                          remoteJabber(7),
                          remoteLinkLoss(8),
                          remoteTest(9),
                          offline(10),
                          autoNegError(11)


                      }
          MAX-ACCESS  read-only
          STATUS      current
          DESCRIPTION "If the MAU is a link or fiber type (FOIRL,
                      10BASE-T, 10BASE-F) then this is equivalent to
                      the link test fail state/low light function.
                      For an AUI or a coax (including broadband) MAU
                      this indicates whether or not loopback is
                      detected on the DI circuit.  The value of this
                      attribute persists between packets for MAU types
                      AUI, 10BASE5, 10BASE2, 10BROAD36, and 10BASE-FP.

                      The value other(1) is returned if the
                      mediaAvailable state is not one of 2 through 11.

                      The value unknown(2) is returned when the MAU's
                      true state is unknown; for example, when it is
                      being initialized.  At power-up or following a
                      reset, the value of this attribute will be
                      unknown for AUI, coax, and 10BASE-FP MAUs.  For
                      these MAUs loopback will be tested on each
                      transmission during which no collision is
                      detected.  If DI is receiving input when DO
                      returns to IDL after a transmission and there
                      has been no collision during the transmission
                      then loopback will be detected.  The value of
                      this attribute will only change during
                      non-collided transmissions for AUI, coax, and
                      10BASE-FP MAUs.

                      For 100Mbps and 1000Mbps MAUs, the enumerations
                      match the states within the respective link
                      integrity state diagrams, fig 32-16, 23-12 and
                      24-15 of sections 32, 23 and 24 of [16].  Any
                      MAU which implements management of
                      auto-negotiation will map remote fault
                      indication to remote fault.

                      The value available(3) indicates that the link,
                      light, or loopback is normal.  The value
                      notAvailable(4) indicates link loss, low light,
                      or no loopback.

                      The value remoteFault(5) indicates that a fault
                      has been detected at the remote end of the link.
                      This value applies to 10BASE-FB, 100BASE-T4 Far
                      End Fault Indication and non-specified remote
                      faults from a system running auto-negotiation.


                      The values remoteJabber(7), remoteLinkLoss(8),
                      and remoteTest(9) SHOULD be used instead of
                      remoteFault(5) where the reason for remote fault
                      is identified in the remote signaling protocol.

                      The value invalidSignal(6) indicates that an
                      invalid signal has been received from the other
                      end of the link.  InvalidSignal(6) applies only
                      to MAUs of type 10BASE-FB.

                      Where an IEEE Std 802.3u-1995 clause 22 MII
                      is present, a logic one in the remote fault bit
                      (reference section 22.2.4.2.8 of that document)
                      maps to the value remoteFault(5), and a logic
                      zero in the link status bit (reference section
                      22.2.4.2.10 of that document) maps to the value
                      notAvailable(4).  The value notAvailable(4)
                      takes precedence over the value remoteFault(5).

                      Any MAU that implements management of clause 37
                      Auto-Negotiation will map the received RF1 and
                      RF2 bit values for Offline to offline(10), Link
                      Failure to remoteFault(5) and Auto-Negotiation
                      Error to autoNegError(11)."
          REFERENCE   "[IEEE 802.3 Std], 30.5.1.1.4, aMediaAvailable."
          ::= { ifMauEntry 5 }

      ifMauMediaAvailableStateExits OBJECT-TYPE
          SYNTAX      Counter32
          MAX-ACCESS  read-only
          STATUS      current
          DESCRIPTION "A count of the number of times that
                      ifMauMediaAvailable for this MAU instance leaves
                      the state available(3).
                      Discontinuities in the value of this counter can
                      occur at re-initialization of the management
                      system, and at other times as indicated by the
                      value of ifCounterDiscontinuityTime."
          REFERENCE   "[IEEE 802.3 Std], 30.5.1.1.5,
                      aLoseMediaCounter.
                      RFC 2233, ifCounterDiscontinuityTime."
          ::= { ifMauEntry 6 }

      ifMauJabberState OBJECT-TYPE
          SYNTAX      INTEGER {
                          other(1),
                          unknown(2),
                          noJabber(3),


                          jabbering(4)
                      }
          MAX-ACCESS  read-only
          STATUS      current
          DESCRIPTION "The value other(1) is returned if the jabber
                      state is not 2, 3, or 4.  The agent MUST always
                      return other(1) for MAU type dot3MauTypeAUI.

                      The value unknown(2) is returned when the MAU's
                      true state is unknown; for example, when it is
                      being initialized.

                      If the MAU is not jabbering the agent returns
                      noJabber(3).  This is the 'normal' state.

                      If the MAU is in jabber state the agent returns
                      the jabbering(4) value."
          REFERENCE   "[IEEE 802.3 Std], 30.5.1.1.6,
                      aJabber.jabberFlag."
          ::= { ifMauEntry 7 }

      ifMauJabberingStateEnters OBJECT-TYPE
          SYNTAX      Counter32
          MAX-ACCESS  read-only
          STATUS      current
          DESCRIPTION "A count of the number of times that
                      mauJabberState for this MAU instance enters the
                      state jabbering(4). This counter will always
                      indicate zero for MAUs of type dot1MauTypeAUI
                      and those of speeds above 10Mbps.

                      Discontinuities in the value of this counter can
                      occur at re-initialization of the management
                      system, and at other times as indicated by the
                      value of ifCounterDiscontinuityTime."
          REFERENCE   "[IEEE 802.3 Std], 30.5.1.1.6,
                      aJabber.jabberCounter.
                      RFC 2233, ifCounterDiscontinuityTime."
          ::= { ifMauEntry 8 }

      ifMauFalseCarriers OBJECT-TYPE
          SYNTAX      Counter32
          MAX-ACCESS  read-only
          STATUS      current
          DESCRIPTION "A count of the number of false carrier events
                      during IDLE in 100BASE-X and 1000BASE-X links.

                      For all other MAU types, this counter will


                      always indicate zero. This counter does not
                      increment at the symbol rate.

                      It can increment after a valid carrier
                      completion at a maximum rate of once per 100 ms
                      for 100BASE-X and once per 10us for 1000BASE-X
                      until the next CarrierEvent.

                      Discontinuities in the value of this counter can
                      occur at re-initialization of the management
                      system, and at other times as indicated by the
                      value of ifCounterDiscontinuityTime."
          REFERENCE   "[IEEE 802.3 Std], 30.5.1.1.10, aFalseCarriers.
                      RFC 2233, ifCounterDiscontinuityTime."
          ::= { ifMauEntry 9 }

      ifMauTypeList OBJECT-TYPE
          SYNTAX      Integer32
          MAX-ACCESS  read-only
          STATUS      deprecated
          DESCRIPTION "********* THIS OBJECT IS DEPRECATED **********

                      A value that uniquely identifies the set of
                      possible IEEE 802.3 types that the MAU could be.
                      The value is a sum which initially takes the
                      value zero.  Then, for each type capability of
                      this MAU, 2 raised to the power noted below is
                      added to the sum. For example, a MAU which has
                      the capability to be only 10BASE-T would have a
                      value of 512 (2**9).  In contrast, a MAU which
                      supports both 10Base-T (full duplex) and
                      100BASE-TX (full duplex) would have a value of
                      ((2**11) + (2**16)) or 67584.

                      The powers of 2 assigned to the capabilities are
                      these:

                      Power  Capability
                        0      other or unknown
                        1      AUI
                        2      10BASE-5
                        3      FOIRL
                        4      10BASE-2
                        5      10BASE-T duplex mode unknown
                        6      10BASE-FP
                        7      10BASE-FB
                        8      10BASE-FL duplex mode unknown
                        9      10BROAD36


                       10      10BASE-T  half duplex mode
                       11      10BASE-T  full duplex mode
                       12      10BASE-FL half duplex mode
                       13      10BASE-FL full duplex mode
                       14      100BASE-T4
                       15      100BASE-TX half duplex mode
                       16      100BASE-TX full duplex mode
                       17      100BASE-FX half duplex mode
                       18      100BASE-FX full duplex mode
                       19      100BASE-T2 half duplex mode
                       20      100BASE-T2 full duplex mode

                      If auto-negotiation is present on this MAU, this
                      object will map to ifMauAutoNegCapability.

                      This object has been deprecated in favour of
                      ifMauTypeListBits."
          ::= { ifMauEntry 10 }

      ifMauDefaultType OBJECT-TYPE
          SYNTAX      OBJECT IDENTIFIER
          MAX-ACCESS  read-write
          STATUS      current
          DESCRIPTION "This object identifies the default
                      administrative baseband MAU type, to be used in
                      conjunction with the operational MAU type
                      denoted by ifMauType.

                      The set of possible values for this object is
                      the same as the set defined for the ifMauType
                      object.

                      This object represents the
                      administratively-configured type of the MAU.  If
                      auto-negotiation is not enabled or is not
                      implemented for this MAU, the value of this
                      object determines the operational type of the
                      MAU.  In this case, a set to this object will
                      force the MAU into the specified operating mode.

                      If auto-negotiation is implemented and enabled
                      for this MAU, the operational type of the MAU
                      is determined by auto-negotiation, and the value
                      of this object denotes the type to which the MAU
                      will automatically revert if/when
                      auto-negotiation is later disabled.

                      NOTE TO IMPLEMENTORS:  It may be necessary to


                      provide for underlying hardware implementations
                      which do not follow the exact behavior specified
                      above.  In particular, when
                      ifMauAutoNegAdminStatus transitions from enabled
                      to disabled, the agent implementation MUST
                      ensure that the operational type of the MAU (as
                      reported by ifMauType) correctly transitions to
                      the value specified by this object, rather than
                      continuing to operate at the value earlier
                      determined by the auto-negotiation function."
          REFERENCE   "[IEEE 802.3 Std], 30.5.1.1.1, aMAUID, and
                      22.2.4.1.4."
          ::= { ifMauEntry 11 }

      ifMauAutoNegSupported OBJECT-TYPE
          SYNTAX      TruthValue
          MAX-ACCESS  read-only
          STATUS      current
          DESCRIPTION "This object indicates whether or not
                      auto-negotiation is supported on this MAU."
          ::= { ifMauEntry 12 }

      ifMauTypeListBits OBJECT-TYPE
          SYNTAX      BITS {
              bOther(0),         -- other or unknown
              bAUI(1),           -- AUI
              b10base5(2),       -- 10BASE-5
              bFoirl(3),         -- FOIRL

              b10base2(4),       -- 10BASE-2
              b10baseT(5),       -- 10BASE-T duplex mode unknown
              b10baseFP(6),      -- 10BASE-FP
              b10baseFB(7),      -- 10BASE-FB
              b10baseFL(8),      -- 10BASE-FL duplex mode unknown
              b10broad36(9),     -- 10BROAD36
              b10baseTHD(10),    -- 10BASE-T  half duplex mode
              b10baseTFD(11),    -- 10BASE-T  full duplex mode
              b10baseFLHD(12),   -- 10BASE-FL half duplex mode
              b10baseFLFD(13),   -- 10BASE-FL full duplex mode

              b100baseT4(14),    -- 100BASE-T4
              b100baseTXHD(15),  -- 100BASE-TX half duplex mode
              b100baseTXFD(16),  -- 100BASE-TX full duplex mode
              b100baseFXHD(17),  -- 100BASE-FX half duplex mode
              b100baseFXFD(18),  -- 100BASE-FX full duplex mode
              b100baseT2HD(19),  -- 100BASE-T2 half duplex mode
              b100baseT2FD(20),  -- 100BASE-T2 full duplex mode


              b1000baseXHD(21),  -- 1000BASE-X half duplex mode
              b1000baseXFD(22),  -- 1000BASE-X full duplex mode
              b1000baseLXHD(23), -- 1000BASE-LX half duplex mode
              b1000baseLXFD(24), -- 1000BASE-LX full duplex mode
              b1000baseSXHD(25), -- 1000BASE-SX half duplex mode
              b1000baseSXFD(26), -- 1000BASE-SX full duplex mode
              b1000baseCXHD(27), -- 1000BASE-CX half duplex mode
              b1000baseCXFD(28), -- 1000BASE-CX full duplex mode
              b1000baseTHD(29),  -- 1000BASE-T half duplex mode
              b1000baseTFD(30)   -- 1000BASE-T full duplex mode
          }
          MAX-ACCESS  read-only
          STATUS      current
          DESCRIPTION "A value that uniquely identifies the set of
                      possible IEEE 802.3 types that the MAU could be.
                      If auto-negotiation is present on this MAU, this
                      object will map to ifMauAutoNegCapability.

                      Note that this MAU may be capable of operating
                      as a MAU type that is beyond the scope of this
                      MIB.  This is indicated by returning the
                      bit value bOther in addition to any bit values
                      for capabilities that are listed above."
          ::= { ifMauEntry 13 }

      -- The ifJackTable applies to MAUs attached to interfaces
      -- which have one or more external jacks (connectors).

      ifJackTable OBJECT-TYPE
          SYNTAX      SEQUENCE OF IfJackEntry
          MAX-ACCESS  not-accessible
          STATUS      current
          DESCRIPTION "Information about the external jacks attached
                      to MAUs attached to an interface."
          ::= { dot3IfMauBasicGroup 2 }

      ifJackEntry OBJECT-TYPE
          SYNTAX      IfJackEntry
          MAX-ACCESS  not-accessible
          STATUS      current
          DESCRIPTION "An entry in the table, containing information
                      about a particular jack."
          INDEX       { ifMauIfIndex,
                        ifMauIndex,
                        ifJackIndex
                      }
          ::= { ifJackTable 1 }


      IfJackEntry ::=
          SEQUENCE {
              ifJackIndex                         Integer32,
              ifJackType                          JackType
          }

      ifJackIndex OBJECT-TYPE
          SYNTAX      Integer32 (1..2147483647)
          MAX-ACCESS  not-accessible
          STATUS      current
          DESCRIPTION "This variable uniquely identifies the jack
                      described by this entry from among other jacks
                      attached to the same MAU."
          ::= { ifJackEntry 1 }

      ifJackType OBJECT-TYPE
          SYNTAX      JackType
          MAX-ACCESS  read-only
          STATUS      current
          DESCRIPTION "The jack connector type, as it appears on the
                      outside of the system."
          ::= { ifJackEntry 2 }

      -- The ifMauAutoNegTable applies to systems in which
      -- auto-negotiation is supported on one or more MAUs
      -- attached to interfaces.  Note that if auto-negotiation
      -- is present and enabled, the ifMauType object reflects
      -- the result of the auto-negotiation function.

      ifMauAutoNegTable OBJECT-TYPE
          SYNTAX      SEQUENCE OF IfMauAutoNegEntry
          MAX-ACCESS  not-accessible
          STATUS      current
          DESCRIPTION "Configuration and status objects for the
                      auto-negotiation function of MAUs attached to
                      interfaces."
          ::= { dot3IfMauAutoNegGroup 1 }

      ifMauAutoNegEntry OBJECT-TYPE
          SYNTAX      IfMauAutoNegEntry
          MAX-ACCESS  not-accessible
          STATUS      current
          DESCRIPTION "An entry in the table, containing configuration
                      and status information for the auto-negotiation
                      function of a particular MAU."
          INDEX       { ifMauIfIndex,
                        ifMauIndex
                      }


          ::= { ifMauAutoNegTable 1 }

      IfMauAutoNegEntry ::=
          SEQUENCE {
              ifMauAutoNegAdminStatus             INTEGER,
              ifMauAutoNegRemoteSignaling         INTEGER,
              ifMauAutoNegConfig                  INTEGER,
              ifMauAutoNegCapability              Integer32,
              ifMauAutoNegCapAdvertised           Integer32,
              ifMauAutoNegCapReceived             Integer32,
              ifMauAutoNegRestart                 INTEGER,
              ifMauAutoNegCapabilityBits          BITS,
              ifMauAutoNegCapAdvertisedBits       BITS,
              ifMauAutoNegCapReceivedBits         BITS,
              ifMauAutoNegRemoteFaultAdvertised   INTEGER,
              ifMauAutoNegRemoteFaultReceived     INTEGER
          }

      ifMauAutoNegAdminStatus OBJECT-TYPE
          SYNTAX      INTEGER {
                          enabled(1),
                          disabled(2)
                      }
          MAX-ACCESS  read-write
          STATUS      current
          DESCRIPTION "Setting this object to enabled(1) will cause
                      the interface which has the auto-negotiation
                      signaling ability to be enabled.

                      If the value of this object is disabled(2) then
                      the interface will act as it would if it had no
                      auto-negotiation signaling.  Under these
                      conditions, an IEEE 802.3 MAU will immediately
                      be forced to the state indicated by the value of
                      the object ifMauDefaultType.

                      NOTE TO IMPLEMENTORS:  When
                      ifMauAutoNegAdminStatus transitions from enabled
                      to disabled, the agent implementation MUST
                      ensure that the operational type of the MAU (as
                      reported by ifMauType) correctly transitions to
                      the value specified by the ifMauDefaultType
                      object, rather than continuing to operate at the
                      value earlier determined by the auto-negotiation
                      function."
          REFERENCE   "[IEEE 802.3 Std], 30.6.1.1.2,
                      aAutoNegAdminState and 30.6.1.2.2,
                      acAutoNegAdminControl."


          ::= { ifMauAutoNegEntry 1 }

      ifMauAutoNegRemoteSignaling OBJECT-TYPE
          SYNTAX      INTEGER {
                          detected(1),
                          notdetected(2)
                      }
          MAX-ACCESS  read-only
          STATUS      current
          DESCRIPTION "A value indicating whether the remote end of
                      the link is using auto-negotiation signaling. It
                      takes the value detected(1) if and only if,
                      during the previous link negotiation, FLP Bursts
                      were received."
          REFERENCE   "[IEEE 802.3 Std], 30.6.1.1.3,
                      aAutoNegRemoteSignaling."
          ::= { ifMauAutoNegEntry 2 }

      ifMauAutoNegConfig OBJECT-TYPE
          SYNTAX      INTEGER {
                          other(1),
                          configuring(2),
                          complete(3),
                          disabled(4),
                          parallelDetectFail(5)
                      }
          MAX-ACCESS  read-only
          STATUS      current
          DESCRIPTION "A value indicating the current status of the
                      auto-negotiation process.  The enumeration
                      parallelDetectFail(5) maps to a failure in
                      parallel detection as defined in 28.2.3.1 of
                      [IEEE 802.3 Std]."
          REFERENCE   "[IEEE 802.3 Std], 30.6.1.1.4,
                      aAutoNegAutoConfig."
          ::= { ifMauAutoNegEntry 4 }

      ifMauAutoNegCapability OBJECT-TYPE
          SYNTAX      Integer32
          MAX-ACCESS  read-only
          STATUS      deprecated
          DESCRIPTION "********* THIS OBJECT IS DEPRECATED **********

                      A value that uniquely identifies the set of
                      capabilities of the local auto-negotiation
                      entity.  The value is a sum which initially
                      takes the value zero.  Then, for each capability
                      of this interface, 2 raised to the power noted


                      below is added to the sum. For example, an
                      interface which has the capability to support
                      only 100Base-TX half duplex would have a value
                      of 32768 (2**15).  In contrast, an interface
                      which supports both 100Base-TX half duplex and
                      and 100Base-TX full duplex would have a value of
                      98304 ((2**15) + (2**16)).

                      The powers of 2 assigned to the capabilities are
                      these:

                      Power   Capability
                        0       other or unknown
                       (1-9)    (reserved)
                       10       10BASE-T  half duplex mode
                       11       10BASE-T  full duplex mode
                       12       (reserved)
                       13       (reserved)
                       14       100BASE-T4
                       15       100BASE-TX half duplex mode
                       16       100BASE-TX full duplex mode
                       17       (reserved)
                       18       (reserved)
                       19      100BASE-T2 half duplex mode
                       20      100BASE-T2 full duplex mode

                      Note that interfaces that support this MIB may
                      have capabilities that extend beyond the scope
                      of this MIB.
                      This object has been deprecated in favour of
                      ifMauAutoNegCapabilityBits"
          REFERENCE   "[IEEE 802.3 Std], 30.6.1.1.5,
                      aAutoNegLocalTechnologyAbility."
          ::= { ifMauAutoNegEntry 5 }

      ifMauAutoNegCapAdvertised OBJECT-TYPE
          SYNTAX      Integer32
          MAX-ACCESS  read-write
          STATUS      deprecated
          DESCRIPTION "********* THIS OBJECT IS DEPRECATED **********

                      A value that uniquely identifies the set of
                      capabilities advertised by the local
                      auto-negotiation entity. Refer to
                      ifMauAutoNegCapability for a description of the
                      possible values of this object.

                      Capabilities in this object that are not


                      available in ifMauAutoNegCapability cannot be
                      enabled.

                      This object has been deprecated in favour of
                      ifMauAutoNegCapAdvertisedBits"
          REFERENCE   "[IEEE 802.3 Std], 30.6.1.1.6,
                      aAutoNegAdvertisedTechnologyAbility."
          ::= { ifMauAutoNegEntry 6 }

      ifMauAutoNegCapReceived OBJECT-TYPE
          SYNTAX      Integer32
          MAX-ACCESS  read-only
          STATUS      deprecated
          DESCRIPTION "********* THIS OBJECT IS DEPRECATED **********

                      A value that uniquely identifies the set of
                      capabilities received from the remote
                      auto-negotiation entity. Refer to
                      ifMauAutoNegCapability for a description of the
                      possible values of this object.

                      Note that interfaces that support this MIB may
                      be attached to remote auto-negotiation entities
                      which have capabilities beyond the scope of this
                      MIB.

                      This object has been deprecated in favour of
                      ifMauAutoNegCapReceivedBits"
          REFERENCE   "[IEEE 802.3 Std], 30.6.1.1.7,
                      aAutoNegReceivedTechnologyAbility."
          ::= { ifMauAutoNegEntry 7 }

      ifMauAutoNegRestart OBJECT-TYPE
          SYNTAX      INTEGER {
                          restart(1),
                          norestart(2)
                      }
          MAX-ACCESS  read-write
          STATUS      current
          DESCRIPTION "If the value of this object is set to
                      restart(1) then this will force auto-negotiation
                      to begin link renegotiation. If auto-negotiation
                      signaling is disabled, a write to this object
                      has no effect.

                      Setting the value of this object to norestart(2)
                      has no effect."
          REFERENCE   "[IEEE 802.3 Std], 30.6.1.2.1,


                      acAutoNegRestartAutoConfig."
          ::= { ifMauAutoNegEntry 8 }

      ifMauAutoNegCapabilityBits OBJECT-TYPE
          SYNTAX      BITS {
              bOther(0),        -- other or unknown
              b10baseT(1),      -- 10BASE-T  half duplex mode
              b10baseTFD(2),    -- 10BASE-T  full duplex mode
              b100baseT4(3),    -- 100BASE-T4
              b100baseTX(4),    -- 100BASE-TX half duplex mode
              b100baseTXFD(5),  -- 100BASE-TX full duplex mode
              b100baseT2(6),    -- 100BASE-T2 half duplex mode
              b100baseT2FD(7),  -- 100BASE-T2 full duplex mode
              bfdxPause(8),     -- PAUSE for full-duplex links
              bfdxAPause(9),    -- Asymmetric PAUSE for full-duplex
                                --     links
              bfdxSPause(10),   -- Symmetric PAUSE for full-duplex
                                --     links
              bfdxBPause(11),   -- Asymmetric and Symmetric PAUSE for
                                --     full-duplex links
              b1000baseX(12),   -- 1000BASE-X, -LX, -SX, -CX half
                                --     duplex mode
              b1000baseXFD(13), -- 1000BASE-X, -LX, -SX, -CX full
                                --     duplex mode
              b1000baseT(14),   -- 1000BASE-T half duplex mode
              b1000baseTFD(15)  -- 1000BASE-T full duplex mode
          }
          MAX-ACCESS  read-only
          STATUS      current
          DESCRIPTION "A value that uniquely identifies the set of
                      capabilities of the local auto-negotiation
                      entity.  Note that interfaces that support this
                      MIB may have capabilities that extend beyond the
                      scope of this MIB.

                      Note that the local auto-negotiation entity may
                      support some capabilities beyond the scope of
                      this MIB.  This is indicated by returning the
                      bit value bOther in addition to any bit values
                      for capabilities that are listed above."
          REFERENCE   "[IEEE 802.3 Std], 30.6.1.1.5,
                      aAutoNegLocalTechnologyAbility."
          ::= { ifMauAutoNegEntry 9 }

      ifMauAutoNegCapAdvertisedBits OBJECT-TYPE
          SYNTAX      BITS {
              bOther(0),        -- other or unknown
              b10baseT(1),      -- 10BASE-T  half duplex mode


              b10baseTFD(2),    -- 10BASE-T  full duplex mode
              b100baseT4(3),    -- 100BASE-T4
              b100baseTX(4),    -- 100BASE-TX half duplex mode
              b100baseTXFD(5),  -- 100BASE-TX full duplex mode
              b100baseT2(6),    -- 100BASE-T2 half duplex mode
              b100baseT2FD(7),  -- 100BASE-T2 full duplex mode
              bFdxPause(8),     -- PAUSE for full-duplex links
              bFdxAPause(9),    -- Asymmetric PAUSE for full-duplex
                                --     links
              bFdxSPause(10),   -- Symmetric PAUSE for full-duplex
                                --     links
              bFdxBPause(11),   -- Asymmetric and Symmetric PAUSE for
                                --     full-duplex links
              b1000baseX(12),   -- 1000BASE-X, -LX, -SX, -CX half
                                --     duplex mode
              b1000baseXFD(13), -- 1000BASE-X, -LX, -SX, -CX full
                                --     duplex mode
              b1000baseT(14),   -- 1000BASE-T half duplex mode
              b1000baseTFD(15)  -- 1000BASE-T full duplex mode
          }
          MAX-ACCESS  read-write
          STATUS      current
          DESCRIPTION "A value that uniquely identifies the set of
                      capabilities advertised by the local
                      auto-negotiation entity.

                      Capabilities in this object that are not
                      available in ifMauAutoNegCapabilityBits cannot
                      be enabled.
                      Note that the local auto-negotiation entity may
                      advertise some capabilities beyond the scope of
                      this MIB.  This is indicated by returning the
                      bit value bOther in addition to any bit values
                      for capabilities that are listed above."
          REFERENCE   "[IEEE 802.3 Std], 30.6.1.1.6,
                      aAutoNegAdvertisedTechnologyAbility."
          ::= { ifMauAutoNegEntry 10 }

      ifMauAutoNegCapReceivedBits OBJECT-TYPE
          SYNTAX      BITS {
               bOther(0),        -- other or unknown
               b10baseT(1),      -- 10BASE-T  half duplex mode
               b10baseTFD(2),    -- 10BASE-T  full duplex mode
               b100baseT4(3),    -- 100BASE-T4
               b100baseTX(4),    -- 100BASE-TX half duplex mode
               b100baseTXFD(5),  -- 100BASE-TX full duplex mode
               b100baseT2(6),    -- 100BASE-T2 half duplex mode
               b100baseT2FD(7),  -- 100BASE-T2 full duplex mode


               bFdxPause(8),     -- PAUSE for full-duplex links
               bFdxAPause(9),    -- Asymmetric PAUSE for full-duplex
                                 --     links
               bFdxSPause(10),   -- Symmetric PAUSE for full-duplex
                                 --     links
               bFdxBPause(11),   -- Asymmetric and Symmetric PAUSE for
                                 --     full-duplex links
               b1000baseX(12),   -- 1000BASE-X, -LX, -SX, -CX half
                                 --     duplex mode
               b1000baseXFD(13), -- 1000BASE-X, -LX, -SX, -CX full
                                 --     duplex mode
               b1000baseT(14),   -- 1000BASE-T half duplex mode
               b1000baseTFD(15)  -- 1000BASE-T full duplex mode
          }
          MAX-ACCESS  read-only
          STATUS      current
          DESCRIPTION "A value that uniquely identifies the set of
                      capabilities received from the remote
                      auto-negotiation entity.

                      Note that interfaces that support this MIB may
                      be attached to remote auto-negotiation entities
                      which have capabilities beyond the scope of this
                      MIB.  This is indicated by returning the bit
                      value bOther in addition to any bit values for
                      capabilities that are listed above."
          REFERENCE   "[IEEE 802.3 Std], 30.6.1.1.7,
                      aAutoNegReceivedTechnologyAbility."
          ::= { ifMauAutoNegEntry 11 }
      ifMauAutoNegRemoteFaultAdvertised OBJECT-TYPE
          SYNTAX      INTEGER {
                          noError(1),
                          offline(2),
                          linkFailure(3),
                          autoNegError(4)
                      }
          MAX-ACCESS  read-write
          STATUS      current
          DESCRIPTION "A value that identifies any local fault
                      indications that this MAU has detected and will
                      advertise at the next auto-negotiation
                      interaction for 1000Mbps MAUs."
          REFERENCE   "[IEEE 802.3 Std], 30.6.1.1.6,
                      aAutoNegAdvertisedTechnologyAbility."
          ::= { ifMauAutoNegEntry 12 }

      ifMauAutoNegRemoteFaultReceived OBJECT-TYPE
          SYNTAX      INTEGER {


                          noError(1),
                          offline(2),
                          linkFailure(3),
                          autoNegError(4)
                      }
          MAX-ACCESS  read-only
          STATUS      current
          DESCRIPTION "A value that identifies any fault indications
                      received from the far end of a link by the
                      local auto-negotiation entity for 1000Mbps
                      MAUs."
          REFERENCE   "[IEEE 802.3 Std], 30.6.1.1.7,
                      aAutoNegReceivedTechnologyAbility."
          ::= { ifMauAutoNegEntry 13 }

      --
      -- The Basic Broadband MAU Table
      --

      broadMauBasicTable OBJECT-TYPE
          SYNTAX      SEQUENCE OF BroadMauBasicEntry
          MAX-ACCESS  not-accessible
          STATUS      deprecated
          DESCRIPTION "********* THIS OBJECT IS DEPRECATED **********

                      Table of descriptive and status information
                      about the broadband MAUs connected to
                      interfaces."
          ::= { dot3BroadMauBasicGroup 1 }

      broadMauBasicEntry OBJECT-TYPE
          SYNTAX      BroadMauBasicEntry
          MAX-ACCESS  not-accessible
          STATUS      deprecated
          DESCRIPTION "********* THIS OBJECT IS DEPRECATED **********

                      An entry in the table, containing information
                      about a single broadband MAU."
          INDEX       { broadMauIfIndex,
                        broadMauIndex
                      }
          ::= { broadMauBasicTable 1 }

      BroadMauBasicEntry ::=
          SEQUENCE {
              broadMauIfIndex                     Integer32,
              broadMauIndex                       Integer32,
              broadMauXmtRcvSplitType             INTEGER,


              broadMauXmtCarrierFreq              Integer32,
              broadMauTranslationFreq             Integer32
          }

      broadMauIfIndex OBJECT-TYPE
          SYNTAX      Integer32 (1..2147483647)
          MAX-ACCESS  read-only
          STATUS      deprecated
          DESCRIPTION "********* THIS OBJECT IS DEPRECATED **********

                      This variable uniquely identifies the interface
                      to which the MAU described by this entry is
                      connected."
          REFERENCE   "Reference RFC 1213, ifIndex."
          ::= { broadMauBasicEntry 1 }

      broadMauIndex OBJECT-TYPE
          SYNTAX      Integer32 (1..2147483647)
          MAX-ACCESS  read-only
          STATUS      deprecated
          DESCRIPTION "********* THIS OBJECT IS DEPRECATED **********

                      This variable uniquely identifies the MAU
                      connected to interface broadMauIfIndex that is
                      described by this entry."
          REFERENCE   "[IEEE 802.3 Std], 30.5.1.1.1, aMAUID."
          ::= { broadMauBasicEntry 2 }

      broadMauXmtRcvSplitType OBJECT-TYPE
          SYNTAX      INTEGER {
                          other(1),
                          single(2),
                          dual(3)
                      }
          MAX-ACCESS  read-only
          STATUS      deprecated
          DESCRIPTION "********* THIS OBJECT IS DEPRECATED **********

                      This object indicates the type of frequency
                      multiplexing/cabling system used to separate the
                      transmit and receive paths for the 10BROAD36
                      MAU.

                      The value other(1) is returned if the split type
                      is not either single or dual.

                      The value single(2) indicates a single cable
                      system.  The value dual(3) indicates a dual


                      cable system, offset normally zero."
          REFERENCE   "[IEEE 802.3 Std], 30.5.1.1.8,
                      aBbMAUXmitRcvSplitType."
          ::= { broadMauBasicEntry 3 }

      broadMauXmtCarrierFreq OBJECT-TYPE
          SYNTAX      Integer32
          MAX-ACCESS  read-only
          STATUS      deprecated
          DESCRIPTION "********* THIS OBJECT IS DEPRECATED **********

                      This variable indicates the transmit carrier
                      frequency of the 10BROAD36 MAU in MHz/4; that
                      is, in units of 250 kHz."
          REFERENCE   "[IEEE 802.3 Std], 30.5.1.1.9,
                      aBroadbandFrequencies.xmitCarrierFrequency."
          ::= { broadMauBasicEntry 4 }

      broadMauTranslationFreq OBJECT-TYPE
          SYNTAX      Integer32
          MAX-ACCESS  read-only
          STATUS      deprecated
          DESCRIPTION "********* THIS OBJECT IS DEPRECATED **********

                      This variable indicates the translation offset
                      frequency of the 10BROAD36 MAU in MHz/4; that
                      is, in units of 250 kHz."
          REFERENCE   "[IEEE 802.3 Std], 30.5.1.1.9,
                      aBroadbandFrequencies.translationFrequency."
          ::= { broadMauBasicEntry 5 }

      -- Notifications for use by 802.3 MAUs

      snmpDot3MauTraps OBJECT IDENTIFIER ::= { snmpDot3MauMgt 0 }

      rpMauJabberTrap NOTIFICATION-TYPE
          OBJECTS     { rpMauJabberState }
          STATUS      current
          DESCRIPTION "This trap is sent whenever a managed repeater
                      MAU enters the jabber state.

                      The agent MUST throttle the generation of
                      consecutive rpMauJabberTraps so that there is at
                      least a five-second gap between them."
          REFERENCE   "[IEEE 802.3 Mgt], 30.5.1.3.1, nJabber
                      notification."
          ::= { snmpDot3MauTraps 1 }


      ifMauJabberTrap NOTIFICATION-TYPE
          OBJECTS     { ifMauJabberState }
          STATUS      current
          DESCRIPTION "This trap is sent whenever a managed interface
                      MAU enters the jabber state.

                      The agent MUST throttle the generation of
                      consecutive ifMauJabberTraps so that there is at
                      least a five-second gap between them."
          REFERENCE   "[IEEE 802.3 Mgt], 30.5.1.3.1, nJabber
                      notification."
          ::= { snmpDot3MauTraps 2 }

      -- Conformance information

      mauModConf
              OBJECT IDENTIFIER ::= { mauMod 1 }
        mauModCompls
              OBJECT IDENTIFIER ::= { mauModConf 1 }
        mauModObjGrps
              OBJECT IDENTIFIER ::= { mauModConf 2 }
        mauModNotGrps
              OBJECT IDENTIFIER ::= { mauModConf 3 }
      -- Object groups

      mauRpGrpBasic OBJECT-GROUP
          OBJECTS     { rpMauGroupIndex,
                        rpMauPortIndex,
                        rpMauIndex,
                        rpMauType,
                        rpMauStatus,
                        rpMauMediaAvailable,
                        rpMauMediaAvailableStateExits,
                        rpMauJabberState,
                        rpMauJabberingStateEnters
                      }
          STATUS      current
          DESCRIPTION "Basic conformance group for MAUs attached to
                      repeater ports.  This group is also the
                      conformance specification for RFC 1515
                      implementations."
          ::= { mauModObjGrps 1 }

      mauRpGrp100Mbs OBJECT-GROUP
          OBJECTS     { rpMauFalseCarriers }
          STATUS      current
          DESCRIPTION "Conformance group for MAUs attached to
                      repeater ports with 100 Mb/s or greater


                      capability."
          ::= { mauModObjGrps 2 }

      mauRpGrpJack OBJECT-GROUP
          OBJECTS     { rpJackType }
          STATUS      current
          DESCRIPTION "Conformance group for MAUs attached to
                      repeater ports with managed jacks."
          ::= { mauModObjGrps 3 }

      mauIfGrpBasic OBJECT-GROUP
          OBJECTS     { ifMauIfIndex,
                        ifMauIndex,
                        ifMauType,
                        ifMauStatus,
                        ifMauMediaAvailable,
                        ifMauMediaAvailableStateExits,
                        ifMauJabberState,
                        ifMauJabberingStateEnters
                      }
          STATUS      current
          DESCRIPTION "Basic conformance group for MAUs attached to
                      interfaces.  This group also provides a
                      conformance specification for RFC 1515
                      implementations."
          ::= { mauModObjGrps 4 }

      mauIfGrp100Mbs OBJECT-GROUP
          OBJECTS     { ifMauFalseCarriers,
                        ifMauTypeList,
                        ifMauDefaultType,
                        ifMauAutoNegSupported
                      }
          STATUS      deprecated
          DESCRIPTION "********* THIS GROUP IS DEPRECATED **********

                      Conformance group for MAUs attached to
                      interfaces with 100 Mb/s capability.

                      This object group has been deprecated in favor
                      of mauIfGrpHighCapacity."
          ::= { mauModObjGrps 5 }

      mauIfGrpJack OBJECT-GROUP
          OBJECTS     { ifJackType }
          STATUS      current
          DESCRIPTION "Conformance group for MAUs attached to
                      interfaces with managed jacks."


          ::= { mauModObjGrps 6 }

      mauIfGrpAutoNeg OBJECT-GROUP
          OBJECTS     { ifMauAutoNegAdminStatus,
                        ifMauAutoNegRemoteSignaling,
                        ifMauAutoNegConfig,
                        ifMauAutoNegCapability,
                        ifMauAutoNegCapAdvertised,
                        ifMauAutoNegCapReceived,
                        ifMauAutoNegRestart
                      }
          STATUS      deprecated
          DESCRIPTION "********* THIS GROUP IS DEPRECATED **********

                      Conformance group for MAUs attached to
                      interfaces with managed auto-negotiation.

                      This object group has been deprecated in favor
                      of mauIfGrpAutoNeg2."
          ::= { mauModObjGrps 7 }

      mauBroadBasic OBJECT-GROUP
          OBJECTS     { broadMauIfIndex,
                        broadMauIndex,
                        broadMauXmtRcvSplitType,
                        broadMauXmtCarrierFreq,
                        broadMauTranslationFreq
                      }
          STATUS      deprecated
          DESCRIPTION "********* THIS GROUP IS DEPRECATED **********

                      Conformance group for broadband MAUs attached
                      to interfaces.

                      This object group is deprecated.  There have
                      been no reported implementations of this group,
                      and it was felt to be unlikely that there will
                      be any future implementations."
          ::= { mauModObjGrps 8 }

      mauIfGrpHighCapacity OBJECT-GROUP
          OBJECTS     { ifMauFalseCarriers,
                        ifMauTypeListBits,
                        ifMauDefaultType,
                        ifMauAutoNegSupported
                      }
          STATUS      current
          DESCRIPTION "Conformance group for MAUs attached to


                      interfaces with 100 Mb/s or greater capability."
          ::= { mauModObjGrps 9 }

      mauIfGrpAutoNeg2 OBJECT-GROUP
          OBJECTS     { ifMauAutoNegAdminStatus,
                        ifMauAutoNegRemoteSignaling,
                        ifMauAutoNegConfig,
                        ifMauAutoNegCapabilityBits,
                        ifMauAutoNegCapAdvertisedBits,
                        ifMauAutoNegCapReceivedBits,
                        ifMauAutoNegRestart
                      }
          STATUS      current
          DESCRIPTION "Conformance group for MAUs attached to
                      interfaces with managed auto-negotiation."
          ::= { mauModObjGrps 10 }

      mauIfGrpAutoNeg1000Mbps OBJECT-GROUP
          OBJECTS     { ifMauAutoNegRemoteFaultAdvertised,
                        ifMauAutoNegRemoteFaultReceived
                      }
          STATUS      current
          DESCRIPTION "Conformance group for 1000Mbps MAUs attached to
                      interfaces with managed auto-negotiation."
          ::= { mauModObjGrps 11 }

      -- Notification groups

      rpMauNotifications NOTIFICATION-GROUP
          NOTIFICATIONS { rpMauJabberTrap }
          STATUS      current
          DESCRIPTION "Notifications for repeater MAUs."
          ::= { mauModNotGrps 1 }

      ifMauNotifications NOTIFICATION-GROUP
          NOTIFICATIONS { ifMauJabberTrap }
          STATUS      current
          DESCRIPTION "Notifications for interface MAUs."
          ::= { mauModNotGrps 2 }

      -- Compliances

      mauModRpCompl MODULE-COMPLIANCE
          STATUS      deprecated
          DESCRIPTION "******** THIS COMPLIANCE IS DEPRECATED ********

                      Compliance for MAUs attached to repeater
                      ports.


                      This compliance is deprecated and replaced by
                      mauModRpCompl2, which corrects an oversight by
                      allowing rpMauStatus to be implemented
                      read-only."

          MODULE -- this module
              MANDATORY-GROUPS { mauRpGrpBasic }

              GROUP       mauRpGrp100Mbs
              DESCRIPTION "Implementation of this optional group is
                          recommended for MAUs which have 100Mb/s or
                          greater capability."

              GROUP       mauRpGrpJack
              DESCRIPTION "Implementation of this optional group is
                          recommended for MAUs which have one or more
                          external jacks."

              GROUP       rpMauNotifications
              DESCRIPTION "Implementation of this group is recommended
                          for MAUs attached to repeater ports."
          ::= { mauModCompls 1 }

      mauModIfCompl MODULE-COMPLIANCE
          STATUS      deprecated
          DESCRIPTION "******** THIS COMPLIANCE IS DEPRECATED ********

                      Compliance for MAUs attached to interfaces.

                      This compliance is deprecated and replaced by
                      mauModIfCompl2."

          MODULE -- this module
              MANDATORY-GROUPS { mauIfGrpBasic }

              GROUP       mauIfGrp100Mbs
              DESCRIPTION "Implementation of this optional group is
                          recommended for MAUs which have 100Mb/s
                          capability."

              GROUP       mauIfGrpJack
              DESCRIPTION "Implementation of this optional group is
                          recommended for MAUs which have one or more
                          external jacks."

              GROUP       mauIfGrpAutoNeg
              DESCRIPTION "Implementation of this group is mandatory
                          for MAUs which support managed


                          auto-negotiation."

              GROUP       mauBroadBasic
              DESCRIPTION "Implementation of this group is mandatory
                          for broadband MAUs."

              GROUP       ifMauNotifications
              DESCRIPTION "Implementation of this group is recommended
                          for MAUs attached to interfaces."
          ::= { mauModCompls 2 }

      mauModIfCompl2 MODULE-COMPLIANCE
          STATUS      current
          DESCRIPTION "Compliance for MAUs attached to interfaces."

          MODULE -- this module
              MANDATORY-GROUPS { mauIfGrpBasic }

              GROUP       mauIfGrpHighCapacity
              DESCRIPTION "Implementation of this optional group is
                          recommended for MAUs which have 100Mb/s
                          or greater capability."

              GROUP       mauIfGrpJack
              DESCRIPTION "Implementation of this optional group is
                          recommended for MAUs which have one or more
                          external jacks."

              GROUP       mauIfGrpAutoNeg2
              DESCRIPTION "Implementation of this group is mandatory
                          for MAUs which support managed
                          auto-negotiation."

              GROUP       mauIfGrpAutoNeg1000Mbps
              DESCRIPTION "Implementation of this group is mandatory
                          for MAUs which have 1000Mb/s or greater
                          capability and support managed
                          auto-negotiation."

              GROUP       ifMauNotifications
              DESCRIPTION "Implementation of this group is recommended
                          for MAUs attached to interfaces."

              OBJECT      ifMauStatus
              MIN-ACCESS  read-only
              DESCRIPTION "Write access is not required."
          ::= { mauModCompls 3 }


      mauModRpCompl2 MODULE-COMPLIANCE
          STATUS      current
          DESCRIPTION "Compliance for MAUs attached to repeater
                      ports."

          MODULE -- this module
              MANDATORY-GROUPS { mauRpGrpBasic }

              GROUP       mauRpGrp100Mbs
              DESCRIPTION "Implementation of this optional group is
                          recommended for MAUs which have 100Mb/s or
                          greater capability."

              GROUP       mauRpGrpJack
              DESCRIPTION "Implementation of this optional group is
                          recommended for MAUs which have one or more
                          external jacks."

              GROUP       rpMauNotifications
              DESCRIPTION "Implementation of this group is recommended
                          for MAUs attached to repeater ports."

              OBJECT      rpMauStatus
              MIN-ACCESS  read-only
              DESCRIPTION "Write access is not required."
          ::= { mauModCompls 4 }

END

ENTITY-MIB DEFINITIONS ::= BEGIN

IMPORTS
    MODULE-IDENTITY, OBJECT-TYPE, mib-2, NOTIFICATION-TYPE
        FROM SNMPv2-SMI
    TDomain, TAddress, TEXTUAL-CONVENTION,
    AutonomousType, RowPointer, TimeStamp, TruthValue
        FROM SNMPv2-TC
    MODULE-COMPLIANCE, OBJECT-GROUP, NOTIFICATION-GROUP
        FROM SNMPv2-CONF
    SnmpAdminString
        FROM SNMP-FRAMEWORK-MIB;

entityMIB MODULE-IDENTITY
    LAST-UPDATED "9912070000Z" -- December 7, 1999
    ORGANIZATION "IETF ENTMIB Working Group"
    CONTACT-INFO
            "        WG E-mail: entmib@cisco.com
                  Subscribe: majordomo@cisco.com
                         msg body: subscribe entmib

                     Keith McCloghrie
                     ENTMIB Working Group Chair
                     Cisco Systems Inc.
                     170 West Tasman Drive
                     San Jose, CA 95134
                     +1 408-526-5260
                     kzm@cisco.com

                     Andy Bierman
                     ENTMIB Working Group Editor
                     Cisco Systems Inc.
                     170 West Tasman Drive
                     San Jose, CA 95134
                     +1 408-527-3711
                     abierman@cisco.com"
    DESCRIPTION
            "The MIB module for representing multiple logical
            entities supported by a single SNMP agent."
    REVISION        "9912070000Z"
    DESCRIPTION
            "Initial Version of Entity MIB (Version 2).
             This revision obsoletes RFC 2037.
             This version published as RFC 2737."
    REVISION        "9610310000Z"
    DESCRIPTION


            "Initial version (version 1), published as
             RFC 2037."
    ::= { mib-2 47 }

entityMIBObjects OBJECT IDENTIFIER ::= { entityMIB 1 }

-- MIB contains four groups
entityPhysical OBJECT IDENTIFIER ::= { entityMIBObjects 1 }
entityLogical  OBJECT IDENTIFIER ::= { entityMIBObjects 2 }
entityMapping  OBJECT IDENTIFIER ::= { entityMIBObjects 3 }
entityGeneral  OBJECT IDENTIFIER ::= { entityMIBObjects 4 }

-- Textual Conventions
PhysicalIndex ::= TEXTUAL-CONVENTION
    STATUS            current
    DESCRIPTION
            "An arbitrary value which uniquely identifies the physical
            entity.  The value should be a small positive integer; index
            values for different physical entities are not necessarily
            contiguous."
    SYNTAX INTEGER (1..2147483647)

PhysicalClass ::= TEXTUAL-CONVENTION
    STATUS            current
    DESCRIPTION
            "An enumerated value which provides an indication of the
            general hardware type of a particular physical entity.
            There are no restrictions as to the number of
            entPhysicalEntries of each entPhysicalClass, which must be
            instantiated by an agent.

            The enumeration 'other' is applicable if the physical entity
            class is known, but does not match any of the supported
            values.

            The enumeration 'unknown' is applicable if the physical
            entity class is unknown to the agent.

            The enumeration 'chassis' is applicable if the physical
            entity class is an overall container for networking
            equipment.  Any class of physical entity except a stack may
            be contained within a chassis, and a chassis may only be
            contained within a stack.

            The enumeration 'backplane' is applicable if the physical
            entity class is some sort of device for aggregating and
            forwarding networking traffic, such as a shared backplane in
            a modular ethernet switch.  Note that an agent may model a


            backplane as a single physical entity, which is actually
            implemented as multiple discrete physical components (within
            a chassis or stack).

            The enumeration 'container' is applicable if the physical
            entity class is capable of containing one or more removable
            physical entities, possibly of different types. For example,
            each (empty or full) slot in a chassis will be modeled as a
            container. Note that all removable physical entities should
            be modeled within a container entity, such as field-
            replaceable modules, fans, or power supplies.  Note that all
            known containers should be modeled by the agent, including
            empty containers.

            The enumeration 'powerSupply' is applicable if the physical
            entity class is a power-supplying component.

            The enumeration 'fan' is applicable if the physical entity
            class is a fan or other heat-reduction component.

            The enumeration 'sensor' is applicable if the physical
            entity class is some sort of sensor, such as a temperature
            sensor within a router chassis.

            The enumeration 'module' is applicable if the physical
            entity class is some sort of self-contained sub-system.  If
            it is removable, then it should be modeled within a
            container entity, otherwise it should be modeled directly
            within another physical entity (e.g., a chassis or another
            module).

            The enumeration 'port' is applicable if the physical entity
            class is some sort of networking port, capable of receiving
            and/or transmitting networking traffic.

            The enumeration 'stack' is applicable if the physical entity
            class is some sort of super-container (possibly virtual),
            intended to group together multiple chassis entities.  A
            stack may be realized by a 'virtual' cable, a real
            interconnect cable, attached to multiple chassis, or may in
            fact be comprised of multiple interconnect cables. A stack
            should not be modeled within any other physical entities,
            but a stack may be contained within another stack.  Only
            chassis entities should be contained within a stack."
    SYNTAX      INTEGER  {
       other(1),
       unknown(2),
       chassis(3),


       backplane(4),
       container(5),     -- e.g., chassis slot or daughter-card holder
       powerSupply(6),
       fan(7),
       sensor(8),
       module(9),        -- e.g., plug-in card or daughter-card
       port(10),
       stack(11)         -- e.g., stack of multiple chassis entities
    }

SnmpEngineIdOrNone ::= TEXTUAL-CONVENTION
    STATUS            current
    DESCRIPTION
            "A specially formatted SnmpEngineID string for use with the
            Entity MIB.

            If an instance of an object of SYNTAX SnmpEngineIdOrNone has
            a non-zero length, then the object encoding and semantics
            are defined by the SnmpEngineID textual convention (see RFC
            2571 [RFC2571]).

            If an instance of an object of SYNTAX SnmpEngineIdOrNone
            contains a zero-length string, then no appropriate
            SnmpEngineID is associated with the logical entity (i.e.,
            SNMPv3 not supported)."
    SYNTAX OCTET STRING (SIZE(0..32)) -- empty string or SnmpEngineID

--           The Physical Entity Table
entPhysicalTable OBJECT-TYPE
    SYNTAX      SEQUENCE OF EntPhysicalEntry
    MAX-ACCESS  not-accessible
    STATUS      current
    DESCRIPTION
            "This table contains one row per physical entity.  There is
            always at least one row for an 'overall' physical entity."
    ::= { entityPhysical 1 }

entPhysicalEntry       OBJECT-TYPE
    SYNTAX      EntPhysicalEntry
    MAX-ACCESS  not-accessible
    STATUS      current
    DESCRIPTION
            "Information about a particular physical entity.

            Each entry provides objects (entPhysicalDescr,
            entPhysicalVendorType, and entPhysicalClass) to help an NMS
            identify and characterize the entry, and objects
            (entPhysicalContainedIn and entPhysicalParentRelPos) to help


            an NMS relate the particular entry to other entries in this
            table."
    INDEX   { entPhysicalIndex }
    ::= { entPhysicalTable 1 }

EntPhysicalEntry ::= SEQUENCE {
      entPhysicalIndex          PhysicalIndex,
      entPhysicalDescr          SnmpAdminString,
      entPhysicalVendorType     AutonomousType,
      entPhysicalContainedIn    INTEGER,
      entPhysicalClass          PhysicalClass,
      entPhysicalParentRelPos   INTEGER,
      entPhysicalName           SnmpAdminString,
      entPhysicalHardwareRev    SnmpAdminString,
      entPhysicalFirmwareRev    SnmpAdminString,
      entPhysicalSoftwareRev    SnmpAdminString,
      entPhysicalSerialNum      SnmpAdminString,
      entPhysicalMfgName        SnmpAdminString,
      entPhysicalModelName      SnmpAdminString,
      entPhysicalAlias          SnmpAdminString,
      entPhysicalAssetID        SnmpAdminString,
      entPhysicalIsFRU          TruthValue
}

entPhysicalIndex    OBJECT-TYPE
    SYNTAX      PhysicalIndex
    MAX-ACCESS  not-accessible
    STATUS      current
    DESCRIPTION
            "The index for this entry."
    ::= { entPhysicalEntry 1 }

entPhysicalDescr OBJECT-TYPE
    SYNTAX      SnmpAdminString
    MAX-ACCESS  read-only
    STATUS      current
    DESCRIPTION
            "A textual description of physical entity.  This object
            should contain a string which identifies the manufacturer's
            name for the physical entity, and should be set to a
            distinct value for each version or model of the physical
            entity. "
    ::= { entPhysicalEntry 2 }

entPhysicalVendorType OBJECT-TYPE
    SYNTAX      AutonomousType
    MAX-ACCESS  read-only
    STATUS      current


    DESCRIPTION
            "An indication of the vendor-specific hardware type of the
            physical entity.  Note that this is different from the
            definition of MIB-II's sysObjectID.

            An agent should set this object to a enterprise-specific
            registration identifier value indicating the specific
            equipment type in detail.  The associated instance of
            entPhysicalClass is used to indicate the general type of
            hardware device.

            If no vendor-specific registration identifier exists for
            this physical entity, or the value is unknown by this agent,
            then the value { 0 0 } is returned."
    ::= { entPhysicalEntry 3 }

entPhysicalContainedIn OBJECT-TYPE
    SYNTAX      INTEGER (0..2147483647)
    MAX-ACCESS  read-only
    STATUS      current
    DESCRIPTION
            "The value of entPhysicalIndex for the physical entity which
            'contains' this physical entity.  A value of zero indicates
            this physical entity is not contained in any other physical
            entity.  Note that the set of 'containment' relationships
            define a strict hierarchy; that is, recursion is not
            allowed.

            In the event a physical entity is contained by more than one
            physical entity (e.g., double-wide modules), this object
            should identify the containing entity with the lowest value
            of entPhysicalIndex."
    ::= { entPhysicalEntry 4 }

entPhysicalClass OBJECT-TYPE
    SYNTAX      PhysicalClass
    MAX-ACCESS  read-only
    STATUS      current
    DESCRIPTION
            "An indication of the general hardware type of the physical
            entity.

            An agent should set this object to the standard enumeration
            value which most accurately indicates the general class of
            the physical entity, or the primary class if there is more
            than one.

            If no appropriate standard registration identifier exists


            for this physical entity, then the value 'other(1)' is
            returned. If the value is unknown by this agent, then the
            value 'unknown(2)' is returned."
    ::= { entPhysicalEntry 5 }

entPhysicalParentRelPos OBJECT-TYPE
    SYNTAX      INTEGER (-1..2147483647)
    MAX-ACCESS  read-only
    STATUS      current
    DESCRIPTION
            "An indication of the relative position of this 'child'
            component among all its 'sibling' components. Sibling
            components are defined as entPhysicalEntries which share the
            same instance values of each of the entPhysicalContainedIn
            and entPhysicalClass objects.

            An NMS can use this object to identify the relative ordering
            for all sibling components of a particular parent
            (identified by the entPhysicalContainedIn instance in each
            sibling entry).

            This value should match any external labeling of the
            physical component if possible. For example, for a container
            (e.g., card slot) labeled as 'slot #3',
            entPhysicalParentRelPos should have the value '3'.  Note
            that the entPhysicalEntry for the module plugged in slot 3
            should have an entPhysicalParentRelPos value of '1'.

            If the physical position of this component does not match
            any external numbering or clearly visible ordering, then
            user documentation or other external reference material
            should be used to determine the parent-relative position. If
            this is not possible, then the the agent should assign a
            consistent (but possibly arbitrary) ordering to a given set
            of 'sibling' components, perhaps based on internal
            representation of the components.

            If the agent cannot determine the parent-relative position
            for some reason, or if the associated value of
            entPhysicalContainedIn is '0', then the value '-1' is
            returned. Otherwise a non-negative integer is returned,
            indicating the parent-relative position of this physical
            entity.

            Parent-relative ordering normally starts from '1' and
            continues to 'N', where 'N' represents the highest
            positioned child entity.  However, if the physical entities
            (e.g., slots) are labeled from a starting position of zero,


            then the first sibling should be associated with a
            entPhysicalParentRelPos value of '0'.  Note that this
            ordering may be sparse or dense, depending on agent
            implementation.

            The actual values returned are not globally meaningful, as
            each 'parent' component may use different numbering
            algorithms. The ordering is only meaningful among siblings
            of the same parent component.

            The agent should retain parent-relative position values
            across reboots, either through algorithmic assignment or use
            of non-volatile storage."
    ::= { entPhysicalEntry 6 }

entPhysicalName OBJECT-TYPE
    SYNTAX      SnmpAdminString
    MAX-ACCESS  read-only
    STATUS      current
    DESCRIPTION
            "The textual name of the physical entity.  The value of this
            object should be the name of the component as assigned by
            the local device and should be suitable for use in commands
            entered at the device's `console'.  This might be a text
            name, such as `console' or a simple component number (e.g.,
            port or module number), such as `1', depending on the
            physical component naming syntax of the device.

            If there is no local name, or this object is otherwise not
            applicable, then this object contains a zero-length string.

            Note that the value of entPhysicalName for two physical
            entities will be the same in the event that the console
            interface does not distinguish between them, e.g., slot-1
            and the card in slot-1."
    ::= { entPhysicalEntry 7 }

entPhysicalHardwareRev    OBJECT-TYPE
    SYNTAX      SnmpAdminString
    MAX-ACCESS  read-only
    STATUS      current
    DESCRIPTION
            "The vendor-specific hardware revision string for the
            physical entity.  The preferred value is the hardware
            revision identifier actually printed on the component itself
            (if present).

            Note that if revision information is stored internally in a


            non-printable (e.g., binary) format, then the agent must
            convert such information to a printable format, in an
            implementation-specific manner.

            If no specific hardware revision string is associated with
            the physical component, or this information is unknown to
            the agent, then this object will contain a zero-length
            string."
    ::= { entPhysicalEntry 8 }

entPhysicalFirmwareRev    OBJECT-TYPE
    SYNTAX      SnmpAdminString
    MAX-ACCESS  read-only
    STATUS      current
    DESCRIPTION
            "The vendor-specific firmware revision string for the
            physical entity.

            Note that if revision information is stored internally in a
            non-printable (e.g., binary) format, then the agent must
            convert such information to a printable format, in an
            implementation-specific manner.

            If no specific firmware programs are associated with the
            physical component, or this information is unknown to the
            agent, then this object will contain a zero-length string."
    ::= { entPhysicalEntry 9 }

entPhysicalSoftwareRev    OBJECT-TYPE
    SYNTAX      SnmpAdminString
    MAX-ACCESS  read-only
    STATUS      current
    DESCRIPTION
            "The vendor-specific software revision string for the
            physical entity.

            Note that if revision information is stored internally in a
            non-printable (e.g., binary) format, then the agent must
            convert such information to a printable format, in an
            implementation-specific manner.

            If no specific software programs are associated with the
            physical component, or this information is unknown to the
            agent, then this object will contain a zero-length string."
    ::= { entPhysicalEntry 10 }

entPhysicalSerialNum   OBJECT-TYPE
    SYNTAX      SnmpAdminString (SIZE (0..32))


    MAX-ACCESS  read-write
    STATUS      current
    DESCRIPTION
            "The vendor-specific serial number string for the physical
            entity.  The preferred value is the serial number string
            actually printed on the component itself (if present).

            On the first instantiation of an physical entity, the value
            of entPhysicalSerialNum associated with that entity is set
            to the correct vendor-assigned serial number, if this
            information is available to the agent.  If a serial number
            is unknown or non-existent, the entPhysicalSerialNum will be
            set to a zero-length string instead.

            Note that implementations which can correctly identify the
            serial numbers of all installed physical entities do not
            need to provide write access to the entPhysicalSerialNum
            object. Agents which cannot provide non-volatile storage for
            the entPhysicalSerialNum strings are not required to
            implement write access for this object.

            Not every physical component will have a serial number, or
            even need one.  Physical entities for which the associated
            value of the entPhysicalIsFRU object is equal to 'false(2)'
            (e.g., the repeater ports within a repeater module), do not
            need their own unique serial number. An agent does not have
            to provide write access for such entities, and may return a
            zero-length string.

            If write access is implemented for an instance of
            entPhysicalSerialNum, and a value is written into the
            instance, the agent must retain the supplied value in the
            entPhysicalSerialNum instance associated with the same
            physical entity for as long as that entity remains
            instantiated. This includes instantiations across all re-
            initializations/reboots of the network management system,
            including those which result in a change of the physical
            entity's entPhysicalIndex value."
    ::= { entPhysicalEntry 11 }

entPhysicalMfgName   OBJECT-TYPE
    SYNTAX      SnmpAdminString
    MAX-ACCESS  read-only
    STATUS      current
    DESCRIPTION
            "The name of the manufacturer of this physical component.
            The preferred value is the manufacturer name string actually
            printed on the component itself (if present).


            Note that comparisons between instances of the
            entPhysicalModelName, entPhysicalFirmwareRev,
            entPhysicalSoftwareRev, and the entPhysicalSerialNum
            objects, are only meaningful amongst entPhysicalEntries with
            the same value of entPhysicalMfgName.

            If the manufacturer name string associated with the physical
            component is unknown to the agent, then this object will
            contain a zero-length string."
    ::= { entPhysicalEntry 12 }

entPhysicalModelName   OBJECT-TYPE
    SYNTAX      SnmpAdminString
    MAX-ACCESS  read-only
    STATUS      current
    DESCRIPTION
            "The vendor-specific model name identifier string associated
            with this physical component.  The preferred value is the
            customer-visible part number, which may be printed on the
            component itself.

            If the model name string associated with the physical
            component is unknown to the agent, then this object will
            contain a zero-length string."
    ::= { entPhysicalEntry 13 }

entPhysicalAlias    OBJECT-TYPE
    SYNTAX      SnmpAdminString (SIZE (0..32))
    MAX-ACCESS  read-write
    STATUS      current
    DESCRIPTION
            "This object is an 'alias' name for the physical entity as
            specified by a network manager, and provides a non-volatile
            'handle' for the physical entity.

            On the first instantiation of an physical entity, the value
            of entPhysicalAlias associated with that entity is set to
            the zero-length string.  However, agent may set the value to
            a locally unique default value, instead of a zero-length
            string.

            If write access is implemented for an instance of
            entPhysicalAlias, and a value is written into the instance,
            the agent must retain the supplied value in the
            entPhysicalAlias instance associated with the same physical
            entity for as long as that entity remains instantiated.
            This includes instantiations across all re-
            initializations/reboots of the network management system,


            including those which result in a change of the physical
            entity's entPhysicalIndex value."
    ::= { entPhysicalEntry 14 }

entPhysicalAssetID OBJECT-TYPE
    SYNTAX      SnmpAdminString (SIZE (0..32))
    MAX-ACCESS  read-write
    STATUS      current
    DESCRIPTION
            "This object is a user-assigned asset tracking identifier
            for the physical entity as specified by a network manager,
            and provides non-volatile storage of this information.

            On the first instantiation of an physical entity, the value
            of entPhysicalAssetID associated with that entity is set to
            the zero-length string.

            Not every physical component will have a asset tracking
            identifier, or even need one.  Physical entities for which
            the associated value of the entPhysicalIsFRU object is equal
            to 'false(2)' (e.g., the repeater ports within a repeater
            module), do not need their own unique asset tracking
            identifier. An agent does not have to provide write access
            for such entities, and may instead return a zero-length
            string.

            If write access is implemented for an instance of
            entPhysicalAssetID, and a value is written into the
            instance, the agent must retain the supplied value in the
            entPhysicalAssetID instance associated with the same
            physical entity for as long as that entity remains
            instantiated.  This includes instantiations across all re-
            initializations/reboots of the network management system,
            including those which result in a change of the physical
            entity's entPhysicalIndex value.

            If no asset tracking information is associated with the
            physical component, then this object will contain a zero-
            length string."
    ::= { entPhysicalEntry 15 }

entPhysicalIsFRU OBJECT-TYPE
    SYNTAX      TruthValue
    MAX-ACCESS  read-only
    STATUS      current
    DESCRIPTION
            "This object indicates whether or not this physical entity
            is considered a 'field replaceable unit' by the vendor.  If


            this object contains the value 'true(1)' then this
            entPhysicalEntry identifies a field replaceable unit.  For
            all entPhysicalEntries which represent components that are
            permanently contained within a field replaceable unit, the
            value 'false(2)' should be returned for this object."

    ::= { entPhysicalEntry 16 }

--           The Logical Entity Table
entLogicalTable OBJECT-TYPE
    SYNTAX      SEQUENCE OF EntLogicalEntry
    MAX-ACCESS  not-accessible
    STATUS      current
    DESCRIPTION
            "This table contains one row per logical entity.  For agents
            which implement more than one naming scope, at least one
            entry must exist. Agents which instantiate all MIB objects
            within a single naming scope are not required to implement
            this table."
    ::= { entityLogical 1 }

entLogicalEntry       OBJECT-TYPE
    SYNTAX      EntLogicalEntry
    MAX-ACCESS  not-accessible
    STATUS      current
    DESCRIPTION
            "Information about a particular logical entity.  Entities
            may be managed by this agent or other SNMP agents (possibly)
            in the same chassis."
    INDEX       { entLogicalIndex }
    ::= { entLogicalTable 1 }

EntLogicalEntry ::= SEQUENCE {
      entLogicalIndex            INTEGER,
      entLogicalDescr            SnmpAdminString,
      entLogicalType             AutonomousType,
      entLogicalCommunity        OCTET STRING,
      entLogicalTAddress         TAddress,
      entLogicalTDomain          TDomain,
      entLogicalContextEngineID  SnmpEngineIdOrNone,
      entLogicalContextName      SnmpAdminString
}

entLogicalIndex OBJECT-TYPE
    SYNTAX      INTEGER (1..2147483647)
    MAX-ACCESS  not-accessible
    STATUS      current
    DESCRIPTION


            "The value of this object uniquely identifies the logical
            entity. The value should be a small positive integer; index
            values for different logical entities are are not
            necessarily contiguous."
    ::= { entLogicalEntry 1 }

entLogicalDescr OBJECT-TYPE
    SYNTAX      SnmpAdminString
    MAX-ACCESS  read-only
    STATUS      current
    DESCRIPTION
            "A textual description of the logical entity.  This object
            should contain a string which identifies the manufacturer's
            name for the logical entity, and should be set to a distinct
            value for each version of the logical entity. "
    ::= { entLogicalEntry 2 }

entLogicalType OBJECT-TYPE
    SYNTAX      AutonomousType
    MAX-ACCESS  read-only
    STATUS      current
    DESCRIPTION
            "An indication of the type of logical entity.  This will
            typically be the OBJECT IDENTIFIER name of the node in the
            SMI's naming hierarchy which represents the major MIB
            module, or the majority of the MIB modules, supported by the
            logical entity.  For example:
               a logical entity of a regular host/router -&gt; mib-2
               a logical entity of a 802.1d bridge -&gt; dot1dBridge
               a logical entity of a 802.3 repeater -&gt; snmpDot3RptrMgmt
            If an appropriate node in the SMI's naming hierarchy cannot
            be identified, the value 'mib-2' should be used."
    ::= { entLogicalEntry 3 }

entLogicalCommunity OBJECT-TYPE
    SYNTAX      OCTET STRING (SIZE (0..255))
    MAX-ACCESS  read-only
    STATUS      deprecated
    DESCRIPTION
            "An SNMPv1 or SNMPv2C community-string which can be used to
            access detailed management information for this logical
            entity.  The agent should allow read access with this
            community string (to an appropriate subset of all managed
            objects) and may also return a community string based on the
            privileges of the request used to read this object.  Note
            that an agent may return a community string with read-only
            privileges, even if this object is accessed with a read-
            write community string. However, the agent must take care


            not to return a community string which allows more
            privileges than the community string used to access this
            object.

            A compliant SNMP agent may wish to conserve naming scopes by
            representing multiple logical entities in a single 'default'
            naming scope.  This is possible when the logical entities
            represented by the same value of entLogicalCommunity have no
            object instances in common.  For example, 'bridge1' and
            'repeater1' may be part of the main naming scope, but at
            least one additional community string is needed to represent
            'bridge2' and 'repeater2'.

            Logical entities 'bridge1' and 'repeater1' would be
            represented by sysOREntries associated with the 'default'
            naming scope.

            For agents not accessible via SNMPv1 or SNMPv2C, the value
            of this object is the empty string.  This object may also
            contain an empty string if a community string has not yet
            been assigned by the agent, or no community string with
            suitable access rights can be returned for a particular SNMP
            request.

            Note that this object is deprecated. Agents which implement
            SNMPv3 access should use the entLogicalContextEngineID and
            entLogicalContextName objects to identify the context
            associated with each logical entity.  SNMPv3 agents may
            return a zero-length string for this object, or may continue
            to return a community string (e.g., tri-lingual agent
            support)."
    ::= { entLogicalEntry 4 }

entLogicalTAddress OBJECT-TYPE
    SYNTAX      TAddress
    MAX-ACCESS  read-only
    STATUS      current
    DESCRIPTION
            "The transport service address by which the logical entity
            receives network management traffic, formatted according to
            the corresponding value of entLogicalTDomain.

            For snmpUDPDomain, a TAddress is 6 octets long, the initial
            4 octets containing the IP-address in network-byte order and
            the last 2 containing the UDP port in network-byte order.
            Consult 'Transport Mappings for Version 2 of the Simple
            Network Management Protocol' (RFC 1906 [RFC1906]) for
            further information on snmpUDPDomain."


    ::= { entLogicalEntry 5 }

entLogicalTDomain OBJECT-TYPE
    SYNTAX      TDomain
    MAX-ACCESS  read-only
    STATUS      current
    DESCRIPTION
            "Indicates the kind of transport service by which the
            logical entity receives network management traffic.
            Possible values for this object are presently found in the
            Transport Mappings for SNMPv2 document (RFC 1906
            [RFC1906])."
    ::= { entLogicalEntry 6 }

entLogicalContextEngineID    OBJECT-TYPE
    SYNTAX      SnmpEngineIdOrNone
    MAX-ACCESS  read-only
    STATUS      current
    DESCRIPTION
            "The authoritative contextEngineID that can be used to send
            an SNMP message concerning information held by this logical
            entity, to the address specified by the associated
            'entLogicalTAddress/entLogicalTDomain' pair.

            This object, together with the associated
            entLogicalContextName object, defines the context associated
            with a particular logical entity, and allows access to SNMP
            engines identified by a contextEngineId and contextName
            pair.

            If no value has been configured by the agent, a zero-length
            string is returned, or the agent may choose not to
            instantiate this object at all."
    ::= { entLogicalEntry 7 }

entLogicalContextName    OBJECT-TYPE
    SYNTAX      SnmpAdminString
    MAX-ACCESS  read-only
    STATUS      current
    DESCRIPTION
            "The contextName that can be used to send an SNMP message
            concerning information held by this logical entity, to the
            address specified by the associated
            'entLogicalTAddress/entLogicalTDomain' pair.

            This object, together with the associated
            entLogicalContextEngineID object, defines the context
            associated with a particular logical entity, and allows


            access to SNMP engines identified by a contextEngineId and
            contextName pair.

            If no value has been configured by the agent, a zero-length
            string is returned, or the agent may choose not to
            instantiate this object at all."
    ::= { entLogicalEntry 8 }

entLPMappingTable OBJECT-TYPE
    SYNTAX      SEQUENCE OF EntLPMappingEntry
    MAX-ACCESS  not-accessible
    STATUS      current
    DESCRIPTION
            "This table contains zero or more rows of logical entity to
            physical equipment associations. For each logical entity
            known by this agent, there are zero or more mappings to the
            physical resources which are used to realize that logical
            entity.

            An agent should limit the number and nature of entries in
            this table such that only meaningful and non-redundant
            information is returned. For example, in a system which
            contains a single power supply, mappings between logical
            entities and the power supply are not useful and should not
            be included.

            Also, only the most appropriate physical component which is
            closest to the root of a particular containment tree should
            be identified in an entLPMapping entry.

            For example, suppose a bridge is realized on a particular
            module, and all ports on that module are ports on this
            bridge. A mapping between the bridge and the module would be
            useful, but additional mappings between the bridge and each
            of the ports on that module would be redundant (since the
            entPhysicalContainedIn hierarchy can provide the same
            information). If, on the other hand, more than one bridge
            was utilizing ports on this module, then mappings between
            each bridge and the ports it used would be appropriate.

            Also, in the case of a single backplane repeater, a mapping
            for the backplane to the single repeater entity is not
            necessary."
    ::= { entityMapping 1 }

entLPMappingEntry       OBJECT-TYPE
    SYNTAX      EntLPMappingEntry
    MAX-ACCESS  not-accessible


    STATUS      current
    DESCRIPTION
            "Information about a particular logical entity to physical
            equipment association. Note that the nature of the
            association is not specifically identified in this entry.
            It is expected that sufficient information exists in the
            MIBs used to manage a particular logical entity to infer how
            physical component information is utilized."
    INDEX       { entLogicalIndex, entLPPhysicalIndex }
    ::= { entLPMappingTable 1 }

EntLPMappingEntry ::= SEQUENCE {
      entLPPhysicalIndex         PhysicalIndex
}

entLPPhysicalIndex OBJECT-TYPE
    SYNTAX      PhysicalIndex
    MAX-ACCESS  read-only
    STATUS      current
    DESCRIPTION
            "The value of this object identifies the index value of a
            particular entPhysicalEntry associated with the indicated
            entLogicalEntity."
    ::= { entLPMappingEntry 1 }

-- logical entity/component to alias table
entAliasMappingTable OBJECT-TYPE
    SYNTAX      SEQUENCE OF EntAliasMappingEntry
    MAX-ACCESS  not-accessible
    STATUS      current
    DESCRIPTION
            "This table contains zero or more rows, representing
            mappings of logical entity and physical component to
            external MIB identifiers.  Each physical port in the system
            may be associated with a mapping to an external identifier,
            which itself is associated with a particular logical
            entity's naming scope.  A 'wildcard' mechanism is provided
            to indicate that an identifier is associated with more than
            one logical entity."
    ::= { entityMapping 2 }

entAliasMappingEntry       OBJECT-TYPE
    SYNTAX      EntAliasMappingEntry
    MAX-ACCESS  not-accessible
    STATUS      current
    DESCRIPTION
            "Information about a particular physical equipment, logical
            entity to external identifier binding. Each logical


            entity/physical component pair may be associated with one
            alias mapping.  The logical entity index may also be used as
            a 'wildcard' (refer to the entAliasLogicalIndexOrZero object
            DESCRIPTION clause for details.)

            Note that only entPhysicalIndex values which represent
            physical ports (i.e. associated entPhysicalClass value is
            'port(10)') are permitted to exist in this table."
    INDEX { entPhysicalIndex, entAliasLogicalIndexOrZero }
    ::= { entAliasMappingTable 1 }

EntAliasMappingEntry ::= SEQUENCE {
      entAliasLogicalIndexOrZero        INTEGER,
      entAliasMappingIdentifier          RowPointer
}

entAliasLogicalIndexOrZero OBJECT-TYPE
    SYNTAX      INTEGER (0..2147483647)
    MAX-ACCESS  not-accessible
    STATUS      current
    DESCRIPTION
            "The value of this object identifies the logical entity
            which defines the naming scope for the associated instance
            of the 'entAliasMappingIdentifier' object.

            If this object has a non-zero value, then it identifies the
            logical entity named by the same value of entLogicalIndex.

            If this object has a value of zero, then the mapping between
            the physical component and the alias identifier for this
            entAliasMapping entry is associated with all unspecified
            logical entities. That is, a value of zero (the default
            mapping) identifies any logical entity which does not have
            an explicit entry in this table for a particular
            entPhysicalIndex/entAliasMappingIdentifier pair.

            For example, to indicate that a particular interface (e.g.,
            physical component 33) is identified by the same value of
            ifIndex for all logical entities, the following instance
            might exist:

                    entAliasMappingIdentifier.33.0 = ifIndex.5

            In the event an entPhysicalEntry is associated differently
            for some logical entities, additional entAliasMapping
            entries may exist, e.g.:

                    entAliasMappingIdentifier.33.0 = ifIndex.6


                    entAliasMappingIdentifier.33.4 =  ifIndex.1
                    entAliasMappingIdentifier.33.5 =  ifIndex.1
                    entAliasMappingIdentifier.33.10 = ifIndex.12

            Note that entries with non-zero entAliasLogicalIndexOrZero
            index values have precedence over any zero-indexed entry. In
            this example, all logical entities except 4, 5, and 10,
            associate physical entity 33 with ifIndex.6."
    ::= { entAliasMappingEntry 1 }

entAliasMappingIdentifier OBJECT-TYPE
    SYNTAX      RowPointer
    MAX-ACCESS  read-only
    STATUS      current
    DESCRIPTION
            "The value of this object identifies a particular conceptual
            row associated with the indicated entPhysicalIndex and
            entLogicalIndex pair.

            Since only physical ports are modeled in this table, only
            entries which represent interfaces or ports are allowed.  If
            an ifEntry exists on behalf of a particular physical port,
            then this object should identify the associated 'ifEntry'.
            For repeater ports, the appropriate row in the
            'rptrPortGroupTable' should be identified instead.

            For example, suppose a physical port was represented by
            entPhysicalEntry.3, entLogicalEntry.15 existed for a
            repeater, and entLogicalEntry.22 existed for a bridge.  Then
            there might be two related instances of
            entAliasMappingIdentifier:
               entAliasMappingIdentifier.3.15 == rptrPortGroupIndex.5.2
               entAliasMappingIdentifier.3.22 == ifIndex.17
            It is possible that other mappings (besides interfaces and
            repeater ports) may be defined in the future, as required.

            Bridge ports are identified by examining the Bridge MIB and
            appropriate ifEntries associated with each 'dot1dBasePort',
            and are thus not represented in this table."
    ::= { entAliasMappingEntry 2 }

-- physical mapping table
entPhysicalContainsTable OBJECT-TYPE
    SYNTAX      SEQUENCE OF EntPhysicalContainsEntry
    MAX-ACCESS  not-accessible
    STATUS      current
    DESCRIPTION
            "A table which exposes the container/'containee'


            relationships between physical entities. This table provides
            all the information found by constructing the virtual
            containment tree for a given entPhysicalTable, but in a more
            direct format.

            In the event a physical entity is contained by more than one
            other physical entity (e.g., double-wide modules), this
            table should include these additional mappings, which cannot
            be represented in the entPhysicalTable virtual containment
            tree."
    ::= { entityMapping 3 }

entPhysicalContainsEntry OBJECT-TYPE
    SYNTAX      EntPhysicalContainsEntry
    MAX-ACCESS  not-accessible
    STATUS      current
    DESCRIPTION
            "A single container/'containee' relationship."
    INDEX       { entPhysicalIndex, entPhysicalChildIndex }
    ::= { entPhysicalContainsTable 1 }

EntPhysicalContainsEntry ::= SEQUENCE {
      entPhysicalChildIndex     PhysicalIndex
}

entPhysicalChildIndex OBJECT-TYPE
    SYNTAX      PhysicalIndex
    MAX-ACCESS  read-only
    STATUS      current
    DESCRIPTION
            "The value of entPhysicalIndex for the contained physical
            entity."
    ::= { entPhysicalContainsEntry 1 }

-- last change time stamp for the whole MIB
entLastChangeTime OBJECT-TYPE
    SYNTAX      TimeStamp
    MAX-ACCESS  read-only
    STATUS      current
    DESCRIPTION
            "The value of sysUpTime at the time a conceptual row is
            created, modified, or deleted in any of these tables:
                    - entPhysicalTable
                    - entLogicalTable
                    - entLPMappingTable
                    - entAliasMappingTable
                    - entPhysicalContainsTable
            "


    ::= { entityGeneral 1 }

-- Entity MIB Trap Definitions
entityMIBTraps      OBJECT IDENTIFIER ::= { entityMIB 2 }
entityMIBTrapPrefix OBJECT IDENTIFIER ::= { entityMIBTraps 0 }

entConfigChange NOTIFICATION-TYPE
    STATUS             current
    DESCRIPTION
            "An entConfigChange notification is generated when the value
            of entLastChangeTime changes. It can be utilized by an NMS
            to trigger logical/physical entity table maintenance polls.

            An agent should not generate more than one entConfigChange
            'notification-event' in a given time interval (five seconds
            is the suggested default).  A 'notification-event' is the
            transmission of a single trap or inform PDU to a list of
            notification destinations.

            If additional configuration changes occur within the
            throttling period, then notification-events for these
            changes should be suppressed by the agent until the current
            throttling period expires.  At the end of a throttling
            period, one notification-event should be generated if any
            configuration changes occurred since the start of the
            throttling period. In such a case, another throttling period
            is started right away.

            An NMS should periodically check the value of
            entLastChangeTime to detect any missed entConfigChange
            notification-events, e.g., due to throttling or transmission
            loss."
   ::= { entityMIBTrapPrefix 1 }

-- conformance information
entityConformance OBJECT IDENTIFIER ::= { entityMIB 3 }

entityCompliances OBJECT IDENTIFIER ::= { entityConformance 1 }
entityGroups      OBJECT IDENTIFIER ::= { entityConformance 2 }

-- compliance statements
entityCompliance MODULE-COMPLIANCE
    STATUS  deprecated
    DESCRIPTION
            "The compliance statement for SNMP entities which implement
            version 1 of the Entity MIB."
    MODULE  -- this module
        MANDATORY-GROUPS {


                           entityPhysicalGroup,
                           entityLogicalGroup,
                           entityMappingGroup,
                           entityGeneralGroup,
                           entityNotificationsGroup
        }
    ::= { entityCompliances 1 }

entity2Compliance MODULE-COMPLIANCE
    STATUS  current
    DESCRIPTION
            "The compliance statement for SNMP entities which implement
            version 2 of the Entity MIB."
    MODULE  -- this module
        MANDATORY-GROUPS {
                           entityPhysicalGroup,
                           entityPhysical2Group,
                           entityGeneralGroup,
                           entityNotificationsGroup
        }
        GROUP entityLogical2Group
        DESCRIPTION
            "Implementation of this group is not mandatory for agents
            which model all MIB object instances within a single naming
            scope."

        GROUP entityMappingGroup
        DESCRIPTION
            "Implementation of the entPhysicalContainsTable is mandatory
            for all agents.  Implementation of the entLPMappingTable and
            entAliasMappingTables are not mandatory for agents which
            model all MIB object instances within a single naming scope.

            Note that the entAliasMappingTable may be useful for all
            agents, however implementation of the entityLogicalGroup or
            entityLogical2Group is required to support this table."

        OBJECT entPhysicalSerialNum
        MIN-ACCESS   not-accessible
        DESCRIPTION
            "Read and write access is not required for agents which
            cannot identify serial number information for physical
            entities, and/or cannot provide non-volatile storage for
            NMS-assigned serial numbers.

            Write access is not required for agents which can identify
            serial number information for physical entities, but cannot
            provide non-volatile storage for NMS-assigned serial


            numbers.

            Write access is not required for physical entities for
            physical entities for which the associated value of the
            entPhysicalIsFRU object is equal to 'false(2)'."

        OBJECT entPhysicalAlias
        MIN-ACCESS   read-only
        DESCRIPTION
            "Write access is required only if the associated
            entPhysicalClass value is equal to 'chassis(3)'."

        OBJECT entPhysicalAssetID
        MIN-ACCESS   not-accessible
        DESCRIPTION
            "Read and write access is not required for agents which
            cannot provide non-volatile storage for NMS-assigned asset
            identifiers.

            Write access is not required for physical entities for which
            the associated value of entPhysicalIsFRU is equal to
            'false(2)'."
    ::= { entityCompliances 2 }

-- MIB groupings
entityPhysicalGroup    OBJECT-GROUP
    OBJECTS {
              entPhysicalDescr,
              entPhysicalVendorType,
              entPhysicalContainedIn,
              entPhysicalClass,
              entPhysicalParentRelPos,
              entPhysicalName
            }
    STATUS  current
    DESCRIPTION
            "The collection of objects which are used to represent
            physical system components, for which a single agent
            provides management information."
    ::= { entityGroups 1 }

entityLogicalGroup    OBJECT-GROUP
    OBJECTS {
              entLogicalDescr,
              entLogicalType,
              entLogicalCommunity,
              entLogicalTAddress,
              entLogicalTDomain


            }
    STATUS  deprecated
    DESCRIPTION
            "The collection of objects which are used to represent the
            list of logical entities for which a single agent provides
            management information."
    ::= { entityGroups 2 }

entityMappingGroup    OBJECT-GROUP
    OBJECTS {
              entLPPhysicalIndex,
              entAliasMappingIdentifier,
              entPhysicalChildIndex
            }
    STATUS  current
    DESCRIPTION
            "The collection of objects which are used to represent the
            associations between multiple logical entities, physical
            components, interfaces, and port identifiers for which a
            single agent provides management information."
    ::= { entityGroups 3 }

entityGeneralGroup    OBJECT-GROUP
    OBJECTS {
              entLastChangeTime
            }
    STATUS  current
    DESCRIPTION
            "The collection of objects which are used to represent
            general entity information for which a single agent provides
            management information."
    ::= { entityGroups 4 }

entityNotificationsGroup NOTIFICATION-GROUP
    NOTIFICATIONS { entConfigChange }
    STATUS        current
    DESCRIPTION
            "The collection of notifications used to indicate Entity MIB
            data consistency and general status information."
    ::= { entityGroups 5 }

entityPhysical2Group    OBJECT-GROUP
    OBJECTS {
              entPhysicalHardwareRev,
              entPhysicalFirmwareRev,
              entPhysicalSoftwareRev,
              entPhysicalSerialNum,
              entPhysicalMfgName,


              entPhysicalModelName,
              entPhysicalAlias,
              entPhysicalAssetID,
              entPhysicalIsFRU
            }

    STATUS  current
    DESCRIPTION
            "The collection of objects which are used to represent
            physical system components, for which a single agent
            provides management information.  This group augments the
            objects contained in the entityPhysicalGroup."
    ::= { entityGroups 6 }

entityLogical2Group    OBJECT-GROUP
    OBJECTS {
              entLogicalDescr,
              entLogicalType,
              entLogicalTAddress,
              entLogicalTDomain,
              entLogicalContextEngineID,
              entLogicalContextName
            }
    STATUS  current
    DESCRIPTION
            "The collection of objects which are used to represent the
            list of logical entities for which a single SNMP entity
            provides management information."
    ::= { entityGroups 7 }

END

IF-MIB DEFINITIONS ::= BEGIN

IMPORTS
    MODULE-IDENTITY, OBJECT-TYPE, Counter32, Gauge32, Counter64,
    Integer32, TimeTicks, mib-2,
    NOTIFICATION-TYPE                        FROM SNMPv2-SMI
    TEXTUAL-CONVENTION, DisplayString,
    PhysAddress, TruthValue, RowStatus,
    TimeStamp, AutonomousType, TestAndIncr   FROM SNMPv2-TC
    MODULE-COMPLIANCE, OBJECT-GROUP,
    NOTIFICATION-GROUP                       FROM SNMPv2-CONF
    snmpTraps                                FROM SNMPv2-MIB
    IANAifType                               FROM IANAifType-MIB;

ifMIB MODULE-IDENTITY
    LAST-UPDATED "200006140000Z"
    ORGANIZATION "IETF Interfaces MIB Working Group"
    CONTACT-INFO
            "   Keith McCloghrie
                Cisco Systems, Inc.
                170 West Tasman Drive
                San Jose, CA  95134-1706
                US

                408-526-5260
                kzm@cisco.com"
    DESCRIPTION
            "The MIB module to describe generic objects for network
            interface sub-layers.  This MIB is an updated version of
            MIB-II's ifTable, and incorporates the extensions defined in
            RFC 1229."


    REVISION      "200006140000Z"
    DESCRIPTION
            "Clarifications agreed upon by the Interfaces MIB WG, and
            published as RFC 2863."
    REVISION      "199602282155Z"
    DESCRIPTION
            "Revisions made by the Interfaces MIB WG, and published in
            RFC 2233."
    REVISION      "199311082155Z"
    DESCRIPTION
            "Initial revision, published as part of RFC 1573."
    ::= { mib-2 31 }

ifMIBObjects OBJECT IDENTIFIER ::= { ifMIB 1 }

interfaces   OBJECT IDENTIFIER ::= { mib-2 2 }

--
-- Textual Conventions
--

-- OwnerString has the same semantics as used in RFC 1271

OwnerString ::= TEXTUAL-CONVENTION
    DISPLAY-HINT "255a"
    STATUS       deprecated
    DESCRIPTION
            "This data type is used to model an administratively
            assigned name of the owner of a resource.  This information
            is taken from the NVT ASCII character set.  It is suggested
            that this name contain one or more of the following: ASCII
            form of the manager station's transport address, management
            station name (e.g., domain name), network management
            personnel's name, location, or phone number.  In some cases
            the agent itself will be the owner of an entry.  In these
            cases, this string shall be set to a string starting with
            'agent'."
    SYNTAX       OCTET STRING (SIZE(0..255))

-- InterfaceIndex contains the semantics of ifIndex and should be used
-- for any objects defined in other MIB modules that need these semantics.

InterfaceIndex ::= TEXTUAL-CONVENTION
    DISPLAY-HINT "d"
    STATUS       current
    DESCRIPTION


            "A unique value, greater than zero, for each interface or
            interface sub-layer in the managed system.  It is
            recommended that values are assigned contiguously starting
            from 1.  The value for each interface sub-layer must remain
            constant at least from one re-initialization of the entity's
            network management system to the next re-initialization."
    SYNTAX       Integer32 (1..2147483647)

InterfaceIndexOrZero ::= TEXTUAL-CONVENTION
    DISPLAY-HINT "d"
    STATUS       current
    DESCRIPTION
            "This textual convention is an extension of the
            InterfaceIndex convention.  The latter defines a greater
            than zero value used to identify an interface or interface
            sub-layer in the managed system.  This extension permits the
            additional value of zero.  the value zero is object-specific
            and must therefore be defined as part of the description of
            any object which uses this syntax.  Examples of the usage of
            zero might include situations where interface was unknown,
            or when none or all interfaces need to be referenced."
    SYNTAX       Integer32 (0..2147483647)

ifNumber  OBJECT-TYPE
    SYNTAX      Integer32
    MAX-ACCESS  read-only
    STATUS      current
    DESCRIPTION
            "The number of network interfaces (regardless of their
            current state) present on this system."
    ::= { interfaces 1 }

ifTableLastChange  OBJECT-TYPE
    SYNTAX      TimeTicks
    MAX-ACCESS  read-only
    STATUS      current
    DESCRIPTION
            "The value of sysUpTime at the time of the last creation or
            deletion of an entry in the ifTable.  If the number of
            entries has been unchanged since the last re-initialization
            of the local network management subsystem, then this object
            contains a zero value."
    ::= { ifMIBObjects 5 }

-- the Interfaces table

-- The Interfaces table contains information on the entity's


-- interfaces.  Each sub-layer below the internetwork-layer
-- of a network interface is considered to be an interface.

ifTable OBJECT-TYPE
    SYNTAX      SEQUENCE OF IfEntry
    MAX-ACCESS  not-accessible
    STATUS      current
    DESCRIPTION
            "A list of interface entries.  The number of entries is
            given by the value of ifNumber."
    ::= { interfaces 2 }

ifEntry OBJECT-TYPE
    SYNTAX      IfEntry
    MAX-ACCESS  not-accessible
    STATUS      current
    DESCRIPTION
            "An entry containing management information applicable to a
            particular interface."
    INDEX   { ifIndex }
    ::= { ifTable 1 }

IfEntry ::=
    SEQUENCE {
        ifIndex                 InterfaceIndex,
        ifDescr                 DisplayString,
        ifType                  IANAifType,
        ifMtu                   Integer32,
        ifSpeed                 Gauge32,
        ifPhysAddress           PhysAddress,
        ifAdminStatus           INTEGER,
        ifOperStatus            INTEGER,
        ifLastChange            TimeTicks,
        ifInOctets              Counter32,
        ifInUcastPkts           Counter32,
        ifInNUcastPkts          Counter32,  -- deprecated
        ifInDiscards            Counter32,
        ifInErrors              Counter32,
        ifInUnknownProtos       Counter32,
        ifOutOctets             Counter32,
        ifOutUcastPkts          Counter32,
        ifOutNUcastPkts         Counter32,  -- deprecated
        ifOutDiscards           Counter32,
        ifOutErrors             Counter32,
        ifOutQLen               Gauge32,    -- deprecated
        ifSpecific              OBJECT IDENTIFIER -- deprecated
    }


ifIndex OBJECT-TYPE
    SYNTAX      InterfaceIndex
    MAX-ACCESS  read-only
    STATUS      current
    DESCRIPTION
            "A unique value, greater than zero, for each interface.  It
            is recommended that values are assigned contiguously
            starting from 1.  The value for each interface sub-layer
            must remain constant at least from one re-initialization of
            the entity's network management system to the next re-
            initialization."
    ::= { ifEntry 1 }

ifDescr OBJECT-TYPE
    SYNTAX      DisplayString (SIZE (0..255))
    MAX-ACCESS  read-only
    STATUS      current
    DESCRIPTION
            "A textual string containing information about the
            interface.  This string should include the name of the
            manufacturer, the product name and the version of the
            interface hardware/software."
    ::= { ifEntry 2 }

ifType OBJECT-TYPE
    SYNTAX      IANAifType
    MAX-ACCESS  read-only
    STATUS      current
    DESCRIPTION
            "The type of interface.  Additional values for ifType are
            assigned by the Internet Assigned Numbers Authority (IANA),
            through updating the syntax of the IANAifType textual
            convention."
    ::= { ifEntry 3 }

ifMtu OBJECT-TYPE
    SYNTAX      Integer32
    MAX-ACCESS  read-only
    STATUS      current
    DESCRIPTION
            "The size of the largest packet which can be sent/received
            on the interface, specified in octets.  For interfaces that
            are used for transmitting network datagrams, this is the
            size of the largest network datagram that can be sent on the
            interface."
    ::= { ifEntry 4 }

ifSpeed OBJECT-TYPE


    SYNTAX      Gauge32
    MAX-ACCESS  read-only
    STATUS      current
    DESCRIPTION
            "An estimate of the interface's current bandwidth in bits
            per second.  For interfaces which do not vary in bandwidth
            or for those where no accurate estimation can be made, this
            object should contain the nominal bandwidth.  If the
            bandwidth of the interface is greater than the maximum value
            reportable by this object then this object should report its
            maximum value (4,294,967,295) and ifHighSpeed must be used
            to report the interace's speed.  For a sub-layer which has
            no concept of bandwidth, this object should be zero."
    ::= { ifEntry 5 }

ifPhysAddress OBJECT-TYPE
    SYNTAX      PhysAddress
    MAX-ACCESS  read-only
    STATUS      current
    DESCRIPTION
            "The interface's address at its protocol sub-layer.  For
            example, for an 802.x interface, this object normally
            contains a MAC address.  The interface's media-specific MIB
            must define the bit and byte ordering and the format of the
            value of this object.  For interfaces which do not have such
            an address (e.g., a serial line), this object should contain
            an octet string of zero length."
    ::= { ifEntry 6 }

ifAdminStatus OBJECT-TYPE
    SYNTAX  INTEGER {
                up(1),       -- ready to pass packets
                down(2),
                testing(3)   -- in some test mode
            }
    MAX-ACCESS  read-write
    STATUS      current
    DESCRIPTION
            "The desired state of the interface.  The testing(3) state
            indicates that no operational packets can be passed.  When a
            managed system initializes, all interfaces start with
            ifAdminStatus in the down(2) state.  As a result of either
            explicit management action or per configuration information
            retained by the managed system, ifAdminStatus is then
            changed to either the up(1) or testing(3) states (or remains
            in the down(2) state)."
    ::= { ifEntry 7 }


ifOperStatus OBJECT-TYPE
    SYNTAX  INTEGER {
                up(1),        -- ready to pass packets
                down(2),
                testing(3),   -- in some test mode
                unknown(4),   -- status can not be determined
                              -- for some reason.
                dormant(5),
                notPresent(6),    -- some component is missing
                lowerLayerDown(7) -- down due to state of
                                  -- lower-layer interface(s)
            }
    MAX-ACCESS  read-only
    STATUS      current
    DESCRIPTION
            "The current operational state of the interface.  The
            testing(3) state indicates that no operational packets can
            be passed.  If ifAdminStatus is down(2) then ifOperStatus
            should be down(2).  If ifAdminStatus is changed to up(1)
            then ifOperStatus should change to up(1) if the interface is
            ready to transmit and receive network traffic; it should
            change to dormant(5) if the interface is waiting for
            external actions (such as a serial line waiting for an
            incoming connection); it should remain in the down(2) state
            if and only if there is a fault that prevents it from going
            to the up(1) state; it should remain in the notPresent(6)
            state if the interface has missing (typically, hardware)
            components."
    ::= { ifEntry 8 }

ifLastChange OBJECT-TYPE
    SYNTAX      TimeTicks
    MAX-ACCESS  read-only
    STATUS      current
    DESCRIPTION
            "The value of sysUpTime at the time the interface entered
            its current operational state.  If the current state was
            entered prior to the last re-initialization of the local
            network management subsystem, then this object contains a
            zero value."
    ::= { ifEntry 9 }

ifInOctets OBJECT-TYPE
    SYNTAX      Counter32
    MAX-ACCESS  read-only
    STATUS      current
    DESCRIPTION
            "The total number of octets received on the interface,


            including framing characters.

            Discontinuities in the value of this counter can occur at
            re-initialization of the management system, and at other
            times as indicated by the value of
            ifCounterDiscontinuityTime."
    ::= { ifEntry 10 }

ifInUcastPkts OBJECT-TYPE
    SYNTAX      Counter32
    MAX-ACCESS  read-only
    STATUS      current
    DESCRIPTION
            "The number of packets, delivered by this sub-layer to a
            higher (sub-)layer, which were not addressed to a multicast
            or broadcast address at this sub-layer.

            Discontinuities in the value of this counter can occur at
            re-initialization of the management system, and at other
            times as indicated by the value of
            ifCounterDiscontinuityTime."
    ::= { ifEntry 11 }

ifInNUcastPkts OBJECT-TYPE
    SYNTAX  Counter32
    MAX-ACCESS  read-only
    STATUS      deprecated
    DESCRIPTION
            "The number of packets, delivered by this sub-layer to a
            higher (sub-)layer, which were addressed to a multicast or
            broadcast address at this sub-layer.

            Discontinuities in the value of this counter can occur at
            re-initialization of the management system, and at other
            times as indicated by the value of
            ifCounterDiscontinuityTime.

            This object is deprecated in favour of ifInMulticastPkts and
            ifInBroadcastPkts."
    ::= { ifEntry 12 }

ifInDiscards OBJECT-TYPE
    SYNTAX      Counter32
    MAX-ACCESS  read-only
    STATUS      current
    DESCRIPTION
            "The number of inbound packets which were chosen to be
            discarded even though no errors had been detected to prevent


            their being deliverable to a higher-layer protocol.  One
            possible reason for discarding such a packet could be to
            free up buffer space.

            Discontinuities in the value of this counter can occur at
            re-initialization of the management system, and at other
            times as indicated by the value of
            ifCounterDiscontinuityTime."
    ::= { ifEntry 13 }

ifInErrors OBJECT-TYPE
    SYNTAX      Counter32
    MAX-ACCESS  read-only
    STATUS      current
    DESCRIPTION
            "For packet-oriented interfaces, the number of inbound
            packets that contained errors preventing them from being
            deliverable to a higher-layer protocol.  For character-
            oriented or fixed-length interfaces, the number of inbound
            transmission units that contained errors preventing them
            from being deliverable to a higher-layer protocol.

            Discontinuities in the value of this counter can occur at
            re-initialization of the management system, and at other
            times as indicated by the value of
            ifCounterDiscontinuityTime."
    ::= { ifEntry 14 }

ifInUnknownProtos OBJECT-TYPE
    SYNTAX      Counter32
    MAX-ACCESS  read-only
    STATUS      current
    DESCRIPTION
            "For packet-oriented interfaces, the number of packets
            received via the interface which were discarded because of
            an unknown or unsupported protocol.  For character-oriented
            or fixed-length interfaces that support protocol
            multiplexing the number of transmission units received via
            the interface which were discarded because of an unknown or
            unsupported protocol.  For any interface that does not
            support protocol multiplexing, this counter will always be
            0.

            Discontinuities in the value of this counter can occur at
            re-initialization of the management system, and at other
            times as indicated by the value of
            ifCounterDiscontinuityTime."
    ::= { ifEntry 15 }


ifOutOctets OBJECT-TYPE
    SYNTAX      Counter32
    MAX-ACCESS  read-only
    STATUS      current
    DESCRIPTION
            "The total number of octets transmitted out of the
            interface, including framing characters.

            Discontinuities in the value of this counter can occur at
            re-initialization of the management system, and at other
            times as indicated by the value of
            ifCounterDiscontinuityTime."
    ::= { ifEntry 16 }

ifOutUcastPkts OBJECT-TYPE
    SYNTAX      Counter32
    MAX-ACCESS  read-only
    STATUS      current
    DESCRIPTION
            "The total number of packets that higher-level protocols
            requested be transmitted, and which were not addressed to a
            multicast or broadcast address at this sub-layer, including
            those that were discarded or not sent.

            Discontinuities in the value of this counter can occur at
            re-initialization of the management system, and at other
            times as indicated by the value of
            ifCounterDiscontinuityTime."
    ::= { ifEntry 17 }

ifOutNUcastPkts OBJECT-TYPE
    SYNTAX      Counter32
    MAX-ACCESS  read-only
    STATUS      deprecated
    DESCRIPTION
            "The total number of packets that higher-level protocols
            requested be transmitted, and which were addressed to a
            multicast or broadcast address at this sub-layer, including
            those that were discarded or not sent.

            Discontinuities in the value of this counter can occur at
            re-initialization of the management system, and at other
            times as indicated by the value of
            ifCounterDiscontinuityTime.

            This object is deprecated in favour of ifOutMulticastPkts
            and ifOutBroadcastPkts."
    ::= { ifEntry 18 }


ifOutDiscards OBJECT-TYPE
    SYNTAX      Counter32
    MAX-ACCESS  read-only
    STATUS      current
    DESCRIPTION
            "The number of outbound packets which were chosen to be
            discarded even though no errors had been detected to prevent
            their being transmitted.  One possible reason for discarding
            such a packet could be to free up buffer space.

            Discontinuities in the value of this counter can occur at
            re-initialization of the management system, and at other
            times as indicated by the value of
            ifCounterDiscontinuityTime."
    ::= { ifEntry 19 }

ifOutErrors OBJECT-TYPE
    SYNTAX      Counter32
    MAX-ACCESS  read-only
    STATUS      current
    DESCRIPTION
            "For packet-oriented interfaces, the number of outbound
            packets that could not be transmitted because of errors.
            For character-oriented or fixed-length interfaces, the
            number of outbound transmission units that could not be
            transmitted because of errors.

            Discontinuities in the value of this counter can occur at
            re-initialization of the management system, and at other
            times as indicated by the value of
            ifCounterDiscontinuityTime."
    ::= { ifEntry 20 }

ifOutQLen OBJECT-TYPE
    SYNTAX      Gauge32
    MAX-ACCESS  read-only
    STATUS      deprecated
    DESCRIPTION
            "The length of the output packet queue (in packets)."
    ::= { ifEntry 21 }

ifSpecific OBJECT-TYPE
    SYNTAX      OBJECT IDENTIFIER
    MAX-ACCESS  read-only
    STATUS      deprecated
    DESCRIPTION
            "A reference to MIB definitions specific to the particular
            media being used to realize the interface.  It is


            recommended that this value point to an instance of a MIB
            object in the media-specific MIB, i.e., that this object
            have the semantics associated with the InstancePointer
            textual convention defined in RFC 2579.  In fact, it is
            recommended that the media-specific MIB specify what value
            ifSpecific should/can take for values of ifType.  If no MIB
            definitions specific to the particular media are available,
            the value should be set to the OBJECT IDENTIFIER { 0 0 }."
    ::= { ifEntry 22 }

--
--   Extension to the interface table
--
-- This table replaces the ifExtnsTable table.
--

ifXTable        OBJECT-TYPE
    SYNTAX      SEQUENCE OF IfXEntry
    MAX-ACCESS  not-accessible
    STATUS      current
    DESCRIPTION
            "A list of interface entries.  The number of entries is
            given by the value of ifNumber.  This table contains
            additional objects for the interface table."
    ::= { ifMIBObjects 1 }

ifXEntry        OBJECT-TYPE
    SYNTAX      IfXEntry
    MAX-ACCESS  not-accessible
    STATUS      current
    DESCRIPTION
            "An entry containing additional management information
            applicable to a particular interface."
    AUGMENTS    { ifEntry }
    ::= { ifXTable 1 }

IfXEntry ::=
    SEQUENCE {
        ifName                  DisplayString,
        ifInMulticastPkts       Counter32,
        ifInBroadcastPkts       Counter32,
        ifOutMulticastPkts      Counter32,
        ifOutBroadcastPkts      Counter32,
        ifHCInOctets            Counter64,
        ifHCInUcastPkts         Counter64,
        ifHCInMulticastPkts     Counter64,


        ifHCInBroadcastPkts     Counter64,
        ifHCOutOctets           Counter64,
        ifHCOutUcastPkts        Counter64,
        ifHCOutMulticastPkts    Counter64,
        ifHCOutBroadcastPkts    Counter64,
        ifLinkUpDownTrapEnable  INTEGER,
        ifHighSpeed             Gauge32,
        ifPromiscuousMode       TruthValue,
        ifConnectorPresent      TruthValue,
        ifAlias                 DisplayString,
        ifCounterDiscontinuityTime TimeStamp
    }

ifName OBJECT-TYPE
    SYNTAX      DisplayString
    MAX-ACCESS  read-only
    STATUS      current
    DESCRIPTION
            "The textual name of the interface.  The value of this
            object should be the name of the interface as assigned by
            the local device and should be suitable for use in commands
            entered at the device's `console'.  This might be a text
            name, such as `le0' or a simple port number, such as `1',
            depending on the interface naming syntax of the device.  If
            several entries in the ifTable together represent a single
            interface as named by the device, then each will have the
            same value of ifName.  Note that for an agent which responds
            to SNMP queries concerning an interface on some other
            (proxied) device, then the value of ifName for such an
            interface is the proxied device's local name for it.

            If there is no local name, or this object is otherwise not
            applicable, then this object contains a zero-length string."
    ::= { ifXEntry 1 }

ifInMulticastPkts OBJECT-TYPE
    SYNTAX      Counter32
    MAX-ACCESS  read-only
    STATUS      current
    DESCRIPTION
            "The number of packets, delivered by this sub-layer to a
            higher (sub-)layer, which were addressed to a multicast
            address at this sub-layer.  For a MAC layer protocol, this
            includes both Group and Functional addresses.

            Discontinuities in the value of this counter can occur at
            re-initialization of the management system, and at other


            times as indicated by the value of
            ifCounterDiscontinuityTime."
    ::= { ifXEntry 2 }

ifInBroadcastPkts OBJECT-TYPE
    SYNTAX      Counter32
    MAX-ACCESS  read-only
    STATUS      current
    DESCRIPTION
            "The number of packets, delivered by this sub-layer to a
            higher (sub-)layer, which were addressed to a broadcast
            address at this sub-layer.

            Discontinuities in the value of this counter can occur at
            re-initialization of the management system, and at other
            times as indicated by the value of
            ifCounterDiscontinuityTime."
    ::= { ifXEntry 3 }

ifOutMulticastPkts OBJECT-TYPE
    SYNTAX      Counter32
    MAX-ACCESS  read-only
    STATUS      current
    DESCRIPTION
            "The total number of packets that higher-level protocols
            requested be transmitted, and which were addressed to a
            multicast address at this sub-layer, including those that
            were discarded or not sent.  For a MAC layer protocol, this
            includes both Group and Functional addresses.

            Discontinuities in the value of this counter can occur at
            re-initialization of the management system, and at other
            times as indicated by the value of
            ifCounterDiscontinuityTime."
    ::= { ifXEntry 4 }

ifOutBroadcastPkts OBJECT-TYPE
    SYNTAX      Counter32
    MAX-ACCESS  read-only
    STATUS      current
    DESCRIPTION
            "The total number of packets that higher-level protocols
            requested be transmitted, and which were addressed to a
            broadcast address at this sub-layer, including those that
            were discarded or not sent.

            Discontinuities in the value of this counter can occur at
            re-initialization of the management system, and at other


            times as indicated by the value of
            ifCounterDiscontinuityTime."
    ::= { ifXEntry 5 }

--
-- High Capacity Counter objects.  These objects are all
-- 64 bit versions of the "basic" ifTable counters.  These
-- objects all have the same basic semantics as their 32-bit
-- counterparts, however, their syntax has been extended
-- to 64 bits.
--

ifHCInOctets OBJECT-TYPE
    SYNTAX      Counter64
    MAX-ACCESS  read-only
    STATUS      current
    DESCRIPTION
            "The total number of octets received on the interface,
            including framing characters.  This object is a 64-bit
            version of ifInOctets.

            Discontinuities in the value of this counter can occur at
            re-initialization of the management system, and at other
            times as indicated by the value of
            ifCounterDiscontinuityTime."
    ::= { ifXEntry 6 }

ifHCInUcastPkts OBJECT-TYPE
    SYNTAX      Counter64
    MAX-ACCESS  read-only
    STATUS      current
    DESCRIPTION
            "The number of packets, delivered by this sub-layer to a
            higher (sub-)layer, which were not addressed to a multicast
            or broadcast address at this sub-layer.  This object is a
            64-bit version of ifInUcastPkts.

            Discontinuities in the value of this counter can occur at
            re-initialization of the management system, and at other
            times as indicated by the value of
            ifCounterDiscontinuityTime."
    ::= { ifXEntry 7 }

ifHCInMulticastPkts OBJECT-TYPE
    SYNTAX      Counter64
    MAX-ACCESS  read-only
    STATUS      current
    DESCRIPTION


            "The number of packets, delivered by this sub-layer to a
            higher (sub-)layer, which were addressed to a multicast
            address at this sub-layer.  For a MAC layer protocol, this
            includes both Group and Functional addresses.  This object
            is a 64-bit version of ifInMulticastPkts.

            Discontinuities in the value of this counter can occur at
            re-initialization of the management system, and at other
            times as indicated by the value of
            ifCounterDiscontinuityTime."
    ::= { ifXEntry 8 }

ifHCInBroadcastPkts OBJECT-TYPE
    SYNTAX      Counter64
    MAX-ACCESS  read-only
    STATUS      current
    DESCRIPTION
            "The number of packets, delivered by this sub-layer to a
            higher (sub-)layer, which were addressed to a broadcast
            address at this sub-layer.  This object is a 64-bit version
            of ifInBroadcastPkts.

            Discontinuities in the value of this counter can occur at
            re-initialization of the management system, and at other
            times as indicated by the value of
            ifCounterDiscontinuityTime."
    ::= { ifXEntry 9 }

ifHCOutOctets OBJECT-TYPE
    SYNTAX      Counter64
    MAX-ACCESS  read-only
    STATUS      current
    DESCRIPTION
            "The total number of octets transmitted out of the
            interface, including framing characters.  This object is a
            64-bit version of ifOutOctets.

            Discontinuities in the value of this counter can occur at
            re-initialization of the management system, and at other
            times as indicated by the value of
            ifCounterDiscontinuityTime."
    ::= { ifXEntry 10 }

ifHCOutUcastPkts OBJECT-TYPE
    SYNTAX      Counter64
    MAX-ACCESS  read-only
    STATUS      current
    DESCRIPTION


            "The total number of packets that higher-level protocols
            requested be transmitted, and which were not addressed to a
            multicast or broadcast address at this sub-layer, including
            those that were discarded or not sent.  This object is a
            64-bit version of ifOutUcastPkts.

            Discontinuities in the value of this counter can occur at
            re-initialization of the management system, and at other
            times as indicated by the value of
            ifCounterDiscontinuityTime."
    ::= { ifXEntry 11 }

ifHCOutMulticastPkts OBJECT-TYPE
    SYNTAX      Counter64
    MAX-ACCESS  read-only
    STATUS      current
    DESCRIPTION
            "The total number of packets that higher-level protocols
            requested be transmitted, and which were addressed to a
            multicast address at this sub-layer, including those that
            were discarded or not sent.  For a MAC layer protocol, this
            includes both Group and Functional addresses.  This object
            is a 64-bit version of ifOutMulticastPkts.

            Discontinuities in the value of this counter can occur at
            re-initialization of the management system, and at other
            times as indicated by the value of
            ifCounterDiscontinuityTime."
    ::= { ifXEntry 12 }

ifHCOutBroadcastPkts OBJECT-TYPE
    SYNTAX      Counter64
    MAX-ACCESS  read-only
    STATUS      current
    DESCRIPTION
            "The total number of packets that higher-level protocols
            requested be transmitted, and which were addressed to a
            broadcast address at this sub-layer, including those that
            were discarded or not sent.  This object is a 64-bit version
            of ifOutBroadcastPkts.

            Discontinuities in the value of this counter can occur at
            re-initialization of the management system, and at other
            times as indicated by the value of
            ifCounterDiscontinuityTime."
    ::= { ifXEntry 13 }

ifLinkUpDownTrapEnable  OBJECT-TYPE


    SYNTAX      INTEGER { enabled(1), disabled(2) }
    MAX-ACCESS  read-write
    STATUS      current
    DESCRIPTION
            "Indicates whether linkUp/linkDown traps should be generated
            for this interface.

            By default, this object should have the value enabled(1) for
            interfaces which do not operate on 'top' of any other
            interface (as defined in the ifStackTable), and disabled(2)
            otherwise."
    ::= { ifXEntry 14 }

ifHighSpeed OBJECT-TYPE
    SYNTAX      Gauge32
    MAX-ACCESS  read-only
    STATUS      current
    DESCRIPTION
            "An estimate of the interface's current bandwidth in units
            of 1,000,000 bits per second.  If this object reports a
            value of `n' then the speed of the interface is somewhere in
            the range of `n-500,000' to `n+499,999'.  For interfaces
            which do not vary in bandwidth or for those where no
            accurate estimation can be made, this object should contain
            the nominal bandwidth.  For a sub-layer which has no concept
            of bandwidth, this object should be zero."
    ::= { ifXEntry 15 }

ifPromiscuousMode  OBJECT-TYPE
    SYNTAX      TruthValue
    MAX-ACCESS  read-write
    STATUS      current
    DESCRIPTION
            "This object has a value of false(2) if this interface only
            accepts packets/frames that are addressed to this station.
            This object has a value of true(1) when the station accepts
            all packets/frames transmitted on the media.  The value
            true(1) is only legal on certain types of media.  If legal,
            setting this object to a value of true(1) may require the
            interface to be reset before becoming effective.

            The value of ifPromiscuousMode does not affect the reception
            of broadcast and multicast packets/frames by the interface."
    ::= { ifXEntry 16 }

ifConnectorPresent   OBJECT-TYPE
    SYNTAX      TruthValue
    MAX-ACCESS  read-only


    STATUS      current
    DESCRIPTION
            "This object has the value 'true(1)' if the interface
            sublayer has a physical connector and the value 'false(2)'
            otherwise."
    ::= { ifXEntry 17 }

ifAlias   OBJECT-TYPE
    SYNTAX      DisplayString (SIZE(0..64))
    MAX-ACCESS  read-write
    STATUS      current
    DESCRIPTION
            "This object is an 'alias' name for the interface as
            specified by a network manager, and provides a non-volatile
            'handle' for the interface.

            On the first instantiation of an interface, the value of
            ifAlias associated with that interface is the zero-length
            string.  As and when a value is written into an instance of
            ifAlias through a network management set operation, then the
            agent must retain the supplied value in the ifAlias instance
            associated with the same interface for as long as that
            interface remains instantiated, including across all re-
            initializations/reboots of the network management system,
            including those which result in a change of the interface's
            ifIndex value.

            An example of the value which a network manager might store
            in this object for a WAN interface is the (Telco's) circuit
            number/identifier of the interface.

            Some agents may support write-access only for interfaces
            having particular values of ifType.  An agent which supports
            write access to this object is required to keep the value in
            non-volatile storage, but it may limit the length of new
            values depending on how much storage is already occupied by
            the current values for other interfaces."
    ::= { ifXEntry 18 }

ifCounterDiscontinuityTime OBJECT-TYPE
    SYNTAX      TimeStamp
    MAX-ACCESS  read-only
    STATUS      current
    DESCRIPTION
            "The value of sysUpTime on the most recent occasion at which
            any one or more of this interface's counters suffered a
            discontinuity.  The relevant counters are the specific
            instances associated with this interface of any Counter32 or


            Counter64 object contained in the ifTable or ifXTable.  If
            no such discontinuities have occurred since the last re-
            initialization of the local management subsystem, then this
            object contains a zero value."
    ::= { ifXEntry 19 }

--           The Interface Stack Group
--
-- Implementation of this group is optional, but strongly recommended
-- for all systems
--

ifStackTable  OBJECT-TYPE
     SYNTAX        SEQUENCE OF IfStackEntry
     MAX-ACCESS    not-accessible
     STATUS        current
     DESCRIPTION
            "The table containing information on the relationships
            between the multiple sub-layers of network interfaces.  In
            particular, it contains information on which sub-layers run
            'on top of' which other sub-layers, where each sub-layer
            corresponds to a conceptual row in the ifTable.  For
            example, when the sub-layer with ifIndex value x runs over
            the sub-layer with ifIndex value y, then this table
            contains:

              ifStackStatus.x.y=active

            For each ifIndex value, I, which identifies an active
            interface, there are always at least two instantiated rows
            in this table associated with I.  For one of these rows, I
            is the value of ifStackHigherLayer; for the other, I is the
            value of ifStackLowerLayer.  (If I is not involved in
            multiplexing, then these are the only two rows associated
            with I.)

            For example, two rows exist even for an interface which has
            no others stacked on top or below it:

              ifStackStatus.0.x=active
              ifStackStatus.x.0=active "
     ::= { ifMIBObjects 2 }

ifStackEntry  OBJECT-TYPE
     SYNTAX        IfStackEntry
     MAX-ACCESS    not-accessible
     STATUS        current


     DESCRIPTION
            "Information on a particular relationship between two sub-
            layers, specifying that one sub-layer runs on 'top' of the
            other sub-layer.  Each sub-layer corresponds to a conceptual
            row in the ifTable."
     INDEX { ifStackHigherLayer, ifStackLowerLayer }
     ::= { ifStackTable 1 }

IfStackEntry ::=
    SEQUENCE {
        ifStackHigherLayer  InterfaceIndexOrZero,
        ifStackLowerLayer   InterfaceIndexOrZero,
        ifStackStatus       RowStatus
     }

ifStackHigherLayer  OBJECT-TYPE
     SYNTAX        InterfaceIndexOrZero
     MAX-ACCESS    not-accessible
     STATUS        current
     DESCRIPTION
            "The value of ifIndex corresponding to the higher sub-layer
            of the relationship, i.e., the sub-layer which runs on 'top'
            of the sub-layer identified by the corresponding instance of
            ifStackLowerLayer.  If there is no higher sub-layer (below
            the internetwork layer), then this object has the value 0."
     ::= { ifStackEntry 1 }

ifStackLowerLayer  OBJECT-TYPE
     SYNTAX        InterfaceIndexOrZero
     MAX-ACCESS    not-accessible
     STATUS        current
     DESCRIPTION
            "The value of ifIndex corresponding to the lower sub-layer
            of the relationship, i.e., the sub-layer which runs 'below'
            the sub-layer identified by the corresponding instance of
            ifStackHigherLayer.  If there is no lower sub-layer, then
            this object has the value 0."
     ::= { ifStackEntry 2 }

ifStackStatus  OBJECT-TYPE
    SYNTAX         RowStatus
    MAX-ACCESS     read-create
    STATUS         current
    DESCRIPTION


            "The status of the relationship between two sub-layers.

            Changing the value of this object from 'active' to
            'notInService' or 'destroy' will likely have consequences up
            and down the interface stack.  Thus, write access to this
            object is likely to be inappropriate for some types of
            interfaces, and many implementations will choose not to
            support write-access for any type of interface."
    ::= { ifStackEntry 3 }

ifStackLastChange OBJECT-TYPE
    SYNTAX         TimeTicks
    MAX-ACCESS     read-only
    STATUS         current
    DESCRIPTION
            "The value of sysUpTime at the time of the last change of
            the (whole) interface stack.  A change of the interface
            stack is defined to be any creation, deletion, or change in
            value of any instance of ifStackStatus.  If the interface
            stack has been unchanged since the last re-initialization of
            the local network management subsystem, then this object
            contains a zero value."
    ::= { ifMIBObjects 6 }

--   Generic Receive Address Table
--
-- This group of objects is mandatory for all types of
-- interfaces which can receive packets/frames addressed to
-- more than one address.
--
-- This table replaces the ifExtnsRcvAddr table.  The main
-- difference is that this table makes use of the RowStatus
-- textual convention, while ifExtnsRcvAddr did not.

ifRcvAddressTable  OBJECT-TYPE
    SYNTAX      SEQUENCE OF IfRcvAddressEntry
    MAX-ACCESS  not-accessible
    STATUS      current
    DESCRIPTION
            "This table contains an entry for each address (broadcast,
            multicast, or uni-cast) for which the system will receive
            packets/frames on a particular interface, except as follows:

            - for an interface operating in promiscuous mode, entries
            are only required for those addresses for which the system
            would receive frames were it not operating in promiscuous
            mode.


            - for 802.5 functional addresses, only one entry is
            required, for the address which has the functional address
            bit ANDed with the bit mask of all functional addresses for
            which the interface will accept frames.

            A system is normally able to use any unicast address which
            corresponds to an entry in this table as a source address."
    ::= { ifMIBObjects 4 }

ifRcvAddressEntry  OBJECT-TYPE
    SYNTAX      IfRcvAddressEntry
    MAX-ACCESS  not-accessible
    STATUS      current
    DESCRIPTION
            "A list of objects identifying an address for which the
            system will accept packets/frames on the particular
            interface identified by the index value ifIndex."
    INDEX  { ifIndex, ifRcvAddressAddress }
    ::= { ifRcvAddressTable 1 }

IfRcvAddressEntry ::=
    SEQUENCE {
        ifRcvAddressAddress   PhysAddress,
        ifRcvAddressStatus    RowStatus,
        ifRcvAddressType      INTEGER
    }

ifRcvAddressAddress OBJECT-TYPE
    SYNTAX      PhysAddress
    MAX-ACCESS  not-accessible
    STATUS      current
    DESCRIPTION
            "An address for which the system will accept packets/frames
            on this entry's interface."
    ::= { ifRcvAddressEntry 1 }

ifRcvAddressStatus OBJECT-TYPE
    SYNTAX      RowStatus
    MAX-ACCESS  read-create
    STATUS      current
    DESCRIPTION
            "This object is used to create and delete rows in the
            ifRcvAddressTable."

    ::= { ifRcvAddressEntry 2 }

ifRcvAddressType OBJECT-TYPE
    SYNTAX      INTEGER {


                    other(1),
                    volatile(2),
                    nonVolatile(3)
                }

    MAX-ACCESS  read-create
    STATUS      current
    DESCRIPTION
            "This object has the value nonVolatile(3) for those entries
            in the table which are valid and will not be deleted by the
            next restart of the managed system.  Entries having the
            value volatile(2) are valid and exist, but have not been
            saved, so that will not exist after the next restart of the
            managed system.  Entries having the value other(1) are valid
            and exist but are not classified as to whether they will
            continue to exist after the next restart."

    DEFVAL  { volatile }
    ::= { ifRcvAddressEntry 3 }

-- definition of interface-related traps.

linkDown NOTIFICATION-TYPE
    OBJECTS { ifIndex, ifAdminStatus, ifOperStatus }
    STATUS  current
    DESCRIPTION
            "A linkDown trap signifies that the SNMP entity, acting in
            an agent role, has detected that the ifOperStatus object for
            one of its communication links is about to enter the down
            state from some other state (but not from the notPresent
            state).  This other state is indicated by the included value
            of ifOperStatus."
    ::= { snmpTraps 3 }

linkUp NOTIFICATION-TYPE
    OBJECTS { ifIndex, ifAdminStatus, ifOperStatus }
    STATUS  current
    DESCRIPTION
            "A linkUp trap signifies that the SNMP entity, acting in an
            agent role, has detected that the ifOperStatus object for
            one of its communication links left the down state and
            transitioned into some other state (but not into the
            notPresent state).  This other state is indicated by the
            included value of ifOperStatus."
    ::= { snmpTraps 4 }

-- conformance information


ifConformance OBJECT IDENTIFIER ::= { ifMIB 2 }

ifGroups      OBJECT IDENTIFIER ::= { ifConformance 1 }
ifCompliances OBJECT IDENTIFIER ::= { ifConformance 2 }

-- compliance statements

ifCompliance3 MODULE-COMPLIANCE
    STATUS  current
    DESCRIPTION
            "The compliance statement for SNMP entities which have
            network interfaces."

    MODULE  -- this module
        MANDATORY-GROUPS { ifGeneralInformationGroup,
                           linkUpDownNotificationsGroup }

-- The groups:
--        ifFixedLengthGroup
--        ifHCFixedLengthGroup
--        ifPacketGroup
--        ifHCPacketGroup
--        ifVHCPacketGroup
-- are mutually exclusive; at most one of these groups is implemented
-- for a particular interface.  When any of these groups is implemented
-- for a particular interface, then ifCounterDiscontinuityGroup must
-- also be implemented for that interface.

        GROUP       ifFixedLengthGroup
        DESCRIPTION
            "This group is mandatory for those network interfaces which
            are character-oriented or transmit data in fixed-length
            transmission units, and for which the value of the
            corresponding instance of ifSpeed is less than or equal to
            20,000,000 bits/second."

        GROUP       ifHCFixedLengthGroup
        DESCRIPTION
            "This group is mandatory for those network interfaces which
            are character-oriented or transmit data in fixed-length
            transmission units, and for which the value of the
            corresponding instance of ifSpeed is greater than 20,000,000
            bits/second."

        GROUP       ifPacketGroup
        DESCRIPTION


            "This group is mandatory for those network interfaces which
            are packet-oriented, and for which the value of the
            corresponding instance of ifSpeed is less than or equal to
            20,000,000 bits/second."

        GROUP       ifHCPacketGroup
        DESCRIPTION
            "This group is mandatory only for those network interfaces
            which are packet-oriented and for which the value of the
            corresponding instance of ifSpeed is greater than 20,000,000
            bits/second but less than or equal to 650,000,000
            bits/second."

        GROUP       ifVHCPacketGroup
        DESCRIPTION
            "This group is mandatory only for those network interfaces
            which are packet-oriented and for which the value of the
            corresponding instance of ifSpeed is greater than
            650,000,000 bits/second."

        GROUP       ifCounterDiscontinuityGroup
        DESCRIPTION
            "This group is mandatory for those network interfaces that
            are required to maintain counters (i.e., those for which one
            of the ifFixedLengthGroup, ifHCFixedLengthGroup,
            ifPacketGroup, ifHCPacketGroup, or ifVHCPacketGroup is
            mandatory)."

        GROUP       ifRcvAddressGroup
        DESCRIPTION
            "The applicability of this group MUST be defined by the
            media-specific MIBs.  Media-specific MIBs must define the
            exact meaning, use, and semantics of the addresses in this
            group."

        OBJECT      ifLinkUpDownTrapEnable
        MIN-ACCESS  read-only
        DESCRIPTION
            "Write access is not required."

        OBJECT      ifPromiscuousMode
        MIN-ACCESS  read-only
        DESCRIPTION
            "Write access is not required."

        OBJECT       ifAdminStatus


        SYNTAX       INTEGER { up(1), down(2) }
        MIN-ACCESS   read-only
        DESCRIPTION
            "Write access is not required, nor is support for the value
            testing(3)."

        OBJECT       ifAlias
        MIN-ACCESS   read-only
        DESCRIPTION
            "Write access is not required."

    ::= { ifCompliances 3 }

-- units of conformance

ifGeneralInformationGroup    OBJECT-GROUP
    OBJECTS { ifIndex, ifDescr, ifType, ifSpeed, ifPhysAddress,
              ifAdminStatus, ifOperStatus, ifLastChange,
              ifLinkUpDownTrapEnable, ifConnectorPresent,
              ifHighSpeed, ifName, ifNumber, ifAlias,
              ifTableLastChange }
    STATUS  current
    DESCRIPTION
            "A collection of objects providing information applicable to
            all network interfaces."
    ::= { ifGroups 10 }

-- the following five groups are mutually exclusive; at most
-- one of these groups is implemented for any interface

ifFixedLengthGroup    OBJECT-GROUP
    OBJECTS { ifInOctets, ifOutOctets, ifInUnknownProtos,
              ifInErrors, ifOutErrors }
    STATUS  current
    DESCRIPTION
            "A collection of objects providing information specific to
            non-high speed (non-high speed interfaces transmit and
            receive at speeds less than or equal to 20,000,000
            bits/second) character-oriented or fixed-length-transmission
            network interfaces."
    ::= { ifGroups 2 }

ifHCFixedLengthGroup    OBJECT-GROUP
    OBJECTS { ifHCInOctets, ifHCOutOctets,
              ifInOctets, ifOutOctets, ifInUnknownProtos,
              ifInErrors, ifOutErrors }
    STATUS  current
    DESCRIPTION


            "A collection of objects providing information specific to
            high speed (greater than 20,000,000 bits/second) character-
            oriented or fixed-length-transmission network interfaces."
    ::= { ifGroups 3 }

ifPacketGroup    OBJECT-GROUP
    OBJECTS { ifInOctets, ifOutOctets, ifInUnknownProtos,
              ifInErrors, ifOutErrors,
              ifMtu, ifInUcastPkts, ifInMulticastPkts,
              ifInBroadcastPkts, ifInDiscards,
              ifOutUcastPkts, ifOutMulticastPkts,
              ifOutBroadcastPkts, ifOutDiscards,
              ifPromiscuousMode }
    STATUS  current
    DESCRIPTION
            "A collection of objects providing information specific to
            non-high speed (non-high speed interfaces transmit and
            receive at speeds less than or equal to 20,000,000
            bits/second) packet-oriented network interfaces."
    ::= { ifGroups 4 }

ifHCPacketGroup    OBJECT-GROUP
    OBJECTS { ifHCInOctets, ifHCOutOctets,
              ifInOctets, ifOutOctets, ifInUnknownProtos,
              ifInErrors, ifOutErrors,
              ifMtu, ifInUcastPkts, ifInMulticastPkts,
              ifInBroadcastPkts, ifInDiscards,
              ifOutUcastPkts, ifOutMulticastPkts,
              ifOutBroadcastPkts, ifOutDiscards,
              ifPromiscuousMode }
    STATUS  current
    DESCRIPTION
            "A collection of objects providing information specific to
            high speed (greater than 20,000,000 bits/second but less
            than or equal to 650,000,000 bits/second) packet-oriented
            network interfaces."
    ::= { ifGroups 5 }

ifVHCPacketGroup    OBJECT-GROUP
    OBJECTS { ifHCInUcastPkts, ifHCInMulticastPkts,
              ifHCInBroadcastPkts, ifHCOutUcastPkts,
              ifHCOutMulticastPkts, ifHCOutBroadcastPkts,
              ifHCInOctets, ifHCOutOctets,
              ifInOctets, ifOutOctets, ifInUnknownProtos,
              ifInErrors, ifOutErrors,
              ifMtu, ifInUcastPkts, ifInMulticastPkts,
              ifInBroadcastPkts, ifInDiscards,
              ifOutUcastPkts, ifOutMulticastPkts,


              ifOutBroadcastPkts, ifOutDiscards,
              ifPromiscuousMode }
    STATUS  current
    DESCRIPTION
            "A collection of objects providing information specific to
            higher speed (greater than 650,000,000 bits/second) packet-
            oriented network interfaces."
    ::= { ifGroups 6 }

ifRcvAddressGroup    OBJECT-GROUP
    OBJECTS { ifRcvAddressStatus, ifRcvAddressType }
    STATUS  current
    DESCRIPTION
            "A collection of objects providing information on the
            multiple addresses which an interface receives."
    ::= { ifGroups 7 }

ifStackGroup2    OBJECT-GROUP
    OBJECTS { ifStackStatus, ifStackLastChange }
    STATUS  current
    DESCRIPTION
            "A collection of objects providing information on the
            layering of MIB-II interfaces."
    ::= { ifGroups 11 }

ifCounterDiscontinuityGroup  OBJECT-GROUP
    OBJECTS { ifCounterDiscontinuityTime }
    STATUS  current
    DESCRIPTION
            "A collection of objects providing information specific to
            interface counter discontinuities."
    ::= { ifGroups 13 }

linkUpDownNotificationsGroup  NOTIFICATION-GROUP
    NOTIFICATIONS { linkUp, linkDown }
    STATUS  current
    DESCRIPTION
            "The notifications which indicate specific changes in the
            value of ifOperStatus."
    ::= { ifGroups 14 }

-- Deprecated Definitions - Objects

--
--    The Interface Test Table
--
-- This group of objects is optional.  However, a media-specific


-- MIB may make implementation of this group mandatory.
--
-- This table replaces the ifExtnsTestTable
--

ifTestTable   OBJECT-TYPE
    SYNTAX      SEQUENCE OF IfTestEntry
    MAX-ACCESS  not-accessible
    STATUS      deprecated
    DESCRIPTION
            "This table contains one entry per interface.  It defines
            objects which allow a network manager to instruct an agent
            to test an interface for various faults.  Tests for an
            interface are defined in the media-specific MIB for that
            interface.  After invoking a test, the object ifTestResult
            can be read to determine the outcome.  If an agent can not
            perform the test, ifTestResult is set to so indicate.  The
            object ifTestCode can be used to provide further test-
            specific or interface-specific (or even enterprise-specific)
            information concerning the outcome of the test.  Only one
            test can be in progress on each interface at any one time.
            If one test is in progress when another test is invoked, the
            second test is rejected.  Some agents may reject a test when
            a prior test is active on another interface.

            Before starting a test, a manager-station must first obtain
            'ownership' of the entry in the ifTestTable for the
            interface to be tested.  This is accomplished with the
            ifTestId and ifTestStatus objects as follows:

          try_again:
              get (ifTestId, ifTestStatus)
              while (ifTestStatus != notInUse)
                  /*
                   * Loop while a test is running or some other
                   * manager is configuring a test.
                   */
                  short delay
                  get (ifTestId, ifTestStatus)
              }

              /*
               * Is not being used right now -- let's compete
               * to see who gets it.
               */
              lock_value = ifTestId

              if ( set(ifTestId = lock_value, ifTestStatus = inUse,


                       ifTestOwner = 'my-IP-address') == FAILURE)
                  /*
                   * Another manager got the ifTestEntry -- go
                   * try again
                   */
                  goto try_again;

              /*
               * I have the lock
               */
              set up any test parameters.

              /*
               * This starts the test
               */
              set(ifTestType = test_to_run);

              wait for test completion by polling ifTestResult

              when test completes, agent sets ifTestResult
                   agent also sets ifTestStatus = 'notInUse'

              retrieve any additional test results, and ifTestId

              if (ifTestId == lock_value+1) results are valid

            A manager station first retrieves the value of the
            appropriate ifTestId and ifTestStatus objects, periodically
            repeating the retrieval if necessary, until the value of
            ifTestStatus is 'notInUse'.  The manager station then tries
            to set the same ifTestId object to the value it just
            retrieved, the same ifTestStatus object to 'inUse', and the
            corresponding ifTestOwner object to a value indicating
            itself.  If the set operation succeeds then the manager has
            obtained ownership of the ifTestEntry, and the value of the
            ifTestId object is incremented by the agent (per the
            semantics of TestAndIncr).  Failure of the set operation
            indicates that some other manager has obtained ownership of
            the ifTestEntry.

            Once ownership is obtained, any test parameters can be
            setup, and then the test is initiated by setting ifTestType.
            On completion of the test, the agent sets ifTestStatus to
            'notInUse'.  Once this occurs, the manager can retrieve the
            results.  In the (rare) event that the invocation of tests
            by two network managers were to overlap, then there would be
            a possibility that the first test's results might be
            overwritten by the second test's results prior to the first


            results being read.  This unlikely circumstance can be
            detected by a network manager retrieving ifTestId at the
            same time as retrieving the test results, and ensuring that
            the results are for the desired request.

            If ifTestType is not set within an abnormally long period of
            time after ownership is obtained, the agent should time-out
            the manager, and reset the value of the ifTestStatus object
            back to 'notInUse'.  It is suggested that this time-out
            period be 5 minutes.

            In general, a management station must not retransmit a
            request to invoke a test for which it does not receive a
            response; instead, it properly inspects an agent's MIB to
            determine if the invocation was successful.  Only if the
            invocation was unsuccessful, is the invocation request
            retransmitted.

            Some tests may require the interface to be taken off-line in
            order to execute them, or may even require the agent to
            reboot after completion of the test.  In these
            circumstances, communication with the management station
            invoking the test may be lost until after completion of the
            test.  An agent is not required to support such tests.
            However, if such tests are supported, then the agent should
            make every effort to transmit a response to the request
            which invoked the test prior to losing communication.  When
            the agent is restored to normal service, the results of the
            test are properly made available in the appropriate objects.
            Note that this requires that the ifIndex value assigned to
            an interface must be unchanged even if the test causes a
            reboot.  An agent must reject any test for which it cannot,
            perhaps due to resource constraints, make available at least
            the minimum amount of information after that test
            completes."
    ::= { ifMIBObjects 3 }

ifTestEntry OBJECT-TYPE
    SYNTAX       IfTestEntry
    MAX-ACCESS   not-accessible
    STATUS       deprecated
    DESCRIPTION
            "An entry containing objects for invoking tests on an
            interface."
    AUGMENTS  { ifEntry }
    ::= { ifTestTable 1 }

IfTestEntry ::=


    SEQUENCE {
        ifTestId           TestAndIncr,
        ifTestStatus       INTEGER,
        ifTestType         AutonomousType,
        ifTestResult       INTEGER,
        ifTestCode         OBJECT IDENTIFIER,
        ifTestOwner        OwnerString
    }

ifTestId         OBJECT-TYPE
    SYNTAX       TestAndIncr
    MAX-ACCESS   read-write
    STATUS       deprecated
    DESCRIPTION
            "This object identifies the current invocation of the
            interface's test."
    ::= { ifTestEntry 1 }

ifTestStatus     OBJECT-TYPE
    SYNTAX       INTEGER { notInUse(1), inUse(2) }
    MAX-ACCESS   read-write
    STATUS       deprecated
    DESCRIPTION
            "This object indicates whether or not some manager currently
            has the necessary 'ownership' required to invoke a test on
            this interface.  A write to this object is only successful
            when it changes its value from 'notInUse(1)' to 'inUse(2)'.
            After completion of a test, the agent resets the value back
            to 'notInUse(1)'."
    ::= { ifTestEntry 2 }

ifTestType       OBJECT-TYPE
    SYNTAX       AutonomousType
    MAX-ACCESS   read-write
    STATUS       deprecated
    DESCRIPTION
            "A control variable used to start and stop operator-
            initiated interface tests.  Most OBJECT IDENTIFIER values
            assigned to tests are defined elsewhere, in association with
            specific types of interface.  However, this document assigns
            a value for a full-duplex loopback test, and defines the
            special meanings of the subject identifier:

                noTest  OBJECT IDENTIFIER ::= { 0 0 }

            When the value noTest is written to this object, no action
            is taken unless a test is in progress, in which case the
            test is aborted.  Writing any other value to this object is


            only valid when no test is currently in progress, in which
            case the indicated test is initiated.

            When read, this object always returns the most recent value
            that ifTestType was set to.  If it has not been set since
            the last initialization of the network management subsystem
            on the agent, a value of noTest is returned."
    ::= { ifTestEntry 3 }

ifTestResult  OBJECT-TYPE
    SYNTAX       INTEGER {
                     none(1),          -- no test yet requested
                     success(2),
                     inProgress(3),
                     notSupported(4),
                     unAbleToRun(5),   -- due to state of system
                     aborted(6),
                     failed(7)
                 }
    MAX-ACCESS   read-only
    STATUS       deprecated
    DESCRIPTION
            "This object contains the result of the most recently
            requested test, or the value none(1) if no tests have been
            requested since the last reset.  Note that this facility
            provides no provision for saving the results of one test
            when starting another, as could be required if used by
            multiple managers concurrently."
    ::= { ifTestEntry 4 }

ifTestCode  OBJECT-TYPE
    SYNTAX       OBJECT IDENTIFIER
    MAX-ACCESS   read-only
    STATUS       deprecated
    DESCRIPTION
            "This object contains a code which contains more specific
            information on the test result, for example an error-code
            after a failed test.  Error codes and other values this
            object may take are specific to the type of interface and/or
            test.  The value may have the semantics of either the
            AutonomousType or InstancePointer textual conventions as
            defined in RFC 2579.  The identifier:

                testCodeUnknown  OBJECT IDENTIFIER ::= { 0 0 }

            is defined for use if no additional result code is
            available."
    ::= { ifTestEntry 5 }


ifTestOwner      OBJECT-TYPE
    SYNTAX       OwnerString
    MAX-ACCESS   read-write
    STATUS       deprecated
    DESCRIPTION
            "The entity which currently has the 'ownership' required to
            invoke a test on this interface."
    ::= { ifTestEntry 6 }

-- Deprecated Definitions - Groups

ifGeneralGroup    OBJECT-GROUP
    OBJECTS { ifDescr, ifType, ifSpeed, ifPhysAddress,
              ifAdminStatus, ifOperStatus, ifLastChange,
              ifLinkUpDownTrapEnable, ifConnectorPresent,
              ifHighSpeed, ifName }
    STATUS  deprecated
    DESCRIPTION
            "A collection of objects deprecated in favour of
            ifGeneralInformationGroup."
    ::= { ifGroups 1 }

ifTestGroup    OBJECT-GROUP
    OBJECTS { ifTestId, ifTestStatus, ifTestType,
              ifTestResult, ifTestCode, ifTestOwner }
    STATUS  deprecated
    DESCRIPTION
            "A collection of objects providing the ability to invoke
            tests on an interface."
    ::= { ifGroups 8 }

ifStackGroup    OBJECT-GROUP
    OBJECTS { ifStackStatus }
    STATUS  deprecated
    DESCRIPTION
            "The previous collection of objects providing information on
            the layering of MIB-II interfaces."
    ::= { ifGroups 9 }

ifOldObjectsGroup    OBJECT-GROUP
    OBJECTS { ifInNUcastPkts, ifOutNUcastPkts,
              ifOutQLen, ifSpecific }
    STATUS  deprecated
    DESCRIPTION


            "The collection of objects deprecated from the original MIB-
            II interfaces group."
    ::= { ifGroups 12 }

-- Deprecated Definitions - Compliance

ifCompliance MODULE-COMPLIANCE
    STATUS  deprecated
    DESCRIPTION
            "A compliance statement defined in a previous version of
            this MIB module, for SNMP entities which have network
            interfaces."

    MODULE  -- this module
        MANDATORY-GROUPS { ifGeneralGroup, ifStackGroup }

        GROUP       ifFixedLengthGroup
        DESCRIPTION
            "This group is mandatory for all network interfaces which
            are character-oriented or transmit data in fixed-length
            transmission units."

        GROUP       ifHCFixedLengthGroup
        DESCRIPTION
            "This group is mandatory only for those network interfaces
            which are character-oriented or transmit data in fixed-
            length transmission units, and for which the value of the
            corresponding instance of ifSpeed is greater than 20,000,000
            bits/second."

        GROUP       ifPacketGroup
        DESCRIPTION
            "This group is mandatory for all network interfaces which
            are packet-oriented."

        GROUP       ifHCPacketGroup
        DESCRIPTION
            "This group is mandatory only for those network interfaces
            which are packet-oriented and for which the value of the
            corresponding instance of ifSpeed is greater than
            650,000,000 bits/second."

        GROUP       ifTestGroup
        DESCRIPTION
            "This group is optional.  Media-specific MIBs which require
            interface tests are strongly encouraged to use this group
            for invoking tests and reporting results.  A medium specific
            MIB which has mandatory tests may make implementation of


            this group mandatory."

        GROUP       ifRcvAddressGroup
        DESCRIPTION
            "The applicability of this group MUST be defined by the
            media-specific MIBs.  Media-specific MIBs must define the
            exact meaning, use, and semantics of the addresses in this
            group."

        OBJECT      ifLinkUpDownTrapEnable
        MIN-ACCESS  read-only
        DESCRIPTION
            "Write access is not required."

        OBJECT      ifPromiscuousMode
        MIN-ACCESS  read-only
        DESCRIPTION
            "Write access is not required."

        OBJECT      ifStackStatus
        SYNTAX      INTEGER { active(1) } -- subset of RowStatus
        MIN-ACCESS  read-only
        DESCRIPTION
            "Write access is not required, and only one of the six
            enumerated values for the RowStatus textual convention need
            be supported, specifically: active(1)."

        OBJECT       ifAdminStatus
        SYNTAX       INTEGER { up(1), down(2) }
        MIN-ACCESS   read-only
        DESCRIPTION
            "Write access is not required, nor is support for the value
            testing(3)."
    ::= { ifCompliances 1 }

ifCompliance2 MODULE-COMPLIANCE
    STATUS      deprecated
    DESCRIPTION
            "A compliance statement defined in a previous version of
            this MIB module, for SNMP entities which have network
            interfaces."

    MODULE  -- this module
        MANDATORY-GROUPS { ifGeneralInformationGroup, ifStackGroup2,
                           ifCounterDiscontinuityGroup }

        GROUP       ifFixedLengthGroup
        DESCRIPTION


            "This group is mandatory for all network interfaces which
            are character-oriented or transmit data in fixed-length
            transmission units."

        GROUP       ifHCFixedLengthGroup
        DESCRIPTION
            "This group is mandatory only for those network interfaces
            which are character-oriented or transmit data in fixed-
            length transmission units, and for which the value of the
            corresponding instance of ifSpeed is greater than 20,000,000
            bits/second."

        GROUP       ifPacketGroup
        DESCRIPTION
            "This group is mandatory for all network interfaces which
            are packet-oriented."

        GROUP       ifHCPacketGroup
        DESCRIPTION
            "This group is mandatory only for those network interfaces
            which are packet-oriented and for which the value of the
            corresponding instance of ifSpeed is greater than
            650,000,000 bits/second."

        GROUP       ifRcvAddressGroup
        DESCRIPTION
            "The applicability of this group MUST be defined by the
            media-specific MIBs.  Media-specific MIBs must define the
            exact meaning, use, and semantics of the addresses in this
            group."

        OBJECT      ifLinkUpDownTrapEnable
        MIN-ACCESS  read-only
        DESCRIPTION
            "Write access is not required."

        OBJECT      ifPromiscuousMode
        MIN-ACCESS  read-only
        DESCRIPTION
            "Write access is not required."

        OBJECT      ifStackStatus
        SYNTAX      INTEGER { active(1) } -- subset of RowStatus
        MIN-ACCESS  read-only
        DESCRIPTION
            "Write access is not required, and only one of the six
            enumerated values for the RowStatus textual convention need
            be supported, specifically: active(1)."


        OBJECT       ifAdminStatus
        SYNTAX       INTEGER { up(1), down(2) }
        MIN-ACCESS   read-only
        DESCRIPTION
            "Write access is not required, nor is support for the value
            testing(3)."

        OBJECT       ifAlias
        MIN-ACCESS   read-only
        DESCRIPTION
            "Write access is not required."

    ::= { ifCompliances 2 }

END

IF-INVERTED-STACK-MIB DEFINITIONS ::= BEGIN

IMPORTS
  MODULE-IDENTITY, OBJECT-TYPE, mib-2      FROM SNMPv2-SMI
  RowStatus                                FROM SNMPv2-TC
  MODULE-COMPLIANCE, OBJECT-GROUP          FROM SNMPv2-CONF
  ifStackGroup2,
  ifStackHigherLayer, ifStackLowerLayer    FROM IF-MIB;

ifInvertedStackMIB MODULE-IDENTITY
  LAST-UPDATED "200006140000Z"
  ORGANIZATION "IETF Interfaces MIB Working Group"
  CONTACT-INFO
          "   Keith McCloghrie
              Cisco Systems, Inc.
              170 West Tasman Drive
              San Jose, CA  95134-1706
              US

              408-526-5260
              kzm@cisco.com"
  DESCRIPTION
          "The MIB module which provides the Inverted Stack Table for
          interface sub-layers."
  REVISION      "200006140000Z"
  DESCRIPTION
          "Initial revision, published as RFC 2864"
  ::= { mib-2 77 }

ifInvMIBObjects OBJECT IDENTIFIER ::= { ifInvertedStackMIB 1 }

--
--           The Inverted Interface Stack Group
--

ifInvStackTable  OBJECT-TYPE
   SYNTAX        SEQUENCE OF IfInvStackEntry
   MAX-ACCESS    not-accessible
   STATUS        current
   DESCRIPTION
          "A table containing information on the relationships between


          the multiple sub-layers of network interfaces.  In
          particular, it contains information on which sub-layers run
          'underneath' which other sub-layers, where each sub-layer
          corresponds to a conceptual row in the ifTable.  For
          example, when the sub-layer with ifIndex value x runs
          underneath the sub-layer with ifIndex value y, then this
          table contains:

            ifInvStackStatus.x.y=active

          For each ifIndex value, z, which identifies an active
          interface, there are always at least two instantiated rows
          in this table associated with z.  For one of these rows, z
          is the value of ifStackHigherLayer; for the other, z is the
          value of ifStackLowerLayer.  (If z is not involved in
          multiplexing, then these are the only two rows associated
          with z.)

          For example, two rows exist even for an interface which has
          no others stacked on top or below it:

            ifInvStackStatus.z.0=active
            ifInvStackStatus.0.z=active

          This table contains exactly the same number of rows as the
          ifStackTable, but the rows appear in a different order."
   REFERENCE
          "ifStackTable of RFC 2863"
   ::= { ifInvMIBObjects 1 }

ifInvStackEntry  OBJECT-TYPE
   SYNTAX        IfInvStackEntry
   MAX-ACCESS    not-accessible
   STATUS        current
   DESCRIPTION
          "Information on a particular relationship between two sub-
          layers, specifying that one sub-layer runs underneath the
          other sub-layer.  Each sub-layer corresponds to a conceptual
          row in the ifTable."
   INDEX { ifStackLowerLayer, ifStackHigherLayer }
   ::= { ifInvStackTable 1 }

IfInvStackEntry ::=
  SEQUENCE {
      ifInvStackStatus       RowStatus
   }

ifInvStackStatus  OBJECT-TYPE


  SYNTAX         RowStatus
  MAX-ACCESS     read-create
  STATUS         current
  DESCRIPTION
          "The status of the relationship between two sub-layers.

          An instance of this object exists for each instance of the
          ifStackStatus object, and vice versa.  For example, if the
          variable ifStackStatus.H.L exists, then the variable
          ifInvStackStatus.L.H must also exist, and vice versa.  In
          addition, the two variables always have the same value.

          However, unlike ifStackStatus, the ifInvStackStatus object
          is NOT write-able.  A network management application wishing
          to change a relationship between sub-layers H and L cannot
          do so by modifying the value of ifInvStackStatus.L.H, but
          must instead modify the value of ifStackStatus.H.L.  After
          the ifStackTable is modified, the change will be reflected
          in this table."
  ::= { ifInvStackEntry 1 }

-- conformance information

ifInvConformance OBJECT IDENTIFIER ::= { ifInvMIBObjects 2 }

ifInvGroups      OBJECT IDENTIFIER ::= { ifInvConformance 1 }
ifInvCompliances OBJECT IDENTIFIER ::= { ifInvConformance 2 }

-- compliance statements

ifInvCompliance MODULE-COMPLIANCE
  STATUS  current
  DESCRIPTION
          "The compliance statement for SNMP entities which provide
          inverted information on the layering of network interfaces."

  MODULE  -- this module
      MANDATORY-GROUPS { ifInvStackGroup }

      OBJECT       ifInvStackStatus
      SYNTAX       INTEGER { active(1) }
      DESCRIPTION
          "Support is only required for 'active'."


  MODULE  IF-MIB
      MANDATORY-GROUPS { ifStackGroup2 }

  ::= { ifInvCompliances 1 }

-- units of conformance

ifInvStackGroup    OBJECT-GROUP
  OBJECTS { ifInvStackStatus }
  STATUS  current
  DESCRIPTION
          "A collection of objects providing inverted information on
          the layering of MIB-II interfaces."
  ::= { ifInvGroups 1 }

END

HDSL2-SHDSL-LINE-MIB DEFINITIONS ::= BEGIN

IMPORTS
MODULE-IDENTITY,
OBJECT-TYPE,
Counter32,
Unsigned32,
Gauge32,
NOTIFICATION-TYPE,
Integer32,
transmission                  FROM SNMPv2-SMI
RowStatus,
TEXTUAL-CONVENTION            FROM SNMPv2-TC
ifIndex                       FROM IF-MIB
PerfCurrentCount,
PerfIntervalCount             FROM PerfHist-TC-MIB
SnmpAdminString               FROM SNMP-FRAMEWORK-MIB
MODULE-COMPLIANCE,
OBJECT-GROUP,
NOTIFICATION-GROUP            FROM SNMPv2-CONF;

hdsl2ShdslMIB MODULE-IDENTITY
    LAST-UPDATED "200205090000Z" -- May 9, 2002
    ORGANIZATION "ADSLMIB Working Group"
    CONTACT-INFO "WG-email:  adslmib@ietf.org
               Info:      https://www1.ietf.org/mailman/listinfo/adslmib
               Chair:     Mike Sneed


               Postal:    P.O. Box 37324
                          Raleigh NC 27627-7324
               Email:     sneedmike@hotmail.com

               Co-editor: Bob Ray
                          PESA Switching Systems, Inc.
               Postal:    330-A Wynn Drive
                          Huntsville, AL 35805 USA
               Email:     rray@pesa.com
               Phone:     +1 256 726 9200 ext. 142

               Co-editor: Rajesh Abbi
                          Alcatel USA
               Postal:    2912 Wake Forest Road
                          Raleigh, NC 27609-7860 USA

               Email:     Rajesh.Abbi@alcatel.com
               Phone:     +1 919 850 6194
              "

DESCRIPTION
     "This MIB module defines a collection of objects for managing
      HDSL2/SHDSL lines.  An agent may reside at either end of the
      line, however the MIB is designed to require no management
      communication between the modems beyond that inherent in the
      low-level EOC line protocol as defined in ANSI T1E1.4/2000-006
      (for HDSL2 lines), or in ITU G.991.2 (for SHDSL lines)."
 REVISION "200205090000Z" -- May 9, 2002
 DESCRIPTION "Initial version, published as RFC 3276."

 ::= { transmission 48 }

hdsl2ShdslMibObjects OBJECT IDENTIFIER ::= { hdsl2ShdslMIB 1 }

-- Textual Conventions used in this MIB
--

Hdsl2ShdslPerfCurrDayCount ::= TEXTUAL-CONVENTION
   STATUS    current
   DESCRIPTION
     "A gauge associated with interface performance measurements in
      a current 1-day (24 hour) measurement interval.

      The value of this gauge starts at zero at the beginning of an
      interval and is increased when associated events occur, until
      the end of the 1-day interval.  At that time the value of the
      gauge is stored in the previous 1-day history interval, as
      defined in a companion object of type


      Hdsl2Shdsl1DayIntevalCount, and the current interval gauge
      is restarted at zero.

      In the case where the agent has no valid data available for
      this interval the corresponding object instance is not
      available and upon a retrieval request a corresponding error
      message shall be returned to indicate that this instance does
      not exist.  Please note that zero is a valid value."
   SYNTAX  Gauge32

Hdsl2Shdsl1DayIntervalCount ::= TEXTUAL-CONVENTION
   STATUS    current
   DESCRIPTION
     "A counter associated with interface performance measurements
      during the most previous 1-day (24 hour) measurement interval.
      The value of this gauge is equal to the value of the current
      day gauge, as defined in a companion object of type
      Hdsl2ShdslPerfCurrDayCount, at the end of its most recent
      interval.

      In the case where the agent has no valid data available for
      this interval the corresponding object instance is not
      available and upon a retrieval request a corresponding error
      message shall be returned to indicate that this instance does
      not exist."
   SYNTAX  Gauge32

Hdsl2ShdslPerfTimeElapsed ::= TEXTUAL-CONVENTION
   STATUS    current
   DESCRIPTION
     "The number of seconds that have elapsed since the beginning of
      the current measurement period.  If, for some reason, such as
      an adjustment in the system's time-of-day clock or the addition
      of a leap second, the current interval exceeds the maximum
      value, the agent will return the maximum value.

      For 15 minute intervals, the range is limited to (0..899).
      For 24 hour intervals, the range is limited to (0..86399)."
   SYNTAX    Unsigned32(0..86399)

Hdsl2ShdslPerfIntervalThreshold ::= TEXTUAL-CONVENTION
   STATUS    current
   DESCRIPTION
     "This convention defines a range of values that may be set in
      a fault threshold alarm control.  As the number of seconds in
      a 15-minute interval numbers at most 900, objects of this type
      may have a range of 0...900, where the value of 0 disables the
      alarm."


   SYNTAX    Unsigned32(0..900)

Hdsl2ShdslUnitId ::= TEXTUAL-CONVENTION
   STATUS    current
   DESCRIPTION
     "This is the unique identification for all units in a
      HDSL2/SHDSL Span.  It is based on the EOC unit addressing
      scheme with reference to the xtuC."
   SYNTAX    INTEGER
           {
           xtuC(1),
           xtuR(2),
           xru1(3),
           xru2(4),
           xru3(5),
           xru4(6),
           xru5(7),
           xru6(8),
           xru7(9),
           xru8(10)
           }

Hdsl2ShdslUnitSide ::= TEXTUAL-CONVENTION
   STATUS    current
   DESCRIPTION
     "This is the referenced side of a HDSL2/SHDSL unit - Network
      or Customer side.  The side facing the Network is the Network
      side, while the side facing the Customer is the Customer side."
   SYNTAX    INTEGER
           {
           networkSide(1),
           customerSide(2)
           }

Hdsl2ShdslWirePair ::= TEXTUAL-CONVENTION
   STATUS    current
   DESCRIPTION
     "This is the referenced pair of wires in a HDSL2/SHDSL Segment.
      HDSL2 only supports a single pair (wirePair1), while SHDSL
      supports an optional second pair (wirePair2)."
   SYNTAX    INTEGER
           {
           wirePair1(1),
           wirePair2(2)
           }

Hdsl2ShdslTransmissionModeType ::= TEXTUAL-CONVENTION
   STATUS    current


   DESCRIPTION
     "Contains the regional setting of the HDSL2/SHDSL span,
     represented as a bit-map of possible settings. The various
     bit positions are:

     Bit   Meaning      Description
     1     region 1     Indicates ITU-T G.991.2 Annex A.
     2     region 2     Indicates ITU-T G.991.2 Annex B."
   SYNTAX      BITS
           {
           region1(0),
           region2(1)
           }

Hdsl2ShdslClockReferenceType ::= TEXTUAL-CONVENTION
   STATUS    current
   DESCRIPTION
     "The various STU-C symbol clock references for the
     HDSL2/SHDSL span, represented as an enumeration."
   SYNTAX    INTEGER
          {
          localClk(1),          -- Mode-1 per G991.2
          networkClk(2),        -- Mode-2 per G991.2
          dataOrNetworkClk(3),  -- Mode-3a per G991.2
          dataClk(4)            -- Mode-3b per G991.2
          }

-- Span Configuration Group
--

hdsl2ShdslSpanConfTable OBJECT-TYPE
   SYNTAX     SEQUENCE OF Hdsl2ShdslSpanConfEntry
   MAX-ACCESS not-accessible
   STATUS     current
   DESCRIPTION
     "This table supports overall configuration of HDSL2/SHDSL
      Spans.  Entries in this table MUST be maintained in a
      persistent manner."
   ::= { hdsl2ShdslMibObjects 1 }

hdsl2ShdslSpanConfEntry OBJECT-TYPE
   SYNTAX      Hdsl2ShdslSpanConfEntry
   MAX-ACCESS  not-accessible
   STATUS      current
   DESCRIPTION
     "An entry in the hdsl2ShdslSpanConfTable.  Each entry
      represents the complete Span in a single HDSL2/SHDSL line.
      It is indexed by the ifIndex of the associated HDSL2/SHDSL


      line."
   INDEX { ifIndex }
   ::= { hdsl2ShdslSpanConfTable 1 }

Hdsl2ShdslSpanConfEntry ::=
   SEQUENCE
   {
   hdsl2ShdslSpanConfNumRepeaters          Unsigned32,
   hdsl2ShdslSpanConfProfile               SnmpAdminString,
   hdsl2ShdslSpanConfAlarmProfile          SnmpAdminString
   }

   hdsl2ShdslSpanConfNumRepeaters OBJECT-TYPE
   SYNTAX      Unsigned32(0..8)
   UNITS       "repeaters"
   MAX-ACCESS  read-write
   STATUS      current
   DESCRIPTION
     "This object provisions the number of repeaters/regenerators
     in this HDSL2/SHDSL Span."
   ::= { hdsl2ShdslSpanConfEntry 1 }

hdsl2ShdslSpanConfProfile OBJECT-TYPE
   SYNTAX      SnmpAdminString (SIZE(1..32))
   MAX-ACCESS  read-write
   STATUS      current
   DESCRIPTION
     "This object is a pointer to a span configuration profile in
     the hdsl2ShdslSpanConfProfileTable, which applies to this span.
     The value of this object is the index of the referenced profile
     in the hdsl2ShdslSpanConfProfileTable.  Note that span
     configuration profiles are only applicable to SHDSL lines.

     HDSL2 lines MUST reference the default profile, 'DEFVAL'.
     By default, this object will have the value 'DEFVAL' (the index
     of the default profile).

     Any attempt to set this object to a value that is not the value
     of the index for an active entry in the profile table,
     hdsl2ShdslSpanConfProfileTable, MUST be rejected."
   ::= { hdsl2ShdslSpanConfEntry 2 }

hdsl2ShdslSpanConfAlarmProfile OBJECT-TYPE
   SYNTAX      SnmpAdminString (SIZE(1..32))
   MAX-ACCESS  read-write
   STATUS      current
   DESCRIPTION
     "This object is a pointer to an Alarm configuration profile in


     the hdsl2ShdslEndpointAlarmConfProfileTable.  The value of this
     object is the index of the referenced profile in the
     hdsl2ShdslEndpointAlarmConfProfileTable.  The alarm threshold
     configuration in the referenced profile will be used by default
     for all segment endpoints in this span.  Individual endpoints
     may override this profile by explicitly specifying some other
     profile in the hdsl2ShdslEndpointConfTable.  By default, this
     object will have the value 'DEFVAL' (the index of the default
     profile).

     Any attempt to set this object to a value that is not the value
     of the index for an active entry in the profile table,
     hdsl2ShdslEndpointAlarmConfProfileTable, MUST be rejected."
   ::= { hdsl2ShdslSpanConfEntry 3 }

-- Span Status Group
--

hdsl2ShdslSpanStatusTable OBJECT-TYPE
   SYNTAX     SEQUENCE OF Hdsl2ShdslSpanStatusEntry
   MAX-ACCESS not-accessible
   STATUS     current
   DESCRIPTION
     "This table provides overall status information of
      HDSL2/SHDSL spans.  This table contains live data from
      equipment.  As such, it is NOT persistent."
   ::= { hdsl2ShdslMibObjects 2 }

hdsl2ShdslSpanStatusEntry OBJECT-TYPE
   SYNTAX      Hdsl2ShdslSpanStatusEntry
   MAX-ACCESS  not-accessible
   STATUS      current
   DESCRIPTION
     "An entry in the hdsl2ShdslSpanStatusTable.  Each entry
      represents the complete span in a single HDSL2/SHDSL line.
      It is indexed by the ifIndex of the associated HDSL2/SHDSL
      line."
   INDEX { ifIndex }
   ::= { hdsl2ShdslSpanStatusTable 1 }

Hdsl2ShdslSpanStatusEntry ::=
   SEQUENCE
   {
   hdsl2ShdslStatusNumAvailRepeaters        Unsigned32,
   hdsl2ShdslStatusMaxAttainableLineRate    Unsigned32,
   hdsl2ShdslStatusActualLineRate           Unsigned32,
   hdsl2ShdslStatusTransmissionModeCurrent
             Hdsl2ShdslTransmissionModeType


   }

hdsl2ShdslStatusNumAvailRepeaters OBJECT-TYPE
   SYNTAX      Unsigned32(0..8)
   MAX-ACCESS  read-only
   STATUS      current
   DESCRIPTION
     "Contains the actual number of repeaters/regenerators
      discovered in this HDSL2/SHDSL span."
   ::= { hdsl2ShdslSpanStatusEntry 1 }

hdsl2ShdslStatusMaxAttainableLineRate OBJECT-TYPE
   SYNTAX      Unsigned32(0..4112000)
   UNITS       "bps"
   MAX-ACCESS  read-only
   STATUS      current
   DESCRIPTION
     "Contains the maximum attainable line rate in this HDSL2/SHDSL
      span.  This object provides the maximum rate the line is
      capable of achieving.  This is based upon measurements made
      during line probing."
   ::= { hdsl2ShdslSpanStatusEntry 2 }

hdsl2ShdslStatusActualLineRate OBJECT-TYPE
   SYNTAX      Unsigned32(0..4112000)
   UNITS       "bps"
   MAX-ACCESS  read-only
   STATUS      current
   DESCRIPTION
     "Contains the actual line rate in this HDSL2/SHDSL span.  This
     should equal ifSpeed."
   ::= { hdsl2ShdslSpanStatusEntry 3 }

hdsl2ShdslStatusTransmissionModeCurrent OBJECT-TYPE
   SYNTAX      Hdsl2ShdslTransmissionModeType
   MAX-ACCESS  read-only
   STATUS      current
   DESCRIPTION
     "Contains the current Power Spectral Density (PSD) regional
      setting of the HDSL2/SHDSL span."
   ::= { hdsl2ShdslSpanStatusEntry 4 }

-- Unit Inventory Group
--

hdsl2ShdslInventoryTable OBJECT-TYPE
   SYNTAX     SEQUENCE OF Hdsl2ShdslInventoryEntry
   MAX-ACCESS not-accessible


   STATUS     current
   DESCRIPTION
     "This table supports retrieval of unit inventory information
      available via the EOC from units in a HDSL2/SHDSL line.

      Entries in this table are dynamically created during the
      line discovery process.  The life cycle for these entries
      is as follows:

         - xtu discovers a device, either a far-end xtu or an xru
         - an inventory table entry is created for the device
         - the line goes down for whatever reason
         - inventory table entries for unreachable devices are
           destroyed.

      As these entries are created/destroyed dynamically, they
      are NOT persistent."
   ::= { hdsl2ShdslMibObjects 3 }

hdsl2ShdslInventoryEntry OBJECT-TYPE
   SYNTAX      Hdsl2ShdslInventoryEntry
   MAX-ACCESS  not-accessible
   STATUS      current
   DESCRIPTION
     "An entry in the hdsl2ShdslInventoryTable.  Each entry
      represents inventory information for a single unit in a
      HDSL2/SHDSL line.  It is indexed by the ifIndex of the
      HDSL2/SHDSL line and the Hdsl2ShdslUnitId of the
      associated unit."
   INDEX { ifIndex, hdsl2ShdslInvIndex }
   ::= { hdsl2ShdslInventoryTable 1 }

Hdsl2ShdslInventoryEntry ::=
   SEQUENCE
   {
   hdsl2ShdslInvIndex                      Hdsl2ShdslUnitId,
   hdsl2ShdslInvVendorID                   OCTET STRING,
   hdsl2ShdslInvVendorModelNumber          OCTET STRING,
   hdsl2ShdslInvVendorSerialNumber         OCTET STRING,
   hdsl2ShdslInvVendorEOCSoftwareVersion   Integer32,
   hdsl2ShdslInvStandardVersion            Integer32,
   hdsl2ShdslInvVendorListNumber           OCTET STRING,
   hdsl2ShdslInvVendorIssueNumber          OCTET STRING,
   hdsl2ShdslInvVendorSoftwareVersion      OCTET STRING,
   hdsl2ShdslInvEquipmentCode              OCTET STRING,
   hdsl2ShdslInvVendorOther                OCTET STRING,
   hdsl2ShdslInvTransmissionModeCapability
                         Hdsl2ShdslTransmissionModeType


   }

hdsl2ShdslInvIndex OBJECT-TYPE
   SYNTAX      Hdsl2ShdslUnitId
   MAX-ACCESS  not-accessible
   STATUS      current
   DESCRIPTION
      "Each entry in this table corresponds to a physical element
      in a HDSL2/SHDSL Span.  It is based on the EOC unit addressing
      scheme with reference to the xtuC."
   ::= { hdsl2ShdslInventoryEntry 1 }

hdsl2ShdslInvVendorID OBJECT-TYPE
   SYNTAX      OCTET STRING(SIZE(8))
   MAX-ACCESS  read-only
   STATUS      current
   DESCRIPTION
     "Vendor ID as reported in an Inventory Response message."
   ::= { hdsl2ShdslInventoryEntry 2 }

hdsl2ShdslInvVendorModelNumber OBJECT-TYPE
   SYNTAX      OCTET STRING(SIZE(12))
   MAX-ACCESS  read-only
   STATUS      current
   DESCRIPTION
     "Vendor model number as reported in an Inventory Response
      message."
   ::= { hdsl2ShdslInventoryEntry 3 }

hdsl2ShdslInvVendorSerialNumber OBJECT-TYPE
   SYNTAX      OCTET STRING(SIZE(12))
   MAX-ACCESS  read-only
   STATUS      current
   DESCRIPTION
     "Vendor serial number as reported in an Inventory Response
      message."
   ::= { hdsl2ShdslInventoryEntry 4 }

hdsl2ShdslInvVendorEOCSoftwareVersion OBJECT-TYPE
   SYNTAX      Integer32
   MAX-ACCESS  read-only
   STATUS      current
   DESCRIPTION
     "Vendor EOC version as reported in a Discovery Response
      message."
   ::= { hdsl2ShdslInventoryEntry 5 }

hdsl2ShdslInvStandardVersion OBJECT-TYPE


   SYNTAX      Integer32
   MAX-ACCESS  read-only
   STATUS      current
   DESCRIPTION
     "Version of the HDSL2/SHDSL standard implemented, as reported
      in an Inventory Response message."
   ::= { hdsl2ShdslInventoryEntry 6 }

hdsl2ShdslInvVendorListNumber OBJECT-TYPE
   SYNTAX      OCTET STRING(SIZE(3))
   MAX-ACCESS  read-only
   STATUS      current
   DESCRIPTION
     "Vendor list number as reported in an Inventory Response
      message."
   ::= { hdsl2ShdslInventoryEntry 7 }

hdsl2ShdslInvVendorIssueNumber OBJECT-TYPE
   SYNTAX      OCTET STRING(SIZE(2))
   MAX-ACCESS  read-only
   STATUS      current
   DESCRIPTION
     "Vendor issue number as reported in an Inventory Response
      message."
   ::= { hdsl2ShdslInventoryEntry 8 }

hdsl2ShdslInvVendorSoftwareVersion OBJECT-TYPE
   SYNTAX      OCTET STRING(SIZE(6))
   MAX-ACCESS  read-only
   STATUS      current
   DESCRIPTION
     "Vendor software version as reported in an Inventory Response
      message."
   ::= { hdsl2ShdslInventoryEntry 9 }

hdsl2ShdslInvEquipmentCode OBJECT-TYPE
   SYNTAX      OCTET STRING(SIZE(10))
   MAX-ACCESS  read-only
   STATUS      current
   DESCRIPTION
     "Equipment code conforming to ANSI T1.213, Coded Identification
      of Equipment Entities."
   ::= { hdsl2ShdslInventoryEntry 10 }

hdsl2ShdslInvVendorOther OBJECT-TYPE
   SYNTAX      OCTET STRING(SIZE(12))
   MAX-ACCESS  read-only
   STATUS      current


   DESCRIPTION
     "Other vendor information as reported in an Inventory Response
      message."
   ::= { hdsl2ShdslInventoryEntry 11 }

hdsl2ShdslInvTransmissionModeCapability OBJECT-TYPE
   SYNTAX      Hdsl2ShdslTransmissionModeType
   MAX-ACCESS  read-only
   STATUS      current
   DESCRIPTION
     "Contains the transmission mode capability of the SHDSL unit."
   ::= { hdsl2ShdslInventoryEntry 12 }

-- Segment Endpoint Configuration Group
--

hdsl2ShdslEndpointConfTable OBJECT-TYPE
   SYNTAX      SEQUENCE OF Hdsl2ShdslEndpointConfEntry
   MAX-ACCESS  not-accessible
   STATUS      current
   DESCRIPTION
     "This table supports configuration parameters for segment
      endpoints in a HDSL2/SHDSL line.  As this table is indexed
      by ifIndex, it MUST be maintained in a persistent manner."
   ::= { hdsl2ShdslMibObjects 4 }

hdsl2ShdslEndpointConfEntry OBJECT-TYPE
   SYNTAX      Hdsl2ShdslEndpointConfEntry
   MAX-ACCESS  not-accessible
   STATUS      current
   DESCRIPTION
     "An entry in the hdsl2ShdslEndpointConfTable.  Each entry
      represents a single segment endpoint in a HDSL2/SHDSL line.
      It is indexed by the ifIndex of the HDSL2/SHDSL line, the
      UnitId of the associated unit, the side of the unit, and the
      wire-pair of the associated modem."
   INDEX { ifIndex, hdsl2ShdslInvIndex, hdsl2ShdslEndpointSide,
           hdsl2ShdslEndpointWirePair}
   ::= { hdsl2ShdslEndpointConfTable 1 }

Hdsl2ShdslEndpointConfEntry ::=
   SEQUENCE
   {
   hdsl2ShdslEndpointSide                   Hdsl2ShdslUnitSide,
   hdsl2ShdslEndpointWirePair               Hdsl2ShdslWirePair,
   hdsl2ShdslEndpointAlarmConfProfile       SnmpAdminString
   }


hdsl2ShdslEndpointSide OBJECT-TYPE
   SYNTAX      Hdsl2ShdslUnitSide
   MAX-ACCESS  not-accessible
   STATUS      current
   DESCRIPTION
     "The side of the unit associated with this segment endpoint -
      Network/Customer side - as per the Hdsl2ShdslUnitSide textual
      convention."
   ::= { hdsl2ShdslEndpointConfEntry 1 }

hdsl2ShdslEndpointWirePair OBJECT-TYPE
   SYNTAX      Hdsl2ShdslWirePair
   MAX-ACCESS  not-accessible
   STATUS      current
   DESCRIPTION
     "The wire-pair of the modem associated with this segment
      endpoint as per the Hdsl2ShdslWirePair textual convention."
   ::= { hdsl2ShdslEndpointConfEntry 2 }

hdsl2ShdslEndpointAlarmConfProfile OBJECT-TYPE
   SYNTAX      SnmpAdminString (SIZE(0..32))
   MAX-ACCESS  read-write
   STATUS      current
   DESCRIPTION
     "This object configures the alarm threshold values to be used
      for this segment endpoint.  The values are obtained from the
      alarm configuration profile referenced by this object.  The
      value of this object is the index of the referenced profile in
      the hdsl2ShdslEndpointAlarmConfProfileTable, or NULL (a zero-
      length SnmpAdminString).  If the value is a zero-length
      SnmpAdminString, the endpoint uses the default Alarm
      Configuration Profile for the associated span as per the
      hdsl2ShdslSpanConfAlarmProfile object in the
      hdsl2ShdslSpanConfTable.  The default value of this object is
      a zero-length SnmpAdminString.

      Any attempt to set this object to a value that is not the value
      of the index for an active entry in the profile table,
      hdsl2ShdslEndpointAlarmConfProfileTable, MUST be rejected."
   ::= { hdsl2ShdslEndpointConfEntry 3 }

-- Segment Endpoint Current Status/Performance Group
--

hdsl2ShdslEndpointCurrTable OBJECT-TYPE
   SYNTAX      SEQUENCE OF Hdsl2ShdslEndpointCurrEntry
   MAX-ACCESS  not-accessible
   STATUS      current


   DESCRIPTION
     "This table contains current status and performance information
      for segment endpoints in HDSL2/SHDSL Lines.  As with other
      tables in this MIB indexed by ifIndex, entries in this table
      MUST be maintained in a persistent manner."
   ::= { hdsl2ShdslMibObjects 5 }

hdsl2ShdslEndpointCurrEntry OBJECT-TYPE
   SYNTAX      Hdsl2ShdslEndpointCurrEntry
   MAX-ACCESS  not-accessible
   STATUS      current
   DESCRIPTION
     "An entry in the hdsl2ShdslEndpointCurrTable.  Each entry
     contains status and performance information relating to a
     single segment endpoint.  It is indexed by the ifIndex of the
     HDSL2/SHDSL line, the UnitId of the associated unit, the side
     of the unit, and the wire-pair of the associated modem."
   INDEX { ifIndex, hdsl2ShdslInvIndex, hdsl2ShdslEndpointSide,
           hdsl2ShdslEndpointWirePair }
   ::= { hdsl2ShdslEndpointCurrTable 1 }

Hdsl2ShdslEndpointCurrEntry ::=
   SEQUENCE
   {
   hdsl2ShdslEndpointCurrAtn                Integer32,
   hdsl2ShdslEndpointCurrSnrMgn             Integer32,
   hdsl2ShdslEndpointCurrStatus             BITS,
   hdsl2ShdslEndpointES                     Counter32,
   hdsl2ShdslEndpointSES                    Counter32,
   hdsl2ShdslEndpointCRCanomalies           Counter32,
   hdsl2ShdslEndpointLOSWS                  Counter32,
   hdsl2ShdslEndpointUAS                    Counter32,
   hdsl2ShdslEndpointCurr15MinTimeElapsed
                             Hdsl2ShdslPerfTimeElapsed,
   hdsl2ShdslEndpointCurr15MinES            PerfCurrentCount,
   hdsl2ShdslEndpointCurr15MinSES           PerfCurrentCount,
   hdsl2ShdslEndpointCurr15MinCRCanomalies  PerfCurrentCount,
   hdsl2ShdslEndpointCurr15MinLOSWS         PerfCurrentCount,
   hdsl2ShdslEndpointCurr15MinUAS           PerfCurrentCount,
   hdsl2ShdslEndpointCurr1DayTimeElapsed
                             Hdsl2ShdslPerfTimeElapsed,
   hdsl2ShdslEndpointCurr1DayES
                             Hdsl2ShdslPerfCurrDayCount,
   hdsl2ShdslEndpointCurr1DaySES
                             Hdsl2ShdslPerfCurrDayCount,
   hdsl2ShdslEndpointCurr1DayCRCanomalies
                             Hdsl2ShdslPerfCurrDayCount,
   hdsl2ShdslEndpointCurr1DayLOSWS


                             Hdsl2ShdslPerfCurrDayCount,
   hdsl2ShdslEndpointCurr1DayUAS
                             Hdsl2ShdslPerfCurrDayCount
   }

hdsl2ShdslEndpointCurrAtn OBJECT-TYPE
   SYNTAX      Integer32(-127..128)
   UNITS       "dB"
   MAX-ACCESS  read-only
   STATUS      current
   DESCRIPTION
     "The current loop attenuation for this endpoint as reported in
      a Network or Customer Side Performance Status message."
   REFERENCE   "HDSL2 Section 7.5.3.7; SHDSL Section 9.5.5.7"
   ::= { hdsl2ShdslEndpointCurrEntry 1 }

hdsl2ShdslEndpointCurrSnrMgn OBJECT-TYPE
   SYNTAX      Integer32(-127..128)
   UNITS       "dB"
   MAX-ACCESS  read-only
   STATUS      current
   DESCRIPTION
     "The current SNR margin for this endpoint as reported in a
      Status Response/SNR message."
   REFERENCE   "HDSL2 Section 7.5.3.7; SHDSL Section 9.5.5.7"
   ::= { hdsl2ShdslEndpointCurrEntry 2 }

hdsl2ShdslEndpointCurrStatus OBJECT-TYPE
   SYNTAX      BITS
               {
               noDefect(0),
               powerBackoff(1),
               deviceFault(2),
               dcContinuityFault(3),
               snrMarginAlarm(4),
               loopAttenuationAlarm(5),
               loswFailureAlarm(6),
               configInitFailure(7),
               protocolInitFailure(8),
               noNeighborPresent(9),
               loopbackActive(10)
               }
   MAX-ACCESS  read-only
   STATUS      current
   DESCRIPTION
     "Contains the current state of the endpoint.  This is a
     bitmap of possible conditions. The various bit positions
     are:


     noDefect               There no defects on the line.

     powerBackoff           Indicates enhanced Power Backoff.

     deviceFault            Indicates a vendor-dependent
                            diagnostic or self-test fault
                            has been detected.

     dcContinuityFault      Indicates vendor-dependent
                            conditions that interfere with
                            span powering such as short and
                            open circuits.

     snrMarginAlarm         Indicates that the SNR margin
                            has dropped below the alarm threshold.

     loopAttenuationAlarm   Indicates that the loop attenuation
                            exceeds the alarm threshold.

     loswFailureAlarm       Indicates a forward LOSW alarm.

     configInitFailure      Endpoint failure during initialization
                            due to paired endpoint not able to
                            support requested configuration.

     protocolInitFailure    Endpoint failure during initialization
                            due to incompatible protocol used by
                            the paired endpoint.

     noNeighborPresent      Endpoint failure during initialization
                            due to no activation sequence detected
                            from paired endpoint.

     loopbackActive         A loopback is currently active at this
                            Segment Endpoint.

     This is intended to supplement ifOperStatus.  Note that there
     is a 1-1 relationship between the status bits defined in this
     object and the notification thresholds defined elsewhere in
     this MIB."
   REFERENCE   "HDSL2 Section 7.5.3.7; SHDSL Section 9.5.5.7"
   ::= { hdsl2ShdslEndpointCurrEntry 3 }

hdsl2ShdslEndpointES OBJECT-TYPE
   SYNTAX      Counter32
   UNITS       "seconds"
   MAX-ACCESS  read-only
   STATUS      current


   DESCRIPTION
     "Count of Errored Seconds (ES) on this endpoint since the xU
      was last restarted."
   REFERENCE   "HDSL2 Section 7.5.3.7; SHDSL Section 9.5.5.7"
   ::= { hdsl2ShdslEndpointCurrEntry 4 }

hdsl2ShdslEndpointSES OBJECT-TYPE
   SYNTAX       Counter32
   UNITS        "seconds"
   MAX-ACCESS   read-only
   STATUS       current
   DESCRIPTION
     "Count of Severely Errored Seconds (SES) on this endpoint
      since the xU was last restarted."
   REFERENCE   "HDSL2 Section 7.5.3.7; SHDSL Section 9.5.5.7"
   ::= { hdsl2ShdslEndpointCurrEntry 5 }

hdsl2ShdslEndpointCRCanomalies OBJECT-TYPE
   SYNTAX       Counter32
   UNITS        "detected CRC Anomalies"
   MAX-ACCESS   read-only
   STATUS       current
   DESCRIPTION
     "Count of CRC anomalies on this endpoint since the xU was
      last restarted."
   REFERENCE   "HDSL2 Section 7.5.3.7; SHDSL Section 9.5.5.7"
   ::= { hdsl2ShdslEndpointCurrEntry 6 }

hdsl2ShdslEndpointLOSWS OBJECT-TYPE
   SYNTAX       Counter32
   UNITS        "seconds"
   MAX-ACCESS   read-only
   STATUS       current
   DESCRIPTION
     "Count of Loss of Sync Word (LOSW) Seconds on this endpoint
      since the xU was last restarted."
   REFERENCE   "HDSL2 Section 7.5.3.7; SHDSL Section 9.5.5.7"
   ::= { hdsl2ShdslEndpointCurrEntry 7 }

hdsl2ShdslEndpointUAS OBJECT-TYPE
   SYNTAX       Counter32
   UNITS        "seconds"
   MAX-ACCESS   read-only
   STATUS       current
   DESCRIPTION
     "Count of Unavailable Seconds (UAS) on this endpoint since
      the xU was last restarted."
   REFERENCE   "HDSL2 Section 7.5.3.7; SHDSL Section 9.5.5.7"


   ::= { hdsl2ShdslEndpointCurrEntry 8 }

hdsl2ShdslEndpointCurr15MinTimeElapsed OBJECT-TYPE
   SYNTAX       Hdsl2ShdslPerfTimeElapsed
   UNITS        "seconds"
   MAX-ACCESS   read-only
   STATUS       current
   DESCRIPTION
     "Total elapsed seconds in the current 15-minute interval."
   ::= { hdsl2ShdslEndpointCurrEntry 9 }

hdsl2ShdslEndpointCurr15MinES OBJECT-TYPE
   SYNTAX       PerfCurrentCount
   UNITS        "seconds"
   MAX-ACCESS   read-only
   STATUS       current
   DESCRIPTION
     "Count of Errored Seconds (ES) in the current 15-minute
      interval."
   REFERENCE   "HDSL2 Section 7.5.3.7; SHDSL Section 9.5.5.7"
   ::= { hdsl2ShdslEndpointCurrEntry 10 }

hdsl2ShdslEndpointCurr15MinSES OBJECT-TYPE
   SYNTAX       PerfCurrentCount
   UNITS        "seconds"
   MAX-ACCESS   read-only
   STATUS       current
   DESCRIPTION
     "Count of Severely Errored Seconds (SES) in the current
      15-minute interval."
   REFERENCE   "HDSL2 Section 7.5.3.7; SHDSL Section 9.5.5.7"
   ::= { hdsl2ShdslEndpointCurrEntry 11 }

hdsl2ShdslEndpointCurr15MinCRCanomalies OBJECT-TYPE
   SYNTAX       PerfCurrentCount
   UNITS        "detected CRC Anomalies"
   MAX-ACCESS   read-only
   STATUS       current
   DESCRIPTION
     "Count of CRC anomalies in the current 15-minute interval."
   REFERENCE   "HDSL2 Section 7.5.3.7; SHDSL Section 9.5.5.7"
   ::= { hdsl2ShdslEndpointCurrEntry 12 }

hdsl2ShdslEndpointCurr15MinLOSWS OBJECT-TYPE
   SYNTAX       PerfCurrentCount
   UNITS        "seconds"
   MAX-ACCESS   read-only
   STATUS       current


   DESCRIPTION
     "Count of Loss of Sync Word (LOSW) Seconds in the current
      15-minute interval."
   REFERENCE   "HDSL2 Section 7.5.3.7; SHDSL Section 9.5.5.7"
   ::= { hdsl2ShdslEndpointCurrEntry 13 }

hdsl2ShdslEndpointCurr15MinUAS OBJECT-TYPE
   SYNTAX       PerfCurrentCount
   UNITS        "seconds"
   MAX-ACCESS   read-only
   STATUS       current
   DESCRIPTION
     "Count of Unavailable Seconds (UAS) in the current 15-minute
      interval."
   REFERENCE   "HDSL2 Section 7.5.3.7; SHDSL Section 9.5.5.7"
   ::= { hdsl2ShdslEndpointCurrEntry 14 }

hdsl2ShdslEndpointCurr1DayTimeElapsed OBJECT-TYPE
   SYNTAX       Hdsl2ShdslPerfTimeElapsed
   UNITS        "seconds"
   MAX-ACCESS   read-only
   STATUS       current
   DESCRIPTION
     "Number of seconds that have elapsed since the beginning of
      the current 1-day interval."
   ::= { hdsl2ShdslEndpointCurrEntry 15 }

hdsl2ShdslEndpointCurr1DayES OBJECT-TYPE
   SYNTAX       Hdsl2ShdslPerfCurrDayCount
   UNITS        "seconds"
   MAX-ACCESS   read-only
   STATUS       current
   DESCRIPTION
     "Count of Errored Seconds (ES) during the current day as
      measured by hdsl2ShdslEndpointCurr1DayTimeElapsed."
   REFERENCE   "HDSL2 Section 7.5.3.7; SHDSL Section 9.5.5.7"
   ::= { hdsl2ShdslEndpointCurrEntry 16 }

hdsl2ShdslEndpointCurr1DaySES OBJECT-TYPE
   SYNTAX       Hdsl2ShdslPerfCurrDayCount
   UNITS        "seconds"
   MAX-ACCESS   read-only
   STATUS       current
   DESCRIPTION
     "Count of Severely Errored Seconds (SES) during the current
      day as measured by hdsl2ShdslEndpointCurr1DayTimeElapsed."
   REFERENCE   "HDSL2 Section 7.5.3.7; SHDSL Section 9.5.5.7"
   ::= { hdsl2ShdslEndpointCurrEntry 17 }


hdsl2ShdslEndpointCurr1DayCRCanomalies OBJECT-TYPE
   SYNTAX       Hdsl2ShdslPerfCurrDayCount
   UNITS        "detected CRC Anomalies"
   MAX-ACCESS   read-only
   STATUS       current
   DESCRIPTION
     "Count of CRC anomalies during the current day as measured
      by hdsl2ShdslEndpointCurr1DayTimeElapsed."
   REFERENCE   "HDSL2 Section 7.5.3.7; SHDSL Section 9.5.5.7"
   ::= { hdsl2ShdslEndpointCurrEntry 18 }

hdsl2ShdslEndpointCurr1DayLOSWS OBJECT-TYPE
   SYNTAX       Hdsl2ShdslPerfCurrDayCount
   UNITS        "seconds"
   MAX-ACCESS   read-only
   STATUS       current
   DESCRIPTION
     "Count of Loss of Sync Word (LOSW) Seconds during the current
      day as measured by hdsl2ShdslEndpointCurr1DayTimeElapsed."
   REFERENCE   "HDSL2 Section 7.5.3.7; SHDSL Section 9.5.5.7"
   ::= { hdsl2ShdslEndpointCurrEntry 19 }

hdsl2ShdslEndpointCurr1DayUAS OBJECT-TYPE
   SYNTAX       Hdsl2ShdslPerfCurrDayCount
   UNITS        "seconds"
   MAX-ACCESS   read-only
   STATUS       current
   DESCRIPTION
     "Count of Unavailable Seconds (UAS) during the current day as
      measured by hdsl2ShdslEndpointCurr1DayTimeElapsed."
   REFERENCE   "HDSL2 Section 7.5.3.7; SHDSL Section 9.5.5.7"
   ::= { hdsl2ShdslEndpointCurrEntry 20 }

-- Segment Endpoint 15-Minute Interval Status/Performance Group
--

hdsl2Shdsl15MinIntervalTable OBJECT-TYPE
   SYNTAX      SEQUENCE OF Hdsl2Shdsl15MinIntervalEntry
   MAX-ACCESS  not-accessible
   STATUS      current
   DESCRIPTION
     "This table provides one row for each HDSL2/SHDSL endpoint
      performance data collection interval.  This table contains
      live data from equipment.  As such, it is NOT persistent."
   ::= { hdsl2ShdslMibObjects 6 }

hdsl2Shdsl15MinIntervalEntry OBJECT-TYPE
   SYNTAX      Hdsl2Shdsl15MinIntervalEntry


   MAX-ACCESS  not-accessible
   STATUS      current
   DESCRIPTION
     "An entry in the hdsl2Shdsl15MinIntervalTable."
   INDEX { ifIndex, hdsl2ShdslInvIndex, hdsl2ShdslEndpointSide,
           hdsl2ShdslEndpointWirePair, hdsl2Shdsl15MinIntervalNumber}
   ::= { hdsl2Shdsl15MinIntervalTable 1 }

Hdsl2Shdsl15MinIntervalEntry ::=
   SEQUENCE
   {
   hdsl2Shdsl15MinIntervalNumber         Unsigned32,
   hdsl2Shdsl15MinIntervalES             PerfIntervalCount,
   hdsl2Shdsl15MinIntervalSES            PerfIntervalCount,
   hdsl2Shdsl15MinIntervalCRCanomalies   PerfIntervalCount,
   hdsl2Shdsl15MinIntervalLOSWS          PerfIntervalCount,
   hdsl2Shdsl15MinIntervalUAS            PerfIntervalCount
   }

hdsl2Shdsl15MinIntervalNumber OBJECT-TYPE
   SYNTAX      Unsigned32(1..96)
   MAX-ACCESS  not-accessible
   STATUS      current
   DESCRIPTION
     "Performance Data Interval number. 1 is the the most recent
      previous interval; interval 96 is 24 hours ago. Intervals
      2..96 are optional."
   ::= { hdsl2Shdsl15MinIntervalEntry 1 }

hdsl2Shdsl15MinIntervalES OBJECT-TYPE
   SYNTAX      PerfIntervalCount
   UNITS       "seconds"
   MAX-ACCESS  read-only
   STATUS      current
   DESCRIPTION
     "Count of Errored Seconds (ES) during the interval."
   REFERENCE   "HDSL2 Section 7.5.3.7; SHDSL Section 9.5.5.7"
   ::= { hdsl2Shdsl15MinIntervalEntry 2 }

hdsl2Shdsl15MinIntervalSES OBJECT-TYPE
   SYNTAX      PerfIntervalCount
   UNITS       "seconds"
   MAX-ACCESS  read-only
   STATUS      current
   DESCRIPTION
     "Count of Severely Errored Seconds (SES) during the interval."
   REFERENCE   "HDSL2 Section 7.5.3.7; SHDSL Section 9.5.5.7"
   ::= { hdsl2Shdsl15MinIntervalEntry 3 }


hdsl2Shdsl15MinIntervalCRCanomalies OBJECT-TYPE
   SYNTAX      PerfIntervalCount
   UNITS       "detected CRC Anomalies"
   MAX-ACCESS  read-only
   STATUS      current
   DESCRIPTION
     "Count of CRC anomalies during the interval."
   REFERENCE   "HDSL2 Section 7.5.3.7; SHDSL Section 9.5.5.7"
   ::= { hdsl2Shdsl15MinIntervalEntry 4 }

hdsl2Shdsl15MinIntervalLOSWS OBJECT-TYPE
   SYNTAX      PerfIntervalCount
   UNITS       "seconds"
   MAX-ACCESS  read-only
   STATUS      current
   DESCRIPTION
     "Count of Loss of Sync Word (LOSW) Seconds during the
      interval."
   REFERENCE   "HDSL2 Section 7.5.3.7; SHDSL Section 9.5.5.7"
   ::= { hdsl2Shdsl15MinIntervalEntry 5 }

hdsl2Shdsl15MinIntervalUAS OBJECT-TYPE
   SYNTAX      PerfIntervalCount
   UNITS       "seconds"
   MAX-ACCESS  read-only
   STATUS      current
   DESCRIPTION
     "Count of Unavailable Seconds (UAS) during the interval."
   REFERENCE   "HDSL2 Section 7.5.3.7; SHDSL Section 9.5.5.7"
   ::= { hdsl2Shdsl15MinIntervalEntry 6 }

-- Segment Endpoint 1-Day Interval Status/Performance Group
--

hdsl2Shdsl1DayIntervalTable OBJECT-TYPE
   SYNTAX      SEQUENCE OF Hdsl2Shdsl1DayIntervalEntry
   MAX-ACCESS  not-accessible
   STATUS      current
   DESCRIPTION
     "This table provides one row for each HDSL2/SHDSL endpoint
      performance data collection interval.  This table contains
      live data from equipment.  As such, it is NOT persistent."
   ::= { hdsl2ShdslMibObjects 7 }

hdsl2Shdsl1DayIntervalEntry OBJECT-TYPE
   SYNTAX      Hdsl2Shdsl1DayIntervalEntry
   MAX-ACCESS  not-accessible
   STATUS      current


   DESCRIPTION
     "An entry in the hdsl2Shdsl1DayIntervalTable."
   INDEX { ifIndex, hdsl2ShdslInvIndex, hdsl2ShdslEndpointSide,
           hdsl2ShdslEndpointWirePair, hdsl2Shdsl1DayIntervalNumber }
   ::= { hdsl2Shdsl1DayIntervalTable 1 }

Hdsl2Shdsl1DayIntervalEntry ::=
   SEQUENCE
   {
   hdsl2Shdsl1DayIntervalNumber         Unsigned32,
   hdsl2Shdsl1DayIntervalMoniSecs       Hdsl2ShdslPerfTimeElapsed,
   hdsl2Shdsl1DayIntervalES             Hdsl2Shdsl1DayIntervalCount,
   hdsl2Shdsl1DayIntervalSES            Hdsl2Shdsl1DayIntervalCount,
   hdsl2Shdsl1DayIntervalCRCanomalies   Hdsl2Shdsl1DayIntervalCount,
   hdsl2Shdsl1DayIntervalLOSWS          Hdsl2Shdsl1DayIntervalCount,
   hdsl2Shdsl1DayIntervalUAS            Hdsl2Shdsl1DayIntervalCount
   }

hdsl2Shdsl1DayIntervalNumber OBJECT-TYPE
   SYNTAX      Unsigned32(1..30)
   MAX-ACCESS  not-accessible
   STATUS      current
   DESCRIPTION
     "History Data Interval number. Interval 1 is the the most
      recent previous day; interval 30 is 30 days ago. Intervals
      2..30 are optional."
   ::= { hdsl2Shdsl1DayIntervalEntry 1 }

hdsl2Shdsl1DayIntervalMoniSecs OBJECT-TYPE
   SYNTAX       Hdsl2ShdslPerfTimeElapsed
   UNITS        "seconds"
   MAX-ACCESS   read-only
   STATUS       current
   DESCRIPTION
     "The amount of time in the 1-day interval over which the
      performance monitoring information is actually counted.
      This value will be the same as the interval duration except
      in a situation where performance monitoring data could not
      be collected for any reason."
   ::= { hdsl2Shdsl1DayIntervalEntry 2 }

hdsl2Shdsl1DayIntervalES OBJECT-TYPE
   SYNTAX       Hdsl2Shdsl1DayIntervalCount
   UNITS        "seconds"
   MAX-ACCESS   read-only
   STATUS       current
   DESCRIPTION
     "Count of Errored Seconds (ES) during the 1-day interval as


      measured by hdsl2Shdsl1DayIntervalMoniSecs."
   REFERENCE   "HDSL2 Section 7.5.3.7; SHDSL Section 9.5.5.7"
   ::= { hdsl2Shdsl1DayIntervalEntry 3 }

hdsl2Shdsl1DayIntervalSES OBJECT-TYPE
   SYNTAX       Hdsl2Shdsl1DayIntervalCount
   UNITS        "seconds"
   MAX-ACCESS   read-only
   STATUS       current
   DESCRIPTION
     "Count of Severely Errored Seconds (SES) during the 1-day
      interval as measured by hdsl2Shdsl1DayIntervalMoniSecs."
   REFERENCE   "HDSL2 Section 7.5.3.7; SHDSL Section 9.5.5.7"
   ::= { hdsl2Shdsl1DayIntervalEntry 4 }

hdsl2Shdsl1DayIntervalCRCanomalies OBJECT-TYPE
   SYNTAX       Hdsl2Shdsl1DayIntervalCount
   UNITS        "detected CRC Anomalies"
   MAX-ACCESS   read-only
   STATUS       current
   DESCRIPTION
     "Count of CRC anomalies during the 1-day interval as
      measured by hdsl2Shdsl1DayIntervalMoniSecs."
   REFERENCE   "HDSL2 Section 7.5.3.7; SHDSL Section 9.5.5.7"
   ::= { hdsl2Shdsl1DayIntervalEntry 5 }

hdsl2Shdsl1DayIntervalLOSWS OBJECT-TYPE
   SYNTAX       Hdsl2Shdsl1DayIntervalCount
   UNITS        "seconds"
   MAX-ACCESS   read-only
   STATUS       current
   DESCRIPTION
     "Count of Loss of Sync Word (LOSW) Seconds during the 1-day
      interval as measured by hdsl2Shdsl1DayIntervalMoniSecs."
   REFERENCE   "HDSL2 Section 7.5.3.7; SHDSL Section 9.5.5.7"
   ::= { hdsl2Shdsl1DayIntervalEntry 6 }

hdsl2Shdsl1DayIntervalUAS OBJECT-TYPE
   SYNTAX       Hdsl2Shdsl1DayIntervalCount
   UNITS        "seconds"
   MAX-ACCESS   read-only
   STATUS       current
   DESCRIPTION
     "Count of Unavailable Seconds (UAS) during the 1-day interval
      as measured by hdsl2Shdsl1DayIntervalMoniSecs."
   REFERENCE   "HDSL2 Section 7.5.3.7; SHDSL Section 9.5.5.7"
   ::= { hdsl2Shdsl1DayIntervalEntry 7 }


-- Maintenance Group
--

hdsl2ShdslEndpointMaintTable OBJECT-TYPE
   SYNTAX      SEQUENCE OF Hdsl2ShdslEndpointMaintEntry
   MAX-ACCESS  not-accessible
   STATUS      current
   DESCRIPTION
     "This table supports maintenance operations (eg. loopbacks)
      to be performed on HDSL2/SHDSL segment endpoints.  This table
      contains live data from equipment.  As such, it is NOT
      persistent."
   ::= { hdsl2ShdslMibObjects 8 }

hdsl2ShdslEndpointMaintEntry OBJECT-TYPE
   SYNTAX      Hdsl2ShdslEndpointMaintEntry
   MAX-ACCESS  not-accessible
   STATUS      current
   DESCRIPTION
     "An entry in the hdsl2ShdslEndpointMaintTable.  Each entry
      corresponds to a single segment endpoint, and is indexed by the
      ifIndex of the HDSL2/SHDSL line, the UnitId of the associated
      unit and the side of the unit."
   INDEX { ifIndex, hdsl2ShdslInvIndex, hdsl2ShdslEndpointSide }
   ::= { hdsl2ShdslEndpointMaintTable 1 }

Hdsl2ShdslEndpointMaintEntry ::=
   SEQUENCE
   {
   hdsl2ShdslMaintLoopbackConfig      INTEGER,
   hdsl2ShdslMaintTipRingReversal     INTEGER,
   hdsl2ShdslMaintPowerBackOff        INTEGER,
   hdsl2ShdslMaintSoftRestart         INTEGER
   }

hdsl2ShdslMaintLoopbackConfig OBJECT-TYPE
   SYNTAX      INTEGER
               {
               noLoopback(1),
               normalLoopback(2),
               specialLoopback(3)
               }
   MAX-ACCESS  read-write
   STATUS      current
   DESCRIPTION
     "This object controls configuration of loopbacks for the
      associated segment endpoint.  The status of the loopback
      is obtained via the hdsl2ShdslEndpointCurrStatus object."


   ::= { hdsl2ShdslEndpointMaintEntry 1 }

hdsl2ShdslMaintTipRingReversal OBJECT-TYPE
   SYNTAX      INTEGER
               {
               normal(1),
               reversed(2)
               }
   MAX-ACCESS  read-only
   STATUS      current
   DESCRIPTION
     "This object indicates the state of the tip/ring pair at the
      associated segment endpoint."
   ::= { hdsl2ShdslEndpointMaintEntry 2 }

hdsl2ShdslMaintPowerBackOff OBJECT-TYPE
   SYNTAX      INTEGER
               {
               default(1),
               enhanced(2)
               }
   MAX-ACCESS  read-write
   STATUS      current
   DESCRIPTION
     "This object configures the receiver at the associated
      segment endpoint to operate in default or enhanced power
      backoff mode."
   ::= { hdsl2ShdslEndpointMaintEntry 3 }

hdsl2ShdslMaintSoftRestart OBJECT-TYPE
   SYNTAX      INTEGER
               {
               ready(1),
               restart(2)
               }
   MAX-ACCESS  read-write
   STATUS      current
   DESCRIPTION
     "This object enables the manager to trigger a soft restart
      of the modem at the associated segment endpoint.  The manager
      may only set this object to the 'restart(2)' value, which
      initiates a restart.  The agent will perform a restart after
      approximately 5 seconds.  Following the 5 second period, the
      agent will restore the object to the 'ready(1)' state."
   ::= { hdsl2ShdslEndpointMaintEntry 4 }

hdsl2ShdslUnitMaintTable OBJECT-TYPE
   SYNTAX      SEQUENCE OF Hdsl2ShdslUnitMaintEntry


   MAX-ACCESS  not-accessible
   STATUS      current
   DESCRIPTION
     "This table supports maintenance operations for units in a
      HDSL2/SHDSL line.  Entries in this table MUST be maintained
      in a persistent manner."
   ::= { hdsl2ShdslMibObjects 9 }

hdsl2ShdslUnitMaintEntry OBJECT-TYPE
   SYNTAX      Hdsl2ShdslUnitMaintEntry
   MAX-ACCESS  not-accessible
   STATUS      current
   DESCRIPTION
     "An entry in the hdsl2ShdslUnitMaintTable.  Each entry
      corresponds to a single unit, and is indexed by the ifIndex
      of the HDSL2/SHDSL line and the UnitId of the associated
      unit."
   INDEX { ifIndex, hdsl2ShdslInvIndex  }
   ::= { hdsl2ShdslUnitMaintTable 1 }

Hdsl2ShdslUnitMaintEntry ::=
   SEQUENCE
   {
   hdsl2ShdslMaintLoopbackTimeout     Integer32,
   hdsl2ShdslMaintUnitPowerSource     INTEGER
   }

hdsl2ShdslMaintLoopbackTimeout OBJECT-TYPE
   SYNTAX      Integer32(0..4095)
   UNITS       "minutes"
   MAX-ACCESS  read-write
   STATUS      current
   DESCRIPTION
     "This object configures the timeout value for loopbacks
      initiated at segments endpoints contained in the associated
      unit.  A value of 0 disables the timeout."
   ::= { hdsl2ShdslUnitMaintEntry 1 }

hdsl2ShdslMaintUnitPowerSource OBJECT-TYPE
   SYNTAX      INTEGER
               {
               local(1),
               span(2)
               }
   MAX-ACCESS  read-only
   STATUS      current
   DESCRIPTION
     "This object indicates the DC power source being used by the


      associated unit."
   ::= { hdsl2ShdslUnitMaintEntry 2 }

-- Span Configuration Profile Group
--

hdsl2ShdslSpanConfProfileTable OBJECT-TYPE
   SYNTAX      SEQUENCE OF Hdsl2ShdslSpanConfProfileEntry
   MAX-ACCESS  not-accessible
   STATUS      current
   DESCRIPTION
     "This table supports definitions of span configuration
      profiles for SHDSL lines.  HDSL2 does not support these
      configuration options.  This table MUST be maintained
      in a persistent manner."
   ::= { hdsl2ShdslMibObjects 10 }

hdsl2ShdslSpanConfProfileEntry OBJECT-TYPE
   SYNTAX      Hdsl2ShdslSpanConfProfileEntry
   MAX-ACCESS  not-accessible
   STATUS      current
   DESCRIPTION
     "Each entry corresponds to a single span configuration
      profile.  Each profile contains a set of span configuration
      parameters.  The configuration parameters in a profile are
      applied to those lines referencing that profile (see the
      hdsl2ShdslSpanConfProfile object).  Profiles may be
      created/deleted using the row creation/deletion mechanism
      via hdsl2ShdslSpanConfProfileRowStatus.  If an active
      entry is referenced in hdsl2ShdslSpanConfProfile, the
      entry MUST remain active until all references are removed."
   INDEX { IMPLIED hdsl2ShdslSpanConfProfileName }
   ::= { hdsl2ShdslSpanConfProfileTable 1 }

Hdsl2ShdslSpanConfProfileEntry ::=
   SEQUENCE
   {
   hdsl2ShdslSpanConfProfileName               SnmpAdminString,
   hdsl2ShdslSpanConfWireInterface             INTEGER,
   hdsl2ShdslSpanConfMinLineRate               Unsigned32,
   hdsl2ShdslSpanConfMaxLineRate               Unsigned32,
   hdsl2ShdslSpanConfPSD                       INTEGER,
   hdsl2ShdslSpanConfTransmissionMode
                                   Hdsl2ShdslTransmissionModeType,
   hdsl2ShdslSpanConfRemoteEnabled             INTEGER,
   hdsl2ShdslSpanConfPowerFeeding              INTEGER,
   hdsl2ShdslSpanConfCurrCondTargetMarginDown  Integer32,
   hdsl2ShdslSpanConfWorstCaseTargetMarginDown Integer32,


   hdsl2ShdslSpanConfCurrCondTargetMarginUp    Integer32,
   hdsl2ShdslSpanConfWorstCaseTargetMarginUp   Integer32,
   hdsl2ShdslSpanConfUsedTargetMargins         BITS,
   hdsl2ShdslSpanConfReferenceClock
                                   Hdsl2ShdslClockReferenceType,
   hdsl2ShdslSpanConfLineProbeEnable           INTEGER,
   hdsl2ShdslSpanConfProfileRowStatus          RowStatus
   }

hdsl2ShdslSpanConfProfileName OBJECT-TYPE
   SYNTAX      SnmpAdminString (SIZE(1..32))
   MAX-ACCESS  not-accessible
   STATUS      current
   DESCRIPTION
     "This object is the unique index associated with this profile.
      Entries in this table are referenced via the object
      hdsl2ShdslSpanConfProfile in Hdsl2ShdslSpanConfEntry."
   ::= { hdsl2ShdslSpanConfProfileEntry 1 }

hdsl2ShdslSpanConfWireInterface OBJECT-TYPE
   SYNTAX      INTEGER
               {
               twoWire(1),
               fourWire(2)
               }
   MAX-ACCESS  read-create
   STATUS      current
   DESCRIPTION
     "This object configures the two-wire or optional four-wire
      operation for SHDSL Lines."
   DEFVAL      { twoWire }
   ::= { hdsl2ShdslSpanConfProfileEntry 2 }

hdsl2ShdslSpanConfMinLineRate OBJECT-TYPE
   SYNTAX      Unsigned32(0..4112000)
   UNITS       "bps"
   MAX-ACCESS  read-create
   STATUS      current
   DESCRIPTION
     "This object configures the minimum transmission rate for
      the associated SHDSL Line in bits-per-second (bps).  If
      the minimum line rate equals the maximum line rate
      (hdsl2ShdslSpanMaxLineRate), the line rate is considered
      'fixed'.  If the minimum line rate is less than the maximum
      line rate, the line rate is considered 'rate-adaptive'."
   DEFVAL      { 1552000 }
   ::= { hdsl2ShdslSpanConfProfileEntry 3 }


hdsl2ShdslSpanConfMaxLineRate OBJECT-TYPE
   SYNTAX      Unsigned32(0..4112000)
   UNITS       "bps"
   MAX-ACCESS  read-create
   STATUS      current
   DESCRIPTION
     "This object configures the maximum transmission rate for
      the associated SHDSL Line in bits-per-second (bps).  If
      the minimum line rate equals the maximum line rate
      (hdsl2ShdslSpanMaxLineRate), the line rate is considered
      'fixed'.  If the minimum line rate is less than the maximum
      line rate, the line rate is considered 'rate-adaptive'."
   DEFVAL      { 1552000 }
   ::= { hdsl2ShdslSpanConfProfileEntry 4 }

hdsl2ShdslSpanConfPSD OBJECT-TYPE
   SYNTAX      INTEGER
               {
               symmetric(1),
               asymmetric(2)
               }
   MAX-ACCESS  read-create
   STATUS      current
   DESCRIPTION
     "This object configures use of symmetric/asymmetric PSD (Power
      Spectral Density) Mask for the associated SHDSL Line.  Support
      for symmetric PSD is mandatory for all supported data rates.
      Support for asymmetric PSD is optional."
   DEFVAL      { symmetric }
   ::= { hdsl2ShdslSpanConfProfileEntry 5 }

hdsl2ShdslSpanConfTransmissionMode OBJECT-TYPE
   SYNTAX      Hdsl2ShdslTransmissionModeType
   MAX-ACCESS  read-create
   STATUS      current
   DESCRIPTION
     "This object specifies the regional setting for the SHDSL
      line."
   DEFVAL      { { region1 } }
   ::= { hdsl2ShdslSpanConfProfileEntry 6 }

hdsl2ShdslSpanConfRemoteEnabled OBJECT-TYPE
   SYNTAX      INTEGER
               {
               enabled(1),
               disabled(2)
               }
   MAX-ACCESS  read-create


   STATUS      current
   DESCRIPTION
     "This object enables/disables support for remote management
      of the units in a SHDSL line from the STU-R via the EOC."
   DEFVAL      { enabled }
   ::= { hdsl2ShdslSpanConfProfileEntry 7 }

hdsl2ShdslSpanConfPowerFeeding OBJECT-TYPE
   SYNTAX      INTEGER
               {
               noPower(1),
               powerFeed(2),
               wettingCurrent(3)
               }
   MAX-ACCESS  read-create
   STATUS      current
   DESCRIPTION
     "This object enables/disables support for optional power
      feeding in a SHDSL line."
   DEFVAL      { noPower }
   ::= { hdsl2ShdslSpanConfProfileEntry 8 }

hdsl2ShdslSpanConfCurrCondTargetMarginDown OBJECT-TYPE
   SYNTAX      Integer32(-10..21)
   UNITS       "dB"
   MAX-ACCESS  read-create
   STATUS      current
   DESCRIPTION
     "This object specifies the downstream current condition target
      SNR margin for a SHDSL line.  The SNR margin is the difference
      between the desired SNR and the actual SNR.  Target SNR margin
      is the desired SNR margin for a unit."
   DEFVAL      { 0 }
   ::= { hdsl2ShdslSpanConfProfileEntry 9 }

hdsl2ShdslSpanConfWorstCaseTargetMarginDown OBJECT-TYPE
   SYNTAX      Integer32(-10..21)
   UNITS       "dB"
   MAX-ACCESS  read-create
   STATUS      current
   DESCRIPTION
     "This object specifies the downstream worst case target SNR
      margin for a SHDSL line.  The SNR margin is the difference
      between the desired SNR and the actual SNR.  Target SNR
      margin is the desired SNR margin for a unit."
   DEFVAL      { 0 }
   ::= { hdsl2ShdslSpanConfProfileEntry 10 }


hdsl2ShdslSpanConfCurrCondTargetMarginUp OBJECT-TYPE
   SYNTAX      Integer32(-10..21)
   UNITS       "dB"
   MAX-ACCESS  read-create
   STATUS      current
   DESCRIPTION
     "This object specifies the upstream current condition target
      SNR margin for a SHDSL line.  The SNR margin is the difference
      between the desired SNR and the actual SNR.  Target SNR margin
      is the desired SNR margin for a unit."
   DEFVAL      { 0 }
   ::= { hdsl2ShdslSpanConfProfileEntry 11 }

hdsl2ShdslSpanConfWorstCaseTargetMarginUp OBJECT-TYPE
   SYNTAX      Integer32(-10..21)
   UNITS       "dB"
   MAX-ACCESS  read-create
   STATUS      current
   DESCRIPTION
     "This object specifies the upstream worst case target SNR
      margin for a SHDSL line.  The SNR margin is the difference
      between the desired SNR and the actual SNR.  Target SNR margin
      is the desired SNR margin for a unit."
   DEFVAL      { 0 }
   ::= { hdsl2ShdslSpanConfProfileEntry 12 }

hdsl2ShdslSpanConfUsedTargetMargins OBJECT-TYPE
   SYNTAX      BITS
               {
               currCondDown(0),
               worstCaseDown(1),
               currCondUp(2),
               worstCaseUp(3)
               }
   MAX-ACCESS  read-create
   STATUS      current
   DESCRIPTION
     "Contains indicates whether a target SNR margin is enabled or
      disabled.  This is a bit-map of possible settings.  The
      various bit positions are:

      currCondDown     current condition downstream target SNR
                       margin enabled

      worstCaseDown    worst case downstream target SNR margin
                       enabled

      currCondUp       current condition upstream target SNR


                       margin enabled

      worstCaseUp      worst case upstream target SNR margin
                       enabled."
   DEFVAL      { { currCondDown } }
   ::= { hdsl2ShdslSpanConfProfileEntry 13 }

hdsl2ShdslSpanConfReferenceClock OBJECT-TYPE
   SYNTAX      Hdsl2ShdslClockReferenceType
   MAX-ACCESS  read-create
   STATUS      current
   DESCRIPTION
     "This object configures the clock reference for the STU-C
     in a SHDSL Line."
   DEFVAL      { localClk }
   ::= { hdsl2ShdslSpanConfProfileEntry 14 }

hdsl2ShdslSpanConfLineProbeEnable OBJECT-TYPE
   SYNTAX      INTEGER
               {
               disable(1),
               enable(2)
               }
   MAX-ACCESS  read-create
   STATUS      current
   DESCRIPTION
     "This object enables/disables support for Line Probe of
     the units in a SHDSL line.  When Line Probe is enabled, the
     system performs Line Probing to find the best possible
     rate.  If Line probe is disabled, the rate adaptation phase
     is skipped to shorten set up time."
   DEFVAL      { disable }
   ::= { hdsl2ShdslSpanConfProfileEntry 15 }

hdsl2ShdslSpanConfProfileRowStatus OBJECT-TYPE
   SYNTAX      RowStatus
   MAX-ACCESS  read-create
   STATUS      current
   DESCRIPTION
     "This object controls creation/deletion of the associated
      entry in this table per the semantics of RowStatus.  If an
      active entry is referenced in hdsl2ShdslSpanConfProfile, the
      entry MUST remain active until all references are removed."
   ::= { hdsl2ShdslSpanConfProfileEntry 16 }

-- Segment Endpoint Alarm Configuration Profile group
--


hdsl2ShdslEndpointAlarmConfProfileTable OBJECT-TYPE
   SYNTAX      SEQUENCE OF Hdsl2ShdslEndpointAlarmConfProfileEntry
   MAX-ACCESS  not-accessible
   STATUS      current
   DESCRIPTION
     "This table supports definitions of alarm configuration
      profiles for HDSL2/SHDSL segment endpoints.  This table
      MUST be maintained in a persistent manner."
   ::= { hdsl2ShdslMibObjects 11 }

hdsl2ShdslEndpointAlarmConfProfileEntry OBJECT-TYPE
   SYNTAX      Hdsl2ShdslEndpointAlarmConfProfileEntry
   MAX-ACCESS  not-accessible
   STATUS      current
   DESCRIPTION
     "Each entry corresponds to a single alarm configuration profile.
      Each profile contains a set of parameters for setting alarm
      thresholds for various performance attributes monitored at
      HDSL2/SHDSL segment endpoints.  Profiles may be created/deleted
      using the row creation/deletion mechanism via
      hdsl2ShdslEndpointAlarmConfProfileRowStatus.  If an active
      entry is referenced in either hdsl2ShdslSpanConfAlarmProfile
      or hdsl2ShdslEndpointAlarmConfProfile, the entry MUST remain
      active until all references are removed."
   INDEX { IMPLIED hdsl2ShdslEndpointAlarmConfProfileName }
   ::= { hdsl2ShdslEndpointAlarmConfProfileTable 1 }

Hdsl2ShdslEndpointAlarmConfProfileEntry ::=
   SEQUENCE
   {
   hdsl2ShdslEndpointAlarmConfProfileName       SnmpAdminString,
   hdsl2ShdslEndpointThreshLoopAttenuation      Integer32,
   hdsl2ShdslEndpointThreshSNRMargin            Integer32,
   hdsl2ShdslEndpointThreshES
               Hdsl2ShdslPerfIntervalThreshold,
   hdsl2ShdslEndpointThreshSES
               Hdsl2ShdslPerfIntervalThreshold,
   hdsl2ShdslEndpointThreshCRCanomalies         Integer32,
   hdsl2ShdslEndpointThreshLOSWS
               Hdsl2ShdslPerfIntervalThreshold,
   hdsl2ShdslEndpointThreshUAS
               Hdsl2ShdslPerfIntervalThreshold,
   hdsl2ShdslEndpointAlarmConfProfileRowStatus  RowStatus
   }

hdsl2ShdslEndpointAlarmConfProfileName OBJECT-TYPE
   SYNTAX      SnmpAdminString (SIZE(1..32))
   MAX-ACCESS  not-accessible


   STATUS      current
   DESCRIPTION
     "This object is the unique index associated with this profile."
   ::= { hdsl2ShdslEndpointAlarmConfProfileEntry 1 }

hdsl2ShdslEndpointThreshLoopAttenuation OBJECT-TYPE
   SYNTAX      Integer32(-127..128)
   UNITS       "dB"
   MAX-ACCESS  read-create
   STATUS      current
   DESCRIPTION
     "This object configures the loop attenuation alarm threshold.
      When the current value of hdsl2ShdslEndpointCurrAtn reaches
      or exceeds this threshold, a hdsl2ShdslLoopAttenCrossing
      MAY be generated."
   DEFVAL      { 0 }
   ::= { hdsl2ShdslEndpointAlarmConfProfileEntry 2 }

hdsl2ShdslEndpointThreshSNRMargin OBJECT-TYPE
   SYNTAX      Integer32(-127..128)
   UNITS       "dB"
   MAX-ACCESS  read-create
   STATUS      current
   DESCRIPTION
     "This object configures the SNR margin alarm threshold.
      When the current value of hdsl2ShdslEndpointCurrSnrMgn
      reaches or drops below this threshold, a
      hdsl2ShdslSNRMarginCrossing MAY be generated."
   DEFVAL      { 0 }
   ::= { hdsl2ShdslEndpointAlarmConfProfileEntry 3 }

hdsl2ShdslEndpointThreshES OBJECT-TYPE
   SYNTAX      Hdsl2ShdslPerfIntervalThreshold
   UNITS       "seconds"
   MAX-ACCESS  read-create
   STATUS      current
   DESCRIPTION
     "This object configures the threshold for the number of
      errored seconds (ES) within any given 15-minute performance
      data collection interval.  If the value of errored seconds
      in a particular 15-minute collection interval reaches/
      exceeds this value, a hdsl2ShdslPerfESThresh MAY be
      generated.  At most one notification will be sent per
      interval per endpoint."
   DEFVAL      { 0 }
   ::= { hdsl2ShdslEndpointAlarmConfProfileEntry 4 }

hdsl2ShdslEndpointThreshSES OBJECT-TYPE


   SYNTAX      Hdsl2ShdslPerfIntervalThreshold
   UNITS       "seconds"
   MAX-ACCESS  read-create
   STATUS      current
   DESCRIPTION
     "This object configures the threshold for the number of
      severely errored seconds (SES) within any given 15-minute
      performance data collection interval.  If the value of
      severely errored seconds in a particular 15-minute collection
      interval reaches/exceeds this value, a hdsl2ShdslPerfSESThresh
      MAY be generated.  At most one notification will be sent per
      interval per endpoint."
   DEFVAL      { 0 }
   ::= { hdsl2ShdslEndpointAlarmConfProfileEntry 5 }

hdsl2ShdslEndpointThreshCRCanomalies OBJECT-TYPE
   SYNTAX      Integer32
   UNITS       "detected CRC Anomalies"
   MAX-ACCESS  read-create
   STATUS      current
   DESCRIPTION
     "This object configures the threshold for the number of
      CRC anomalies within any given 15-minute performance data
      collection interval.  If the value of CRC anomalies in a
      particular 15-minute collection interval reaches/exceeds
      this value, a hdsl2ShdslPerfCRCanomaliesThresh MAY be
      generated.  At most one notification will be sent per
      interval per endpoint."
   DEFVAL      { 0 }
   ::= { hdsl2ShdslEndpointAlarmConfProfileEntry 6 }

hdsl2ShdslEndpointThreshLOSWS OBJECT-TYPE
   SYNTAX      Hdsl2ShdslPerfIntervalThreshold
   UNITS       "seconds"
   MAX-ACCESS  read-create
   STATUS      current
   DESCRIPTION
     "This object configures the threshold for the number of
      Loss of Sync Word (LOSW) Seconds within any given 15-minute
      performance data collection interval.  If the value of LOSW
      in a particular 15-minute collection interval reaches/exceeds
      this value, a hdsl2ShdslPerfLOSWSThresh MAY be generated.
      At most one notification will be sent per interval per
      endpoint."
   DEFVAL      { 0 }
   ::= { hdsl2ShdslEndpointAlarmConfProfileEntry 7 }

hdsl2ShdslEndpointThreshUAS OBJECT-TYPE


   SYNTAX      Hdsl2ShdslPerfIntervalThreshold
   UNITS       "seconds"
   MAX-ACCESS  read-create
   STATUS      current
   DESCRIPTION
     "This object configures the threshold for the number of
      unavailable seconds (UAS) within any given 15-minute
      performance data collection interval.  If the value of UAS
      in a particular 15-minute collection interval reaches/exceeds
      this value, a hdsl2ShdslPerfUASThresh MAY be generated.
      At most one notification will be sent per interval per
      endpoint."
   DEFVAL      { 0 }
   ::= { hdsl2ShdslEndpointAlarmConfProfileEntry 8 }

hdsl2ShdslEndpointAlarmConfProfileRowStatus OBJECT-TYPE
   SYNTAX      RowStatus
   MAX-ACCESS  read-create
   STATUS      current
   DESCRIPTION
     "This object controls creation/deletion of the associated
      entry in this table as per the semantics of RowStatus.
      If an active entry is referenced in either
      hdsl2ShdslSpanConfAlarmProfile or
      hdsl2ShdslEndpointAlarmConfProfile, the entry MUST remain
      active until all references are removed."
   ::= { hdsl2ShdslEndpointAlarmConfProfileEntry 9 }

-- Notifications Group
--

hdsl2ShdslNotifications OBJECT IDENTIFIER ::= { hdsl2ShdslMIB 0 }

hdsl2ShdslLoopAttenCrossing NOTIFICATION-TYPE
   OBJECTS
   {
   hdsl2ShdslEndpointCurrAtn,
   hdsl2ShdslEndpointThreshLoopAttenuation
   }
   STATUS     current
   DESCRIPTION
     "This notification indicates that the loop attenuation
      threshold (as per the hdsl2ShdslEndpointThreshLoopAttenuation
      value) has been reached/exceeded for the HDSL2/SHDSL segment
      endpoint."
   ::= { hdsl2ShdslNotifications 1 }

hdsl2ShdslSNRMarginCrossing NOTIFICATION-TYPE


   OBJECTS
   {

   hdsl2ShdslEndpointCurrSnrMgn,
   hdsl2ShdslEndpointThreshSNRMargin
   }
   STATUS     current
   DESCRIPTION
     "This notification indicates that the SNR margin threshold (as
      per the hdsl2ShdslEndpointThreshSNRMargin value) has been
      reached/exceeded for the HDSL2/SHDSL segment endpoint."
   ::= { hdsl2ShdslNotifications 2 }

hdsl2ShdslPerfESThresh NOTIFICATION-TYPE
   OBJECTS
   {
   hdsl2ShdslEndpointCurr15MinES,
   hdsl2ShdslEndpointThreshES
   }
   STATUS     current
   DESCRIPTION
     "This notification indicates that the errored seconds threshold
      (as per the hdsl2ShdslEndpointThreshES value) has been reached/
      exceeded for the HDSL2/SHDSL segment endpoint."
   ::= { hdsl2ShdslNotifications 3 }

hdsl2ShdslPerfSESThresh NOTIFICATION-TYPE
   OBJECTS
   {
   hdsl2ShdslEndpointCurr15MinSES,
   hdsl2ShdslEndpointThreshSES
   }
   STATUS     current
   DESCRIPTION
     "This notification indicates that the severely errored seconds
      threshold (as per the hdsl2ShdslEndpointThreshSES value) has
      been reached/exceeded for the HDSL2/SHDSL Segment Endpoint."
   ::= { hdsl2ShdslNotifications 4 }

hdsl2ShdslPerfCRCanomaliesThresh NOTIFICATION-TYPE
   OBJECTS
   {
   hdsl2ShdslEndpointCurr15MinCRCanomalies,
   hdsl2ShdslEndpointThreshCRCanomalies
   }
   STATUS    current
   DESCRIPTION
     "This notification indicates that the CRC anomalies threshold


      (as per the hdsl2ShdslEndpointThreshCRCanomalies value) has
      been reached/exceeded for the HDSL2/SHDSL Segment Endpoint."
   ::= { hdsl2ShdslNotifications 5 }

hdsl2ShdslPerfLOSWSThresh NOTIFICATION-TYPE
   OBJECTS
   {

   hdsl2ShdslEndpointCurr15MinLOSWS,
   hdsl2ShdslEndpointThreshLOSWS
   }
   STATUS     current
   DESCRIPTION
     "This notification indicates that the LOSW seconds threshold
      (as per the hdsl2ShdslEndpointThreshLOSWS value) has been
      reached/exceeded for the HDSL2/SHDSL segment endpoint."
   ::= { hdsl2ShdslNotifications 6 }

hdsl2ShdslPerfUASThresh NOTIFICATION-TYPE
   OBJECTS
   {
   hdsl2ShdslEndpointCurr15MinUAS,
   hdsl2ShdslEndpointThreshUAS
   }
   STATUS     current
   DESCRIPTION
     "This notification indicates that the unavailable seconds
      threshold (as per the hdsl2ShdslEndpointThreshUAS value) has
      been reached/exceeded for the HDSL2/SHDSL segment endpoint."
   ::= { hdsl2ShdslNotifications 7 }

hdsl2ShdslSpanInvalidNumRepeaters NOTIFICATION-TYPE
   OBJECTS
   {
   hdsl2ShdslSpanConfNumRepeaters
   }
   STATUS     current
   DESCRIPTION
     "This notification indicates that a mismatch has been detected
      between the number of repeater/regenerator units configured
      for a HDSL2/SHDSL line via the hdsl2ShdslSpanConfNumRepeaters
      object and the actual number of repeater/regenerator units
      discovered via the EOC."
   ::= { hdsl2ShdslNotifications 8 }

hdsl2ShdslLoopbackFailure NOTIFICATION-TYPE
   OBJECTS
   {


   hdsl2ShdslMaintLoopbackConfig
   }
   STATUS     current
   DESCRIPTION
     "This notification indicates that an endpoint maintenance
      loopback command failed for an HDSL2/SHDSL segment."
   ::= { hdsl2ShdslNotifications 9 }

hdsl2ShdslpowerBackoff NOTIFICATION-TYPE
   OBJECTS
   {
   hdsl2ShdslEndpointCurrStatus
   }
   STATUS    current
   DESCRIPTION
     "This notification indicates that the bit setting for
      powerBackoff in the hdsl2ShdslEndpointCurrStatus object for
      this endpoint has changed."
   ::= { hdsl2ShdslNotifications 10 }

hdsl2ShdsldeviceFault NOTIFICATION-TYPE
   OBJECTS
   {
   hdsl2ShdslEndpointCurrStatus
   }
   STATUS    current
   DESCRIPTION
     "This notification indicates that the bit setting for
      deviceFault in the hdsl2ShdslEndpointCurrStatus object for
      this endpoint has changed."
   ::= { hdsl2ShdslNotifications 11 }

hdsl2ShdsldcContinuityFault NOTIFICATION-TYPE
   OBJECTS
   {
   hdsl2ShdslEndpointCurrStatus
   }
   STATUS    current
   DESCRIPTION
     "This notification indicates that the bit setting for
      dcContinuityFault in the hdsl2ShdslEndpointCurrStatus object
      for this endpoint has changed."
   ::= { hdsl2ShdslNotifications 12 }

hdsl2ShdslconfigInitFailure NOTIFICATION-TYPE
   OBJECTS
   {
   hdsl2ShdslEndpointCurrStatus


   }
   STATUS    current
   DESCRIPTION
     "This notification indicates that the bit setting for
      configInitFailure in the hdsl2ShdslEndpointCurrStatus object
      for this endpoint has changed."
   ::= { hdsl2ShdslNotifications 13 }

hdsl2ShdslprotocolInitFailure NOTIFICATION-TYPE
   OBJECTS
   {
   hdsl2ShdslEndpointCurrStatus
   }
   STATUS    current
   DESCRIPTION
     "This notification indicates that the bit setting for
      protocolInitFailure in the hdsl2ShdslEndpointCurrStatus
      object for this endpoint has changed."
   ::= { hdsl2ShdslNotifications 14 }

hdsl2ShdslnoNeighborPresent NOTIFICATION-TYPE
   OBJECTS
   {
   hdsl2ShdslEndpointCurrStatus
   }
   STATUS    current
   DESCRIPTION
     "This notification indicates that the bit setting for
      noNeighborPresent in the hdsl2ShdslEndpointCurrStatus object
      for this endpoint has changed."
   ::= { hdsl2ShdslNotifications 15 }

hdsl2ShdslLocalPowerLoss NOTIFICATION-TYPE
   OBJECTS
   {
   hdsl2ShdslInvVendorID
   }
   STATUS    current
   DESCRIPTION
     "This notification indicates impending unit failure due to
      loss of local power (last gasp)."
   ::= { hdsl2ShdslNotifications 16 }

-- conformance information
--

hdsl2ShdslConformance OBJECT IDENTIFIER ::= { hdsl2ShdslMIB 3 }
hdsl2ShdslGroups      OBJECT IDENTIFIER ::=


             { hdsl2ShdslConformance 1 }
hdsl2ShdslCompliances OBJECT IDENTIFIER ::=
             { hdsl2ShdslConformance 2 }

-- agent compliance statements

hdsl2ShdslLineMibCompliance MODULE-COMPLIANCE
   STATUS  current
   DESCRIPTION
     "The section outlines compliance requirements for this MIB."
   MODULE
   MANDATORY-GROUPS
   {
   hdsl2ShdslSpanConfGroup,
   hdsl2ShdslSpanStatusGroup,
   hdsl2ShdslInventoryGroup,
   hdsl2ShdslEndpointConfGroup,
   hdsl2ShdslEndpointCurrGroup,
   hdsl2Shdsl15MinIntervalGroup,
   hdsl2Shdsl1DayIntervalGroup,
   hdsl2ShdslMaintenanceGroup,
   hdsl2ShdslEndpointAlarmConfGroup,
   hdsl2ShdslNotificationGroup
   }

GROUP  hdsl2ShdslInventoryShdslGroup
   DESCRIPTION
     "Support for this group is only required for implementations
     supporting SHDSL lines."

GROUP  hdsl2ShdslSpanShdslStatusGroup
   DESCRIPTION
     "Support for this group is only required for implementations
     supporting SHDSL lines."

GROUP  hdsl2ShdslSpanConfProfileGroup
   DESCRIPTION
     "Support for this group is only required for implementations
     supporting SHDSL lines."

   ::= { hdsl2ShdslCompliances 1 }

-- units of conformance
--

hdsl2ShdslSpanConfGroup OBJECT-GROUP
   OBJECTS
   {


   hdsl2ShdslSpanConfNumRepeaters,
   hdsl2ShdslSpanConfProfile,
   hdsl2ShdslSpanConfAlarmProfile
   }
   STATUS      current
   DESCRIPTION
     "This group supports objects for configuring span related
      parameters for HDSL2/SHDSL lines."
   ::= { hdsl2ShdslGroups 1 }

hdsl2ShdslSpanStatusGroup OBJECT-GROUP
   OBJECTS
   {
   hdsl2ShdslStatusNumAvailRepeaters
   }
   STATUS      current
   DESCRIPTION
     "This group supports objects for retrieving span related
      status for HDSL2/SHDSL lines."
   ::= { hdsl2ShdslGroups 2 }

hdsl2ShdslInventoryShdslGroup OBJECT-GROUP
   OBJECTS
   {
   hdsl2ShdslInvTransmissionModeCapability
   }
   STATUS      current
   DESCRIPTION
     "This group supports objects for retrieving SHDSL-specific
      inventory information."
   ::= { hdsl2ShdslGroups 3 }

hdsl2ShdslSpanShdslStatusGroup OBJECT-GROUP
   OBJECTS
   {
   hdsl2ShdslStatusMaxAttainableLineRate,
   hdsl2ShdslStatusActualLineRate,
   hdsl2ShdslStatusTransmissionModeCurrent
   }
   STATUS      current
   DESCRIPTION
     "This group supports objects for retrieving SHDSL-specific
      span related status."
   ::= { hdsl2ShdslGroups 4 }

hdsl2ShdslInventoryGroup OBJECT-GROUP
   OBJECTS
   {


   hdsl2ShdslInvVendorID,
   hdsl2ShdslInvVendorModelNumber,
   hdsl2ShdslInvVendorSerialNumber,
   hdsl2ShdslInvVendorEOCSoftwareVersion,
   hdsl2ShdslInvStandardVersion,
   hdsl2ShdslInvVendorListNumber,
   hdsl2ShdslInvVendorIssueNumber,
   hdsl2ShdslInvVendorSoftwareVersion,
   hdsl2ShdslInvEquipmentCode,
   hdsl2ShdslInvVendorOther
   }
   STATUS      current
   DESCRIPTION
     "This group supports objects that provide unit inventory
      information about the units in HDSL2/SHDSL lines."
   ::= { hdsl2ShdslGroups 5 }

hdsl2ShdslEndpointConfGroup OBJECT-GROUP
   OBJECTS
   {
   hdsl2ShdslEndpointCurrAtn
   }
   STATUS      current
   DESCRIPTION
     "This group supports objects for configuring parameters for
      segment endpoints in HDSL2/SHDSL lines."
   ::= { hdsl2ShdslGroups 6 }

hdsl2ShdslEndpointCurrGroup OBJECT-GROUP
   OBJECTS
   {
   hdsl2ShdslEndpointCurrAtn,
   hdsl2ShdslEndpointCurrSnrMgn,
   hdsl2ShdslEndpointCurrStatus,
   hdsl2ShdslEndpointES,
   hdsl2ShdslEndpointSES,
   hdsl2ShdslEndpointCRCanomalies,
   hdsl2ShdslEndpointLOSWS,
   hdsl2ShdslEndpointUAS,
   hdsl2ShdslEndpointCurr15MinTimeElapsed,
   hdsl2ShdslEndpointCurr15MinES,
   hdsl2ShdslEndpointCurr15MinSES,
   hdsl2ShdslEndpointCurr15MinCRCanomalies,
   hdsl2ShdslEndpointCurr15MinLOSWS,
   hdsl2ShdslEndpointCurr15MinUAS,
   hdsl2ShdslEndpointCurr1DayTimeElapsed,
   hdsl2ShdslEndpointCurr1DayES,
   hdsl2ShdslEndpointCurr1DaySES,


   hdsl2ShdslEndpointCurr1DayCRCanomalies,
   hdsl2ShdslEndpointCurr1DayLOSWS,
   hdsl2ShdslEndpointCurr1DayUAS
   }
   STATUS      current
   DESCRIPTION
     "This group supports objects which provide current status and
      performance measurements relating to segment endpoints in
      HDSL2/SHDSL lines."
   ::= { hdsl2ShdslGroups 7 }

hdsl2Shdsl15MinIntervalGroup OBJECT-GROUP
   OBJECTS
   {
   hdsl2Shdsl15MinIntervalES,
   hdsl2Shdsl15MinIntervalSES,
   hdsl2Shdsl15MinIntervalCRCanomalies,
   hdsl2Shdsl15MinIntervalLOSWS,
   hdsl2Shdsl15MinIntervalUAS
   }
   STATUS      current
   DESCRIPTION
     "This group supports objects which maintain historic
      performance measurements relating to segment endpoints in
      HDSL2/SHDSL lines in 15-minute intervals."
   ::= { hdsl2ShdslGroups 8 }

hdsl2Shdsl1DayIntervalGroup OBJECT-GROUP
   OBJECTS
   {
   hdsl2Shdsl1DayIntervalMoniSecs,
   hdsl2Shdsl1DayIntervalES,
   hdsl2Shdsl1DayIntervalSES,
   hdsl2Shdsl1DayIntervalCRCanomalies,
   hdsl2Shdsl1DayIntervalLOSWS,
   hdsl2Shdsl1DayIntervalUAS
   }
   STATUS      current
   DESCRIPTION
     "This group supports objects which maintain historic
      performance measurements relating to segment endpoints in
      HDSL2/SHDSL lines in 1-day intervals."
   ::= { hdsl2ShdslGroups 9 }

hdsl2ShdslMaintenanceGroup OBJECT-GROUP
   OBJECTS
   {
   hdsl2ShdslMaintLoopbackConfig,


   hdsl2ShdslMaintTipRingReversal,
   hdsl2ShdslMaintPowerBackOff,
   hdsl2ShdslMaintSoftRestart,
   hdsl2ShdslMaintLoopbackTimeout,
   hdsl2ShdslMaintUnitPowerSource
   }
   STATUS      current
   DESCRIPTION
     "This group supports objects that provide support for
      maintenance actions for HDSL2/SHDSL lines."
   ::= { hdsl2ShdslGroups 10 }

hdsl2ShdslEndpointAlarmConfGroup OBJECT-GROUP
   OBJECTS
   {
   hdsl2ShdslEndpointAlarmConfProfile,
   hdsl2ShdslEndpointThreshLoopAttenuation,
   hdsl2ShdslEndpointThreshSNRMargin,
   hdsl2ShdslEndpointThreshES,
   hdsl2ShdslEndpointThreshSES,
   hdsl2ShdslEndpointThreshCRCanomalies,
   hdsl2ShdslEndpointThreshLOSWS,
   hdsl2ShdslEndpointThreshUAS,
   hdsl2ShdslEndpointAlarmConfProfileRowStatus
   }
   STATUS      current
   DESCRIPTION
     "This group supports objects that allow configuration of alarm
      thresholds for various performance parameters for HDSL2/SHDSL
      lines."
   ::= { hdsl2ShdslGroups 11 }

hdsl2ShdslNotificationGroup NOTIFICATION-GROUP
   NOTIFICATIONS
   {
   hdsl2ShdslLoopAttenCrossing,
   hdsl2ShdslSNRMarginCrossing,
   hdsl2ShdslPerfESThresh,
   hdsl2ShdslPerfSESThresh,
   hdsl2ShdslPerfCRCanomaliesThresh,
   hdsl2ShdslPerfLOSWSThresh,
   hdsl2ShdslPerfUASThresh,
   hdsl2ShdslSpanInvalidNumRepeaters,
   hdsl2ShdslLoopbackFailure,
   hdsl2ShdslpowerBackoff,
   hdsl2ShdsldeviceFault,
   hdsl2ShdsldcContinuityFault,
   hdsl2ShdslconfigInitFailure,


   hdsl2ShdslprotocolInitFailure,
   hdsl2ShdslnoNeighborPresent,
   hdsl2ShdslLocalPowerLoss
   }
   STATUS      current
   DESCRIPTION
     "This group supports notifications of significant conditions
     associated with HDSL2/SHDSL lines."
   ::= { hdsl2ShdslGroups 12 }

hdsl2ShdslSpanConfProfileGroup OBJECT-GROUP
   OBJECTS
   {
   hdsl2ShdslSpanConfWireInterface,
   hdsl2ShdslSpanConfMinLineRate,
   hdsl2ShdslSpanConfMaxLineRate,
   hdsl2ShdslSpanConfPSD,
   hdsl2ShdslSpanConfTransmissionMode,
   hdsl2ShdslSpanConfRemoteEnabled,
   hdsl2ShdslSpanConfPowerFeeding,
   hdsl2ShdslSpanConfCurrCondTargetMarginDown,
   hdsl2ShdslSpanConfWorstCaseTargetMarginDown,
   hdsl2ShdslSpanConfCurrCondTargetMarginUp,
   hdsl2ShdslSpanConfWorstCaseTargetMarginUp,
   hdsl2ShdslSpanConfUsedTargetMargins,
   hdsl2ShdslSpanConfReferenceClock,
   hdsl2ShdslSpanConfLineProbeEnable,
   hdsl2ShdslSpanConfProfileRowStatus
   }
   STATUS      current
   DESCRIPTION
     "This group supports objects that constitute configuration
      profiles for configuring span related parameters in SHDSL
      lines."
   ::= { hdsl2ShdslGroups 13 }
END

ENTITY-SENSOR-MIB DEFINITIONS ::= BEGIN

IMPORTS
        MODULE-IDENTITY, OBJECT-TYPE,
        Integer32, Unsigned32, mib-2
                FROM SNMPv2-SMI
        MODULE-COMPLIANCE, OBJECT-GROUP
                FROM SNMPv2-CONF
        TEXTUAL-CONVENTION, TimeStamp
                FROM SNMPv2-TC
        entPhysicalIndex, entityPhysicalGroup
                FROM ENTITY-MIB
        SnmpAdminString
                FROM SNMP-FRAMEWORK-MIB;

entitySensorMIB MODULE-IDENTITY
    LAST-UPDATED    "200212160000Z"
    ORGANIZATION    "IETF Entity MIB Working Group"
    CONTACT-INFO
            "        Andy Bierman
                     Cisco Systems, Inc.
                Tel: +1 408-527-3711
             E-mail: abierman@cisco.com
             Postal: 170 West Tasman Drive
                     San Jose, CA USA 95134

                     Dan Romascanu
                     Avaya Inc.
                Tel: +972-3-645-8414
              Email: dromasca@avaya.com
             Postal: Atidim technology Park, Bldg. #3
                     Tel Aviv, Israel, 61131

                     K.C. Norseth
                     L-3 Communications
                Tel: +1 801-594-2809
              Email: kenyon.c.norseth@L-3com.com
             Postal: 640 N. 2200 West.


                     Salt Lake City, Utah 84116-0850

             Send comments to &lt;entmib@ietf.org&gt;
             Mailing list subscription info:
               http://www.ietf.org/mailman/listinfo/entmib "
    DESCRIPTION
            "This module defines Entity MIB extensions for physical
             sensors.

             Copyright (C) The Internet Society (2002). This version
             of this MIB module is part of RFC 3433; see the RFC
             itself for full legal notices."

    REVISION        "200212160000Z"
    DESCRIPTION
            "Initial version of the Entity Sensor MIB module, published
             as RFC 3433."
    ::= { mib-2 99 }

entitySensorObjects              OBJECT IDENTIFIER
     ::= { entitySensorMIB 1 }

-- entitySensorNotifications        OBJECT IDENTIFIER
--     ::= { entitySensorMIB 2 }
entitySensorConformance          OBJECT IDENTIFIER
     ::= { entitySensorMIB 3 }

--
-- Textual Conventions
--

EntitySensorDataType ::= TEXTUAL-CONVENTION
    STATUS       current
    DESCRIPTION
            "An object using this data type represents the Entity Sensor
            measurement data type associated with a physical sensor
            value. The actual data units are determined by examining an
            object of this type together with the associated
            EntitySensorDataScale object.

            An object of this type SHOULD be defined together with
            objects of type EntitySensorDataScale and
            EntitySensorPrecision.  Together, associated objects of
            these three types are used to identify the semantics of an
            object of type EntitySensorValue.


            Valid values are:

               other(1):        a measure other than those listed below
               unknown(2):      unknown measurement, or arbitrary,
                                relative numbers
               voltsAC(3):      electric potential
               voltsDC(4):      electric potential
               amperes(5):      electric current
               watts(6):        power
               hertz(7):        frequency
               celsius(8):      temperature
               percentRH(9):    percent relative humidity
               rpm(10):         shaft revolutions per minute
               cmm(11),:        cubic meters per minute (airflow)
               truthvalue(12):  value takes { true(1), false(2) }

            "
    SYNTAX INTEGER {
        other(1),
        unknown(2),
        voltsAC(3),
        voltsDC(4),
        amperes(5),
        watts(6),
        hertz(7),
        celsius(8),
        percentRH(9),
        rpm(10),
        cmm(11),
        truthvalue(12)
    }

EntitySensorDataScale ::= TEXTUAL-CONVENTION
    STATUS       current
    DESCRIPTION
            "An object using this data type represents a data scaling
            factor, represented with an International System of Units
            (SI) prefix.  The actual data units are determined by
            examining an object of this type together with the
            associated EntitySensorDataType object.

            An object of this type SHOULD be defined together with
            objects of type EntitySensorDataType and
            EntitySensorPrecision.  Together, associated objects of
            these three types are used to identify the semantics of an
            object of type EntitySensorValue."
    REFERENCE
            "The International System of Units (SI),


            National Institute of Standards and Technology,
            Spec. Publ. 330, August 1991."
    SYNTAX INTEGER {
        yocto(1),   -- 10^-24
        zepto(2),   -- 10^-21
        atto(3),    -- 10^-18
        femto(4),   -- 10^-15
        pico(5),    -- 10^-12
        nano(6),    -- 10^-9
        micro(7),   -- 10^-6
        milli(8),   -- 10^-3
        units(9),   -- 10^0
        kilo(10),   -- 10^3
        mega(11),   -- 10^6
        giga(12),   -- 10^9
        tera(13),   -- 10^12
        exa(14),    -- 10^15
        peta(15),   -- 10^18
        zetta(16),  -- 10^21
        yotta(17)   -- 10^24
    }

EntitySensorPrecision ::= TEXTUAL-CONVENTION
    STATUS       current
    DESCRIPTION
            "An object using this data type represents a sensor
            precision range.

            An object of this type SHOULD be defined together with
            objects of type EntitySensorDataType and
            EntitySensorDataScale.  Together, associated objects of
            these three types are used to identify the semantics of an
            object of type EntitySensorValue.

            If an object of this type contains a value in the range 1 to
            9, it represents the number of decimal places in the
            fractional part of an associated EntitySensorValue fixed-
            point number.

            If an object of this type contains a value in the range -8
            to -1, it represents the number of accurate digits in the
            associated EntitySensorValue fixed-point number.

            The value zero indicates the associated EntitySensorValue
            object is not a fixed-point number.

            Agent implementors must choose a value for the associated
            EntitySensorPrecision object so that the precision and


            accuracy of the associated EntitySensorValue object is
            correctly indicated.

            For example, a physical entity representing a temperature
            sensor that can measure 0 degrees to 100 degrees C in 0.1
            degree increments, +/- 0.05 degrees, would have an
            EntitySensorPrecision value of '1', an EntitySensorDataScale
            value of 'units(9)', and an EntitySensorValue ranging from
            '0' to '1000'.  The EntitySensorValue would be interpreted
            as 'degrees C * 10'."
    SYNTAX Integer32 (-8..9)

EntitySensorValue ::= TEXTUAL-CONVENTION
    STATUS       current
    DESCRIPTION
            "An object using this data type represents an Entity Sensor
            value.
            An object of this type SHOULD be defined together with
            objects of type EntitySensorDataType, EntitySensorDataScale
            and EntitySensorPrecision.  Together, associated objects of
            those three types are used to identify the semantics of an
            object of this data type.

            The semantics of an object using this data type are
            determined by the value of the associated
            EntitySensorDataType object.

            If the associated EntitySensorDataType object is equal to
            'voltsAC(3)', 'voltsDC(4)', 'amperes(5)', 'watts(6),
            'hertz(7)', 'celsius(8)', or 'cmm(11)', then an object of
            this type MUST contain a fixed point number ranging from
            -999,999,999 to +999,999,999.  The value -1000000000
            indicates an underflow error. The value +1000000000
            indicates an overflow error.  The EntitySensorPrecision
            indicates how many fractional digits are represented in the
            associated EntitySensorValue object.

            If the associated EntitySensorDataType object is equal to
            'percentRH(9)', then an object of this type MUST contain a
            number ranging from 0 to 100.

            If the associated EntitySensorDataType object is equal to
            'rpm(10)', then an object of this type MUST contain a number
            ranging from -999,999,999 to +999,999,999.

            If the associated EntitySensorDataType object is equal to
            'truthvalue(12)', then an object of this type MUST contain
            either the value 'true(1)' or the value 'false(2)'.


            If the associated EntitySensorDataType object is equal to
            'other(1)' or unknown(2)', then an object of this type MUST
            contain a number ranging from -1000000000 to 1000000000."
    SYNTAX Integer32 (-1000000000..1000000000)

EntitySensorStatus ::= TEXTUAL-CONVENTION
    STATUS       current
    DESCRIPTION
            "An object using this data type represents the operational
            status of a physical sensor.

            The value 'ok(1)' indicates that the agent can obtain the
            sensor value.

            The value 'unavailable(2)' indicates that the agent
            presently cannot obtain the sensor value.

            The value 'nonoperational(3)' indicates that the agent
            believes the sensor is broken.  The sensor could have a hard
            failure (disconnected wire), or a soft failure such as out-
            of-range, jittery, or wildly fluctuating readings."
    SYNTAX INTEGER {
        ok(1),
        unavailable(2),
        nonoperational(3)
    }

--
-- Entity Sensor Table
--

entPhySensorTable OBJECT-TYPE
    SYNTAX        SEQUENCE OF EntPhySensorEntry
    MAX-ACCESS    not-accessible
    STATUS        current
    DESCRIPTION
            "This table contains one row per physical sensor represented
            by an associated row in the entPhysicalTable."
    ::= { entitySensorObjects 1 }

entPhySensorEntry OBJECT-TYPE
    SYNTAX        EntPhySensorEntry
    MAX-ACCESS    not-accessible
    STATUS        current
    DESCRIPTION
            "Information about a particular physical sensor.


            An entry in this table describes the present reading of a
            sensor, the measurement units and scale, and sensor
            operational status.

            Entries are created in this table by the agent.  An entry
            for each physical sensor SHOULD be created at the same time
            as the associated entPhysicalEntry.  An entry SHOULD be
            destroyed if the associated entPhysicalEntry is destroyed."
    INDEX  { entPhysicalIndex }    -- SPARSE-AUGMENTS
    ::= { entPhySensorTable 1 }

EntPhySensorEntry ::= SEQUENCE {
        entPhySensorType            EntitySensorDataType,
        entPhySensorScale           EntitySensorDataScale,
        entPhySensorPrecision       EntitySensorPrecision,
        entPhySensorValue           EntitySensorValue,
        entPhySensorOperStatus      EntitySensorStatus,
        entPhySensorUnitsDisplay    SnmpAdminString,
        entPhySensorValueTimeStamp  TimeStamp,
        entPhySensorValueUpdateRate Unsigned32
}

entPhySensorType OBJECT-TYPE
    SYNTAX        EntitySensorDataType
    MAX-ACCESS    read-only
    STATUS        current
    DESCRIPTION
            "The type of data returned by the associated
            entPhySensorValue object.

            This object SHOULD be set by the agent during entry
            creation, and the value SHOULD NOT change during operation."
    ::= { entPhySensorEntry 1 }

entPhySensorScale OBJECT-TYPE
    SYNTAX        EntitySensorDataScale
    MAX-ACCESS    read-only
    STATUS        current
    DESCRIPTION
            "The exponent to apply to values returned by the associated
            entPhySensorValue object.

            This object SHOULD be set by the agent during entry
            creation, and the value SHOULD NOT change during operation."
    ::= { entPhySensorEntry 2 }


entPhySensorPrecision OBJECT-TYPE
    SYNTAX        EntitySensorPrecision
    MAX-ACCESS    read-only
    STATUS        current
    DESCRIPTION
            "The number of decimal places of precision in fixed-point
            sensor values returned by the associated entPhySensorValue
            object.

            This object SHOULD be set to '0' when the associated
            entPhySensorType value is not a fixed-point type: e.g.,
            'percentRH(9)', 'rpm(10)', 'cmm(11)', or 'truthvalue(12)'.

            This object SHOULD be set by the agent during entry
            creation, and the value SHOULD NOT change during operation."
    ::= { entPhySensorEntry 3 }

entPhySensorValue OBJECT-TYPE
    SYNTAX        EntitySensorValue
    MAX-ACCESS    read-only
    STATUS        current
    DESCRIPTION
            "The most recent measurement obtained by the agent for this
            sensor.

            To correctly interpret the value of this object, the
            associated entPhySensorType, entPhySensorScale, and
            entPhySensorPrecision objects must also be examined."
    ::= { entPhySensorEntry 4 }

entPhySensorOperStatus OBJECT-TYPE
    SYNTAX        EntitySensorStatus
    MAX-ACCESS    read-only
    STATUS        current
    DESCRIPTION
            "The operational status of the sensor."
    ::= { entPhySensorEntry 5 }

entPhySensorUnitsDisplay OBJECT-TYPE
    SYNTAX      SnmpAdminString
    MAX-ACCESS  read-only
    STATUS      current
    DESCRIPTION
            "A textual description of the data units that should be used
            in the display of entPhySensorValue."
    ::= { entPhySensorEntry 6 }


entPhySensorValueTimeStamp OBJECT-TYPE
    SYNTAX        TimeStamp
    MAX-ACCESS    read-only
    STATUS        current
    DESCRIPTION
            "The value of sysUpTime at the time the status and/or value
            of this sensor was last obtained by the agent."
    ::= { entPhySensorEntry 7 }

entPhySensorValueUpdateRate  OBJECT-TYPE
    SYNTAX        Unsigned32
    UNITS         "milliseconds"
    MAX-ACCESS    read-only
    STATUS        current
    DESCRIPTION
            "An indication of the frequency that the agent updates the
            associated entPhySensorValue object, representing in
            milliseconds.

            The value zero indicates:

                - the sensor value is updated on demand (e.g.,
                  when polled by the agent for a get-request),
                - the sensor value is updated when the sensor
                  value changes (event-driven),
                - the agent does not know the update rate.

            "
    ::= { entPhySensorEntry 8 }

--
-- Conformance Section
--

entitySensorCompliances OBJECT IDENTIFIER
    ::= { entitySensorConformance 1 }
entitySensorGroups      OBJECT IDENTIFIER
    ::= { entitySensorConformance 2 }

entitySensorCompliance MODULE-COMPLIANCE
    STATUS  current
    DESCRIPTION
            "Describes the requirements for conformance to the Entity
            Sensor MIB module."
    MODULE  -- this module
        MANDATORY-GROUPS { entitySensorValueGroup }


    MODULE ENTITY-MIB
        MANDATORY-GROUPS { entityPhysicalGroup }

    ::= { entitySensorCompliances 1 }

-- Object Groups

entitySensorValueGroup OBJECT-GROUP
    OBJECTS {
             entPhySensorType,
             entPhySensorScale,
             entPhySensorPrecision,
             entPhySensorValue,
             entPhySensorOperStatus,
             entPhySensorUnitsDisplay,
             entPhySensorValueTimeStamp,
             entPhySensorValueUpdateRate
    }
    STATUS  current
    DESCRIPTION
            "A collection of objects representing physical entity sensor
            information."
    ::= { entitySensorGroups 1 }

END

APS-MIB DEFINITIONS ::= BEGIN

IMPORTS
        MODULE-IDENTITY, NOTIFICATION-TYPE, OBJECT-TYPE,
        Gauge32, Counter32, Integer32, transmission
                FROM SNMPv2-SMI

        TEXTUAL-CONVENTION, RowStatus,
        TimeStamp, StorageType
                FROM SNMPv2-TC

        SnmpAdminString
                FROM SNMP-FRAMEWORK-MIB


        ifIndex, InterfaceIndex
                FROM IF-MIB

        MODULE-COMPLIANCE, OBJECT-GROUP, NOTIFICATION-GROUP
                FROM SNMPv2-CONF;

apsMIB MODULE-IDENTITY
    LAST-UPDATED        "200302280000Z"  -- February 28, 2003
    ORGANIZATION        "IETF AToMMIB Working Group"
    CONTACT-INFO
        "       Jim Kuhfeld
                Postal: RedBack Networks. Inc.
                300 Holger Way
                San Jose, CA 95134-1362
                Tel: +1 408 750 5465
                Email: jkuhfeld@redback.com

                Jeff Johnson
                Postal: RedBack Networks. Inc.
                300 Holger Way
                San Jose, CA 95134-1362
                Tel: +1 408 750 5460
                Email: jeff@redback.com

                Michael Thatcher
                Postal: RedBack Networks. Inc.
                300 Holger Way
                San Jose, CA 95134-1362
                Tel: +1 408 750 5449
                Email: thatcher@redback.com"
    DESCRIPTION
        "This management information module supports the configuration
         and management of SONET linear APS groups. The definitions and
         descriptions used in this MIB have been derived from
         Synchronous Optical Network (SONET) Transport Systems:
         Common Generic Criteria, GR-253-CORE Issue 3, September 2000,
         section 5.3. The MIB is also consistent with the Multiplex
         Section Protection (MSP) protocol as specified in ITU-T
         Recommendation G.783, Characteristics of synchronous digital
         hierarchy (SDH) equipment function blocks, Annex A and B.

         Copyright (C) The Internet Society (2003).  This version of
         this MIB module is part of RFC 3498; see the RFC itself for
         full legal notices.
         "


    REVISION      "200302280000Z"  -- February 28, 2003
    DESCRIPTION
          "Initial version of this MIB, published as RFC 3498."
        ::= { transmission 49 }

apsMIBObjects OBJECT IDENTIFIER
        ::= { apsMIB 1 }

apsMIBNotifications OBJECT IDENTIFIER
        ::= { apsMIB 2 }

apsMIBConformance OBJECT IDENTIFIER
        ::= { apsMIB 3 }

ApsK1K2 ::= TEXTUAL-CONVENTION
    STATUS current
    DESCRIPTION
        "This Textual Convention describes an object that stores
         a SONET K1 and K2 byte APS protocol field.

         K1 is located in the first octet, K2 is located in
         the second octet. Bits are numbered from left to right.

         Bits 1-4 of the K1 byte indicate a request.

         1111  Lockout of Protection
         1110  Forced Switch
         1101  SF - High Priority
         1100  SF - Low Priority
         1011  SD - High Priority
         1010  SD - Low Priority
         1001  not used
         1000  Manual Switch
         0111  not used
         0110  Wait-to-Restore
         0101  not used
         0100  Exercise
         0011  not used
         0010  Reverse Request
         0001  Do Not Revert
         0000  No Request

         Bits 5-8 of the K1 byte indicate the channel associated with
         the request defined in bits 1-4.

         0000 is the Null channel.


         1-14 are working channels.
         15   is the extra traffic channel

         Bits 1-4 of the K2 byte indicate a channel. The channel is
         defined with the same syntax as K1 Bits 5-8.

         Bit 5 of the K2 byte indicates the
         architecture.

         0 if the architecture is 1+1
         1 if the architecture is 1:n

         Bits 6-8 of the K2 byte indicates the mode.

         000 - 011 are reserved for future use
         100  indicates the mode is unidirectional
         101  indicates the mode is bidirectional
         110  RDI-L
         111  AIS-L
        "
    REFERENCE
        "Bellcore (Telcordia Technologies) GR-253-CORE, Issue 3,
        September 2000, 5.3.5."
    SYNTAX      OCTET STRING (SIZE (2))

ApsSwitchCommand ::= TEXTUAL-CONVENTION
    STATUS       current
    DESCRIPTION
        "An APS switch command allows a user to perform protection
         switch actions.

         If the APS switch command cannot be executed because an
         equal or higher priority request is in effect, an
         inconsistentValue error is returned.

         The Switch command values are:

         noCmd

         This value should be returned by a read request when no switch
         command has been written to the object in question since
         initialization. This value may not be used in a write
         operation.  If noCmd is used in a write operation a wrongValue
         error is returned.


         clear

         Clears all of the switch commands listed below for the
         specified channel.

         lockoutOfProtection

         Prevents any of the working channels from switching to the
         protection line. The specified channel should be the protection
         channel, otherwise an inconsistentValue error is returned.

         forcedSwitchWorkToProtect

         Switches the specified working channel to the protection line.
         If the protection channel is specified an inconsistentValue
         error is returned.

         forcedSwitchProtectToWork

         Switches the working channel back from the protection
         line to the working line. The specified channel should be
         the protection channel, otherwise an inconsistentValue
         error is returned.

         manualSwitchWorkToProtect

         Switches the specified working channel to the protection line.
         If the protection channel is specified an inconsistentValue
         error is returned.

         manualSwitchProtectToWork

         Switches the working channel back from the protection
         line to the working line. The specified channel should be
         the protection channel, otherwise an inconsistentValue
         error is returned.

         exercise

         Exercises the protocol for a protection switch of the specified
         channel by issuing an Exercise request for that channel and
         checking the response on the APS channel. "
    SYNTAX       INTEGER {
                     noCmd(1),
                     clear(2),
                     lockoutOfProtection(3),
                     forcedSwitchWorkToProtect(4),
                     forcedSwitchProtectToWork(5),


                     manualSwitchWorkToProtect(6),
                     manualSwitchProtectToWork(7),
                     exercise(8)
                 }

ApsControlCommand ::= TEXTUAL-CONVENTION
    STATUS       current
    DESCRIPTION
        "An APS control command applies only to LTE that support the
         1:n architecture and performs the following actions.

         The Control command values are:

         noCmd

         This value should be returned by a read request when no control
         command has been written to the object in question since
         initialization. This value may not be used in a write
         operation.  If noCmd is used in a write operation a wrongValue
         error is returned.

         lockoutWorkingChannel

         Prevents the specified working channel from switching to the
         protection line. If the protection line is specified an
         inconsistentValue error is returned.

         clearLockoutWorkingChannel

         Clears the lockout a working channel command for the channel
         specified. If the protection line is specified an
         inconsistentValue error is returned."
    SYNTAX       INTEGER {
                     noCmd(1),
                     lockoutWorkingChannel(2),
                     clearLockoutWorkingChannel(3)
                 }

--
-- APS Configuration Table
--
-- This table supports the addition, configuration and deletion of APS
-- groups.
--

apsConfig     OBJECT IDENTIFIER ::= { apsMIBObjects 1 }


apsConfigGroups OBJECT-TYPE
    SYNTAX      Gauge32
    MAX-ACCESS  read-only
    STATUS      current
    DESCRIPTION
        "The count of APS groups. This count includes all rows in
         apsConfigTable, regardless of the value of apsConfigRowStatus."
    ::= { apsConfig 1 }

apsConfigTable OBJECT-TYPE
    SYNTAX      SEQUENCE OF ApsConfigEntry
    MAX-ACCESS  not-accessible
    STATUS      current
    DESCRIPTION
        "This table lists the APS groups that have been configured
         on the system."
    ::= { apsConfig 2 }

apsConfigEntry OBJECT-TYPE
    SYNTAX      ApsConfigEntry
    MAX-ACCESS  not-accessible
    STATUS      current
    DESCRIPTION
        "A conceptual row in the apsConfigTable."
    INDEX { IMPLIED apsConfigName }
    ::= { apsConfigTable  1 }

ApsConfigEntry ::= SEQUENCE {
    apsConfigName                  SnmpAdminString,
    apsConfigRowStatus             RowStatus,
    apsConfigMode                  INTEGER,
    apsConfigRevert                INTEGER,
    apsConfigDirection             INTEGER,
    apsConfigExtraTraffic          INTEGER,
    apsConfigSdBerThreshold        Integer32,
    apsConfigSfBerThreshold        Integer32,
    apsConfigWaitToRestore         Integer32,
    apsConfigCreationTime          TimeStamp,
    apsConfigStorageType           StorageType
}

apsConfigName OBJECT-TYPE
    SYNTAX      SnmpAdminString (SIZE (1..32))
    MAX-ACCESS  not-accessible
    STATUS      current
    DESCRIPTION
        "A textual name for the APS group."
    ::= { apsConfigEntry 1 }


apsConfigRowStatus OBJECT-TYPE
    SYNTAX      RowStatus
    MAX-ACCESS  read-create
    STATUS      current
    DESCRIPTION
        "The status of this APS group entry.

        An entry may not exist in the active state unless all
        objects in the entry have an appropriate value. Also,
        all associated apsChanConfigEntry rows must represent
        a set of consecutive channel numbers beginning with
        0 or 1, depending on the selected architecture.

        When set to notInService changes may be made to apsConfigMode,
        apsConfigRevert, apsConfigDirection, apsConfigExtraTraffic,
        apsConfigSdBerThreshold, apsConfigSfBerThreshold,
        and apsConfigWaitToRestore. Also, associated apsChanConfigTable
        objects may be added, deleted and modified."
    ::= { apsConfigEntry 2 }

apsConfigMode OBJECT-TYPE
    SYNTAX      INTEGER {
                        onePlusOne(1),
                        oneToN(2),
                        onePlusOneCompatible(3),
                        onePlusOneOptimized(4)
                        }
    MAX-ACCESS  read-create
    STATUS      current
    DESCRIPTION
       "The architecture of the APS group.

        onePlusOne

        The 1+1 architecture permanently bridges the working
        line to the protection line.

        oneToN

        The 1:n architecture allows one protection channel to
        protect up to n working channels. When a fault is detected
        on one of the n working channels that channel is bridged
        over the protection channel.

        onePlusOneCompatible


        This refers to 1 + 1 bidirectional switching compatible with
        1:n bidirectional switching as specified in ITU-T
        Recommendation G.783 (04/97) section A.3.4.1. Since this
        mode necessitates bidirectional switching, apsConfigDirection
        must be set to bidirectional whenever onePlusOneCompatible
        is set.

        onePlusOneOptimized

        This refers to 1 + 1 bidirectional switching optimized
        for a network using predominantly 1 + 1 bidirectional
        switching as specified in ITU-T Recommendation G.783 (04/97)
        section B.1. Since this mode necessitates bidirectional
        switching, apsConfigDirection must be set to bidirectional
        whenever onePlusOneOptimized is set.

        This object may not be modified if the associated
        apsConfigRowStatus object is equal to active(1)."
    DEFVAL {onePlusOne}
    ::= { apsConfigEntry 3 }

apsConfigRevert OBJECT-TYPE
    SYNTAX      INTEGER { nonrevertive(1), revertive(2) }
    MAX-ACCESS  read-create
    STATUS      current
    DESCRIPTION
       "The revertive mode of the APS group.

        nonrevertive

        Traffic remains on the protection line until another switch
        request is received.

        revertive

        When the condition that caused a switch to the protection
        line has been cleared the signal is switched back to the
        working line. Since switching is revertive with the 1:n
        architecture, apsConfigRevert must be set to revertive if
        apsConfigMode is set to oneToN.

        Switching may optionally be revertive with the 1+1 architecture.

        This object may not be modified if the associated
        apsConfigRowStatus object is equal to active(1). "
    DEFVAL { nonrevertive }
    ::= { apsConfigEntry 4 }


apsConfigDirection OBJECT-TYPE
    SYNTAX      INTEGER { unidirectional(1), bidirectional(2) }
    MAX-ACCESS  read-create
    STATUS      current
    DESCRIPTION
       "The directional mode of the APS group.

        unidirectional

        The unidirectional mode provides protection in one direction.

        bidirectional

        The bidirectional mode provides protection in both
        directions.

        This object may not be modified if the associated
        apsConfigRowStatus object is equal to active(1). "
    DEFVAL {unidirectional}
    ::= { apsConfigEntry 5 }

apsConfigExtraTraffic OBJECT-TYPE
    SYNTAX      INTEGER { enabled(1), disabled(2) }
    MAX-ACCESS  read-create
    STATUS      current
    DESCRIPTION
       "This object enables or disables the transfer of extra traffic
        on the protection channel in a 1:n architecture. This object
        must be set to disabled if the architecture is 1+1. It may be
        necessary to disable this in order to interwork with other SONET
        network elements that don't support extra traffic.

        This object may not be modified if the associated
        apsConfigRowStatus object is equal to active(1). "
    DEFVAL { disabled }
    ::= { apsConfigEntry 6 }

apsConfigSdBerThreshold OBJECT-TYPE
    SYNTAX      Integer32 (5..9)
    MAX-ACCESS  read-create
    STATUS      current
    DESCRIPTION
        "The Signal Degrade Bit Error Rate.

         The negated value of this number is used as the exponent of
         10 for computing the threshold value for the Bit Error Rate
         (BER). For example, a value of 5 indicates a BER threshold of
         10^-5.


         This object may be modified if the associated
         apsConfigRowStatus object is equal to active(1)."
    DEFVAL { 5 }
    ::= { apsConfigEntry 7 }

apsConfigSfBerThreshold OBJECT-TYPE
    SYNTAX      Integer32 (3..5)
    MAX-ACCESS  read-create
    STATUS      current
    DESCRIPTION
        "The Signal Failure Bit Error Rate.

         The negated value of this number is used as the exponent of
         10 for computing the threshold value for the Bit Error Rate
         (BER). For example, a value of 5 indicates a BER threshold of
         10^-5.

         This object may be modified if the associated
         apsConfigRowStatus object is equal to active(1)."
    DEFVAL { 3 }
    ::= { apsConfigEntry 8 }

apsConfigWaitToRestore OBJECT-TYPE
    SYNTAX      Integer32 (0..720)
    UNITS       "seconds"
    MAX-ACCESS  read-create
    STATUS      current
    DESCRIPTION
        "The Wait To Restore period in seconds.

         After clearing of a condition that necessitated an
         automatic switch, the wait to restore period must elapse
         before reverting. This is intended to avoid rapid switch
         oscillations.

         GR-253-CORE specifies a Wait To Restore range of 5 to 12
         minutes. G.783 defines a 5 to 12 minute Wait To Restore
         range in section 5.4.1.1.3, but also allows for a shorter
         WTR period in  Table 2-1,
         WaitToRestore value (MI_WTRtime: 0..(5)..12 minutes).

         This object may not be modified if the associated
         apsConfigRowStatus object is equal to active(1)."
    DEFVAL { 300 }
    ::= { apsConfigEntry 9 }


apsConfigCreationTime OBJECT-TYPE
    SYNTAX      TimeStamp
    MAX-ACCESS  read-only
    STATUS      current
    DESCRIPTION
        "The value of sysUpTime at the time the row was
         created"
    ::= { apsConfigEntry 10 }

apsConfigStorageType OBJECT-TYPE
    SYNTAX      StorageType
    MAX-ACCESS  read-create
    STATUS      current
    DESCRIPTION
        "The storage type for this conceptual row.
         Conceptual rows having the value 'permanent' need not
         allow write-access to any columnar objects in the row."
    DEFVAL      { nonVolatile }
    ::= { apsConfigEntry 11 }

--
-- APS Status Table
--
-- This table provides APS group statistics.
--

apsStatusTable OBJECT-TYPE
    SYNTAX      SEQUENCE OF ApsStatusEntry
    MAX-ACCESS  not-accessible
    STATUS      current
    DESCRIPTION
        "This table provides status information about APS groups
         that have been configured on the system."
    ::= { apsMIBObjects 2 }

apsStatusEntry OBJECT-TYPE
    SYNTAX      ApsStatusEntry
    MAX-ACCESS  not-accessible
    STATUS      current
    DESCRIPTION
        "A conceptual row in the apsStatusTable."
    AUGMENTS { apsConfigEntry }
    ::= { apsStatusTable  1 }

ApsStatusEntry ::= SEQUENCE {
    apsStatusK1K2Rcv               ApsK1K2,
    apsStatusK1K2Trans             ApsK1K2,
    apsStatusCurrent               BITS,


    apsStatusModeMismatches        Counter32,
    apsStatusChannelMismatches     Counter32,
    apsStatusPSBFs                 Counter32,
    apsStatusFEPLFs                Counter32,
    apsStatusSwitchedChannel       Integer32,
    apsStatusDiscontinuityTime     TimeStamp
}

apsStatusK1K2Rcv OBJECT-TYPE
    SYNTAX      ApsK1K2
    MAX-ACCESS  read-only
    STATUS      current
    DESCRIPTION
        "The current value of the K1 and K2 bytes received on the
         protection channel."
    ::= { apsStatusEntry 1 }

apsStatusK1K2Trans OBJECT-TYPE
    SYNTAX        ApsK1K2
    MAX-ACCESS    read-only
    STATUS        current
    DESCRIPTION
        "The current value of the K1 and K2 bytes transmitted on the
         protection channel."
    ::= { apsStatusEntry 2 }

apsStatusCurrent OBJECT-TYPE
    SYNTAX      BITS {
                  modeMismatch(0),
                  channelMismatch(1),
                  psbf(2),
                  feplf(3),
                  extraTraffic(4)
                 }
    MAX-ACCESS  read-only
    STATUS      current
    DESCRIPTION
        "The current status of the APS group.

         modeMismatch

         Modes other than 1+1 unidirectional monitor protection line
         K2 bit 5, which indicates the architecture and K2 bits
         6-8, which indicate if the mode is unidirectional or
         bidirectional. A conflict between the current local mode
         and the received K2 mode information constitutes a
         mode mismatch.


         channelMismatch

         This bit indicates a  mismatch between the transmitted K1
         channel and the received K2 channel has been detected.

         psbf

         This bit indicates a Protection Switch Byte Failure (PSBF) is
         in effect. This condition occurs when either an inconsistent
         APS byte or an invalid code is detected. An inconsistent APS
         byte occurs when no three consecutive K1 bytes of the last 12
         successive frames are identical, starting with the last frame
         containing a previously consistent byte. An invalid code occurs
         when the incoming K1 byte contains an unused code or a code
         irrelevant for the specific switching operation (e.g., Reverse
         Request while no switching request is outstanding) in three
         consecutive frames. An invalid code also occurs when the
         incoming K1 byte contains an invalid channel number in three
         consecutive frames.

         feplf

         Modes other than 1+1 unidirectional monitor the K1 byte
         for Far-End Protection-Line failures. A Far-End
         Protection-Line defect is declared based on receiving
         SF on the protection line.

         extraTraffic

         This bit indicates whether extra traffic is currently being
         accepted on the protection line. "
    ::= { apsStatusEntry 3 }

apsStatusModeMismatches OBJECT-TYPE
    SYNTAX     Counter32
    MAX-ACCESS read-only
    STATUS     current
    DESCRIPTION
        "A count of Mode Mismatch conditions.

         Discontinuities in the value of this counter can occur at
         re-initialization of the management system, and at other
         times as indicated by the value of
         apsStatusDiscontinuityTime."
    ::= { apsStatusEntry 4 }


apsStatusChannelMismatches OBJECT-TYPE
    SYNTAX     Counter32
    MAX-ACCESS read-only
    STATUS     current
    DESCRIPTION
        "A count of Channel Mismatch conditions.

         Discontinuities in the value of this counter can occur at
         re-initialization of the management system, and at other
         times as indicated by the value of
         apsStatusDiscontinuityTime."
    ::= { apsStatusEntry 5 }

apsStatusPSBFs OBJECT-TYPE
    SYNTAX     Counter32
    MAX-ACCESS read-only
    STATUS     current
    DESCRIPTION
        "A count of Protection Switch Byte Failure conditions.
         This condition occurs when either an inconsistent APS
         byte or an invalid code is detected. An inconsistent APS
         byte occurs when no three consecutive K1 bytes of the last
         12 successive frames are identical, starting with the last
         frame containing a previously consistent byte. An invalid
         code occurs when the incoming K1 byte contains an unused
         code or a code irrelevant for the specific switching
         operation (e.g., Reverse Request while no switching request
         is outstanding) in three consecutive frames. An invalid code
         also occurs when the incoming K1 byte contains an invalid
         channel number in three consecutive frames.

         Discontinuities in the value of this counter can occur at
         re-initialization of the management system, and at other
         times as indicated by the value of
         apsStatusDiscontinuityTime."
    ::= { apsStatusEntry 6 }

apsStatusFEPLFs OBJECT-TYPE
    SYNTAX     Counter32
    MAX-ACCESS read-only
    STATUS     current
    DESCRIPTION
        "A count of Far-End Protection-Line Failure conditions.
         This condition is declared based on receiving SF on
         the protection line in the K1 byte.


         Discontinuities in the value of this counter can occur at
         re-initialization of the management system, and at other
         times as indicated by the value of
         apsStatusDiscontinuityTime."
    ::= { apsStatusEntry 7 }

apsStatusSwitchedChannel OBJECT-TYPE
    SYNTAX     Integer32
    MAX-ACCESS read-only
    STATUS     current
    DESCRIPTION
        "This field is set to the number of the channel that is
         currently switched to protection. The value 0 indicates no
         channel is switched to protection. The values 1-14 indicate
         that working channel is switched to protection."
    ::= { apsStatusEntry 8 }

apsStatusDiscontinuityTime OBJECT-TYPE
    SYNTAX      TimeStamp
    MAX-ACCESS  read-only
    STATUS      current
    DESCRIPTION
        "The value of sysUpTime on the most recent occasion at which
         any one or more of this APS group's counters suffered a
         discontinuity.  The relevant counters are the specific
         instances associated with this APS group of any Counter32
         object contained in apsStatusTable. If no such
         discontinuities have occurred since the last re-initialization
         of the local management subsystem, then this object contains
         a zero value."
    ::= { apsStatusEntry 9 }

--
-- APS Map Group
--
-- Lists the SONET LTE interfaces that may be used to create APS groups.
--

apsMap      OBJECT IDENTIFIER ::= { apsMIBObjects 3 }

apsChanLTEs OBJECT-TYPE
    SYNTAX      Gauge32
    MAX-ACCESS  read-only
    STATUS      current
    DESCRIPTION
        "The count of SONET LTE interfaces on the system.
         Each interface that is included has an ifType value of
         sonet(39)."


    ::= { apsMap 1 }

apsMapTable OBJECT-TYPE
    SYNTAX      SEQUENCE OF ApsMapEntry
    MAX-ACCESS  not-accessible
    STATUS      current
    DESCRIPTION
        "This table lists the SONET LTE interfaces on the system.
         Each interface that is listed has an ifType value of
         sonet(39)."
    ::= { apsMap 2 }

apsMapEntry OBJECT-TYPE
    SYNTAX      ApsMapEntry
    MAX-ACCESS  not-accessible
    STATUS      current
    DESCRIPTION
        "A conceptual row in the apsMapTable."
    INDEX { ifIndex }
    ::= { apsMapTable  1 }

ApsMapEntry ::= SEQUENCE {
    apsMapGroupName             SnmpAdminString,
    apsMapChanNumber            Integer32
}

apsMapGroupName OBJECT-TYPE
    SYNTAX      SnmpAdminString (SIZE (0..32))
    MAX-ACCESS  read-only
    STATUS      current
    DESCRIPTION
        "A textual name for the APS group which this channel is
         included in. If the channel is not part of an APS group
         this value is set to a string of size 0.

         When an instance of apsChanConfigIfIndex is set equal to an
         instance of ifIndex that has an ifType value of sonet(39),
         apsMapGroupName is set equal to the corresponding value of
         apsChanConfigGroupName.

         If an instance of ifIndex that has an ifType value of
         sonet(39) ceases to be equal to an instance of
         apsChanConfigIfIndex, either because of a change in the value
         of apsChanConfigIfIndex, or because of row deletion in the
         ApsChanConfigTable, apsMapGroupName is set to a string of
         size 0."
    ::= { apsMapEntry 2 }


apsMapChanNumber OBJECT-TYPE
    SYNTAX     Integer32 (-1..14)
    MAX-ACCESS read-only
    STATUS     current
    DESCRIPTION
        "This field is set to a unique channel number within an APS
         group.  The value 0 indicates the null channel. The values
         1-14 define a working channel. If the SONET LTE is not part
         of an APS group this value is set to -1.

         When an instance of apsChanConfigIfIndex is set equal to an
         instance of ifIndex that has an  ifType value of sonet(39),
         apsMapChanNumber is set equal to the corresponding value of
         apsChanConfigNumber.

         If an instance of ifIndex that has an  ifType value of
         sonet(39) ceases to be equal to an instance of
         apsChanConfigIfIndex, either because of a change in the
         value of apsChanConfigIfIndex, or because of row deletion
         in the ApsChanConfigTable, apsMapChanNumber is set to -1."
    ::= { apsMapEntry 3 }

--
-- APS Channel Configuration Table
--
-- This table supports the addition, configuration and deletion of
-- channels in APS groups.
--

apsChanConfigTable OBJECT-TYPE
    SYNTAX      SEQUENCE OF ApsChanConfigEntry
    MAX-ACCESS  not-accessible
    STATUS      current
    DESCRIPTION
        "This table lists the APS channels that have been configured
         in APS groups."
    ::= { apsMIBObjects 4 }

apsChanConfigEntry OBJECT-TYPE
    SYNTAX      ApsChanConfigEntry
    MAX-ACCESS  not-accessible
    STATUS      current
    DESCRIPTION
        "A conceptual row in the apsChanConfigTable."
    INDEX {apsChanConfigGroupName, apsChanConfigNumber}
    ::= { apsChanConfigTable  1 }


ApsChanConfigEntry ::= SEQUENCE {
    apsChanConfigGroupName             SnmpAdminString,
    apsChanConfigNumber                Integer32,
    apsChanConfigRowStatus             RowStatus,
    apsChanConfigIfIndex               InterfaceIndex,
    apsChanConfigPriority              INTEGER,
    apsChanConfigStorageType           StorageType
}

apsChanConfigGroupName OBJECT-TYPE
    SYNTAX      SnmpAdminString (SIZE (1..32))
    MAX-ACCESS  not-accessible
    STATUS      current
    DESCRIPTION
        "A textual name for the APS group which this channel is
         included in."
    ::= { apsChanConfigEntry 1 }

apsChanConfigNumber OBJECT-TYPE
    SYNTAX     Integer32 (0..14)
    MAX-ACCESS not-accessible
    STATUS     current
    DESCRIPTION
        "This field is set to a unique channel number within an APS
         group.  The value 0 indicates the null channel.  The values
         1-14 define a working channel.

         This field must be assigned a unique number within the group."
    ::= { apsChanConfigEntry 2 }

apsChanConfigRowStatus OBJECT-TYPE
    SYNTAX      RowStatus
    MAX-ACCESS  read-create
    STATUS      current
    DESCRIPTION
        "The status of this APS channel entry.

         An entry may not exist in the active state unless all
         objects in the entry have an appropriate value.

         A row in the apsChanConfigTable may not be created,
         deleted, set to notInService or otherwise modified
         if the apsChanConfigGroupName value is equal to an
         apsConfigName value and the associated apsConfigRowStatus
         object is equal to active. However, if the apsConfigRowStatus
         object is equal to notInService, a row may be created, deleted
         or modified. In other words, a channel may not be added,
         deleted or modified if the group is active.


         A row may be created with an apsChanConfigGroupName value
         that is not equal to any existing instance of apsConfigName.
         This action is the initial step in adding a SONET LTE to a
         new APS group.

         If this object is set to destroy, the associated instance
         of apsMapGroupName will be set to a string of size 0 and
         the apsMapChanNumber will be set to -1. The channel status
         entry will also be deleted by this action.

         apsChanConfigNumber must be set to a unique channel number
         within the APS group. The value 0 indicates the null channel.
         The values 1-14 define a working channel. When an attempt is
         made to set the  corresponding apsConfigRowStatus field to
         active the apsChanConfigNumber values of all entries with equal
         apsChanConfigGroupName fields must represent a set of
         consecutive integer values beginning with 0 or 1, depending on
         the architecture of the group, and ending with n, where n is
         greater than or equal to 1 and less than or equal to 14.
         Otherwise, the error inconsistentValue is returned to the
         apsConfigRowStatus set attempt."
    ::= { apsChanConfigEntry 3 }

apsChanConfigIfIndex OBJECT-TYPE
    SYNTAX     InterfaceIndex
    MAX-ACCESS read-create
    STATUS     current
    DESCRIPTION
        "The Interface Index assigned to a SONET LTE. This is an
         interface with ifType sonet(39). The value of this object
         must be unique among all instances of apsChanConfigIfIndex.
         In other words, a particular SONET LTE can only be configured
         in one APS group.

         This object cannot be set if the apsChanConfigGroupName
         instance associated with this row is equal to an instance of
         apsConfigName and the corresponding apsConfigRowStatus object
         is set to active.  In other words this value cannot be changed
         if the APS group is active. However, this value may be changed
         if the apsConfigRowStatus value is equal to notInService."
    ::= { apsChanConfigEntry 4 }

apsChanConfigPriority OBJECT-TYPE
    SYNTAX     INTEGER {low(1), high(2)}
    MAX-ACCESS read-create
    STATUS     current
    DESCRIPTION
        "The priority of the channel.


         This field determines whether high or low priority
         SD and SF codes are used in K1 requests.

         This field is only applicable if the channel is to be included
         in a group using the 1:n architecture. It is not applicable if
         the channel is to be included in a group using the 1+1
         architecture, and is ignored in that case.

         This object cannot be set if the apsChanConfigGroupName
         instance associated with this row is equal to an instance of
         apsConfigName and the corresponding apsConfigRowStatus object
         is set to active.  In other words this value cannot be changed
         if the APS group is active.  However, this value may be changed
         if the apsConfigRowStatus value is equal to notInService."
    DEFVAL { low }
    ::= { apsChanConfigEntry 5 }

apsChanConfigStorageType OBJECT-TYPE
    SYNTAX      StorageType
    MAX-ACCESS  read-create
    STATUS      current
    DESCRIPTION
        "The storage type for this conceptual row.
         Conceptual rows having the value 'permanent' need not
         allow write-access to any columnar objects in the row."
    DEFVAL { nonVolatile }
    ::= { apsChanConfigEntry 6 }

--
-- APS Command Table
--
-- This table provides the ability to initiate APS commands.
--

apsCommandTable OBJECT-TYPE
    SYNTAX      SEQUENCE OF ApsCommandEntry
    MAX-ACCESS  not-accessible
    STATUS      current
    DESCRIPTION
        "This table allows commands to be sent to configured APS
          groups."
    ::= { apsMIBObjects 5 }

apsCommandEntry OBJECT-TYPE
    SYNTAX      ApsCommandEntry
    MAX-ACCESS  not-accessible
    STATUS      current
    DESCRIPTION


        "A conceptual row in the apsCommandTable. This row exists only
         if the associated apsConfigEntry is active."
    INDEX {apsChanConfigGroupName, apsChanConfigNumber}
    ::= { apsCommandTable  1 }

ApsCommandEntry ::= SEQUENCE {
    apsCommandSwitch         ApsSwitchCommand,
    apsCommandControl        ApsControlCommand
}

apsCommandSwitch OBJECT-TYPE
    SYNTAX      ApsSwitchCommand
    MAX-ACCESS  read-write
    STATUS      current
    DESCRIPTION
        "Allows the initiation of an APS switch command on the
         APS group and channel specified by the index values.

         When read this object returns the last command written
         or noCmd if no command has been written to this
         channel since initialization. The return of the last command
         written does not imply that this command is currently in
         effect.  This request may have been preempted by a higher
         priority local or remote request. In order to determine the
         current state of the APS group it is necessary to read
         the objects apsStatusK1K2Rcv and apsStatusK1K2Trans.

         The value lockoutOfProtection should only be applied to the
         protection line channel since that switch command prevents any
         of the working channels from switching to the protection line.
         Following the same logic, forcedSwitchProtectToWork and
         manualSwitchProtectToWork should only be applied to the
         protection line channel.

         forcedSwitchWorkToProtect and manualSwitchWorkToProtect
         should only be applied to a working channel."
    ::= { apsCommandEntry 1 }

apsCommandControl OBJECT-TYPE
    SYNTAX      ApsControlCommand
    MAX-ACCESS  read-write
    STATUS      current
    DESCRIPTION
        "Allows the initiation of an APS control command on the
         APS group and channel specified by the index values.


         When read this object returns the last command written or
         noCmd if no command has been written to this channel since
         initialization.

         This object does not apply to the protection line."
    ::= { apsCommandEntry 2 }

--
-- APS Channel Status Table
--
-- This table provides APS channel statistics.
--

apsChanStatusTable OBJECT-TYPE
    SYNTAX      SEQUENCE OF ApsChanStatusEntry
    MAX-ACCESS  not-accessible
    STATUS      current
    DESCRIPTION
        "This table contains status information for all SONET LTE
         interfaces that are included in APS groups."
    ::= { apsMIBObjects 6 }

apsChanStatusEntry OBJECT-TYPE
    SYNTAX      ApsChanStatusEntry
    MAX-ACCESS  not-accessible
    STATUS      current
    DESCRIPTION
        "A conceptual row in the apsChanStatusTable."
    AUGMENTS { apsChanConfigEntry }
    ::= { apsChanStatusTable  1 }

ApsChanStatusEntry ::= SEQUENCE {
    apsChanStatusCurrent               BITS,
    apsChanStatusSignalDegrades        Counter32,
    apsChanStatusSignalFailures        Counter32,
    apsChanStatusSwitchovers           Counter32,
    apsChanStatusLastSwitchover        TimeStamp,
    apsChanStatusSwitchoverSeconds     Counter32,
    apsChanStatusDiscontinuityTime     TimeStamp
}

apsChanStatusCurrent OBJECT-TYPE
    SYNTAX     BITS {
               lockedOut(0),
               sd(1),
               sf(2),
               switched(3),
               wtr(4)


            }
    MAX-ACCESS read-only
    STATUS     current
    DESCRIPTION
        "Indicates the current state of the port.

         lockedOut

         This bit, when applied to a working channel, indicates that
         the channel is prevented from switching to the protection
         line.  When applied to the null channel, this bit indicates
         that no working channel may switch to the protection line.

         sd

         A signal degrade condition is in effect.

         sf

         A signal failure condition is in effect.

         switched

         The switched bit is applied to a working channel if that
         channel is currently switched to the protection line.

         wtr

         A Wait-to-Restore state is in effect."
    ::= { apsChanStatusEntry 1 }

apsChanStatusSignalDegrades OBJECT-TYPE
    SYNTAX     Counter32
    MAX-ACCESS read-only
    STATUS     current
    DESCRIPTION
        "A count of Signal Degrade conditions. This condition
         occurs when the line Bit Error Rate exceeds the currently
         configured value of the relevant instance of
         apsConfigSdBerThreshold.

         Discontinuities in the value of this counter can occur at
         re-initialization of the management system, and at other
         times as indicated by the value of
         apsChanStatusDiscontinuityTime."

    ::= { apsChanStatusEntry 2 }


apsChanStatusSignalFailures OBJECT-TYPE
    SYNTAX     Counter32
    MAX-ACCESS read-only
    STATUS     current
    DESCRIPTION
        "A count of Signal Failure conditions that have been
         detected on the incoming signal. This condition occurs
         when a loss of signal, loss of frame, AIS-L or a Line
         bit error rate exceeding the currently configured value of
         the relevant instance of apsConfigSfBerThreshold.

         Discontinuities in the value of this counter can occur at
         re-initialization of the management system, and at other
         times as indicated by the value of
         apsChanStatusDiscontinuityTime."

    ::= { apsChanStatusEntry 3 }

apsChanStatusSwitchovers OBJECT-TYPE
    SYNTAX     Counter32
    MAX-ACCESS read-only
    STATUS     current
    DESCRIPTION
        "When queried with index value apsChanConfigNumber other than
         0, this object will return the number of times this channel
         has switched to the protection line.

         When queried with index value apsChanConfigNumber set to 0,
         which is the protection line, this object will return the
         number of times that any working channel has been switched
         back to the working line from this protection line.

         Discontinuities in the value of this counter can occur at
         re-initialization of the management system, and at other
         times as indicated by the value of
         apsChanStatusDiscontinuityTime."

    ::= { apsChanStatusEntry 4 }

apsChanStatusLastSwitchover OBJECT-TYPE
    SYNTAX     TimeStamp
    MAX-ACCESS read-only
    STATUS     current
    DESCRIPTION
        "When queried with index value apsChanConfigNumber other than
         0, this object will return the value of sysUpTime when this
         channel last completed a switch to the protection line. If


         this channel has never switched to the protection line, the
         value 0 will be returned.

         When queried with index value apsChanConfigNumber set to 0,
         which is the protection line, this object will return the
         value of sysUpTime the last time that a working channel was
         switched back to the working line from this protection line.
         If no working channel has ever switched back to the working
         line from this protection line, the value 0 will be returned."

    ::= { apsChanStatusEntry 5 }

apsChanStatusSwitchoverSeconds OBJECT-TYPE
    SYNTAX     Counter32
    MAX-ACCESS read-only
    STATUS     current
    DESCRIPTION
        "The cumulative Protection Switching Duration (PSD) time in
         seconds. For a working channel, this is the cumulative number
         of seconds that service was carried on the protection line.
         For the protection line, this is the cumulative number of
         seconds that the protection line has been used to carry any
         working channel traffic. This information is only valid if
         revertive switching is enabled. The value 0 will be returned
         otherwise.

         Discontinuities in the value of this counter can occur at
         re-initialization of the management system, and at other
         times as indicated by the value of
         apsChanStatusDiscontinuityTime. For example, if the value
         of an instance of apsChanStatusSwitchoverSeconds changes
         from a non-zero value to zero due to revertive switching
         being disabled, it is expected that the corresponding
         value of apsChanStatusDiscontinuityTime will be updated
         to reflect the time of the configuration change.
         "
    ::= { apsChanStatusEntry 6 }

apsChanStatusDiscontinuityTime OBJECT-TYPE
    SYNTAX      TimeStamp
    MAX-ACCESS  read-only
    STATUS      current
    DESCRIPTION
        "The value of sysUpTime on the most recent occasion at which
         any one or more of this channel's counters suffered a
         discontinuity.  The relevant counters are the specific
         instances associated with this channel of any Counter32
         object contained in apsChanStatusTable. If no such


         discontinuities have occurred since the last re-initialization
         of the local management subsystem, then this object contains
         a zero value."
    ::= { apsChanStatusEntry 7 }

apsNotificationEnable OBJECT-TYPE
    SYNTAX     BITS {
               switchover(0),
               modeMismatch(1),
               channelMismatch(2),
               psbf(3),
               feplf(4)
            }
    MAX-ACCESS read-write
    STATUS     current
    DESCRIPTION
        "Provides the ability to enable and disable notifications
         defined in this MIB.

         switchover

         Indicates  apsEventSwitchover notifications
         should be generated.

         modeMismatch

         Indicates  apsEventModeMismatch notifications
         should be generated.

         channelMismatch

         Indicates  apsEventChannelMismatch notifications
         should be generated.

         psbf

         Indicates  apsEventPSBF notifications
         should be generated.

         feplf

         Indicates  apsEventFEPLF notifications
         should be generated. "
    DEFVAL { { } }
    ::= { apsMIBObjects 7 }

--
-- APS EVENTS


--

apsNotificationsPrefix OBJECT IDENTIFIER
        ::= { apsMIBNotifications 0 }

apsEventSwitchover NOTIFICATION-TYPE
    OBJECTS { apsChanStatusSwitchovers, apsChanStatusCurrent }
    STATUS  current
    DESCRIPTION
        "An apsEventSwitchover notification is sent when the
        value of an instance of apsChanStatusSwitchovers increments."
    ::= { apsNotificationsPrefix 1 }

apsEventModeMismatch NOTIFICATION-TYPE
    OBJECTS { apsStatusModeMismatches, apsStatusCurrent }
    STATUS  current
    DESCRIPTION
        "An apsEventModeMismatch notification is sent when the
        value of an instance of apsStatusModeMismatches increments."
    ::= { apsNotificationsPrefix 2 }

apsEventChannelMismatch NOTIFICATION-TYPE
    OBJECTS { apsStatusChannelMismatches, apsStatusCurrent }
    STATUS  current
    DESCRIPTION
        "An apsEventChannelMismatch notification is sent when the
        value of an instance of apsStatusChannelMismatches increments."
    ::= { apsNotificationsPrefix 3 }

apsEventPSBF NOTIFICATION-TYPE
    OBJECTS { apsStatusPSBFs, apsStatusCurrent }
    STATUS  current
    DESCRIPTION
        "An apsEventPSBF notification is sent when the
        value of an instance of apsStatusPSBFs increments."
    ::= { apsNotificationsPrefix 4 }

apsEventFEPLF NOTIFICATION-TYPE
    OBJECTS { apsStatusFEPLFs, apsStatusCurrent }
    STATUS  current
    DESCRIPTION
        "An apsEventFEPLFs notification is sent when the
        value of an instance of apsStatusFEPLFs increments."
    ::= { apsNotificationsPrefix 5 }

-- conformance information


apsGroups      OBJECT IDENTIFIER ::= { apsMIBConformance 1 }
apsCompliances OBJECT IDENTIFIER ::= { apsMIBConformance 2 }

apsFullCompliance MODULE-COMPLIANCE
    STATUS  current
    DESCRIPTION
        "When this MIB is implemented with support for read-create, then
        such an implementation can claim read/write compliance. Linear
        APS groups can then be both monitored and configured with this
        MIB.

        Note that An agent is not required to process SNMP Set Requests
        that affect multiple control objects within this MIB. This is
        intended to simplify the processing of Set Requests for the
        various control tables by eliminating the possibility that a
        single Set PDU will contain multiple varbinds which are in
        conflict. "

    MODULE
    MANDATORY-GROUPS { apsConfigGeneral, apsStatusGeneral,
                       apsChanGeneral }

        OBJECT  apsConfigRowStatus
        SYNTAX INTEGER { active(1) }
        WRITE-SYNTAX INTEGER { createAndGo(4), destroy(6) }
        DESCRIPTION
            "Support for createAndWait and notInService is not
             required."

        OBJECT  apsChanConfigRowStatus
        SYNTAX INTEGER { active(1) }
        WRITE-SYNTAX INTEGER { createAndGo(4), destroy(6) }
        DESCRIPTION
            "Support for createAndWait and notInService is not
             required."

        GROUP       apsConfigWtr
        DESCRIPTION
            "Implementation of this group is optional for all
             linear APS implementations. The information is
             applicable to groups supporting a configurable
             WTR period."

        GROUP       apsCommandOnePlusOne
        DESCRIPTION
            "Implementation of this group is optional for all
             linear APS implementations. The information is
             applicable to groups implementing the linear


             APS 1+1 architecture and supporting set operations."

       GROUP       apsCommandOneToN
        DESCRIPTION
            "Implementation of this group is optional for all
             linear APS implementations. The information is
             applicable to groups implementing the linear
             APS 1:n architecture and supporting set operations."

       GROUP       apsChanOneToN
        DESCRIPTION
            "Implementation of this group is optional for all
             linear APS implementations. The information is
             applicable to groups implementing the linear
             APS 1:n architecture."

       GROUP       apsTotalsGroup
        DESCRIPTION
            "Implementation of this group is optional for all
             linear APS implementations."

       GROUP       apsMapGroup
        DESCRIPTION
            "Implementation of this group is optional for all
             linear APS implementations."

       GROUP       apsEventGroup
        DESCRIPTION
            "Implementation of this group is optional for all
             linear APS implementations."

    ::= { apsCompliances 1 }

--
-- Read-Only Compliance
--

apsReadOnlyCompliance MODULE-COMPLIANCE
    STATUS  current
    DESCRIPTION
        "When this MIB is implemented without support for read-create
         (i.e. in read-only mode), then that implementation can claim
         read-only compliance. In that case, linear APS groups can be
         monitored but cannot be configured with this MIB."

    MODULE
    MANDATORY-GROUPS { apsConfigGeneral, apsStatusGeneral,
                       apsChanGeneral }


        OBJECT  apsConfigMode
        MIN-ACCESS  read-only
        DESCRIPTION
            "Write access is not required."

        OBJECT  apsConfigRevert
        MIN-ACCESS  read-only
        DESCRIPTION
            "Write access is not required."

        OBJECT  apsConfigDirection
        MIN-ACCESS  read-only
        DESCRIPTION
            "Write access is not required."

        OBJECT  apsConfigExtraTraffic
        MIN-ACCESS  read-only
        DESCRIPTION
            "Write access is not required."

        OBJECT  apsConfigSdBerThreshold
        MIN-ACCESS  read-only
        DESCRIPTION
            "Write access is not required."

        OBJECT  apsConfigSfBerThreshold
        MIN-ACCESS  read-only
        DESCRIPTION
            "Write access is not required."

        OBJECT  apsConfigWaitToRestore
        MIN-ACCESS  read-only
        DESCRIPTION
            "Write access is not required."

        OBJECT  apsConfigRowStatus
        SYNTAX  INTEGER { active(1) }
        MIN-ACCESS  read-only
        DESCRIPTION
            "Write access is not required, and active is the only status
             that needs to be supported."

        OBJECT  apsConfigStorageType
        MIN-ACCESS  read-only
        DESCRIPTION
            "Write access is not required."

        OBJECT  apsChanConfigIfIndex


        MIN-ACCESS  read-only
        DESCRIPTION
            "Write access is not required."

        OBJECT  apsChanConfigPriority
        MIN-ACCESS  read-only
        DESCRIPTION
            "Write access is not required."

        OBJECT  apsChanConfigRowStatus
        SYNTAX  INTEGER { active(1) }
        MIN-ACCESS  read-only
        DESCRIPTION
            "Write access is not required, and active is the only status
             that needs to be supported."

        OBJECT  apsChanConfigStorageType
        MIN-ACCESS  read-only
        DESCRIPTION
            "Write access is not required."

        OBJECT  apsNotificationEnable
        MIN-ACCESS  read-only
        DESCRIPTION
            "Write access is not required."

        GROUP       apsConfigWtr
        DESCRIPTION
            "Implementation of this group is optional for all
             linear APS implementations. The information is
             applicable to groups supporting a configurable
             WTR period."

        GROUP       apsCommandOnePlusOne
        DESCRIPTION
            "Implementation of this group is optional for all
             linear APS implementations. The information is
             applicable to groups implementing the linear
             APS 1+1 architecture and supporting set operations."

       GROUP       apsCommandOneToN
        DESCRIPTION
            "Implementation of this group is optional for all
             linear APS implementations. The information is
             applicable to groups implementing the linear
             APS 1:n architecture and supporting set operations."

       GROUP       apsChanOneToN


        DESCRIPTION
            "Implementation of this group is optional for all
             linear APS implementations. The information is
             applicable to groups implementing the linear
             APS 1:n architecture."

       GROUP       apsTotalsGroup
        DESCRIPTION
            "Implementation of this group is optional for all
             linear APS implementations."

       GROUP       apsMapGroup
        DESCRIPTION
            "Implementation of this group is optional for all
             linear APS implementations."

       GROUP       apsEventGroup
        DESCRIPTION
            "Implementation of this group is optional for all
             linear APS implementations."

    ::= { apsCompliances 2 }

-- units of conformance

apsConfigGeneral    OBJECT-GROUP
    OBJECTS
    {
        apsConfigMode,
        apsConfigRevert,
        apsConfigDirection,
        apsConfigExtraTraffic,
        apsConfigSdBerThreshold,
        apsConfigSfBerThreshold,
        apsConfigCreationTime,
        apsConfigRowStatus,
        apsConfigStorageType,
        apsNotificationEnable
    }
    STATUS  current
    DESCRIPTION
        "A collection of apsConfigTable objects providing configuration
         information applicable to all linear APS groups."
    ::= { apsGroups 1 }

apsConfigWtr    OBJECT-GROUP
    OBJECTS
    {


        apsConfigWaitToRestore
    }
    STATUS  current
    DESCRIPTION
        "The apsConfigTable object that provides information which is
         applicable to groups supporting a configurable WTR period."
    ::= { apsGroups 2 }

--  If set operations are not supported neither of the following two
--  groups are implemented. If sets are supported only one of these
--  groups is implemented for a linear APS group instance.

apsCommandOnePlusOne    OBJECT-GROUP
    OBJECTS
    {
        apsCommandSwitch
    }
    STATUS  current
    DESCRIPTION
        "The  apsCommandTable object which is applicable to groups
         implementing the linear APS 1+1 architecture. Also, set
         operations must be supported."
    ::= { apsGroups 3 }

apsCommandOneToN    OBJECT-GROUP
    OBJECTS
    {
        apsCommandSwitch,
        apsCommandControl
    }
    STATUS  current
    DESCRIPTION
        "A collection of apsCommandTable objects which are applicable to
         groups implementing the linear APS 1:n architecture. Also, set
         operations must be supported."
    ::= { apsGroups 4 }

apsStatusGeneral    OBJECT-GROUP
    OBJECTS
    {
        apsStatusK1K2Rcv,
        apsStatusK1K2Trans,
        apsStatusCurrent,
        apsStatusModeMismatches,
        apsStatusChannelMismatches,
        apsStatusPSBFs,
        apsStatusFEPLFs,
        apsStatusSwitchedChannel,


        apsStatusDiscontinuityTime
    }
    STATUS  current
    DESCRIPTION
        "A collection of apsStatusTable objects providing status
         information applicable to all linear APS groups."
    ::= { apsGroups 5 }

apsChanGeneral    OBJECT-GROUP
    OBJECTS
    {
        apsChanConfigIfIndex,
        apsChanConfigRowStatus,
        apsChanConfigStorageType,
        apsChanStatusCurrent,
        apsChanStatusSignalDegrades,
        apsChanStatusSignalFailures,
        apsChanStatusSwitchovers,
        apsChanStatusLastSwitchover,
        apsChanStatusSwitchoverSeconds,
        apsChanStatusDiscontinuityTime
   }
    STATUS  current
    DESCRIPTION
        "A collection of channel objects providing information
         applicable to all linear APS channels."
    ::= { apsGroups 6 }

apsChanOneToN    OBJECT-GROUP
    OBJECTS
    {
        apsChanConfigPriority
    }
    STATUS  current
    DESCRIPTION
        "The apsChanConfigTable object that provides information which
         is only applicable to groups implementing the linear APS 1:n
         architecture."
    ::= { apsGroups 7 }

apsTotalsGroup OBJECT-GROUP
    OBJECTS
    {
        apsConfigGroups,
        apsChanLTEs
    }
    STATUS  current
    DESCRIPTION


        "A collection of objects providing optional counts of configured
         APS groups and SONET LTE interfaces."
    ::= { apsGroups 8 }

apsMapGroup OBJECT-GROUP
    OBJECTS
    {
        apsMapGroupName,
        apsMapChanNumber
    }
    STATUS  current
    DESCRIPTION
        "A collection of apsMapTable objects providing a mapping
         from sonet(39) InterfaceIndex to group name and channel
         number for assigned APS channels and a list of unassigned
         sonet(39) interfaces."
    ::= { apsGroups 9 }

apsEventGroup NOTIFICATION-GROUP
    NOTIFICATIONS {apsEventSwitchover, apsEventModeMismatch,
                   apsEventChannelMismatch, apsEventPSBF,
                   apsEventFEPLF }
    STATUS    current
    DESCRIPTION
        "A collection of SONET linear APS notifications."
    ::= { apsGroups 10 }

END

DS3-MIB DEFINITIONS ::= BEGIN

     IMPORTS
          MODULE-IDENTITY, OBJECT-TYPE,
          NOTIFICATION-TYPE, transmission         FROM SNMPv2-SMI


          DisplayString, TimeStamp, TruthValue    FROM SNMPv2-TC
          MODULE-COMPLIANCE, OBJECT-GROUP,
          NOTIFICATION-GROUP                      FROM SNMPv2-CONF
          InterfaceIndex                          FROM IF-MIB
          PerfCurrentCount, PerfIntervalCount,
          PerfTotalCount                          FROM PerfHist-TC-MIB;

     ds3 MODULE-IDENTITY
         LAST-UPDATED "9808012130Z"
         ORGANIZATION "IETF Trunk MIB Working Group"
         CONTACT-INFO
           "        David Fowler

            Postal: Newbridge Networks Corporation
                    600 March Road
                    Kanata, Ontario, Canada K2K 2E6

                    Tel: +1 613 591 3600
                    Fax: +1 613 599 3667

            E-mail: davef@newbridge.com"
         DESCRIPTION
              "The is the MIB module that describes
               DS3 and E3 interfaces objects."

         ::= { transmission 30 }

     -- The DS3/E3 Near End Group

     -- The DS3/E3 Near End Group consists of four tables:
     --    DS3/E3 Configuration
     --    DS3/E3 Current
     --    DS3/E3 Interval
     --    DS3/E3 Total

     -- the DS3/E3 Configuration Table

     dsx3ConfigTable OBJECT-TYPE
          SYNTAX  SEQUENCE OF Dsx3ConfigEntry
          MAX-ACCESS  not-accessible
          STATUS  current
          DESCRIPTION
                 "The DS3/E3 Configuration table."
          ::= { ds3 5 }

     dsx3ConfigEntry OBJECT-TYPE
          SYNTAX  Dsx3ConfigEntry


          MAX-ACCESS  not-accessible
          STATUS  current
          DESCRIPTION
                 "An entry in the DS3/E3 Configuration table."
          INDEX   { dsx3LineIndex }
          ::= { dsx3ConfigTable 1 }

     Dsx3ConfigEntry ::=
          SEQUENCE {
              dsx3LineIndex                        InterfaceIndex,
              dsx3IfIndex                          InterfaceIndex,
              dsx3TimeElapsed                      INTEGER,
              dsx3ValidIntervals                   INTEGER,
              dsx3LineType                         INTEGER,
              dsx3LineCoding                       INTEGER,
              dsx3SendCode                         INTEGER,
              dsx3CircuitIdentifier                DisplayString,
              dsx3LoopbackConfig                   INTEGER,
              dsx3LineStatus                       INTEGER,
              dsx3TransmitClockSource              INTEGER,
              dsx3InvalidIntervals                 INTEGER,
              dsx3LineLength                       INTEGER,
              dsx3LineStatusLastChange             TimeStamp,
              dsx3LineStatusChangeTrapEnable       INTEGER,
              dsx3LoopbackStatus                   INTEGER,
              dsx3Channelization                   INTEGER,
              dsx3Ds1ForRemoteLoop                 INTEGER
     }

     dsx3LineIndex OBJECT-TYPE
          SYNTAX  InterfaceIndex
          MAX-ACCESS  read-only
          STATUS  current
          DESCRIPTION
                 "This object should be made equal to ifIndex.  The
                 next paragraph describes its previous usage.
                 Making the object equal to ifIndex allows propoer
                 use of ifStackTable.

                 Previously, this object was the identifier of a
                 DS3/E3 Interface on a managed device.  If there is
                 an ifEntry that is directly associated with this
                 and only this DS3/E3 interface, it should have the
                 same value as ifIndex.  Otherwise, number the
                 dsx3LineIndices with an unique identifier
                 following the rules of choosing a number that is
                 greater than ifNumber and numbering the inside
                 interfaces (e.g., equipment side) with even


                 numbers and outside interfaces (e.g, network side)
                 with odd numbers."
          ::= { dsx3ConfigEntry 1 }

     dsx3IfIndex OBJECT-TYPE
          SYNTAX  InterfaceIndex
          MAX-ACCESS  read-only
          STATUS  deprecated
          DESCRIPTION
                 "This value for this object is equal to the value
                 of ifIndex from the Interfaces table of MIB II
                 (RFC 1213)."
          ::= { dsx3ConfigEntry 2 }

     dsx3TimeElapsed OBJECT-TYPE
          SYNTAX  INTEGER (0..899)
          MAX-ACCESS  read-only
          STATUS  current
          DESCRIPTION
                 "The number of seconds that have elapsed since the
                 beginning of the near end current error-
                 measurement period.  If, for some reason, such as
                 an adjustment in the system's time-of-day clock,
                 the current interval exceeds the maximum value,
                 the agent will return the maximum value."

          ::= { dsx3ConfigEntry 3 }

     dsx3ValidIntervals OBJECT-TYPE
          SYNTAX  INTEGER (0..96)
          MAX-ACCESS  read-only
          STATUS  current
          DESCRIPTION
                 "The number of previous near end intervals for
                 which data was collected.  The value will be
                 96 unless the interface was brought online within
                 the last 24 hours, in which case the value will be
                 the number of complete 15 minute near end
                 intervals since the interface has been online.  In
                 the case where the agent is a proxy, it is
                 possible that some intervals are unavailable.  In
                 this case, this interval is the maximum interval
                 number for which data is available."
          ::= { dsx3ConfigEntry 4 }

     dsx3LineType OBJECT-TYPE
          SYNTAX  INTEGER {
                     dsx3other(1),


                     dsx3M23(2),
                     dsx3SYNTRAN(3),
                     dsx3CbitParity(4),
                     dsx3ClearChannel(5),
                     e3other(6),
                     e3Framed(7),
                     e3Plcp(8)
                 }
          MAX-ACCESS  read-write
          STATUS  current
          DESCRIPTION
                 "This variable indicates the variety of DS3 C-bit
                 or E3 application implementing this interface. The
                 type of interface affects the interpretation of
                 the usage and error statistics.  The rate of DS3
                 is 44.736 Mbps and E3 is 34.368 Mbps.  The
                 dsx3ClearChannel value means that the C-bits are
                 not used except for sending/receiving AIS.
                 The values, in sequence, describe:

                 TITLE:            SPECIFICATION:
                 dsx3M23            ANSI T1.107-1988 [9]
                 dsx3SYNTRAN        ANSI T1.107-1988 [9]
                 dsx3CbitParity     ANSI T1.107a-1990 [9a]
                 dsx3ClearChannel   ANSI T1.102-1987 [8]
                 e3Framed           CCITT G.751 [12]
                 e3Plcp             ETSI T/NA(91)18 [13]."
          ::= { dsx3ConfigEntry 5 }

     dsx3LineCoding OBJECT-TYPE
          SYNTAX  INTEGER {
                     dsx3Other(1),
                     dsx3B3ZS(2),
                     e3HDB3(3)
                 }
          MAX-ACCESS  read-write
          STATUS  current
          DESCRIPTION
                 "This variable describes the variety of Zero Code
                 Suppression used on this interface, which in turn
                 affects a number of its characteristics.

                 dsx3B3ZS and e3HDB3 refer to the use of specified
                 patterns of normal bits and bipolar violations
                 which are used to replace sequences of zero bits
                 of a specified length."
          ::= { dsx3ConfigEntry 6 }


     dsx3SendCode OBJECT-TYPE
          SYNTAX  INTEGER {
                    dsx3SendNoCode(1),
                    dsx3SendLineCode(2),
                    dsx3SendPayloadCode(3),
                    dsx3SendResetCode(4),
                    dsx3SendDS1LoopCode(5),
                    dsx3SendTestPattern(6)
                    }
          MAX-ACCESS  read-write
          STATUS  current
          DESCRIPTION
                 "This variable indicates what type of code is
                 being sent across the DS3/E3 interface by the
                 device.  (These are optional for E3 interfaces.)
                 Setting this variable causes the interface to
                 begin sending the code requested.
                 The values mean:

                    dsx3SendNoCode
                        sending looped or normal data

                    dsx3SendLineCode
                        sending a request for a line loopback

                    dsx3SendPayloadCode
                        sending a request for a payload loopback
                        (i.e., all DS1/E1s in a DS3/E3 frame)

                    dsx3SendResetCode
                        sending a loopback deactivation request

                    dsx3SendDS1LoopCode
                        requesting to loopback a particular DS1/E1
                        within a DS3/E3 frame.  The DS1/E1 is
                        indicated in dsx3Ds1ForRemoteLoop.

                    dsx3SendTestPattern
                        sending a test pattern."
          ::= { dsx3ConfigEntry 7 }

     dsx3CircuitIdentifier OBJECT-TYPE
          SYNTAX  DisplayString (SIZE (0..255))
          MAX-ACCESS  read-write
          STATUS  current
          DESCRIPTION
                 "This variable contains the transmission vendor's
                 circuit identifier, for the purpose of


                 facilitating troubleshooting."
          ::= { dsx3ConfigEntry 8 }

     dsx3LoopbackConfig OBJECT-TYPE
          SYNTAX  INTEGER {
                      dsx3NoLoop(1),
                      dsx3PayloadLoop(2),
                      dsx3LineLoop(3),
                      dsx3OtherLoop(4),
                      dsx3InwardLoop(5),
                      dsx3DualLoop(6)
                    }
          MAX-ACCESS  read-write
          STATUS  current
          DESCRIPTION
               "This variable represents the desired loopback
               configuration of the DS3/E3 interface.

               The values mean:

               dsx3NoLoop
                 Not in the loopback state.  A device that is
                 not capable of performing a loopback on
                 the interface shall always return this as
                 its value.

               dsx3PayloadLoop
                 The received signal at this interface is looped
                 through the device.  Typically the received signal
                 is looped back for retransmission after it has
                 passed through the device's framing function.

               dsx3LineLoop
                 The received signal at this interface does not
                 go through the device (minimum penetration) but
                 is looped back out.

               dsx3OtherLoop
                 Loopbacks that are not defined here.

               dsx3InwardLoop
                 The sent signal at this interface is looped back
                 through the device.

               dsx3DualLoop
                 Both dsx1LineLoop and dsx1InwardLoop will be
                 active simultaneously."
          ::= { dsx3ConfigEntry 9 }


     dsx3LineStatus OBJECT-TYPE
          SYNTAX  INTEGER (1..4095)
          MAX-ACCESS  read-only
          STATUS  current
          DESCRIPTION
                 "This variable indicates the Line Status of the
                 interface.  It contains loopback state information
                 and failure state information.  The dsx3LineStatus
                 is a bit map represented as a sum, therefore, it
                 can represent multiple failures and a loopback
                 (see dsx3LoopbackConfig object for the type of
                 loopback) simultaneously.  The dsx3NoAlarm must be
                 set if and only if no other flag is set.

                 If the dsx3loopbackState bit is set, the loopback
                 in effect can be determined from the
                 dsx3loopbackConfig object.
       The various bit positions are:
        1     dsx3NoAlarm         No alarm present
        2     dsx3RcvRAIFailure   Receiving Yellow/Remote
                                  Alarm Indication
        4     dsx3XmitRAIAlarm    Transmitting Yellow/Remote
                                  Alarm Indication
        8     dsx3RcvAIS          Receiving AIS failure state
       16     dsx3XmitAIS         Transmitting AIS
       32     dsx3LOF             Receiving LOF failure state
       64     dsx3LOS             Receiving LOS failure state
      128     dsx3LoopbackState   Looping the received signal
      256     dsx3RcvTestCode     Receiving a Test Pattern
      512     dsx3OtherFailure    any line status not defined
                                  here
     1024     dsx3UnavailSigState Near End in Unavailable Signal
                                  State
     2048     dsx3NetEquipOOS     Carrier Equipment Out of Service"
     ::= { dsx3ConfigEntry 10 }

dsx3TransmitClockSource OBJECT-TYPE
     SYNTAX  INTEGER {
                loopTiming(1),
                localTiming(2),
                throughTiming(3)
            }
     MAX-ACCESS  read-write
     STATUS  current
     DESCRIPTION
            "The source of Transmit Clock.

            loopTiming indicates that the recovered receive clock


            is used as the transmit clock.

            localTiming indicates that a local clock source is used
            or that an external clock is attached to the box
            containing the interface.

            throughTiming indicates that transmit clock is derived
            from the recovered receive clock of another DS3
            interface."
          ::= { dsx3ConfigEntry 11 }

     dsx3InvalidIntervals OBJECT-TYPE
          SYNTAX  INTEGER (0..96)
          MAX-ACCESS  read-only
          STATUS  current
          DESCRIPTION
                      "The number of intervals in the range from 0 to
                 dsx3ValidIntervals for which no data is
                 available.  This object will typically be zero
                 except in cases where the data for some intervals
                 are not available (e.g., in proxy situations)."
          ::= { dsx3ConfigEntry 12 }

     dsx3LineLength OBJECT-TYPE
          SYNTAX  INTEGER (0..64000)
          UNITS "meters"
          MAX-ACCESS  read-write
          STATUS  current
          DESCRIPTION
                 "The length of the ds3 line in meters.  This
                 object provides information for line build out
                 circuitry if it exists and can use this object to
                 adjust the line build out."
          ::= { dsx3ConfigEntry 13 }

     dsx3LineStatusLastChange OBJECT-TYPE
          SYNTAX  TimeStamp
          MAX-ACCESS  read-only
          STATUS  current
          DESCRIPTION
                 "The value of MIB II's sysUpTime object at the
                 time this DS3/E3 entered its current line status
                 state.  If the current state was entered prior to
                 the last re-initialization of the proxy-agent,
                 then this object contains a zero value."
          ::= { dsx3ConfigEntry 14 }

     dsx3LineStatusChangeTrapEnable  OBJECT-TYPE


          SYNTAX      INTEGER {
                         enabled(1),
                         disabled(2)
                      }
          MAX-ACCESS  read-write
          STATUS      current
          DESCRIPTION
                 "Indicates whether dsx3LineStatusChange traps
                 should be generated for this interface."
          DEFVAL { disabled }
          ::= { dsx3ConfigEntry 15 }

     dsx3LoopbackStatus  OBJECT-TYPE
          SYNTAX      INTEGER (1..127)
          MAX-ACCESS  read-only
          STATUS      current
          DESCRIPTION
                 "This variable represents the current state of the
                 loopback on the DS3 interface.  It contains
                 information about loopbacks established by a
                 manager and remotely from the far end.

                 The dsx3LoopbackStatus is a bit map represented as
                 a sum, therefore is can represent multiple
                 loopbacks simultaneously.

                 The various bit positions are:
                  1  dsx3NoLoopback
                  2  dsx3NearEndPayloadLoopback
                  4  dsx3NearEndLineLoopback
                  8  dsx3NearEndOtherLoopback
                 16  dsx3NearEndInwardLoopback
                 32  dsx3FarEndPayloadLoopback
                 64  dsx3FarEndLineLoopback"

     ::= { dsx3ConfigEntry 16 }

     dsx3Channelization  OBJECT-TYPE
          SYNTAX      INTEGER {
                         disabled(1),
                         enabledDs1(2),
                         enabledDs2(3)
                      }
          MAX-ACCESS  read-write
          STATUS      current
          DESCRIPTION
                 "Indicates whether this ds3/e3 is channelized or
                 unchannelized.  The value of enabledDs1 indicates


                 that this is a DS3 channelized into DS1s.  The
                 value of enabledDs3 indicated that this is a DS3
                 channelized into DS2s.  Setting this object will
                 cause the creation or deletion of DS2 or DS1
                 entries in the ifTable.  "
     ::= { dsx3ConfigEntry 17 }

     dsx3Ds1ForRemoteLoop  OBJECT-TYPE
          SYNTAX      INTEGER (0..29)

          MAX-ACCESS  read-write
          STATUS      current
          DESCRIPTION
                 "Indicates which ds1/e1 on this ds3/e3 will be
                 indicated in the remote ds1 loopback request.  A
                 value of 0 means no DS1 will be looped.  A value
                 of 29 means all ds1s/e1s will be looped."
     ::= { dsx3ConfigEntry 18 }

     -- the DS3/E3 Current Table

     dsx3CurrentTable OBJECT-TYPE
          SYNTAX  SEQUENCE OF Dsx3CurrentEntry
          MAX-ACCESS  not-accessible
          STATUS  current
          DESCRIPTION
                 "The DS3/E3 current table contains various
                 statistics being collected for the current 15
                 minute interval."
          ::= { ds3 6 }

     dsx3CurrentEntry OBJECT-TYPE
          SYNTAX  Dsx3CurrentEntry
          MAX-ACCESS  not-accessible
          STATUS  current
          DESCRIPTION
                 "An entry in the DS3/E3 Current table."
          INDEX   { dsx3CurrentIndex }
          ::= { dsx3CurrentTable 1 }

     Dsx3CurrentEntry ::=
          SEQUENCE {
              dsx3CurrentIndex           InterfaceIndex,
              dsx3CurrentPESs            PerfCurrentCount,
              dsx3CurrentPSESs           PerfCurrentCount,
              dsx3CurrentSEFSs           PerfCurrentCount,


              dsx3CurrentUASs            PerfCurrentCount,
              dsx3CurrentLCVs            PerfCurrentCount,
              dsx3CurrentPCVs            PerfCurrentCount,
              dsx3CurrentLESs            PerfCurrentCount,
              dsx3CurrentCCVs            PerfCurrentCount,
              dsx3CurrentCESs            PerfCurrentCount,
              dsx3CurrentCSESs           PerfCurrentCount
         }

     dsx3CurrentIndex OBJECT-TYPE
          SYNTAX  InterfaceIndex
          MAX-ACCESS  read-only
          STATUS  current
          DESCRIPTION
                 "The index value which uniquely identifies the
                 DS3/E3 interface to which this entry is
                 applicable.  The interface identified by a
                 particular value of this index is the same
                 interface as identified by the same value an
                 dsx3LineIndex object instance."
          ::= { dsx3CurrentEntry 1 }

     dsx3CurrentPESs OBJECT-TYPE
          SYNTAX  PerfCurrentCount
          MAX-ACCESS  read-only
          STATUS  current
          DESCRIPTION
                 "The counter associated with the number of P-bit
                 Errored Seconds."
          ::= { dsx3CurrentEntry 2 }

     dsx3CurrentPSESs OBJECT-TYPE
          SYNTAX  PerfCurrentCount
          MAX-ACCESS  read-only
          STATUS  current
          DESCRIPTION
                 "The counter associated with the number of P-bit
                 Severely Errored Seconds."
          ::= { dsx3CurrentEntry 3 }

     dsx3CurrentSEFSs OBJECT-TYPE
          SYNTAX  PerfCurrentCount
          MAX-ACCESS  read-only
          STATUS  current
          DESCRIPTION
                 "The counter associated with the number of
                 Severely Errored Framing Seconds."
          ::= { dsx3CurrentEntry 4 }


     dsx3CurrentUASs OBJECT-TYPE
          SYNTAX  PerfCurrentCount
          MAX-ACCESS  read-only
          STATUS  current
          DESCRIPTION
                 "The counter associated with the number of
                 Unavailable Seconds."
          ::= { dsx3CurrentEntry 5 }

     dsx3CurrentLCVs OBJECT-TYPE
          SYNTAX  PerfCurrentCount
          MAX-ACCESS  read-only
          STATUS  current
          DESCRIPTION
                 "The counter associated with the number of Line
                 Coding Violations."
          ::= { dsx3CurrentEntry 6 }

     dsx3CurrentPCVs OBJECT-TYPE
          SYNTAX  PerfCurrentCount
          MAX-ACCESS  read-only
          STATUS  current
          DESCRIPTION
                 "The counter associated with the number of P-bit
                 Coding Violations."
          ::= { dsx3CurrentEntry 7 }

     dsx3CurrentLESs OBJECT-TYPE
          SYNTAX  PerfCurrentCount
          MAX-ACCESS  read-only
          STATUS  current
          DESCRIPTION
                 "The number of Line Errored Seconds."
          ::= { dsx3CurrentEntry 8 }

     dsx3CurrentCCVs OBJECT-TYPE
          SYNTAX  PerfCurrentCount
          MAX-ACCESS  read-only
          STATUS  current
          DESCRIPTION
                 "The number of C-bit Coding Violations."
          ::= { dsx3CurrentEntry 9 }

     dsx3CurrentCESs OBJECT-TYPE
          SYNTAX  PerfCurrentCount
          MAX-ACCESS  read-only
          STATUS  current
          DESCRIPTION


                 "The number of C-bit Errored Seconds."
          ::= { dsx3CurrentEntry 10 }

     dsx3CurrentCSESs OBJECT-TYPE
          SYNTAX  PerfCurrentCount
          MAX-ACCESS  read-only
          STATUS  current
          DESCRIPTION
                 "The number of C-bit Severely Errored Seconds."
          ::= { dsx3CurrentEntry 11 }

     -- the DS3/E3 Interval Table

     dsx3IntervalTable OBJECT-TYPE
          SYNTAX  SEQUENCE OF Dsx3IntervalEntry
          MAX-ACCESS  not-accessible
          STATUS  current
          DESCRIPTION
                 "The DS3/E3 Interval Table contains various
                 statistics collected by each DS3/E3 Interface over
                 the previous 24 hours of operation.  The past 24
                 hours are broken into 96 completed 15 minute
                 intervals.  Each row in this table represents one
                 such interval (identified by dsx3IntervalNumber)
                 and for one specific interface (identifed by
                 dsx3IntervalIndex)."

          ::= { ds3 7 }

     dsx3IntervalEntry OBJECT-TYPE
          SYNTAX  Dsx3IntervalEntry
          MAX-ACCESS  not-accessible
          STATUS  current
          DESCRIPTION
                 "An entry in the DS3/E3 Interval table."
          INDEX   { dsx3IntervalIndex, dsx3IntervalNumber }
          ::= { dsx3IntervalTable 1 }

     Dsx3IntervalEntry ::=
          SEQUENCE {
              dsx3IntervalIndex           InterfaceIndex,
              dsx3IntervalNumber          INTEGER,
              dsx3IntervalPESs            PerfIntervalCount,
              dsx3IntervalPSESs           PerfIntervalCount,
              dsx3IntervalSEFSs           PerfIntervalCount,
              dsx3IntervalUASs            PerfIntervalCount,
              dsx3IntervalLCVs            PerfIntervalCount,
              dsx3IntervalPCVs            PerfIntervalCount,


              dsx3IntervalLESs            PerfIntervalCount,
              dsx3IntervalCCVs            PerfIntervalCount,
              dsx3IntervalCESs            PerfIntervalCount,
              dsx3IntervalCSESs           PerfIntervalCount,
              dsx3IntervalValidData       TruthValue
          }

     dsx3IntervalIndex OBJECT-TYPE
          SYNTAX  InterfaceIndex
          MAX-ACCESS  read-only
          STATUS  current
          DESCRIPTION
                 "The index value which uniquely identifies the
                 DS3/E3 interface to which this entry is
                 applicable.  The interface identified by a
                 particular value of this index is the same
                 interface as identified by the same value an
                 dsx3LineIndex object instance."
          ::= { dsx3IntervalEntry 1 }

     dsx3IntervalNumber OBJECT-TYPE
          SYNTAX  INTEGER (1..96)
          MAX-ACCESS  read-only
          STATUS  current
          DESCRIPTION
                 "A number between 1 and 96, where 1 is the most
                 recently completed 15 minute interval and 96 is
                 the 15 minutes interval completed 23 hours and 45
                 minutes prior to interval 1."
          ::= { dsx3IntervalEntry 2 }

     dsx3IntervalPESs OBJECT-TYPE
          SYNTAX  PerfIntervalCount
          MAX-ACCESS  read-only
          STATUS  current
          DESCRIPTION
                 "The counter associated with the number of P-bit
                 Errored Seconds."
          ::= { dsx3IntervalEntry 3 }

     dsx3IntervalPSESs OBJECT-TYPE
          SYNTAX  PerfIntervalCount
          MAX-ACCESS  read-only
          STATUS  current
          DESCRIPTION
                 "The counter associated with the number of P-bit
                 Severely Errored Seconds."
          ::= { dsx3IntervalEntry 4 }


     dsx3IntervalSEFSs OBJECT-TYPE
          SYNTAX  PerfIntervalCount
          MAX-ACCESS  read-only
          STATUS  current
          DESCRIPTION
                 "The counter associated with the number of
                 Severely Errored Framing Seconds."
          ::= { dsx3IntervalEntry 5 }

     dsx3IntervalUASs OBJECT-TYPE
          SYNTAX  PerfIntervalCount
          MAX-ACCESS  read-only
          STATUS  current
          DESCRIPTION
                 "The counter associated with the number of
                 Unavailable Seconds.  This object may decrease if
                 the occurance of unavailable seconds occurs across
                 an inteval boundary."
          ::= { dsx3IntervalEntry 6 }

     dsx3IntervalLCVs OBJECT-TYPE
          SYNTAX  PerfIntervalCount
          MAX-ACCESS  read-only
          STATUS  current
          DESCRIPTION
                 "The counter associated with the number of Line
                 Coding Violations."
          ::= { dsx3IntervalEntry 7 }

     dsx3IntervalPCVs OBJECT-TYPE
          SYNTAX  PerfIntervalCount
          MAX-ACCESS  read-only
          STATUS  current
          DESCRIPTION
                 "The counter associated with the number of P-bit
                 Coding Violations."
          ::= { dsx3IntervalEntry 8 }

     dsx3IntervalLESs OBJECT-TYPE
          SYNTAX  PerfIntervalCount
          MAX-ACCESS  read-only
          STATUS  current
          DESCRIPTION
                 "The number of Line Errored  Seconds  (BPVs  or
                 illegal  zero  sequences)."
          ::= { dsx3IntervalEntry 9 }

     dsx3IntervalCCVs OBJECT-TYPE


          SYNTAX  PerfIntervalCount
          MAX-ACCESS  read-only
          STATUS  current
          DESCRIPTION
                 "The number of C-bit Coding Violations."
          ::= { dsx3IntervalEntry 10 }

     dsx3IntervalCESs OBJECT-TYPE
          SYNTAX  PerfIntervalCount
          MAX-ACCESS  read-only
          STATUS  current
          DESCRIPTION
                 "The number of C-bit Errored Seconds."
          ::= { dsx3IntervalEntry 11 }

     dsx3IntervalCSESs OBJECT-TYPE
          SYNTAX  PerfIntervalCount
          MAX-ACCESS  read-only
          STATUS  current
          DESCRIPTION
                 "The number of C-bit Severely Errored Seconds."
          ::= { dsx3IntervalEntry 12 }

     dsx3IntervalValidData OBJECT-TYPE
          SYNTAX  TruthValue
          MAX-ACCESS read-only
          STATUS current
          DESCRIPTION
                 "This variable indicates if the data for this
                 interval is valid."
          ::= { dsx3IntervalEntry 13 }

     -- the DS3/E3 Total

     dsx3TotalTable OBJECT-TYPE
          SYNTAX  SEQUENCE OF Dsx3TotalEntry
          MAX-ACCESS  not-accessible
          STATUS  current
          DESCRIPTION
                 "The DS3/E3 Total Table contains the cumulative
                 sum of the various statistics for the 24 hour
                 period preceding the current interval."
          ::= { ds3 8 }

     dsx3TotalEntry OBJECT-TYPE
          SYNTAX  Dsx3TotalEntry
          MAX-ACCESS  not-accessible
          STATUS  current


          DESCRIPTION
                 "An entry in the DS3/E3 Total table."
         INDEX   { dsx3TotalIndex }
          ::= { dsx3TotalTable 1 }

     Dsx3TotalEntry ::=
          SEQUENCE {
              dsx3TotalIndex      InterfaceIndex,
              dsx3TotalPESs       PerfTotalCount,
              dsx3TotalPSESs      PerfTotalCount,
              dsx3TotalSEFSs      PerfTotalCount,
              dsx3TotalUASs       PerfTotalCount,
              dsx3TotalLCVs       PerfTotalCount,
              dsx3TotalPCVs       PerfTotalCount,
              dsx3TotalLESs       PerfTotalCount,
              dsx3TotalCCVs       PerfTotalCount,
              dsx3TotalCESs       PerfTotalCount,
              dsx3TotalCSESs      PerfTotalCount
          }

     dsx3TotalIndex OBJECT-TYPE
          SYNTAX  InterfaceIndex
          MAX-ACCESS  read-only
          STATUS  current
          DESCRIPTION
                 "The index value which uniquely identifies the
                 DS3/E3 interface to which this entry is
                 applicable.  The interface identified by a
                 particular value of this index is the same
                 interface as identified by the same value an
                 dsx3LineIndex object instance."
          ::= { dsx3TotalEntry 1 }

     dsx3TotalPESs OBJECT-TYPE
          SYNTAX  PerfTotalCount
          MAX-ACCESS  read-only
          STATUS  current
          DESCRIPTION
                 "The counter associated with the number of P-bit
                 Errored Seconds, encountered by a DS3 interface in
                 the previous 24 hour interval. Invalid 15 minute
                 intervals count as 0."
          ::= { dsx3TotalEntry 2 }

     dsx3TotalPSESs OBJECT-TYPE
          SYNTAX  PerfTotalCount
          MAX-ACCESS  read-only
          STATUS  current


          DESCRIPTION
                 "The counter associated with the number of P-bit
                 Severely Errored Seconds, encountered by a DS3
                 interface in the previous 24 hour interval.
                 Invalid 15 minute intervals count as 0."
          ::= { dsx3TotalEntry 3 }

     dsx3TotalSEFSs OBJECT-TYPE
          SYNTAX  PerfTotalCount
          MAX-ACCESS  read-only
          STATUS  current
          DESCRIPTION
                 "The counter associated with the number of
                 Severely Errored Framing Seconds, encountered by a
                 DS3/E3 interface in the previous 24 hour interval.
                 Invalid 15 minute intervals count as 0."
          ::= { dsx3TotalEntry 4 }

     dsx3TotalUASs OBJECT-TYPE
          SYNTAX  PerfTotalCount
          MAX-ACCESS  read-only
          STATUS  current
          DESCRIPTION
                 "The counter associated with the number of
                 Unavailable Seconds, encountered by a DS3
                 interface in the previous 24 hour interval.

                 Invalid 15 minute intervals count as 0."
          ::= { dsx3TotalEntry 5 }

     dsx3TotalLCVs OBJECT-TYPE
          SYNTAX  PerfTotalCount
          MAX-ACCESS  read-only
          STATUS  current
          DESCRIPTION
                 "The counter associated with the number of Line
                 Coding Violations encountered by a DS3/E3
                 interface in the previous 24 hour interval.
                 Invalid 15 minute intervals count as 0."
          ::= { dsx3TotalEntry 6 }

     dsx3TotalPCVs OBJECT-TYPE
          SYNTAX  PerfTotalCount
          MAX-ACCESS  read-only
          STATUS  current
          DESCRIPTION
                 "The counter associated with the number of P-bit
                 Coding Violations, encountered by a DS3 interface


                 in the previous 24 hour interval. Invalid 15
                 minute intervals count as 0."
          ::= { dsx3TotalEntry 7 }

     dsx3TotalLESs OBJECT-TYPE
          SYNTAX  PerfTotalCount
          MAX-ACCESS  read-only
          STATUS  current
          DESCRIPTION
                 "The number of Line Errored  Seconds  (BPVs  or
                 illegal  zero  sequences) encountered by a DS3/E3
                 interface in the previous 24 hour interval.
                 Invalid 15 minute intervals count as 0."
          ::= { dsx3TotalEntry 8 }

     dsx3TotalCCVs OBJECT-TYPE
          SYNTAX  PerfTotalCount
          MAX-ACCESS  read-only
          STATUS  current
          DESCRIPTION
                 "The number of C-bit Coding Violations encountered
                 by a DS3 interface in the previous 24 hour
                 interval. Invalid 15 minute intervals count as 0."
          ::= { dsx3TotalEntry 9 }

     dsx3TotalCESs OBJECT-TYPE
          SYNTAX  PerfTotalCount
          MAX-ACCESS  read-only
          STATUS  current
          DESCRIPTION
                 "The number of C-bit Errored Seconds encountered
                 by a DS3 interface in the previous 24 hour
                 interval. Invalid 15 minute intervals count as 0."
          ::= { dsx3TotalEntry 10 }

     dsx3TotalCSESs OBJECT-TYPE
          SYNTAX  PerfTotalCount
          MAX-ACCESS  read-only
          STATUS  current
          DESCRIPTION
                 "The number of C-bit Severely Errored Seconds
                 encountered by a DS3 interface in the previous 24
                 hour interval. Invalid 15 minute intervals count
                 as 0."
          ::= { dsx3TotalEntry 11 }

     -- The DS3 Far End Group


     -- The DS3 Far End Group consists of four tables :
     --   DS3 Far End Configuration
     --   DS3 Far End Current
     --   DS3 Far End Interval
     --   DS3 Far End Total

     -- The DS3 Far End Configuration Table

     dsx3FarEndConfigTable OBJECT-TYPE
          SYNTAX  SEQUENCE OF Dsx3FarEndConfigEntry
          MAX-ACCESS  not-accessible
          STATUS  current
          DESCRIPTION
                 "The DS3 Far End Configuration Table contains
                 configuration information reported in the C-bits
                 from the remote end."
          ::= { ds3 9 }

     dsx3FarEndConfigEntry OBJECT-TYPE
          SYNTAX  Dsx3FarEndConfigEntry
          MAX-ACCESS  not-accessible
          STATUS  current
          DESCRIPTION
                 "An entry in the DS3 Far End Configuration table."
         INDEX   { dsx3FarEndLineIndex }
          ::= { dsx3FarEndConfigTable 1 }

     Dsx3FarEndConfigEntry ::=
          SEQUENCE {
              dsx3FarEndLineIndex          InterfaceIndex,
             dsx3FarEndEquipCode           DisplayString,
             dsx3FarEndLocationIDCode      DisplayString,
             dsx3FarEndFrameIDCode         DisplayString,
             dsx3FarEndUnitCode            DisplayString,
             dsx3FarEndFacilityIDCode      DisplayString
          }

     dsx3FarEndLineIndex OBJECT-TYPE
          SYNTAX  InterfaceIndex
          MAX-ACCESS  read-only
          STATUS  current
          DESCRIPTION
                 "The index value which uniquely identifies the DS3
                 interface to which this entry is applicable.  The
                 interface identified by a particular value of this
                 index is the same interface as identified by the
                 same value an dsx3LineIndex object instance."


         ::= { dsx3FarEndConfigEntry 1 }

     dsx3FarEndEquipCode OBJECT-TYPE
          SYNTAX  DisplayString (SIZE (0..10))
          MAX-ACCESS  read-write
          STATUS  current
          DESCRIPTION
                 "This is the Far End Equipment Identification code
                 that describes the specific piece of equipment.
                 It is sent within the Path Identification
                 Message."
          ::= { dsx3FarEndConfigEntry 2 }

     dsx3FarEndLocationIDCode OBJECT-TYPE
          SYNTAX  DisplayString (SIZE (0..11))
          MAX-ACCESS  read-write
          STATUS  current
          DESCRIPTION
                 "This is the Far End Location Identification code
                 that describes the specific location of the
                 equipment.  It is sent within the Path
                 Identification Message."
          ::= { dsx3FarEndConfigEntry 3 }

     dsx3FarEndFrameIDCode OBJECT-TYPE
          SYNTAX  DisplayString (SIZE (0..10))
          MAX-ACCESS  read-write
          STATUS  current
          DESCRIPTION
                 "This is the Far End Frame Identification code
                 that identifies where the equipment is located
                 within a building at a given location.  It is sent
                 within the Path Identification Message."
          ::= { dsx3FarEndConfigEntry 4 }

     dsx3FarEndUnitCode OBJECT-TYPE
          SYNTAX  DisplayString (SIZE (0..6))
          MAX-ACCESS  read-write
          STATUS  current
          DESCRIPTION
                 "This is the Far End code that identifies the
                 equipment location within a bay.  It is sent
                 within the Path Identification Message."
          ::= { dsx3FarEndConfigEntry 5 }

     dsx3FarEndFacilityIDCode OBJECT-TYPE
          SYNTAX  DisplayString (SIZE (0..38))
          MAX-ACCESS  read-write


          STATUS  current
          DESCRIPTION
                 "This code identifies a specific Far End DS3 path.
                 It is sent within the Path Identification
                 Message."
          ::= { dsx3FarEndConfigEntry 6 }

     -- The DS3 Far End Current

     dsx3FarEndCurrentTable OBJECT-TYPE
          SYNTAX  SEQUENCE OF Dsx3FarEndCurrentEntry
          MAX-ACCESS  not-accessible
          STATUS  current
          DESCRIPTION
                 "The DS3 Far End Current table contains various
                 statistics being collected for the current 15
                 minute interval.  The statistics are collected
                 from the far end block error code within the C-
                 bits."
          ::= { ds3 10 }

     dsx3FarEndCurrentEntry OBJECT-TYPE
          SYNTAX  Dsx3FarEndCurrentEntry
          MAX-ACCESS  not-accessible
          STATUS  current
          DESCRIPTION
                 "An entry in the DS3 Far End Current table."
          INDEX   { dsx3FarEndCurrentIndex }
          ::= { dsx3FarEndCurrentTable 1 }

     Dsx3FarEndCurrentEntry ::=
          SEQUENCE {
              dsx3FarEndCurrentIndex        InterfaceIndex,
              dsx3FarEndTimeElapsed         INTEGER,
              dsx3FarEndValidIntervals      INTEGER,
              dsx3FarEndCurrentCESs         PerfCurrentCount,
              dsx3FarEndCurrentCSESs        PerfCurrentCount,
              dsx3FarEndCurrentCCVs         PerfCurrentCount,
              dsx3FarEndCurrentUASs         PerfCurrentCount,
              dsx3FarEndInvalidIntervals    INTEGER
         }

      dsx3FarEndCurrentIndex OBJECT-TYPE
          SYNTAX  InterfaceIndex
          MAX-ACCESS  read-only
          STATUS  current
          DESCRIPTION
                 "The index value which uniquely identifies the DS3


                 interface to which this entry is applicable.  The
                 interface identified by a particular value of this
                 index is identical to the interface identified by
                 the same value of dsx3LineIndex."
          ::= { dsx3FarEndCurrentEntry 1 }

     dsx3FarEndTimeElapsed OBJECT-TYPE
          SYNTAX  INTEGER (0..899)
          MAX-ACCESS  read-only
          STATUS  current
          DESCRIPTION
                 "The number of seconds that have elapsed since the
                 beginning of the far end current error-measurement
                 period.  If, for some reason, such as an
                 adjustment in the system's time-of-day clock, the
                 current interval exceeds the maximum value, the
                 agent will return the maximum value."
          ::= { dsx3FarEndCurrentEntry 2 }

     dsx3FarEndValidIntervals OBJECT-TYPE
          SYNTAX  INTEGER (0..96)
          MAX-ACCESS  read-only
          STATUS  current
          DESCRIPTION
                 "The number of previous far end intervals for
                 which data was collected.  The value will be
                 96 unless the interface was brought online within
                 the last 24 hours, in which case the value will be
                 the number of complete 15 minute far end intervals
                 since the interface has been online."
          ::= { dsx3FarEndCurrentEntry 3 }

     dsx3FarEndCurrentCESs OBJECT-TYPE
          SYNTAX  PerfCurrentCount
          MAX-ACCESS  read-only
          STATUS  current
          DESCRIPTION
                 "The counter associated with the number of Far Far
                 End C-bit Errored Seconds."
          ::= { dsx3FarEndCurrentEntry 4 }

     dsx3FarEndCurrentCSESs OBJECT-TYPE
          SYNTAX  PerfCurrentCount
          MAX-ACCESS  read-only
          STATUS  current
          DESCRIPTION
                 "The counter associated with the number of Far End
                 C-bit Severely Errored Seconds."


          ::= { dsx3FarEndCurrentEntry 5 }

     dsx3FarEndCurrentCCVs OBJECT-TYPE
          SYNTAX  PerfCurrentCount
          MAX-ACCESS  read-only
          STATUS  current
          DESCRIPTION
                 "The counter associated with the number of Far End
                 C-bit Coding Violations reported via the far end
                 block error count."
          ::= { dsx3FarEndCurrentEntry 6 }

     dsx3FarEndCurrentUASs OBJECT-TYPE
          SYNTAX  PerfCurrentCount
          MAX-ACCESS  read-only
          STATUS  current
          DESCRIPTION
                 "The counter associated with the number of Far End
                 unavailable seconds."
          ::= { dsx3FarEndCurrentEntry 7 }

     dsx3FarEndInvalidIntervals OBJECT-TYPE
          SYNTAX  INTEGER (0..96)
          MAX-ACCESS  read-only
          STATUS  current
          DESCRIPTION
                 "The number of intervals in the range from 0 to
                 dsx3FarEndValidIntervals for which no data is
                 available.  This object will typically be zero
                 except in cases where the data for some intervals
                 are not available (e.g., in proxy situations)."
          ::= { dsx3FarEndCurrentEntry 8 }

     -- The DS3 Far End Interval Table

     dsx3FarEndIntervalTable OBJECT-TYPE
          SYNTAX  SEQUENCE OF Dsx3FarEndIntervalEntry
          MAX-ACCESS  not-accessible
          STATUS  current
          DESCRIPTION
                 "The DS3 Far End Interval Table contains various
                 statistics collected by each DS3 interface over
                 the previous 24 hours of operation.  The past 24
                 hours are broken into 96 completed 15 minute
                 intervals."
          ::= { ds3 11 }

     dsx3FarEndIntervalEntry OBJECT-TYPE


          SYNTAX  Dsx3FarEndIntervalEntry
          MAX-ACCESS  not-accessible
          STATUS  current
          DESCRIPTION
                 "An entry in the DS3 Far End Interval table."
          INDEX   { dsx3FarEndIntervalIndex,
                    dsx3FarEndIntervalNumber }
          ::= { dsx3FarEndIntervalTable 1 }

     Dsx3FarEndIntervalEntry ::=
          SEQUENCE {
               dsx3FarEndIntervalIndex      InterfaceIndex,
               dsx3FarEndIntervalNumber     INTEGER,
               dsx3FarEndIntervalCESs       PerfIntervalCount,
               dsx3FarEndIntervalCSESs      PerfIntervalCount,
               dsx3FarEndIntervalCCVs       PerfIntervalCount,
               dsx3FarEndIntervalUASs       PerfIntervalCount,
               dsx3FarEndIntervalValidData  TruthValue
         }

     dsx3FarEndIntervalIndex OBJECT-TYPE
          SYNTAX  InterfaceIndex
          MAX-ACCESS  read-only
          STATUS  current
          DESCRIPTION
                 "The index value which uniquely identifies the DS3
                 interface to which this entry is applicable.  The
                 interface identified by a particular value of this
                 index is identical to the interface identified by
                 the same value of dsx3LineIndex."
          ::= { dsx3FarEndIntervalEntry 1 }

     dsx3FarEndIntervalNumber OBJECT-TYPE
         SYNTAX  INTEGER (1..96)
         MAX-ACCESS  read-only
         STATUS  current
         DESCRIPTION
                 "A number between 1 and 96, where 1 is the most
                 recently completed 15 minute interval and 96 is
                 the 15 minutes interval completed 23 hours and 45
                 minutes prior to interval 1."
         ::= { dsx3FarEndIntervalEntry 2 }

     dsx3FarEndIntervalCESs OBJECT-TYPE
         SYNTAX  PerfIntervalCount
         MAX-ACCESS  read-only
         STATUS  current
         DESCRIPTION


                 "The counter associated with the number of Far End
                 C-bit Errored Seconds encountered by a DS3
                 interface in one of the previous 96, individual 15
                 minute, intervals. In the case where the agent is
                 a proxy and data is not available, return
                 noSuchInstance."
        ::= { dsx3FarEndIntervalEntry 3 }

     dsx3FarEndIntervalCSESs OBJECT-TYPE
         SYNTAX  PerfIntervalCount
         MAX-ACCESS  read-only
         STATUS  current
         DESCRIPTION
                 "The counter associated with the number of Far End
                 C-bit Severely Errored Seconds."
        ::= { dsx3FarEndIntervalEntry 4 }

     dsx3FarEndIntervalCCVs OBJECT-TYPE
          SYNTAX  PerfIntervalCount
          MAX-ACCESS  read-only
          STATUS  current
          DESCRIPTION
                 "The counter associated with the number of Far End
                 C-bit Coding Violations reported via the far end
                 block error count."
          ::= { dsx3FarEndIntervalEntry 5 }

     dsx3FarEndIntervalUASs OBJECT-TYPE
          SYNTAX  PerfIntervalCount
          MAX-ACCESS  read-only
          STATUS  current
          DESCRIPTION
                 "The counter associated with the number of Far End
                 unavailable seconds."
          ::= { dsx3FarEndIntervalEntry 6 }

     dsx3FarEndIntervalValidData OBJECT-TYPE
          SYNTAX  TruthValue
          MAX-ACCESS  read-only
          STATUS  current
          DESCRIPTION
                 "This variable indicates if the data for this
                 interval is valid."
          ::= { dsx3FarEndIntervalEntry 7 }

     -- The DS3 Far End Total


     dsx3FarEndTotalTable OBJECT-TYPE
          SYNTAX  SEQUENCE OF Dsx3FarEndTotalEntry
          MAX-ACCESS  not-accessible
          STATUS  current
          DESCRIPTION
                 "The DS3 Far End Total Table contains the
                 cumulative sum of the various statistics for the
                 24 hour period preceding the current interval."
          ::= { ds3 12 }

     dsx3FarEndTotalEntry OBJECT-TYPE
          SYNTAX  Dsx3FarEndTotalEntry
          MAX-ACCESS  not-accessible
          STATUS  current
          DESCRIPTION
                 "An entry in the DS3 Far End Total table."
          INDEX   { dsx3FarEndTotalIndex }
          ::= { dsx3FarEndTotalTable 1 }

     Dsx3FarEndTotalEntry ::=
          SEQUENCE {
              dsx3FarEndTotalIndex       InterfaceIndex,
              dsx3FarEndTotalCESs        PerfTotalCount,
              dsx3FarEndTotalCSESs       PerfTotalCount,
              dsx3FarEndTotalCCVs        PerfTotalCount,
              dsx3FarEndTotalUASs        PerfTotalCount
          }

     dsx3FarEndTotalIndex OBJECT-TYPE
          SYNTAX  InterfaceIndex
          MAX-ACCESS  read-only
          STATUS  current
          DESCRIPTION
                 "The index value which uniquely identifies the DS3
                 interface to which this entry is applicable.  The
                 interface identified by a particular value of this
                 index is identical to the interface identified by
                 the same value of dsx3LineIndex."
          ::= { dsx3FarEndTotalEntry 1 }

     dsx3FarEndTotalCESs OBJECT-TYPE
         SYNTAX  PerfTotalCount
         MAX-ACCESS  read-only
         STATUS  current
         DESCRIPTION
                 "The counter associated with the number of Far End
                 C-bit Errored Seconds encountered by a DS3
                 interface in the previous 24 hour interval.


                 Invalid 15 minute intervals count as 0."
         ::= { dsx3FarEndTotalEntry 2 }

     dsx3FarEndTotalCSESs OBJECT-TYPE
         SYNTAX  PerfTotalCount
         MAX-ACCESS  read-only
         STATUS  current
         DESCRIPTION
                 "The counter associated with the number of Far End
                 C-bit Severely Errored Seconds encountered by a
                 DS3 interface in the previous 24 hour interval.
                 Invalid 15 minute intervals count as 0."
         ::= { dsx3FarEndTotalEntry 3 }

     dsx3FarEndTotalCCVs OBJECT-TYPE
         SYNTAX  PerfTotalCount
         MAX-ACCESS  read-only
         STATUS  current
         DESCRIPTION
                 "The counter associated with the number of Far End
                 C-bit Coding Violations reported via the far end
                 block error count encountered by a DS3 interface
                 in the previous 24 hour interval. Invalid 15
                 minute intervals count as 0."
         ::= { dsx3FarEndTotalEntry 4 }

     dsx3FarEndTotalUASs OBJECT-TYPE
         SYNTAX  PerfTotalCount
         MAX-ACCESS  read-only
         STATUS  current
         DESCRIPTION
                 "The counter associated with the number of Far End
                 unavailable seconds encountered by a DS3 interface
                 in the previous 24 hour interval.  Invalid 15
                 minute intervals count as 0."
         ::= { dsx3FarEndTotalEntry 5 }

     -- the DS3/E3 Fractional Table

     -- This table is deprecated.

     dsx3FracTable OBJECT-TYPE
         SYNTAX  SEQUENCE OF Dsx3FracEntry
         MAX-ACCESS  not-accessible
         STATUS  deprecated
         DESCRIPTION
                 "This table is deprecated in favour of using


                 ifStackTable.

                 Implementation of this table was optional.  It was
                 designed for those systems dividing a DS3/E3 into
                 channels containing different data streams that
                 are of local interest.

                 The DS3/E3 fractional table identifies which
                 DS3/E3 channels associated with a CSU are being
                 used to support a logical interface, i.e., an
                 entry in the interfaces table from the Internet-
                 standard MIB.

                 For example, consider a DS3 device with 4 high
                 speed links carrying router traffic, a feed for
                 voice, a feed for video, and a synchronous channel
                 for a non-routed protocol.  We might describe the
                 allocation of channels, in the dsx3FracTable, as
                 follows:
                 dsx3FracIfIndex.2. 1 = 3  dsx3FracIfIndex.2.15 = 4
                 dsx3FracIfIndex.2. 2 = 3  dsx3FracIfIndex.2.16 = 6
                 dsx3FracIfIndex.2. 3 = 3  dsx3FracIfIndex.2.17 = 6
                 dsx3FracIfIndex.2. 4 = 3  dsx3FracIfIndex.2.18 = 6
                 dsx3FracIfIndex.2. 5 = 3  dsx3FracIfIndex.2.19 = 6
                 dsx3FracIfIndex.2. 6 = 3  dsx3FracIfIndex.2.20 = 6
                 dsx3FracIfIndex.2. 7 = 4  dsx3FracIfIndex.2.21 = 6
                 dsx3FracIfIndex.2. 8 = 4  dsx3FracIfIndex.2.22 = 6
                 dsx3FracIfIndex.2. 9 = 4  dsx3FracIfIndex.2.23 = 6
                 dsx3FracIfIndex.2.10 = 4  dsx3FracIfIndex.2.24 = 6
                 dsx3FracIfIndex.2.11 = 4  dsx3FracIfIndex.2.25 = 6
                 dsx3FracIfIndex.2.12 = 5  dsx3FracIfIndex.2.26 = 6
                 dsx3FracIfIndex.2.13 = 5  dsx3FracIfIndex.2.27 = 6
                 dsx3FracIfIndex.2.14 = 5  dsx3FracIfIndex.2.28 = 6
                 For dsx3M23, dsx3 SYNTRAN, dsx3CbitParity, and
                 dsx3ClearChannel  there are 28 legal channels,
                 numbered 1 throug h 28.

                 For e3Framed there are 16 legal channels, numbered
                 1 through 16.  The channels (1..16) correspond
                 directly to the equivalently numbered time-slots."
          ::= { ds3 13 }

     dsx3FracEntry OBJECT-TYPE
          SYNTAX  Dsx3FracEntry
          MAX-ACCESS  not-accessible
          STATUS  deprecated
          DESCRIPTION
                         "An entry in the DS3 Fractional table."


         INDEX   { dsx3FracIndex, dsx3FracNumber }
         ::= { dsx3FracTable 1 }

     Dsx3FracEntry ::=
          SEQUENCE {
              dsx3FracIndex     INTEGER,
              dsx3FracNumber    INTEGER,
              dsx3FracIfIndex   INTEGER
         }

     dsx3FracIndex OBJECT-TYPE
         SYNTAX  INTEGER (1..'7fffffff'h)
         MAX-ACCESS  read-only
         STATUS  deprecated
         DESCRIPTION
                 "The index value which uniquely identifies  the
                 DS3  interface  to which this entry is applicable
                 The interface identified by a  particular value
                 of  this  index is the same interface as
                 identified by the same value  an  dsx3LineIndex
                 object instance."
        ::= { dsx3FracEntry 1 }

     dsx3FracNumber OBJECT-TYPE
         SYNTAX  INTEGER (1..31)
         MAX-ACCESS  read-only
         STATUS  deprecated
         DESCRIPTION
                 "The channel number for this entry."
        ::= { dsx3FracEntry 2 }

     dsx3FracIfIndex OBJECT-TYPE
         SYNTAX  INTEGER (1..'7fffffff'h)
         MAX-ACCESS  read-write
         STATUS  deprecated
         DESCRIPTION
                 "An index value that uniquely identifies an
                 interface.  The interface identified by a
                 particular value of this index is the same
                 interface as  identified by the same value an
                 ifIndex object instance. If no interface is
                 currently using a channel, the value should be
                 zero.  If a single interface occupies more  than
                 one  time slot,  that ifIndex value will be found
                 in multiple time slots."
        ::= { dsx3FracEntry 3 }


      -- Ds3 TRAPS

     ds3Traps OBJECT IDENTIFIER ::= { ds3 15 }

     dsx3LineStatusChange NOTIFICATION-TYPE
         OBJECTS { dsx3LineStatus,
                   dsx3LineStatusLastChange }
         STATUS  current
         DESCRIPTION
                 "A dsx3LineStatusChange trap is sent when the
                 value of an instance of dsx3LineStatus changes. It
                 can be utilized by an NMS to trigger polls.  When
                 the line status change results in a lower level
                 line status change (i.e. ds1), then no traps for
                 the lower level are sent."
                    ::= { ds3Traps 0 1 }

                 -- conformance information

                 ds3Conformance OBJECT IDENTIFIER ::= { ds3 14 }

                 ds3Groups      OBJECT IDENTIFIER ::= { ds3Conformance 1 }
                 ds3Compliances OBJECT IDENTIFIER ::= { ds3Conformance 2 }

                 -- compliance statements

                 ds3Compliance MODULE-COMPLIANCE
                     STATUS  current
                     DESCRIPTION
                             "The compliance statement for DS3/E3
                             interfaces."
         MODULE  -- this module
             MANDATORY-GROUPS { ds3NearEndConfigGroup,
                                ds3NearEndStatisticsGroup }

             GROUP       ds3FarEndGroup
             DESCRIPTION
                 "Implementation of this group is optional for all
                 systems that attach to a DS3 Interface.  However,
                 only C-bit Parity and SYNTRAN DS3 applications
                 have the capability (option) of providing this
                 information."


             GROUP       ds3NearEndOptionalConfigGroup
             DESCRIPTION
                 "Implementation of this group is optional for all
                 systems that attach to a DS3 interface."

             OBJECT      dsx3LineType
             MIN-ACCESS  read-only
             DESCRIPTION
                 "Write access for the line type is not required."

             OBJECT      dsx3LineCoding
             MIN-ACCESS  read-only
             DESCRIPTION
                 "Write access for the line coding is not
                 required."

             OBJECT      dsx3SendCode
             MIN-ACCESS  read-only
             DESCRIPTION
                 "Write access for the send code is not required."

             OBJECT      dsx3LoopbackConfig
             MIN-ACCESS  read-only
             DESCRIPTION
                 "Write access for loopbacks is not required."

             OBJECT      dsx3TransmitClockSource
             MIN-ACCESS  read-only
             DESCRIPTION
                 "Write access for the transmit clock source is not
                 required."

             OBJECT      dsx3LineLength
             MIN-ACCESS  read-only
             DESCRIPTION
                 "Write access for the line length is not
                 required."

             OBJECT      dsx3Channelization
             MIN-ACCESS  read-only
             DESCRIPTION
                 "Write access for the channelization is not
                 required."

         ::= { ds3Compliances 1 }

     -- units of conformance


     ds3NearEndConfigGroup  OBJECT-GROUP
         OBJECTS { dsx3LineIndex,
                   dsx3TimeElapsed,
                   dsx3ValidIntervals,
                   dsx3LineType,
                   dsx3LineCoding,
                   dsx3SendCode,
                   dsx3CircuitIdentifier,
                   dsx3LoopbackConfig,
                   dsx3LineStatus,
                   dsx3TransmitClockSource,
                   dsx3InvalidIntervals,
                   dsx3LineLength,
                   dsx3LoopbackStatus,
                   dsx3Channelization,
                   dsx3Ds1ForRemoteLoop }
         STATUS  current
         DESCRIPTION
                 "A collection of objects providing configuration
                 information applicable to all DS3/E3 interfaces."
         ::= { ds3Groups 1 }

     ds3NearEndStatisticsGroup OBJECT-GROUP
         OBJECTS { dsx3CurrentIndex,
                   dsx3CurrentPESs,
                   dsx3CurrentPSESs,
                   dsx3CurrentSEFSs,
                   dsx3CurrentUASs,
                   dsx3CurrentLCVs,
                   dsx3CurrentPCVs,
                   dsx3CurrentLESs,
                   dsx3CurrentCCVs,
                   dsx3CurrentCESs,
                   dsx3CurrentCSESs,
                   dsx3IntervalIndex,
                   dsx3IntervalNumber,
                   dsx3IntervalPESs,
                   dsx3IntervalPSESs,
                   dsx3IntervalSEFSs,
                   dsx3IntervalUASs,
                   dsx3IntervalLCVs,
                   dsx3IntervalPCVs,
                   dsx3IntervalLESs,
                   dsx3IntervalCCVs,
                   dsx3IntervalCESs,
                   dsx3IntervalCSESs,
                   dsx3IntervalValidData,
                   dsx3TotalIndex,


                   dsx3TotalPESs,
                   dsx3TotalPSESs,
                   dsx3TotalSEFSs,
                   dsx3TotalUASs,
                   dsx3TotalLCVs,
                   dsx3TotalPCVs,
                   dsx3TotalLESs,
                   dsx3TotalCCVs,
                   dsx3TotalCESs,
                   dsx3TotalCSESs }
         STATUS  current
         DESCRIPTION
                 "A collection of objects providing statistics
                 information applicable to all DS3/E3 interfaces."
         ::= { ds3Groups 2 }

     ds3FarEndGroup  OBJECT-GROUP
         OBJECTS { dsx3FarEndLineIndex,
                   dsx3FarEndEquipCode,
                   dsx3FarEndLocationIDCode,
                   dsx3FarEndFrameIDCode,
                   dsx3FarEndUnitCode,
                   dsx3FarEndFacilityIDCode,
                   dsx3FarEndCurrentIndex,
                   dsx3FarEndTimeElapsed,
                   dsx3FarEndValidIntervals,
                   dsx3FarEndCurrentCESs,
                   dsx3FarEndCurrentCSESs,
                   dsx3FarEndCurrentCCVs,
                   dsx3FarEndCurrentUASs,
                   dsx3FarEndInvalidIntervals,
                   dsx3FarEndIntervalIndex,
                   dsx3FarEndIntervalNumber,
                   dsx3FarEndIntervalCESs,
                   dsx3FarEndIntervalCSESs,
                   dsx3FarEndIntervalCCVs,
                   dsx3FarEndIntervalUASs,
                   dsx3FarEndIntervalValidData,
                   dsx3FarEndTotalIndex,
                   dsx3FarEndTotalCESs,
                   dsx3FarEndTotalCSESs,
                   dsx3FarEndTotalCCVs,
                   dsx3FarEndTotalUASs }
         STATUS  current
         DESCRIPTION
                 "A collection of objects providing remote
                 configuration and statistics information
                 applicable to C-bit Parity and SYNTRAN DS3


                 interfaces."
         ::= { ds3Groups 3 }

     ds3DeprecatedGroup OBJECT-GROUP
         OBJECTS { dsx3IfIndex,
                   dsx3FracIndex,
                   dsx3FracNumber,
                   dsx3FracIfIndex }
         STATUS  deprecated
         DESCRIPTION
                 "A collection of obsolete objects that may be
                 implemented for backwards compatibility."
         ::= { ds3Groups 4 }

     ds3NearEndOptionalConfigGroup OBJECT-GROUP
         OBJECTS { dsx3LineStatusLastChange,
                   dsx3LineStatusChangeTrapEnable }

         STATUS    current
         DESCRIPTION
                 "A collection of objects that may be implemented
                 on DS3/E3 interfaces."
         ::= { ds3Groups 5 }

     ds3NearEndOptionalTrapGroup NOTIFICATION-GROUP
         NOTIFICATIONS { dsx3LineStatusChange }
         STATUS    current
         DESCRIPTION
                 "A collection of notifications that may be
                 implemented on DS3/E3 interfaces."
         ::= { ds3Groups 6 }

END

ATM-FORUM-SNMP-M4-MIB DEFINITIONS ::= BEGIN

IMPORTS
     MODULE-IDENTITY, OBJECT-TYPE,
     NOTIFICATION-TYPE, OBJECT-IDENTITY,
     Integer32, IpAddress, Gauge32,
     Unsigned32, enterprises            FROM SNMPv2-SMI
     TEXTUAL-CONVENTION, DisplayString,
     AutonomousType, RowStatus,
     TestAndIncr, RowPointer,
     TruthValue, TimeStamp,
     DateAndTime, TimeInterval          FROM SNMPv2-TC
     MODULE-COMPLIANCE, OBJECT-GROUP,
     NOTIFICATION-GROUP                 FROM SNMPv2-CONF
     ifIndex, ifOperStatus, OwnerString FROM IF-MIB
     atmVplEntry, atmVplVpi,
     atmVplOperStatus,
     atmVclEntry, atmVclVpi, atmVclVci,
     atmVclOperStatus,
     atmVpCrossConnectEntry,
     atmVpCrossConnectL2HOperStatus,
     atmVpCrossConnectH2LOperStatus,
     atmVcCrossConnectEntry,
     atmVcCrossConnectL2HOperStatus,
     atmVcCrossConnectH2LOperStatus     FROM ATM-MIB
     entPhysicalIndex, entPhysicalClass,
     entPhysicalContainedIn,
     entPhysicalParentRelPos
                                        FROM ENTITY-MIB
     hrSWInstalledIndex,
     hrSWInstalledName                  FROM HOST-RESOURCES-MIB;


atmfM4MIB MODULE-IDENTITY
     LAST-UPDATED   "9805140000Z"
     ORGANIZATION   "The ATM Forum"
     CONTACT-INFO
           "The ATM Forum
            2570 West El Camino Real, Suite 304
            Mountain View, CA 94040-1313 USA
            Phone: +1 415-949-6700
            Fax:   +1 415-949-6705
            info@atmforum.com"
     DESCRIPTION
           "This MIB module is the SNMP version of the ATM Forum's
            M4 interface (network element view)."
     REVISION   "9805140000Z"
     DESCRIPTION
           "Initial version of MIB module ATM-FORUM-SNMP-M4-MIB."
    ::= { atmfM4SnmpNEView 1 }

atmForum                OBJECT IDENTIFIER ::= { enterprises 353 }
atmForumNetworkManagement    OBJECT IDENTIFIER ::= { atmForum 5 }
atmfM4      OBJECT IDENTIFIER ::= { atmForumNetworkManagement 1 }
atmfM4SnmpNEView               OBJECT IDENTIFIER ::= { atmfM4 3 }

atmfM4MIBObjects    OBJECT IDENTIFIER ::= { atmfM4MIB 1 }
atmfM4MIBTraps      OBJECT IDENTIFIER ::= { atmfM4MIB 2 }
atmfM4MIBTrapPrefix OBJECT IDENTIFIER ::= { atmfM4MIBTraps 0 }
atmfM4MIBConformance OBJECT IDENTIFIER ::= { atmfM4MIB 3 }

--   This MIB module consists of the following groups:
--        (1)   ATM NE High-Level Objects
--        (2)   Interfaces: Physical Path Termination Point Table
--        (3)   TC Adapter Table
--        (4)   ATM Cell Layer Interface Table
--        (5)   VPL Termination Point Table Extensions
--        (6)   VCL Termination Point Table Extensions
--        (7)   VP Cross-Connect Table Extensions
--        (8)   VC Cross-Connect Table Extensions
--        (9)   VP 'next VPI' Table
--        (10)  VC 'next VCI' Table
--        (11)  ATM Cell Protocol Monitoring Current Data Table
--        (12)  ATM Cell Protocol Monitoring History Data Table
--        (13)  ATM Cell Protocol Monitoring Error Log Table
--        (14)  TC Adapter Protocol Monitoring Current Data Table
--        (15)  TC Adapter Protocol Monitoring History Data Table
--        (16)  VPL UPC/NPC Disagreement Monitoring Current Data Table
--        (17)  VPL UPC/NPC Disagreement Monitoring History Data Table
--        (18)  VCL UPC/NPC Disagreement Monitoring Current Data Table
--        (19)  VCL UPC/NPC Disagreement Monitoring History Data Table
--        (20)  OAM Loopback Test Definitions
--        (21)  VPL/VPC Termination Point Test Table
--        (22)  VCL/VCC Termination Point Test Table
--        (23)  Equipment Table extension
--        (24)  Equipment Holder Table extension
--        (25)  Plug-In Unit Table extension
--        (26)  Hardware Unit/Running Software Relationship Table
--        (27)  Hardware Unit/Installed Software Relationship Table
--        (28)  Alarm Forwarding Discriminator Table
--        (29)  Trap Log Table
--        (30)  Trap Log Entry Table
--        (31)  Alarm Trap Log Entry Table extension
--        (32)  Notifications (traps)
--        (33)  Conformance statements


-- ATM Forum M4 ATM network element (NE) high-level objects

atmfM4NeVendor OBJECT-TYPE
     SYNTAX    DisplayString
     MAX-ACCESS     read-only
     STATUS    current
     DESCRIPTION
          "The vendor of the ATM network element."
     ::= { atmfM4MIBObjects 1 }

atmfM4NeVersion OBJECT-TYPE
     SYNTAX    AutonomousType
     MAX-ACCESS     read-only
     STATUS    current
     DESCRIPTION
          "The version of the ATM network element."
     ::= { atmfM4MIBObjects 2 }

atmfM4NeStartTime OBJECT-TYPE
     SYNTAX    DateAndTime
     MAX-ACCESS     read-only
     STATUS    current
     DESCRIPTION
          "The time at which the agent was last started; in other
          words, the time at which sysUpTime was zero."
     ::= { atmfM4MIBObjects 3 }

atmfM4NeAlarmSeverityIndex OBJECT-TYPE
     SYNTAX    Integer32
     MAX-ACCESS     read-write
     STATUS    current
     DESCRIPTION
          "An index into the alarm severity profile table, specifying
          the severity assignments for M4 alarms reported for the
          ATM network element.  The default value for this object is
          zero."
     ::= { atmfM4MIBObjects 4 }

atmfM4NeSuppressZeroStats OBJECT-TYPE
     SYNTAX    TruthValue
     MAX-ACCESS     read-write
     STATUS    current
     DESCRIPTION
          "When the value of this object is true, no entry will be
          created in any of the historical statistics tables for
          intervals in which all counts are zero.  The default value for
          this object is true(1)."
     ::= { atmfM4MIBObjects 5 }


-- ATM Forum M4 Interface Configuration Table Extensions
-- Physical Path Termination Point Layer

atmfM4PhysPathTpTable OBJECT-TYPE
     SYNTAX    SEQUENCE OF    AtmfM4PhysPathTpEntry
     MAX-ACCESS     not-accessible
     STATUS    current
     DESCRIPTION
          "The ATM Forum M4 interface Configuration table extensions
          for the physical path termination point."
     ::= { atmfM4MIBObjects 6 }

atmfM4PhysPathTpEntry OBJECT-TYPE
     SYNTAX    AtmfM4PhysPathTpEntry
     MAX-ACCESS     not-accessible
     STATUS    current
     DESCRIPTION
          "Columns conceptually added to the interface table
          entry for an ATM interface to model the physical path
          termination point.

          The row of the interface table modeling this object should
          also include columns for the TC Adapter object and the ATM
          interface table defined in RFC 1695.

          The interface table entry for the physical path TP
          fields of an ATM interface are set up without management
          system control (or else that setup is outside the
          scope of M4)."
     INDEX          { ifIndex }
     ::= { atmfM4PhysPathTpTable 1 }

AtmfM4PhysPathTpEntry ::= SEQUENCE {
     atmfM4PhysPathTpHwUnitIndex         Integer32,
     atmfM4PhysPathTpPortID              Integer32,
     atmfM4PhysPathTpAlarmSeverityIndex  Integer32
          }

atmfM4PhysPathTpHwUnitIndex OBJECT-TYPE
     SYNTAX    Integer32 (1..2147483647)
     MAX-ACCESS     read-only
     STATUS    current
     DESCRIPTION
          "Specifies the index of the entry in the entPhysicalTable
          that represents the device (i.e., card) on which the
          physical path terminates."
     ::= { atmfM4PhysPathTpEntry 1 }

atmfM4PhysPathTpPortID OBJECT-TYPE
     SYNTAX    Integer32 (1..2147483647)
     MAX-ACCESS     read-only
     STATUS    current
     DESCRIPTION
          "Identifies the port (within the card identified by the
          hardware unit index) on which the physical path terminates."
     ::= { atmfM4PhysPathTpEntry 2 }

atmfM4PhysPathTpAlarmSeverityIndex OBJECT-TYPE
     SYNTAX    Integer32
     MAX-ACCESS     read-write
     STATUS    current
     DESCRIPTION
          "Specifies the index of the entry in the communications
          alarm severity profile table that should be used.  The default
          value of this object is zero."
     ::= { atmfM4PhysPathTpEntry 3 }


-- ATM Forum M4 Interface Configuration Table Extensions
-- TC Adapter Layer

atmfM4TcAdapterTable OBJECT-TYPE
     SYNTAX    SEQUENCE OF    AtmfM4TcAdapterEntry
     MAX-ACCESS     not-accessible
     STATUS    current
     DESCRIPTION
          "The ATM Forum M4 interface Configuration table extensions
          for the TC Adapter."
     ::= { atmfM4MIBObjects 7 }

atmfM4TcAdapterEntry OBJECT-TYPE
     SYNTAX    AtmfM4TcAdapterEntry
     MAX-ACCESS     not-accessible
     STATUS    current
     DESCRIPTION
          "Columns conceptually added to the interface table
          entry for an ATM interface to model the TC Adapter.

          The row of the interface table modeling this object should
          also include columns for the physical path TP and the ATM
          interface table defined in RFC 1695.

          The interface table entry for the TC Adapter
          fields of an ATM interface are set up without management
          system control (or else that setup is outside the
          scope of M4)."
     INDEX          { ifIndex }
     ::= { atmfM4TcAdapterTable 1 }

AtmfM4TcAdapterEntry ::= SEQUENCE {
     atmfM4TcACellScrambling       TruthValue,
     atmfM4TcAlarmSeverityIndex    Integer32
          }

atmfM4TcACellScrambling OBJECT-TYPE
     SYNTAX    TruthValue
     MAX-ACCESS     read-write
     STATUS    current
     DESCRIPTION
          "This attribute is used by the management system to
          activate and deactivate the ATM cell scrambling function.
          When the value of this attribute is TRUE, cell scrambling
          on the interface is activated.

          This attribute shall be present only for interfaces that
          support the deactivation of cell scrambling.  The ATM Forum
          UNI specification requires cell scrambling for ATM/SONET
          interfaces but allows cell scrambling to be controlled
          (i.e., turned on and off) for ATM/DS3 interfaces.

          The default value of this object is true(1)."
     ::= { atmfM4TcAdapterEntry 1 }

atmfM4TcAlarmSeverityIndex OBJECT-TYPE
     SYNTAX    Integer32
     MAX-ACCESS     read-write
     STATUS    current
     DESCRIPTION
          "Specifies the index of the entry in the communications
          alarm severity profile table that should be used.  The
          default value of this object is zero."
     ::= { atmfM4TcAdapterEntry 2 }


-- ATM Forum M4 Interface Configuration Table Extensions
-- ATM Cell Layer

atmfM4AtmLayerTable OBJECT-TYPE
     SYNTAX    SEQUENCE OF    AtmfM4AtmLayerEntry
     MAX-ACCESS     not-accessible
     STATUS    current
     DESCRIPTION
          "The ATM Forum M4 interface Configuration table extensions
          for the ATM cell layer."
     ::= { atmfM4MIBObjects 8 }

atmfM4AtmLayerEntry OBJECT-TYPE
     SYNTAX    AtmfM4AtmLayerEntry
     MAX-ACCESS     not-accessible
     STATUS    current
     DESCRIPTION
          "Columns conceptually added to the interface table
          entry for an ATM interface to model the ATM cell layer.
          The row of the interface table modeling this object should
          also include columns for the physical path TP and TC Adapter
          object, as well as the ATM interface table defined in
          RFC 1695.

          The default configuration of an entry in this table is
          used whenever the entries for the physical path TP, etc.,
          are created.  The management system configures a UNI,
          B-ICI, or B-ISSI on the interface by first modifying the
          atmfM4IfType column (this can be done in the same SNMP
          set-request that sets up the other necessary variables."
     INDEX          { ifIndex }
     ::= { atmfM4AtmLayerTable 1 }

AtmfM4AtmLayerEntry ::= SEQUENCE {
     atmfM4IfType                  INTEGER,
     atmfM4IfLoopbackLocationCode  Integer32,
     atmfM4IfSubscriberAddress     DisplayString,
     atmfM4IfPreferredCarrier      DisplayString,
     atmfM4IfFarEndCarrierNetwork  DisplayString
          }

atmfM4IfType OBJECT-TYPE
     SYNTAX    INTEGER {
                    none(0),
                    uni(1),
                    bici(2),
                    bissi(3)
                         }
     MAX-ACCESS     read-write
     STATUS    current
     DESCRIPTION
          "Specifies the type of ATM cell layer interface defined
          on the physical path termination point modeled by this
          entry in the interface table.  The default value of this
          object is none(0)."
     ::= { atmfM4AtmLayerEntry 1 }

atmfM4IfLoopbackLocationCode OBJECT-TYPE
     SYNTAX    Integer32
     MAX-ACCESS     read-write
     STATUS    current
     DESCRIPTION
          "Specifies the code that shall exist in incoming OAM
          Loopback cells that are to be looped back at this
          interface.

          A value of zero shall indicate that the management system
          has not set any loopback location code for this interface.
          Therefore, zero should not be used as the actual loopback
          location code for any interface.

          This object shall be present only for table entries that
          represent an actual ATM cell layer interface (i.e., the
          atmfM4IfType is not none(0)).

          The default value of this object is zero."
     ::= { atmfM4AtmLayerEntry 2 }

atmfM4IfSubscriberAddress OBJECT-TYPE
     SYNTAX    DisplayString
     MAX-ACCESS     read-write
     STATUS    current
     DESCRIPTION
          "Specifies the address or newline-delimited list of
          addresses assigned to the UNI.

          This object shall be present only for table entries that
          represent a UNI interface.

          The default value of this object is the null string."
     ::= { atmfM4AtmLayerEntry 3 }

atmfM4IfPreferredCarrier OBJECT-TYPE
     SYNTAX    DisplayString
     MAX-ACCESS     read-write
     STATUS    current
     DESCRIPTION
          "Specifies the name of the default carrier to use when one
          is not explicitly identified in the call set-up message.

          This object shall be present only for table entries that
          represent a UNI interface and only when SVC services are
          supported.

          The default value of this object is the null string."
     ::= { atmfM4AtmLayerEntry 4 }

atmfM4IfFarEndCarrierNetwork OBJECT-TYPE
     SYNTAX    DisplayString
     MAX-ACCESS     read-write
     STATUS    current
     DESCRIPTION
          "Specifies the adjacent carrier to which the B-ICI
          transmission path is connected.

          This object shall be present only for table entries that
          represent a B-ICI interface and only when SVC services are
          supported.

          The default value of this object is the null string."
     ::= { atmfM4AtmLayerEntry 5 }




-- ATM Forum M4 VPL Termination Point Configuration Table Extensions

atmfM4VplTable OBJECT-TYPE
     SYNTAX    SEQUENCE OF    AtmfM4VplEntry
     MAX-ACCESS     not-accessible
     STATUS    current
     DESCRIPTION
          "The ATM Forum M4 VPL Termination Point Configuration
          table extensions.  This table augments the VPL
          configuration table in RFC 1695."
     ::= { atmfM4MIBObjects 9 }

atmfM4VplEntry OBJECT-TYPE
     SYNTAX    AtmfM4VplEntry
     MAX-ACCESS     not-accessible
     STATUS    current
     DESCRIPTION
          "Additional columns for the VPL configuration table entry."
     AUGMENTS { atmVplEntry }
     ::= { atmfM4VplTable 1 }

AtmfM4VplEntry ::= SEQUENCE {
     atmfM4VplSegEndPt        TruthValue
          }

atmfM4VplSegEndPt OBJECT-TYPE
     SYNTAX    TruthValue
     MAX-ACCESS     read-create
     STATUS    current
     DESCRIPTION
          "Specifies whether the VPL termination point is a segment
          end-point."
     DEFVAL    { false }
     ::= { atmfM4VplEntry 1 }


-- ATM Forum M4 VCL Termination Point Configuration Table Extensions

atmfM4VclTable OBJECT-TYPE
     SYNTAX    SEQUENCE OF    AtmfM4VclEntry
     MAX-ACCESS     not-accessible
     STATUS    current
     DESCRIPTION
          "The ATM Forum M4 VCL Termination Point Configuration
          table extensions.  This table augments the VCL
          configuration table in RFC 1695."
     ::= { atmfM4MIBObjects 10 }

atmfM4VclEntry OBJECT-TYPE
     SYNTAX    AtmfM4VclEntry
     MAX-ACCESS     not-accessible
     STATUS    current
     DESCRIPTION
          "Additional columns for the VCL configuration table entry."
     AUGMENTS { atmVclEntry }
     ::= { atmfM4VclTable 1 }

AtmfM4VclEntry ::= SEQUENCE {
     atmfM4VclSegEndPt        TruthValue
          }

atmfM4VclSegEndPt OBJECT-TYPE
     SYNTAX    TruthValue
     MAX-ACCESS     read-create
     STATUS    current
     DESCRIPTION
          "Specifies whether the VCL termination point is a segment
          end-point."
     DEFVAL    { false }
     ::= { atmfM4VclEntry 1 }


-- ATM Forum M4 VP Cross-Connect Table Extensions

atmfM4VpXConnTable OBJECT-TYPE
     SYNTAX    SEQUENCE OF    AtmfM4VpXConnEntry
     MAX-ACCESS     not-accessible
     STATUS    current
     DESCRIPTION
          "The ATM Forum M4 VP Cross-Connect Configuration
          table extensions.  This table augments the VP Cross-Connect
          configuration table in RFC 1695."
     ::= { atmfM4MIBObjects 11 }

atmfM4VpXConnEntry OBJECT-TYPE
     SYNTAX    AtmfM4VpXConnEntry
     MAX-ACCESS     not-accessible
     STATUS    current
     DESCRIPTION
          "Additional columns for the VP Cross-Connect table entry."
     AUGMENTS { atmVpCrossConnectEntry }
     ::= { atmfM4VpXConnTable 1 }

AtmfM4VpXConnEntry ::= SEQUENCE {
     atmfM4VpXConnRecover     TruthValue
          }

atmfM4VpXConnRecover OBJECT-TYPE
     SYNTAX    TruthValue
     MAX-ACCESS     read-create
     STATUS    current
     DESCRIPTION
          "If FALSE, this cross-connection will be removed on
          failure."
     DEFVAL    { true }
     ::= { atmfM4VpXConnEntry 1 }


-- ATM Forum M4 VC Cross-Connect Table Extensions

atmfM4VcXConnTable OBJECT-TYPE
     SYNTAX    SEQUENCE OF    AtmfM4VcXConnEntry
     MAX-ACCESS     not-accessible
     STATUS    current
     DESCRIPTION
          "The ATM Forum M4 VC Cross-Connect Configuration
          table extensions.  This table augments the VC Cross-Connect
          configuration table in RFC 1695."
     ::= { atmfM4MIBObjects 12 }

atmfM4VcXConnEntry OBJECT-TYPE
     SYNTAX    AtmfM4VcXConnEntry
     MAX-ACCESS     not-accessible
     STATUS    current
     DESCRIPTION
          "Additional columns for the VC Cross-Connect table entry."
     AUGMENTS { atmVcCrossConnectEntry }
     ::= { atmfM4VcXConnTable 1 }

AtmfM4VcXConnEntry ::= SEQUENCE {
     atmfM4VcXConnRecover     TruthValue
          }

atmfM4VcXConnRecover OBJECT-TYPE
     SYNTAX    TruthValue
     MAX-ACCESS     read-create
     STATUS    current
     DESCRIPTION
          "If FALSE, this cross-connection will be removed on
          failure."
     DEFVAL    { true }
     ::= { atmfM4VcXConnEntry 1 }


-- ATM Forum M4 VP "Next VPI" Table

atmfM4VpNextVpiTable OBJECT-TYPE
     SYNTAX    SEQUENCE OF    AtmfM4VpNextVpiEntry
     MAX-ACCESS     not-accessible
     STATUS    current
     DESCRIPTION
          "The ATM Forum M4 VP Next VPI value table.  This optional
          table supplies unused VPI values for use in creating
          entries in the atmVplTable."
     ::= { atmfM4MIBObjects 13 }

atmfM4VpNextVpiEntry OBJECT-TYPE
     SYNTAX    AtmfM4VpNextVpiEntry
     MAX-ACCESS     not-accessible
     STATUS    current
     DESCRIPTION
          "Each entry in this table represents the 'next' VPI
          value available for a given ATM interface.

          Each ATM interface (UNI, BICI, BISSI) automatically has
          an entry in this table associated with it."
     INDEX          { ifIndex }
     ::= { atmfM4VpNextVpiTable 1 }

AtmfM4VpNextVpiEntry ::= SEQUENCE {
     atmfM4VpNextVpiValue     INTEGER
          }

atmfM4VpNextVpiValue OBJECT-TYPE
     SYNTAX    INTEGER (-1..4095)
     MAX-ACCESS     read-only
     STATUS    current
     DESCRIPTION
          "This object contains an appropriate value to be used for
          atmVplVpi when creating entries in the atmVplTable.  The
          value -1 indicates that no unassigned entries are available.
          To obtain the atmVplVpi value for a new entry, the manager
          issues a management protocol retrieval operation to obtain
          the current value of this object.  After each retrieval, the
          agent should modify the value to the next unassigned index
          (or -1)."
     ::= { atmfM4VpNextVpiEntry 1 }


-- ATM Forum M4 VC "Next VCI" Table

atmfM4VcNextVciTable OBJECT-TYPE
     SYNTAX    SEQUENCE OF    AtmfM4VcNextVciEntry
     MAX-ACCESS     not-accessible
     STATUS    current
     DESCRIPTION
          "The ATM Forum M4 VC Next VCI value table.  This optional
          table supplies unused VCI values for use in creating
          entries in the atmVclTable."
     ::= { atmfM4MIBObjects 14 }

atmfM4VcNextVciEntry OBJECT-TYPE
     SYNTAX    AtmfM4VcNextVciEntry
     MAX-ACCESS     not-accessible
     STATUS    current
     DESCRIPTION
          "Each entry in this table represents the 'next' VCI
          value available for a given ATM interface.

          Each VPL Termination Point automatically has
          an entry in this table associated with it."
     INDEX          { ifIndex,
                    atmVplVpi }
     ::= { atmfM4VcNextVciTable 1 }

AtmfM4VcNextVciEntry ::= SEQUENCE {
     atmfM4VcNextVciValue     INTEGER
          }

atmfM4VcNextVciValue OBJECT-TYPE
     SYNTAX    INTEGER (-1..65535)
     MAX-ACCESS     read-only
     STATUS    current
     DESCRIPTION
          "This object contains an appropriate value to be used for
          atmVclVci when creating entries in the atmVclTable.  The
          value -1 indicates that no unassigned entries are available.
          To obtain the atmVclVci value for a new entry, the manager
          issues a management protocol retrieval operation to obtain
          the current value of this object.  After each retrieval, the
          agent should modify the value to the next unassigned index
          (or -1)."
     ::= { atmfM4VcNextVciEntry 1 }


-- ATM Cell Protocol Monitoring Current Data (per interface)

atmfM4CellProtoCurrTable OBJECT-TYPE
     SYNTAX    SEQUENCE OF    AtmfM4CellProtoCurrEntry
     MAX-ACCESS     not-accessible
     STATUS    current
     DESCRIPTION
          "The ATM Forum M4 Cell Protocol Monitoring Current Data
          table.

          This table maintains per-interface statistics for the
          fifteen-minute interval currently being collected."
     ::= { atmfM4MIBObjects 15 }

atmfM4CellProtoCurrEntry OBJECT-TYPE
     SYNTAX    AtmfM4CellProtoCurrEntry
     MAX-ACCESS     not-accessible
     STATUS    current
     DESCRIPTION
          "An entry in the ATM Forum M4 Cell Protocol Monitoring
          Current Data table.

          Each ATM interface (UNI, BICI, BISSI) automatically has
          an entry in this table associated with it."
     INDEX          { ifIndex }
     ::= { atmfM4CellProtoCurrTable 1 }

AtmfM4CellProtoCurrEntry ::= SEQUENCE {
     atmfM4CellProtoCurrSuspect         TruthValue,
     atmfM4CellProtoCurrElapsedTime     TimeInterval,
     atmfM4CellProtoCurrSupprIntvls     Gauge32,
     atmfM4CellProtoCurrProtoErrors     Gauge32,
     atmfM4CellProtoCurrInOAMCells      Gauge32
          }

atmfM4CellProtoCurrSuspect OBJECT-TYPE
     SYNTAX    TruthValue
     MAX-ACCESS     read-only
     STATUS    current
     DESCRIPTION
          "If true, the statistics in this entry may be unreliable."
     ::= { atmfM4CellProtoCurrEntry 1 }

atmfM4CellProtoCurrElapsedTime OBJECT-TYPE
     SYNTAX    TimeInterval
     MAX-ACCESS     read-only
     STATUS    current
     DESCRIPTION
          "Amount of time, measured in units of 0.01 second, that
          statistics for this entry (the current interval) have been
          counted."
     ::= { atmfM4CellProtoCurrEntry 2 }

atmfM4CellProtoCurrSupprIntvls OBJECT-TYPE
     SYNTAX    Gauge32
     MAX-ACCESS     read-only
     STATUS    current
     DESCRIPTION
          "This attribute is non-zero only if the ATM NE is
          suppressing ATM Cell Protocol Monitoring History Data
          entry creation when the current interval terminates with
          'all-zeroes' performance measurements.

          When non-zero, this attribute represents the number of
          'all-zeroes' intervals that were suppressed immediately
          prior to the current interval.

          Note that the suppression of 'all-zeroes' intervals is
          controlled by the atmfM4NeSuppressZeroStats object."
     ::= { atmfM4CellProtoCurrEntry 3 }

atmfM4CellProtoCurrProtoErrors OBJECT-TYPE
     SYNTAX    Gauge32
     MAX-ACCESS     read-only
     STATUS    current
     DESCRIPTION
          "The number of ATM cells dropped on this interface, due to
          an unrecognized field or set of fields in the ATM cell
          header, since the start of this interval."
     ::= { atmfM4CellProtoCurrEntry 4 }

atmfM4CellProtoCurrInOAMCells OBJECT-TYPE
     SYNTAX    Gauge32
     MAX-ACCESS     read-only
     STATUS    current
     DESCRIPTION
          "The number of OAM cells received at this interface since
          the start of this interval."
     ::= { atmfM4CellProtoCurrEntry 5 }


-- ATM Cell Protocol Monitoring History Data (per interface and time
-- interval)

atmfM4CellProtoHistTable OBJECT-TYPE
     SYNTAX    SEQUENCE OF    AtmfM4CellProtoHistEntry
     MAX-ACCESS     not-accessible
     STATUS    current
     DESCRIPTION
          "The ATM Forum M4 Cell Protocol Monitoring History Data
          table.

          This table maintains per-interface statistics for previous
          fifteen-minute intervals."
     ::= { atmfM4MIBObjects 16 }

atmfM4CellProtoHistEntry OBJECT-TYPE
     SYNTAX    AtmfM4CellProtoHistEntry
     MAX-ACCESS     not-accessible
     STATUS    current
     DESCRIPTION
          "An entry in the ATM Forum M4 Cell Protocol Monitoring
          History Data table.

          Each ATM interface (UNI, BICI, BISSI) automatically has
          an entry in this table associated with it for each fifteen-
          minute interval in which statistics are collected for it."
     INDEX          { ifIndex,
                    atmfM4CellProtoHistIndex }
     ::= { atmfM4CellProtoHistTable 1 }


AtmfM4CellProtoHistEntry ::= SEQUENCE {
     atmfM4CellProtoHistIndex           INTEGER,
     atmfM4CellProtoHistSuspect         TruthValue,
     atmfM4CellProtoHistElapsedTime     TimeInterval,
     atmfM4CellProtoHistSupprIntvls     Gauge32,
     atmfM4CellProtoHistProtoErrors     Gauge32,
     atmfM4CellProtoHistInOAMCells      Gauge32
          }

atmfM4CellProtoHistIndex OBJECT-TYPE
     SYNTAX    INTEGER (1..96)
     MAX-ACCESS     not-accessible
     STATUS    current
     DESCRIPTION
          "A number between 1 and 96, which identifies the interval
          for which the set of statistics in this entry was
          collected.

          The interval identified by 1 is the most recently completed
          15 minute interval, and the interval identified by N is the
          interval immediately preceding the one identified by N-1."
     ::= { atmfM4CellProtoHistEntry 1 }

atmfM4CellProtoHistSuspect OBJECT-TYPE
     SYNTAX    TruthValue
     MAX-ACCESS     read-only
     STATUS    current
     DESCRIPTION
          "If true, the statistics in this entry may be unreliable."
     ::= { atmfM4CellProtoHistEntry 2 }

atmfM4CellProtoHistElapsedTime OBJECT-TYPE
     SYNTAX    TimeInterval
     MAX-ACCESS     read-only
     STATUS    current
     DESCRIPTION
          "Amount of time, measured in units of 0.01 second, that
          statistics for this entry (the current interval) have been
          counted."
     ::= { atmfM4CellProtoHistEntry 3 }

atmfM4CellProtoHistSupprIntvls OBJECT-TYPE
     SYNTAX    Gauge32
     MAX-ACCESS     read-only
     STATUS    current
     DESCRIPTION
          "This attribute is non-zero only if the ATM NE is
          suppressing ATM Cell Protocol Monitoring History Data
          entry creation when the current interval terminates with
          'all-zeroes' performance measurements.

          When non-zero, this attribute represents the number of
          'all-zeroes' intervals that were suppressed immediately
          prior to this 'non-all-zeroes' history interval.

          Note that the suppression of 'all-zeroes' intervals is
          controlled by the atmfM4NeSuppressZeroStats object."
     ::= { atmfM4CellProtoHistEntry 4 }

atmfM4CellProtoHistProtoErrors OBJECT-TYPE
     SYNTAX    Gauge32
     MAX-ACCESS     read-only
     STATUS    current
     DESCRIPTION
          "The number of ATM cells dropped on this interface, due to
          an unrecognized field or set of fields in the ATM cell
          header, during this interval."
     ::= { atmfM4CellProtoHistEntry 5 }

atmfM4CellProtoHistInOAMCells OBJECT-TYPE
     SYNTAX    Gauge32
     MAX-ACCESS     read-only
     STATUS    current
     DESCRIPTION
          "The number of OAM cells received at this interface during
          this interval."
     ::= { atmfM4CellProtoHistEntry 6 }


-- ATM Cell Protocol Monitoring Error Log (per interface, error code)

atmfM4CellProtoErrorTable OBJECT-TYPE
     SYNTAX    SEQUENCE OF    AtmfM4CellProtoErrorEntry
     MAX-ACCESS     not-accessible
     STATUS    current
     DESCRIPTION
          "The ATM Forum M4 Cell Protocol Monitoring Error Log
          table.

          This table maintains a record of the last error of each
          type encountered on each interface, as a result of ATM
          Cell Protocol Monitoring."
     ::= { atmfM4MIBObjects 17 }

atmfM4CellProtoErrorEntry OBJECT-TYPE
     SYNTAX    AtmfM4CellProtoErrorEntry
     MAX-ACCESS     not-accessible
     STATUS    current
     DESCRIPTION
          "An entry in the ATM Forum M4 Cell Protocol Monitoring
          Error Log table.

          Each ATM interface (UNI, BICI, BISSI) automatically has
          an entry in this table associated with it for each error
          that has occurred since agent start-up."
     INDEX          { ifIndex,
                    atmfM4CellProtoErrorCode }
     ::= { atmfM4CellProtoErrorTable 1 }

AtmfM4CellProtoErrorEntry ::= SEQUENCE {
     atmfM4CellProtoErrorCode      Integer32,
     atmfM4CellProtoErrorTime      TimeStamp,
     atmfM4CellProtoErrorReason    INTEGER,
     atmfM4CellProtoErrorVpi       INTEGER,
     atmfM4CellProtoErrorVci       INTEGER
          }

atmfM4CellProtoErrorCode OBJECT-TYPE
     SYNTAX    Integer32 (0..2147483647)
     MAX-ACCESS     not-accessible
     STATUS    current
     DESCRIPTION
          "Indicates the type of error for which this entry contains
          information.  The range and interpretation of this error
          code value is left up to the individual agent implementor."
     ::= { atmfM4CellProtoErrorEntry 1 }

atmfM4CellProtoErrorTime OBJECT-TYPE
     SYNTAX    TimeStamp
     MAX-ACCESS     read-only
     STATUS    current
     DESCRIPTION
          "Value of sysUpTime when the error occurred."
     ::= { atmfM4CellProtoErrorEntry 2 }

atmfM4CellProtoErrorReason OBJECT-TYPE
     SYNTAX    INTEGER {
                    unassignedVpiVciValue(1),
                    outOfRangeVpiVciValue(2)
                         }
     MAX-ACCESS     read-only
     STATUS    current
     DESCRIPTION
          "The cell header abnormality type: the reason for discarding
          the ATM cell (i.e., unassigned VPI/VCI value or VPI/VCI
          value out of range)."
     ::= { atmfM4CellProtoErrorEntry 3 }

atmfM4CellProtoErrorVpi OBJECT-TYPE
     SYNTAX    INTEGER (0..4095)
     MAX-ACCESS     read-only
     STATUS    current
     DESCRIPTION
          "The VPI value of the discarded cell."
     ::= { atmfM4CellProtoErrorEntry 4 }

atmfM4CellProtoErrorVci OBJECT-TYPE
     SYNTAX    INTEGER (0..65535)
     MAX-ACCESS     read-only
     STATUS    current
     DESCRIPTION
          "The VCI value of the discarded cell."
     ::= { atmfM4CellProtoErrorEntry 5 }


-- TC Adapter Protocol Monitoring Current Data (per interface)

atmfM4TcProtoCurrTable OBJECT-TYPE
     SYNTAX    SEQUENCE OF    AtmfM4TcProtoCurrEntry
     MAX-ACCESS     not-accessible
     STATUS    current
     DESCRIPTION
          "The ATM Forum M4 TC Adapter Protocol Monitoring Current
          Data table.

          This table maintains per-interface statistics for the
          fifteen-minute interval currently being collected."
     ::= { atmfM4MIBObjects 18 }

atmfM4TcProtoCurrEntry OBJECT-TYPE
     SYNTAX    AtmfM4TcProtoCurrEntry
     MAX-ACCESS     not-accessible
     STATUS    current
     DESCRIPTION
          "An entry in the ATM Forum M4 TC Adapter Protocol Monitoring
          Current Data table.

          Each ATM interface (UNI, BICI, BISSI) automatically has
          an entry in this table associated with it."
     INDEX          { ifIndex }
     ::= { atmfM4TcProtoCurrTable 1 }

AtmfM4TcProtoCurrEntry ::= SEQUENCE {
     atmfM4TcProtoCurrSuspect           TruthValue,
     atmfM4TcProtoCurrElapsedTime       TimeInterval,
     atmfM4TcProtoCurrSupprIntvls       Gauge32,
     atmfM4TcProtoCurrDiscardHECViol    Gauge32
          }

atmfM4TcProtoCurrSuspect OBJECT-TYPE
     SYNTAX    TruthValue
     MAX-ACCESS     read-only
     STATUS    current
     DESCRIPTION
          "If true, the statistics in this entry may be unreliable."
     ::= { atmfM4TcProtoCurrEntry 1 }

atmfM4TcProtoCurrElapsedTime OBJECT-TYPE
     SYNTAX    TimeInterval
     MAX-ACCESS     read-only
     STATUS    current
     DESCRIPTION
          "Amount of time, measured in units of 0.01 second, that
          statistics for this entry (the current interval) have been
          counted."
     ::= { atmfM4TcProtoCurrEntry 2 }

atmfM4TcProtoCurrSupprIntvls OBJECT-TYPE
     SYNTAX    Gauge32
     MAX-ACCESS     read-only
     STATUS    current
     DESCRIPTION
          "This attribute is non-zero only if the ATM NE is
          suppressing ATM TC Adapter Protocol Monitoring History Data
          entry creation when the current interval terminates with
          'all-zeroes' performance measurements.

          When non-zero, this attribute represents the number of
          'all-zeroes' intervals that were suppressed immediately
          prior to the current interval.

          Note that the suppression of 'all-zeroes' intervals is
          controlled by the atmfM4NeSuppressZeroStats object."
     ::= { atmfM4TcProtoCurrEntry 3 }

atmfM4TcProtoCurrDiscardHECViol OBJECT-TYPE
     SYNTAX    Gauge32
     MAX-ACCESS     read-only
     STATUS    current
     DESCRIPTION
          "The number of ATM cells discarded on this interface, due to
          a HEC violation, since the start of this interval."
     ::= { atmfM4TcProtoCurrEntry 4 }


-- ATM TC Adapter Protocol Monitoring History Data (per interface and
-- time interval)

atmfM4TcProtoHistTable OBJECT-TYPE
     SYNTAX    SEQUENCE OF    AtmfM4TcProtoHistEntry
     MAX-ACCESS     not-accessible
     STATUS    current
     DESCRIPTION
          "The ATM Forum M4 TC Adapter Protocol Monitoring History
          Data table.

          This table maintains per-interface statistics for previous
          fifteen-minute intervals."
     ::= { atmfM4MIBObjects 19 }

atmfM4TcProtoHistEntry OBJECT-TYPE
     SYNTAX    AtmfM4TcProtoHistEntry
     MAX-ACCESS     not-accessible
     STATUS    current
     DESCRIPTION
          "An entry in the ATM Forum M4 TC Adapter Protocol Monitoring
          History Data table.

          Each ATM interface (UNI, BICI, BISSI) automatically has
          an entry in this table associated with it for each fifteen-
          minute interval in which statistics are collected for it."
     INDEX          { ifIndex,
                    atmfM4TcProtoHistIndex }
     ::= { atmfM4TcProtoHistTable 1 }

AtmfM4TcProtoHistEntry ::= SEQUENCE {
     atmfM4TcProtoHistIndex             INTEGER,
     atmfM4TcProtoHistSuspect           TruthValue,
     atmfM4TcProtoHistElapsedTime       TimeInterval,
     atmfM4TcProtoHistSupprIntvls       Gauge32,
     atmfM4TcProtoHistDiscardHECViol    Gauge32
          }

atmfM4TcProtoHistIndex OBJECT-TYPE
     SYNTAX    INTEGER (1..96)
     MAX-ACCESS     not-accessible
     STATUS    current
     DESCRIPTION
          "A number between 1 and 96, which identifies the interval
          for which the set of statistics in this entry was
          collected.

          The interval identified by 1 is the most recently completed
          15 minute interval, and the interval identified by N is the
          interval immediately preceding the one identified by N-1."
     ::= { atmfM4TcProtoHistEntry 1 }

atmfM4TcProtoHistSuspect OBJECT-TYPE
     SYNTAX    TruthValue
     MAX-ACCESS     read-only
     STATUS    current
     DESCRIPTION
          "If true, the statistics in this entry may be unreliable."
     ::= { atmfM4TcProtoHistEntry 2 }

atmfM4TcProtoHistElapsedTime OBJECT-TYPE
     SYNTAX    TimeInterval
     MAX-ACCESS     read-only
     STATUS    current
     DESCRIPTION
          "Amount of time, measured in units of 0.01 second, that
          statistics for this entry (the current interval) have been
          counted."
     ::= { atmfM4TcProtoHistEntry 3 }

atmfM4TcProtoHistSupprIntvls OBJECT-TYPE
     SYNTAX    Gauge32
     MAX-ACCESS     read-only
     STATUS    current
     DESCRIPTION
          "This attribute is non-zero only if the ATM NE is
          suppressing ATM Cell Protocol Monitoring History Data
          entry creation when the current interval terminates with
          'all-zeroes' performance measurements.

          When non-zero, this attribute represents the number of
          'all-zeroes' intervals that were suppressed immediately
          prior to this 'non-all-zeroes' history interval.

          Note that the suppression of 'all-zeroes' intervals is
          controlled by the atmfM4NeSuppressZeroStats object."
     ::= { atmfM4TcProtoHistEntry 4 }

atmfM4TcProtoHistDiscardHECViol OBJECT-TYPE
     SYNTAX    Gauge32
     MAX-ACCESS     read-only
     STATUS    current
     DESCRIPTION
          "The number of ATM cells discarded on this interface, due to
          a HEC violation, during this interval."
     ::= { atmfM4TcProtoHistEntry 5 }


-- UPC/NPC Disagreement Monitoring Current Data (per VPL
-- termination point)

atmfM4VpUpcNpcCurrTable OBJECT-TYPE
     SYNTAX    SEQUENCE OF    AtmfM4VpUpcNpcCurrEntry
     MAX-ACCESS     not-accessible
     STATUS    current
     DESCRIPTION
          "The ATM Forum M4 UPC/NPC Disagreement Monitoring Current
          Data table for VPL termination points.

          This table maintains per-TP statistics for the
          fifteen-minute interval currently being collected."
     ::= { atmfM4MIBObjects 20 }

atmfM4VpUpcNpcCurrEntry OBJECT-TYPE
     SYNTAX    AtmfM4VpUpcNpcCurrEntry
     MAX-ACCESS     not-accessible
     STATUS    current
     DESCRIPTION
          "An entry in the ATM Forum M4 UPC/NPC Disagreement
          Monitoring Current Data table for VPL termination points.

          Each VPL Termination Point automatically has
          an entry in this table associated with it."
     INDEX          { ifIndex,
                    atmVplVpi }
     ::= { atmfM4VpUpcNpcCurrTable 1 }

AtmfM4VpUpcNpcCurrEntry ::= SEQUENCE {
     atmfM4VpUpcNpcCurrSuspect          TruthValue,
     atmfM4VpUpcNpcCurrElapsedTime      TimeInterval,
     atmfM4VpUpcNpcCurrSupprIntvls      Gauge32,
     atmfM4VpUpcNpcCurrDiscardedCells   Gauge32,
     atmfM4VpUpcNpcCurrDiscardedClp0    Gauge32,
     atmfM4VpUpcNpcCurrPassedCells      Gauge32,
     atmfM4VpUpcNpcCurrPassedClp0       Gauge32
          }

atmfM4VpUpcNpcCurrSuspect OBJECT-TYPE
     SYNTAX    TruthValue
     MAX-ACCESS     read-only
     STATUS    current
     DESCRIPTION
          "If true, the statistics in this entry may be unreliable."
     ::= { atmfM4VpUpcNpcCurrEntry 1 }

atmfM4VpUpcNpcCurrElapsedTime OBJECT-TYPE
     SYNTAX    TimeInterval
     MAX-ACCESS     read-only
     STATUS    current
     DESCRIPTION
          "Amount of time, measured in units of 0.01 second, that
          statistics for this entry (the current interval) have been
          counted."
     ::= { atmfM4VpUpcNpcCurrEntry 2 }

atmfM4VpUpcNpcCurrSupprIntvls OBJECT-TYPE
     SYNTAX    Gauge32
     MAX-ACCESS     read-only
     STATUS    current
     DESCRIPTION
          "This attribute is non-zero only if the ATM NE is
          suppressing UPC/NPC Disagreement Monitoring History Data
          entry creation when the current interval terminates with
          'all-zeroes' performance measurements.

          When non-zero, this attribute represents the number of
          'all-zeroes' intervals that were suppressed immediately
          prior to the current interval.

          Note that the suppression of 'all-zeroes' intervals is
          controlled by the atmfM4NeSuppressZeroStats object."
     ::= { atmfM4VpUpcNpcCurrEntry 3 }

atmfM4VpUpcNpcCurrDiscardedCells OBJECT-TYPE
     SYNTAX    Gauge32
     MAX-ACCESS     read-only
     STATUS    current
     DESCRIPTION
          "The number of discarded cells due to combined CLP=0 and
          CLP=1 UPC/NPC policing."
     ::= { atmfM4VpUpcNpcCurrEntry 4 }

atmfM4VpUpcNpcCurrDiscardedClp0 OBJECT-TYPE
     SYNTAX    Gauge32
     MAX-ACCESS     read-only
     STATUS    current
     DESCRIPTION
          "The number of discarded CLP=0 cells due to CLP=0 only
          UPC/NPC policing.

          This object shall be present only if CLP=0 traffic is
          separately policed."
     ::= { atmfM4VpUpcNpcCurrEntry 5 }

atmfM4VpUpcNpcCurrPassedCells OBJECT-TYPE
     SYNTAX    Gauge32
     MAX-ACCESS     read-only
     STATUS    current
     DESCRIPTION
          "The number of cells that have been successfully passed by
          the combined CLP=0 and CLP=1 UPC/NPC policing."
     ::= { atmfM4VpUpcNpcCurrEntry 6 }

atmfM4VpUpcNpcCurrPassedClp0 OBJECT-TYPE
     SYNTAX    Gauge32
     MAX-ACCESS     read-only
     STATUS    current
     DESCRIPTION
          "The number of CLP=0 cells that have been successfully
          passed by the CLP=0 UPC/NPC policing.

          This object shall be present only if CLP=0 traffic is
          separately policed."
     ::= { atmfM4VpUpcNpcCurrEntry 7 }


-- UPC/NPC Disagreement Monitoring History (per VPL termination
-- point and time interval)

atmfM4VpUpcNpcHistTable OBJECT-TYPE
     SYNTAX    SEQUENCE OF    AtmfM4VpUpcNpcHistEntry
     MAX-ACCESS     not-accessible
     STATUS    current
     DESCRIPTION
          "The ATM Forum M4 UPC/NPC Disagreement Monitoring History
          Data table for VPL termination points.

          This table maintains per-interface statistics for previous
          fifteen-minute intervals."
     ::= { atmfM4MIBObjects 21 }

atmfM4VpUpcNpcHistEntry OBJECT-TYPE
     SYNTAX    AtmfM4VpUpcNpcHistEntry
     MAX-ACCESS     not-accessible
     STATUS    current
     DESCRIPTION
          "An entry in the ATM Forum M4 UPC/NPC Disagreement
          Monitoring History Data table for VPL termination points.

          Each VPL Termination Point automatically has
          an entry in this table associated with it."
     INDEX          { ifIndex,
                    atmVplVpi,
                    atmfM4VpUpcNpcHistIndex }
     ::= { atmfM4VpUpcNpcHistTable 1 }

AtmfM4VpUpcNpcHistEntry ::= SEQUENCE {
     atmfM4VpUpcNpcHistIndex            INTEGER,
     atmfM4VpUpcNpcHistSuspect          TruthValue,
     atmfM4VpUpcNpcHistElapsedTime      TimeInterval,
     atmfM4VpUpcNpcHistSupprIntvls      Gauge32,
     atmfM4VpUpcNpcHistDiscardedCells   Gauge32,
     atmfM4VpUpcNpcHistDiscardedClp0    Gauge32,
     atmfM4VpUpcNpcHistPassedCells      Gauge32,
     atmfM4VpUpcNpcHistPassedClp0       Gauge32
          }

atmfM4VpUpcNpcHistIndex OBJECT-TYPE
     SYNTAX    INTEGER (1..96)
     MAX-ACCESS     not-accessible
     STATUS    current
     DESCRIPTION
          "A number between 1 and 96, which identifies the interval
          for which the set of statistics in this entry was
          collected.

          The interval identified by 1 is the most recently completed
          15 minute interval, and the interval identified by N is the
          interval immediately preceding the one identified by N-1."
     ::= { atmfM4VpUpcNpcHistEntry 1 }

atmfM4VpUpcNpcHistSuspect OBJECT-TYPE
     SYNTAX    TruthValue
     MAX-ACCESS     read-only
     STATUS    current
     DESCRIPTION
          "If true, the statistics in this entry may be unreliable."
     ::= { atmfM4VpUpcNpcHistEntry 2 }

atmfM4VpUpcNpcHistElapsedTime OBJECT-TYPE
     SYNTAX    TimeInterval
     MAX-ACCESS     read-only
     STATUS    current
     DESCRIPTION
          "Amount of time, measured in units of 0.01 second, that
          statistics for this entry (the current interval) have been
          counted."
     ::= { atmfM4VpUpcNpcHistEntry 3 }

atmfM4VpUpcNpcHistSupprIntvls OBJECT-TYPE
     SYNTAX    Gauge32
     MAX-ACCESS     read-only
     STATUS    current
     DESCRIPTION
          "This attribute is non-zero only if the ATM NE is
          suppressing UPC/NPC Disagreement Monitoring History Data
          entry creation when the current interval terminates with
          'all-zeroes' performance measurements.

          When non-zero, this attribute represents the number of
          'all-zeroes' intervals that were suppressed immediately
          prior to this 'non-all-zeroes' history interval.

          Note that the suppression of 'all-zeroes' intervals is
          controlled by the atmfM4NeSuppressZeroStats object."
     ::= { atmfM4VpUpcNpcHistEntry 4 }

atmfM4VpUpcNpcHistDiscardedCells OBJECT-TYPE
     SYNTAX    Gauge32
     MAX-ACCESS     read-only
     STATUS    current
     DESCRIPTION
          "The number of discarded cells due to combined CLP=0 and
          CLP=1 UPC/NPC policing."
     ::= { atmfM4VpUpcNpcHistEntry 5 }

atmfM4VpUpcNpcHistDiscardedClp0 OBJECT-TYPE
     SYNTAX    Gauge32
     MAX-ACCESS     read-only
     STATUS    current
     DESCRIPTION
          "The number of discarded CLP=0 cells due to CLP=0 only
          UPC/NPC policing.

          This object shall be present only if CLP=0 traffic is
          separately policed."
     ::= { atmfM4VpUpcNpcHistEntry 6 }

atmfM4VpUpcNpcHistPassedCells OBJECT-TYPE
     SYNTAX    Gauge32
     MAX-ACCESS     read-only
     STATUS    current
     DESCRIPTION
          "The number of cells that have been successfully passed by
          the combined CLP=0 and CLP=1 UPC/NPC policing."
     ::= { atmfM4VpUpcNpcHistEntry 7 }

atmfM4VpUpcNpcHistPassedClp0 OBJECT-TYPE
     SYNTAX    Gauge32
     MAX-ACCESS     read-only
     STATUS    current
     DESCRIPTION
          "The number of CLP=0 cells that have been successfully
          passed by the CLP=0 UPC/NPC policing.

          This object shall be present only if CLP=0 traffic is
          separately policed."
     ::= { atmfM4VpUpcNpcHistEntry 8 }



-- UPC/NPC Disagreement Monitoring Current Data (per VCL
-- termination point)

atmfM4VcUpcNpcCurrTable OBJECT-TYPE
     SYNTAX    SEQUENCE OF    AtmfM4VcUpcNpcCurrEntry
     MAX-ACCESS     not-accessible
     STATUS    current
     DESCRIPTION
          "The ATM Forum M4 UPC/NPC Disagreement Monitoring Current
          Data table for VCL termination points.

          This table maintains per-TP statistics for the
          fifteen-minute interval currently being collected."
     ::= { atmfM4MIBObjects 22 }

atmfM4VcUpcNpcCurrEntry OBJECT-TYPE
     SYNTAX    AtmfM4VcUpcNpcCurrEntry
     MAX-ACCESS     not-accessible
     STATUS    current
     DESCRIPTION
          "An entry in the ATM Forum M4 UPC/NPC Disagreement
          Monitoring Current Data table for VCL termination points.

          Each VCL Termination Point automatically has
          an entry in this table associated with it."
     INDEX          { ifIndex,
                    atmVclVpi,
                    atmVclVci }
     ::= { atmfM4VcUpcNpcCurrTable 1 }

AtmfM4VcUpcNpcCurrEntry ::= SEQUENCE {
     atmfM4VcUpcNpcCurrSuspect          TruthValue,
     atmfM4VcUpcNpcCurrElapsedTime      TimeInterval,
     atmfM4VcUpcNpcCurrSupprIntvls      Gauge32,
     atmfM4VcUpcNpcCurrDiscardedCells   Gauge32,
     atmfM4VcUpcNpcCurrDiscardedClp0    Gauge32,
     atmfM4VcUpcNpcCurrPassedCells      Gauge32,
     atmfM4VcUpcNpcCurrPassedClp0       Gauge32
          }

atmfM4VcUpcNpcCurrSuspect OBJECT-TYPE
     SYNTAX    TruthValue
     MAX-ACCESS     read-only
     STATUS    current
     DESCRIPTION
          "If true, the statistics in this entry may be unreliable."
     ::= { atmfM4VcUpcNpcCurrEntry 1 }

atmfM4VcUpcNpcCurrElapsedTime OBJECT-TYPE
     SYNTAX    TimeInterval
     MAX-ACCESS     read-only
     STATUS    current
     DESCRIPTION
          "Amount of time, measured in units of 0.01 second, that
          statistics for this entry (the current interval) have been
          counted."
     ::= { atmfM4VcUpcNpcCurrEntry 2 }

atmfM4VcUpcNpcCurrSupprIntvls OBJECT-TYPE
     SYNTAX    Gauge32
     MAX-ACCESS     read-only
     STATUS    current
     DESCRIPTION
          "This attribute is non-zero only if the ATM NE is
          suppressing UPC/NPC Disagreement Monitoring History Data
          entry creation when the current interval terminates with
          'all-zeroes' performance measurements.

          When non-zero, this attribute represents the number of
          'all-zeroes' intervals that were suppressed immediately
          prior to the current interval.

          Note that the suppression of 'all-zeroes' intervals is
          controlled by the atmfM4NeSuppressZeroStats object."
     ::= { atmfM4VcUpcNpcCurrEntry 3 }

atmfM4VcUpcNpcCurrDiscardedCells OBJECT-TYPE
     SYNTAX    Gauge32
     MAX-ACCESS     read-only
     STATUS    current
     DESCRIPTION
          "The number of discarded cells due to combined CLP=0 and
          CLP=1 UPC/NPC policing."
     ::= { atmfM4VcUpcNpcCurrEntry 4 }

atmfM4VcUpcNpcCurrDiscardedClp0 OBJECT-TYPE
     SYNTAX    Gauge32
     MAX-ACCESS     read-only
     STATUS    current
     DESCRIPTION
          "The number of discarded CLP=0 cells due to CLP=0 only
          UPC/NPC policing.

          This object shall be present only if CLP=0 traffic is
          separately policed."
     ::= { atmfM4VcUpcNpcCurrEntry 5 }

atmfM4VcUpcNpcCurrPassedCells OBJECT-TYPE
     SYNTAX    Gauge32
     MAX-ACCESS     read-only
     STATUS    current
     DESCRIPTION
          "The number of cells that have been successfully passed by
          the combined CLP=0 and CLP=1 UPC/NPC policing."
     ::= { atmfM4VcUpcNpcCurrEntry 6 }

atmfM4VcUpcNpcCurrPassedClp0 OBJECT-TYPE
     SYNTAX    Gauge32
     MAX-ACCESS     read-only
     STATUS    current
     DESCRIPTION
          "The number of CLP=0 cells that have been successfully
          passed by the CLP=0 UPC/NPC policing.

          This object shall be present only if CLP=0 traffic is
          separately policed."
     ::= { atmfM4VcUpcNpcCurrEntry 7 }


-- UPC/NPC Disagreement Monitoring History (per VCL termination
-- point and time interval)

atmfM4VcUpcNpcHistTable OBJECT-TYPE
     SYNTAX    SEQUENCE OF    AtmfM4VcUpcNpcHistEntry
     MAX-ACCESS     not-accessible
     STATUS    current
     DESCRIPTION
          "The ATM Forum M4 UPC/NPC Disagreement Monitoring History
          Data table for VCL termination points.

          This table maintains per-interface statistics for previous
          fifteen-minute intervals."
     ::= { atmfM4MIBObjects 23 }

atmfM4VcUpcNpcHistEntry OBJECT-TYPE
     SYNTAX    AtmfM4VcUpcNpcHistEntry
     MAX-ACCESS     not-accessible
     STATUS    current
     DESCRIPTION
          "An entry in the ATM Forum M4 UPC/NPC Disagreement
          Monitoring History Data table for VCL termination points.

          Each VCL Termination Point automatically has
          an entry in this table associated with it."
     INDEX          { ifIndex,
                    atmVclVpi,
                    atmVclVci,
                    atmfM4VcUpcNpcHistIndex }
     ::= { atmfM4VcUpcNpcHistTable 1 }

AtmfM4VcUpcNpcHistEntry ::= SEQUENCE {
     atmfM4VcUpcNpcHistIndex            INTEGER,
     atmfM4VcUpcNpcHistSuspect          TruthValue,
     atmfM4VcUpcNpcHistElapsedTime      TimeInterval,
     atmfM4VcUpcNpcHistSupprIntvls      Gauge32,
     atmfM4VcUpcNpcHistDiscardedCells   Gauge32,
     atmfM4VcUpcNpcHistDiscardedClp0    Gauge32,
     atmfM4VcUpcNpcHistPassedCells      Gauge32,
     atmfM4VcUpcNpcHistPassedClp0       Gauge32
          }

atmfM4VcUpcNpcHistIndex OBJECT-TYPE
     SYNTAX    INTEGER (1..96)
     MAX-ACCESS     not-accessible
     STATUS    current
     DESCRIPTION
          "A number between 1 and 96, which identifies the interval
          for which the set of statistics in this entry was
          collected.

          The interval identified by 1 is the most recently completed
          15 minute interval, and the interval identified by N is the
          interval immediately preceding the one identified by N-1."
     ::= { atmfM4VcUpcNpcHistEntry 1 }

atmfM4VcUpcNpcHistSuspect OBJECT-TYPE
     SYNTAX    TruthValue
     MAX-ACCESS     read-only
     STATUS    current
     DESCRIPTION
          "If true, the statistics in this entry may be unreliable."
     ::= { atmfM4VcUpcNpcHistEntry 2 }

atmfM4VcUpcNpcHistElapsedTime OBJECT-TYPE
     SYNTAX    TimeInterval
     MAX-ACCESS     read-only
     STATUS    current
     DESCRIPTION
          "Amount of time, measured in units of 0.01 second, that
          statistics for this entry (the current interval) have been
          counted."
     ::= { atmfM4VcUpcNpcHistEntry 3 }

atmfM4VcUpcNpcHistSupprIntvls OBJECT-TYPE
     SYNTAX    Gauge32
     MAX-ACCESS     read-only
     STATUS    current
     DESCRIPTION
          "This attribute is non-zero only if the ATM NE is
          suppressing UPC/NPC Disagreement Monitoring History Data
          entry creation when the current interval terminates with
          'all-zeroes' performance measurements.

          When non-zero, this attribute represents the number of
          'all-zeroes' intervals that were suppressed immediately
          prior to this 'non-all-zeroes' history interval.

          Note that the suppression of 'all-zeroes' intervals is
          controlled by the atmfM4NeSuppressZeroStats object."
     ::= { atmfM4VcUpcNpcHistEntry 4 }

atmfM4VcUpcNpcHistDiscardedCells OBJECT-TYPE
     SYNTAX    Gauge32
     MAX-ACCESS     read-only
     STATUS    current
     DESCRIPTION
          "The number of discarded cells due to combined CLP=0 and
          CLP=1 UPC/NPC policing."
     ::= { atmfM4VcUpcNpcHistEntry 5 }

atmfM4VcUpcNpcHistDiscardedClp0 OBJECT-TYPE
     SYNTAX    Gauge32
     MAX-ACCESS     read-only
     STATUS    current
     DESCRIPTION
          "The number of discarded CLP=0 cells due to CLP=0 only
          UPC/NPC policing.

          This object shall be present only if CLP=0 traffic is
          separately policed."
     ::= { atmfM4VcUpcNpcHistEntry 6 }

atmfM4VcUpcNpcHistPassedCells OBJECT-TYPE
     SYNTAX    Gauge32
     MAX-ACCESS     read-only
     STATUS    current
     DESCRIPTION
          "The number of cells that have been successfully passed by
          the combined CLP=0 and CLP=1 UPC/NPC policing."
     ::= { atmfM4VcUpcNpcHistEntry 7 }

atmfM4VcUpcNpcHistPassedClp0 OBJECT-TYPE
     SYNTAX    Gauge32
     MAX-ACCESS     read-only
     STATUS    current
     DESCRIPTION
          "The number of CLP=0 cells that have been successfully
          passed by the CLP=0 UPC/NPC policing.

          This object shall be present only if CLP=0 traffic is
          separately policed."
     ::= { atmfM4VcUpcNpcHistEntry 8 }


-- ATM Forum M4 Test Types

atmfM4TestTypes     OBJECT IDENTIFIER
     ::= { atmfM4MIBObjects 24 }


-- OAM Loopback Tests (VPL, VPC, VCL, and VCC termination points):

atmfM4TestOAMLoopbackSeg OBJECT-IDENTITY
     STATUS    current
     DESCRIPTION
          "This identifies an OAM Loopback Test on a VPL, VPC,
          VCL, or VCC termination point, using a segment OAM
          cell.

          The test type must have appended to it a code that uniquely
          identifies an intermediate point responsible for looping
          back the cell.  If this is absent, the loopback is performed
          at the end of the segment or connection.

          E.g., the OID { atmfM4TestOAMLoopbackSeg 5 } identifies
          that the loopback should be performed at the intermediate
          point labeled 5."
     ::= { atmfM4TestTypes 1 }

atmfM4TestOAMLoopbackE2E OBJECT-IDENTITY
     STATUS    current
     DESCRIPTION
          "This identifies an OAM Loopback Test on a VPL, VPC,
          VCL, or VCC termination point, using an end-to-end OAM
          cell."
     ::= { atmfM4TestTypes 2 }


-- ATM Forum M4 VP Termination Point Test Table

atmfM4VpTestTable OBJECT-TYPE
     SYNTAX    SEQUENCE OF    AtmfM4VpTestEntry
     MAX-ACCESS     not-accessible
     STATUS    current
     DESCRIPTION
          "The ATM Forum M4 VP Termination Point Test table.
          This table allows tests to be run on VPL and VPC
          termination points.

          The operation of this table is entirely analogous to
          that of the ifTestTable in RFC 1573 (which was later
          deprecated in RFC 2233), except that the indexes into
          this table are different."
     ::= { atmfM4MIBObjects 25 }

atmfM4VpTestEntry OBJECT-TYPE
     SYNTAX    AtmfM4VpTestEntry
     MAX-ACCESS     not-accessible
     STATUS    current
     DESCRIPTION
          "An entry containing objects for invoking tests on a
          VPL or VPC termination point."
     INDEX          { ifIndex,
                    atmVplVpi,
                    atmfM4VpTestObject }
     ::= { atmfM4VpTestTable 1 }

AtmfM4VpTestEntry ::= SEQUENCE {
     atmfM4VpTestObject  INTEGER,
     atmfM4VpTestId      TestAndIncr,
     atmfM4VpTestStatus  INTEGER,
     atmfM4VpTestType    AutonomousType,
     atmfM4VpTestResult  INTEGER,
     atmfM4VpTestCode    OBJECT IDENTIFIER,
     atmfM4VpTestOwner   OwnerString
          }

atmfM4VpTestObject OBJECT-TYPE
     SYNTAX    INTEGER {
                    vplTp(1),
                    vpcTp(2)
                         }
     MAX-ACCESS     not-accessible
     STATUS    current
     DESCRIPTION
          "Specifies whether the test applies to the VPL termination
          point with the specified VPI, or the VPC termination point."
     ::= { atmfM4VpTestEntry 1 }

atmfM4VpTestId         OBJECT-TYPE
     SYNTAX       TestAndIncr
     MAX-ACCESS   read-write
     STATUS       current
     DESCRIPTION
           "This object identifies the current invocation of the
           interface's test."
     ::= { atmfM4VpTestEntry 2 }

atmfM4VpTestStatus     OBJECT-TYPE
     SYNTAX       INTEGER { notInUse(1), inUse(2) }
     MAX-ACCESS   read-write
     STATUS       current
     DESCRIPTION
           "This object indicates whether or not some manager
           currently has the necessary 'ownership' required to
           invoke a test on this interface.  A write to this
           object is only successful when it changes its value
           from 'notInUse(1)' to 'inUse(2)'.  After completion of
           a test, the agent resets the value back to
           'notInUse(1)'."
     ::= { atmfM4VpTestEntry 3 }

atmfM4VpTestType       OBJECT-TYPE
     SYNTAX       AutonomousType
     MAX-ACCESS   read-write
     STATUS       current
     DESCRIPTION
           "A control variable used to start and stop operator-
           initiated interface tests.  Most OBJECT IDENTIFIER
           values assigned to tests are defined elsewhere, in
           association with specific types of interface.
           However, this document assigns a value for a full-
           duplex loopback test, and defines the special meanings
           of the subject identifier:

               noTest  OBJECT IDENTIFIER ::= { 0 0 }

           When the value noTest is written to this object, no
           action is taken unless a test is in progress, in which
           case the test is aborted.  Writing any other value to
           this object is only valid when no test is currently in
           progress, in which case the indicated test is
           initiated.

           When read, this object always returns the most recent
           value that atmfM4VpTestType was set to.  If it has not been
           set since the last initialization of the network
           management subsystem on the agent, a value of noTest
           is returned."
     ::= { atmfM4VpTestEntry 4 }

atmfM4VpTestResult  OBJECT-TYPE
     SYNTAX       INTEGER {
                      none(1),          -- no test yet requested
                      success(2),
                      inProgress(3),
                      notSupported(4),
                      unAbleToRun(5),   -- due to state of system
                      aborted(6),
                      failed(7)
                  }
     MAX-ACCESS   read-only
     STATUS       current
     DESCRIPTION
           "This object contains the result of the most recently
           requested test, or the value none(1) if no tests have
           been requested since the last reset.  Note that this
           facility provides no provision for saving the results
           of one test when starting another, as could be
           required if used by multiple managers concurrently."
     ::= { atmfM4VpTestEntry 5 }

atmfM4VpTestCode  OBJECT-TYPE
     SYNTAX       OBJECT IDENTIFIER
     MAX-ACCESS   read-only
     STATUS       current
     DESCRIPTION
           "This object contains a code which contains more
           specific information on the test result, for example
           an error-code after a failed test.  Error codes and
           other values this object may take are specific to the
           type of interface and/or test.  The value may have the
           semantics of either the AutonomousType or
           RowPointer textual conventions as defined in RFC
           1903 [15].  The identifier:

               testCodeUnknown  OBJECT IDENTIFIER ::= { 0 0 }

           is defined for use if no additional result code is
           available."
     ::= { atmfM4VpTestEntry 6 }

atmfM4VpTestOwner      OBJECT-TYPE
     SYNTAX       OwnerString
     MAX-ACCESS   read-write
     STATUS       current
     DESCRIPTION
           "The entity which currently has the 'ownership'
           required to invoke a test on this interface."
     ::= { atmfM4VpTestEntry 7 }



-- ATM Forum M4 VC Termination Point Test Table

atmfM4VcTestTable OBJECT-TYPE
     SYNTAX    SEQUENCE OF    AtmfM4VcTestEntry
     MAX-ACCESS     not-accessible
     STATUS    current
     DESCRIPTION
          "The ATM Forum M4 VC Termination Point Test table.
          This table allows tests to be run on VCL and VCC
          termination points.

          The operation of this table is entirely analogous to
          that of the ifTestTable in RFC 1573 (which was later
          deprecated in RFC 2233), except that the indexes into
          this table are different."
     ::= { atmfM4MIBObjects 26 }

atmfM4VcTestEntry OBJECT-TYPE
     SYNTAX    AtmfM4VcTestEntry
     MAX-ACCESS     not-accessible
     STATUS    current
     DESCRIPTION
          "An entry containing objects for invoking tests on a
          VCL or VCC termination point."
     INDEX          { ifIndex,
                    atmVclVpi,
                    atmVclVci,
                    atmfM4VcTestObject }
     ::= { atmfM4VcTestTable 1 }

AtmfM4VcTestEntry ::= SEQUENCE {
     atmfM4VcTestObject  INTEGER,
     atmfM4VcTestId      TestAndIncr,
     atmfM4VcTestStatus  INTEGER,
     atmfM4VcTestType    AutonomousType,
     atmfM4VcTestResult  INTEGER,
     atmfM4VcTestCode    OBJECT IDENTIFIER,
     atmfM4VcTestOwner   OwnerString
          }

atmfM4VcTestObject OBJECT-TYPE
     SYNTAX    INTEGER {
                    vclTp(1),
                    vccTp(2)
                         }
     MAX-ACCESS     not-accessible
     STATUS    current
     DESCRIPTION
          "Specifies whether the test applies to the VCL termination
          point with the specified VPI and VCI values, or to the VCC
          termination point."
     ::= { atmfM4VcTestEntry 1 }

atmfM4VcTestId         OBJECT-TYPE
     SYNTAX       TestAndIncr
     MAX-ACCESS   read-write
     STATUS       current
     DESCRIPTION
          "This object identifies the current invocation of the
          interface's test."
     ::= { atmfM4VcTestEntry 2 }

atmfM4VcTestStatus     OBJECT-TYPE
     SYNTAX       INTEGER { notInUse(1), inUse(2) }
     MAX-ACCESS   read-write
     STATUS       current
     DESCRIPTION
          "This object indicates whether or not some manager
          currently has the necessary 'ownership' required to
          invoke a test on this interface.  A write to this
          object is only successful when it changes its value
          from 'notInUse(1)' to 'inUse(2)'.  After completion of
          a test, the agent resets the value back to
          'notInUse(1)'."
     ::= { atmfM4VcTestEntry 3 }

atmfM4VcTestType       OBJECT-TYPE
     SYNTAX       AutonomousType
     MAX-ACCESS   read-write
     STATUS       current
     DESCRIPTION
          "A control variable used to start and stop operator-
          initiated interface tests.  Most OBJECT IDENTIFIER
          values assigned to tests are defined elsewhere, in
          association with specific types of interface.
          However, this document assigns a value for a full-
          duplex loopback test, and defines the special meanings
          of the subject identifier:

              noTest  OBJECT IDENTIFIER ::= { 0 0 }

          When the value noTest is written to this object, no
          action is taken unless a test is in progress, in which
          case the test is aborted.  Writing any other value to
          this object is only valid when no test is currently in
          progress, in which case the indicated test is
          initiated.

          When read, this object always returns the most recent
          value that atmfM4VcTestType was set to.  If it has not been
          set since the last initialization of the network
          management subsystem on the agent, a value of noTest
          is returned."
     ::= { atmfM4VcTestEntry 4 }

atmfM4VcTestResult  OBJECT-TYPE
     SYNTAX       INTEGER {
                      none(1),          -- no test yet requested
                      success(2),
                      inProgress(3),
                      notSupported(4),
                      unAbleToRun(5),   -- due to state of system
                      aborted(6),
                      failed(7)
                  }
     MAX-ACCESS   read-only
     STATUS       current
     DESCRIPTION
          "This object contains the result of the most recently
          requested test, or the value none(1) if no tests have
          been requested since the last reset.  Note that this
          facility provides no provision for saving the results
          of one test when starting another, as could be
          required if used by multiple managers concurrently."
     ::= { atmfM4VcTestEntry 5 }

atmfM4VcTestCode  OBJECT-TYPE
     SYNTAX       OBJECT IDENTIFIER
     MAX-ACCESS   read-only
     STATUS       current
     DESCRIPTION
          "This object contains a code which contains more
          specific information on the test result, for example
          an error-code after a failed test.  Error codes and
          other values this object may take are specific to the
          type of interface and/or test.  The value may have the
          semantics of either the AutonomousType or
          RowPointer textual conventions as defined in RFC
          1903 [15].  The identifier:

              testCodeUnknown  OBJECT IDENTIFIER ::= { 0 0 }

          is defined for use if no additional result code is
          available."
     ::= { atmfM4VcTestEntry 6 }

atmfM4VcTestOwner      OBJECT-TYPE
     SYNTAX       OwnerString
     MAX-ACCESS   read-write
     STATUS       current
     DESCRIPTION
          "The entity which currently has the 'ownership'
          required to invoke a test on this termination point."
     ::= { atmfM4VcTestEntry 7 }


-- ATM Forum M4 Equipment Table

atmfM4EquipTable OBJECT-TYPE
     SYNTAX    SEQUENCE OF    AtmfM4EquipEntry
     MAX-ACCESS     not-accessible
     STATUS    current
     DESCRIPTION
          "The ATM Forum M4 Equipment table.  This table augments the
          entPhysicalTable."
     ::= { atmfM4MIBObjects 28 }

atmfM4EquipEntry OBJECT-TYPE
     SYNTAX    AtmfM4EquipEntry
     MAX-ACCESS     not-accessible
     STATUS    current
     DESCRIPTION
          "An entry in the ATM Forum M4 Equipment table.  Each entry
          of this table represents a piece of equipment within the ATM
          NE that neither is nor accepts a replaceable plug-in unit."
     INDEX          { entPhysicalIndex }
     ::= { atmfM4EquipTable 1 }

AtmfM4EquipEntry ::= SEQUENCE {
     atmfM4EquipAdminStatus   INTEGER,
     atmfM4EquipLocation      DisplayString,
     atmfM4EquipOperStatus    INTEGER,
     atmfM4EquipVendor        DisplayString,
     atmfM4EquipVersion       AutonomousType,
     atmfM4EquipUserLabel     DisplayString,
     atmfM4EquipAlarmSeverityIndex Integer32
          }

atmfM4EquipAdminStatus OBJECT-TYPE
     SYNTAX    INTEGER {
                    up(1),
                    down(2)
                         }
     MAX-ACCESS     read-write
     STATUS    current
     DESCRIPTION
          "Used by the administrator to lock and unlock the object."
     ::= { atmfM4EquipEntry 1 }

atmfM4EquipLocation OBJECT-TYPE
     SYNTAX    DisplayString
     MAX-ACCESS     read-write
     STATUS    current
     DESCRIPTION
          "The specific or general location of the component."
     ::= { atmfM4EquipEntry 2 }

atmfM4EquipOperStatus OBJECT-TYPE
     SYNTAX    INTEGER {
                    up(1),
                    down(2),
                    unknown(3)
                         }
     MAX-ACCESS     read-only
     STATUS    current
     DESCRIPTION
          "This attributes identifies whether or not the component is
          capable of performing its normal functions."
     ::= { atmfM4EquipEntry 3 }

atmfM4EquipVendor OBJECT-TYPE
     SYNTAX    DisplayString
     MAX-ACCESS     read-only
     STATUS    current
     DESCRIPTION
          "The vendor of the component."
     ::= { atmfM4EquipEntry 4 }

atmfM4EquipVersion OBJECT-TYPE
     SYNTAX    AutonomousType
     MAX-ACCESS     read-only
     STATUS    current
     DESCRIPTION
          "The version of the component."
     ::= { atmfM4EquipEntry 5 }

atmfM4EquipUserLabel OBJECT-TYPE
     SYNTAX    DisplayString
     MAX-ACCESS     read-write
     STATUS    current
     DESCRIPTION
          "A user-friendly name for the piece of equipment.  The
          default value of this object is the null string."
     ::= { atmfM4EquipEntry 6 }

atmfM4EquipAlarmSeverityIndex OBJECT-TYPE
     SYNTAX    Integer32
     MAX-ACCESS     read-write
     STATUS    current
     DESCRIPTION
          "An index into the alarm severity profile table, specifying
          the severity assignments for M4 alarms reported for this
          component.  The default value of this object is zero."
     ::= { atmfM4EquipEntry 7 }


-- ATM Forum M4 Equipment Holder Table

atmfM4EquipHolderTable OBJECT-TYPE
     SYNTAX    SEQUENCE OF    AtmfM4EquipHolderEntry
     MAX-ACCESS     not-accessible
     STATUS    current
     DESCRIPTION
          "The ATM Forum M4 Equipment Holder table.  This table
          augments the entPhysicalTable."
     ::= { atmfM4MIBObjects 29 }

atmfM4EquipHolderEntry OBJECT-TYPE
     SYNTAX    AtmfM4EquipHolderEntry
     MAX-ACCESS     not-accessible
     STATUS    current
     DESCRIPTION
          "An entry in the ATM Forum M4 Equipment Holder table.  Each
          entry of this table represents a component within the ATM NE
          that accepts a replaceable plug-in unit."
     INDEX          { entPhysicalIndex }
     ::= { atmfM4EquipHolderTable 1 }

AtmfM4EquipHolderEntry ::= SEQUENCE {
     atmfM4EquipHolderType              INTEGER,
     atmfM4EquipHolderAcceptableTypes   DisplayString,
     atmfM4EquipHolderSlotStatus        INTEGER,
     atmfM4EquipHolderSwLoad            INTEGER
          }

atmfM4EquipHolderType OBJECT-TYPE
     SYNTAX    INTEGER {
                    rack(1),
                    shelf(2),
                    drawer(3),
                    slot(4)
                         }
     MAX-ACCESS     read-only
     STATUS    current
     DESCRIPTION
          "The type of the component."
     ::= { atmfM4EquipHolderEntry 1 }

atmfM4EquipHolderAcceptableTypes OBJECT-TYPE
     SYNTAX    DisplayString
     MAX-ACCESS     read-only
     STATUS    current
     DESCRIPTION
          "The types of plug-in units that can be supported by the
          slot, separated by newline characters.

          This attribute shall be present only when the Equipment
          Holder represents a slot."
     ::= { atmfM4EquipHolderEntry 2 }

atmfM4EquipHolderSlotStatus OBJECT-TYPE
     SYNTAX    INTEGER {
                    empty(1),
                    full(2)
                         }
     MAX-ACCESS     read-only
     STATUS    current
     DESCRIPTION
          "This attributes identifies whether or not a plug-in unit is
          present in the slot.

          This attribute shall be present only when the Equipment
          Holder represents a slot."
     ::= { atmfM4EquipHolderEntry 3 }

atmfM4EquipHolderSwLoad OBJECT-TYPE
     SYNTAX    INTEGER (1..2147483647)
     MAX-ACCESS     read-write
     STATUS    current
     DESCRIPTION
          "An index into the installed software table, specifying
          the software that is to be loaded into the plug-in unit
          whenever an automatic reload of software is needed.

          This attribute shall be present only when the Equipment
          Holder represents a slot."
     ::= { atmfM4EquipHolderEntry 4 }


-- ATM Forum M4 Plug-In Unit Table

atmfM4PlugInUnitTable OBJECT-TYPE
     SYNTAX    SEQUENCE OF    AtmfM4PlugInUnitEntry
     MAX-ACCESS     not-accessible
     STATUS    current
     DESCRIPTION
          "The ATM Forum M4 Plug-In Unit table.  This table augments
          the entPhysicalTable."
     ::= { atmfM4MIBObjects 30 }

atmfM4PlugInUnitEntry OBJECT-TYPE
     SYNTAX    AtmfM4PlugInUnitEntry
     MAX-ACCESS     not-accessible
     STATUS    current
     DESCRIPTION
          "An entry in the ATM Forum M4 Plug-In Unit table.  Each
          entry of this table represents a piece of equipment within
          the ATM NE that is inserted into and removed from an
          Equipment Holder."
     INDEX          { entPhysicalIndex }
     ::= { atmfM4PlugInUnitTable 1 }

AtmfM4PlugInUnitEntry ::= SEQUENCE {
     atmfM4PlugInUnitAdminStatus   INTEGER,
     atmfM4PlugInUnitAvailStatus   INTEGER,
     atmfM4PlugInUnitOperStatus    INTEGER,
     atmfM4PlugInUnitVendor        DisplayString,
     atmfM4PlugInUnitVersion       AutonomousType,
     atmfM4PlugInUnitAlarmSeverityIndex Integer32
          }

atmfM4PlugInUnitAdminStatus OBJECT-TYPE
     SYNTAX    INTEGER {
                    up(1),
                    down(2)
                         }
     MAX-ACCESS     read-write
     STATUS    current
     DESCRIPTION
          "Used by the administrator to lock and unlock the object."
     ::= { atmfM4PlugInUnitEntry 1 }

atmfM4PlugInUnitAvailStatus OBJECT-TYPE
     SYNTAX    INTEGER {
                    available(1),
                    inTest(2),
                    failed(3),
                    powerOff(4),
                    notInstalled(5),
                    offLine(6),
                    dependency(7)
                         }
     MAX-ACCESS     read-only
     STATUS    current
     DESCRIPTION
          "Provides further information regarding the state of the
          component."
     ::= { atmfM4PlugInUnitEntry 2 }

atmfM4PlugInUnitOperStatus OBJECT-TYPE
     SYNTAX    INTEGER {
                    up(1),
                    down(2),
                    unknown(3)
                         }
     MAX-ACCESS     read-only
     STATUS    current
     DESCRIPTION
          "This attributes identifies whether or not the component is
          capable of performing its normal functions."
     ::= { atmfM4PlugInUnitEntry 3 }

atmfM4PlugInUnitVendor OBJECT-TYPE
     SYNTAX    DisplayString
     MAX-ACCESS     read-only
     STATUS    current
     DESCRIPTION
          "The vendor of the component."
     ::= { atmfM4PlugInUnitEntry 4 }

atmfM4PlugInUnitVersion OBJECT-TYPE
     SYNTAX    AutonomousType
     MAX-ACCESS     read-only
     STATUS    current
     DESCRIPTION
          "The version of the component."
     ::= { atmfM4PlugInUnitEntry 5 }

atmfM4PlugInUnitAlarmSeverityIndex OBJECT-TYPE
     SYNTAX    Integer32
     MAX-ACCESS     read-write
     STATUS    current
     DESCRIPTION
          "An index into the alarm severity profile table, specifying
          the severity assignments for M4 alarms reported for this
          component.  The default value of this object is zero."
     ::= { atmfM4PlugInUnitEntry 6 }

-- ATM Forum M4 Hardware Unit/Running Software Relationship Table

atmfM4HwRunningSwTable OBJECT-TYPE
     SYNTAX    SEQUENCE OF    AtmfM4HwRunningSwEntry
     MAX-ACCESS     not-accessible
     STATUS    current
     DESCRIPTION
          "The ATM Forum M4 Hardware Unit/Running Software
          relationship table.  This table describes the software that
          is running on each hardware unit in the ATM NE."
     ::= { atmfM4MIBObjects 32 }

atmfM4HwRunningSwEntry OBJECT-TYPE
     SYNTAX    AtmfM4HwRunningSwEntry
     MAX-ACCESS     not-accessible
     STATUS    current
     DESCRIPTION
          "An entry in the ATM Forum M4 Hardware Unit/Running Software
          relationship table.  Each entry of this table identifies an
          entry in the entPhysicalTable and one in the hrSWRunTable."
     INDEX          { atmfM4HwRunningSwHwIndex,
                    atmfM4HwRunningSwIndex }
     ::= { atmfM4HwRunningSwTable 1 }

AtmfM4HwRunningSwEntry ::= SEQUENCE {
     atmfM4HwRunningSwHwIndex INTEGER,
     atmfM4HwRunningSwIndex        INTEGER,
     atmfM4HwRunningSwSwIndex INTEGER
          }

atmfM4HwRunningSwHwIndex OBJECT-TYPE
     SYNTAX    INTEGER (1..2147483647)
     MAX-ACCESS     not-accessible
     STATUS    current
     DESCRIPTION
          "The index, in the entPhysicalTable, of the containing
          hardware unit in this pair."
     ::= { atmfM4HwRunningSwEntry 1 }

atmfM4HwRunningSwIndex OBJECT-TYPE
     SYNTAX    INTEGER (1..2147483647)
     MAX-ACCESS     not-accessible
     STATUS    current
     DESCRIPTION
          "A unique number within the context of the containing
          hardware unit."
     ::= { atmfM4HwRunningSwEntry 2 }

atmfM4HwRunningSwSwIndex OBJECT-TYPE
     SYNTAX    INTEGER (1..2147483647)
     MAX-ACCESS     read-only
     STATUS    current
     DESCRIPTION
          "The index, in the hrSWRunTable, of the software product
          represented by this entry."
     ::= { atmfM4HwRunningSwEntry 3 }


-- ATM Forum M4 Hardware Unit/Installed Software Relationship Table

atmfM4HwInstalledSwTable OBJECT-TYPE
     SYNTAX    SEQUENCE OF    AtmfM4HwInstalledSwEntry
     MAX-ACCESS     not-accessible
     STATUS    current
     DESCRIPTION
          "The ATM Forum M4 Hardware Unit/Installed Software
          relationship table.  This table describes the software that
          is installed on each hardware unit in the ATM NE."
     ::= { atmfM4MIBObjects 33 }

atmfM4HwInstalledSwEntry OBJECT-TYPE
     SYNTAX    AtmfM4HwInstalledSwEntry
     MAX-ACCESS     not-accessible
     STATUS    current
     DESCRIPTION
          "An entry in the ATM Forum M4 Hardware Unit/Installed
          Software relationship table.  Each entry of this table
          identifies an entry in the entPhysicalTable and one in
          the hrSWInstalledTable."
     INDEX          { atmfM4HwInstalledSwHwIndex,
                    atmfM4HwInstalledSwIndex }
     ::= { atmfM4HwInstalledSwTable 1 }

AtmfM4HwInstalledSwEntry ::= SEQUENCE {
     atmfM4HwInstalledSwHwIndex    INTEGER,
     atmfM4HwInstalledSwIndex      INTEGER,
     atmfM4HwInstalledSwSwIndex    INTEGER,
     atmfM4HwSwAlarmSeverityIndex  Integer32
          }

atmfM4HwInstalledSwHwIndex OBJECT-TYPE
     SYNTAX    INTEGER (1..2147483647)
     MAX-ACCESS     not-accessible
     STATUS    current
     DESCRIPTION
          "The index, in the entPhysicalTable, of the containing
          physical entity in this pair."
     ::= { atmfM4HwInstalledSwEntry 1 }

atmfM4HwInstalledSwIndex OBJECT-TYPE
     SYNTAX    INTEGER (1..2147483647)
     MAX-ACCESS     not-accessible
     STATUS    current
     DESCRIPTION
          "A unique number within the context of the containing
          hardware unit."
     ::= { atmfM4HwInstalledSwEntry 2 }

atmfM4HwInstalledSwSwIndex OBJECT-TYPE
     SYNTAX    INTEGER (1..2147483647)
     MAX-ACCESS     read-only
     STATUS    current
     DESCRIPTION
          "The index, in the hrSWInstalledTable, of the software
          product represented by this entry."
     ::= { atmfM4HwInstalledSwEntry 3 }

atmfM4HwSwAlarmSeverityIndex OBJECT-TYPE
     SYNTAX    Integer32
     MAX-ACCESS     read-write
     STATUS    current
     DESCRIPTION
          "An index into the alarm severity profile table, specifying
          the severity assignments for M4 alarms reported for this
          piece of software installed on the hardware unit.  The
          default value of this object is zero."
     ::= { atmfM4HwInstalledSwEntry 4 }



-- ATM Forum M4 Alarm Severity Identifier Textual Convention

AtmfM4AlarmLogSeverity ::= TEXTUAL-CONVENTION
     STATUS    current
     DESCRIPTION
          "The value of this object identifies the severity of
          an alarm in the log, including 'cleared'."
     SYNTAX    INTEGER {
                    cleared(-1),
                    indeterminate(0),
                    critical(1),
                    major(2),
                    minor(3),
                    warning(4)
                         }

AtmfM4AlarmSeverity ::= TEXTUAL-CONVENTION
     STATUS    current
     DESCRIPTION
          "The value of this object identifies the severity of
          an alarm that has occurred.  (Note that there is no
          value corresponding to 'cleared'.)"
     SYNTAX    INTEGER {
                    indeterminate(0),
                    critical(1),
                    major(2),
                    minor(3),
                    warning(4)
                         }

-- ATM Forum M4 Alarm Severity Profile Table

atmfM4AlarmSevDefault OBJECT-TYPE
     SYNTAX    AtmfM4AlarmSeverity
     MAX-ACCESS     read-write
     STATUS    current
     DESCRIPTION
          "The default severity value used for new profile
          index/trap ID pairs that have not yet been modified.
          This value is also used whenever an object's alarm
          severity profile index is set to 0.  The default value
          of this object is minor(3)."
     ::= { atmfM4MIBObjects 34 }

atmfM4AlarmSevProfileIndexNext OBJECT-TYPE
     SYNTAX    Integer32
     MAX-ACCESS     read-only
     STATUS    current
     DESCRIPTION
          "This object contains an appropriate value to be used for
          atmfM4AlarmSevProfileIndex when creating entries in the
          atmfM4AlarmSevProfileTable.

          The value -1 indicates that no unassigned entries are
          available.

          To obtain the index value for a new entry, the manager
          issues a management protocol retrieval operation to obtain
          the current value of this object.  After each retrieval, the
          agent should modify the value to the next unassigned index
          (or -1)."
     ::= { atmfM4MIBObjects 35 }

atmfM4AlarmSevProfileTable OBJECT-TYPE
     SYNTAX    SEQUENCE OF    AtmfM4AlarmSevProfileEntry
     MAX-ACCESS     not-accessible
     STATUS    current
     DESCRIPTION
          "The ATM Forum M4 alarm severity profile table.
          This table specifies which profiles exist. Creating
          or deleting an entry in this table automatically
          creates or deletes the corresponding entries in the
          atmfM4AlarmSeverityTable."
     ::= { atmfM4MIBObjects 36 }

atmfM4AlarmSevProfileEntry OBJECT-TYPE
     SYNTAX    AtmfM4AlarmSevProfileEntry
     MAX-ACCESS     not-accessible
     STATUS    current
     DESCRIPTION
          "A group of severities, one for each alarm type in
          the communications alarm group."
     INDEX          { atmfM4AlarmSevProfileIndex }
     ::= { atmfM4AlarmSevProfileTable 1 }

AtmfM4AlarmSevProfileEntry ::= SEQUENCE {
     atmfM4AlarmSevProfileIndex         Integer32,
     atmfM4AlarmSevProfileRowStatus     RowStatus
          }

atmfM4AlarmSevProfileIndex OBJECT-TYPE
     SYNTAX    Integer32 (1..2147483647)
     MAX-ACCESS     not-accessible
     STATUS    current
     DESCRIPTION
          "A number identifying this alarm severity profile."
     ::= { atmfM4AlarmSevProfileEntry 1 }

atmfM4AlarmSevProfileRowStatus OBJECT-TYPE
     SYNTAX    RowStatus
     MAX-ACCESS     read-create
     STATUS    current
     DESCRIPTION
          "This object is used to create a new row or to delete
          an existing row in the table."
     ::= { atmfM4AlarmSevProfileEntry 2 }


-- ATM Forum M4 Alarm Severity Table

atmfM4AlarmSevTable OBJECT-TYPE
     SYNTAX    SEQUENCE OF    AtmfM4AlarmSevEntry
     MAX-ACCESS     not-accessible
     STATUS    current
     DESCRIPTION
          "The ATM Forum M4 alarm severity table.
          This table associates profile index and trap
          ID pairs with severities to be used for
          M4 alarm traps that have occurred.
          (Note that this table does not apply to cleared alarms.)"
     ::= { atmfM4MIBObjects 37 }

atmfM4AlarmSevEntry OBJECT-TYPE
     SYNTAX    AtmfM4AlarmSevEntry
     MAX-ACCESS     not-accessible
     STATUS    current
     DESCRIPTION
          "An entry in this table associates an alarm severity
          profile index/trap ID pair with a severity.
          Deleting a particular profile's row in the alarm severity
          profile table deletes all rows in this table with the
          same profile index.
          Conceptually, rows corresponding to all possible trap ID's
          are created in this table when a new alarm severity profile
          is created, but the agent will return a default value
          except for those few traps for which values have been set."
     INDEX          { atmfM4AlarmSevProfileIndex,
                    atmfM4AlarmSevTrapId }
     ::= { atmfM4AlarmSevTable 1 }

AtmfM4AlarmSevEntry ::= SEQUENCE {
     atmfM4AlarmSevTrapId     OBJECT IDENTIFIER,
     atmfM4AlarmSeverity      AtmfM4AlarmSeverity
          }

atmfM4AlarmSevTrapId OBJECT-TYPE
     SYNTAX    OBJECT IDENTIFIER
     MAX-ACCESS     not-accessible
     STATUS    current
     DESCRIPTION
          "The ID of the trap type to which this entry applies."
     ::= { atmfM4AlarmSevEntry 1 }

atmfM4AlarmSeverity OBJECT-TYPE
     SYNTAX    AtmfM4AlarmSeverity
     MAX-ACCESS     read-create
     STATUS    current
     DESCRIPTION
          "The severity to be used for this trap type when the TrapId
          is selected.
          If no value for this object has ever been set since
          the corresponding profile was created, the agent should
          return the value of the object atmfM4AlarmSevDefault."
     ::= { atmfM4AlarmSevEntry 2 }


-- ATM Forum M4 Alarm Forwarding Discriminator Table

atmfM4ForwardAllTraps OBJECT-IDENTITY
     STATUS    current
     DESCRIPTION
          "This is used as the value of the object
          atmfM4ForwardedTrapObject when traps from all objects
          are to be forwarded, or when there is only one
          object of the type that forwards the specified
          trap type."
     ::= { atmfM4MIBObjects 38 }


atmfM4TrapForwardingTable OBJECT-TYPE
     SYNTAX    SEQUENCE OF    AtmfM4TrapForwardingEntry
     MAX-ACCESS     not-accessible
     STATUS    current
     DESCRIPTION
          "The ATM Forum M4 Trap forwarding discriminator
          table.
          This table specifies which traps will be sent to
          which management system."
     ::= { atmfM4MIBObjects 39 }

atmfM4TrapForwardingEntry OBJECT-TYPE
     SYNTAX    AtmfM4TrapForwardingEntry
     MAX-ACCESS     not-accessible
     STATUS    current
     DESCRIPTION
          "Information about a group of traps to be sent to
          a particular IP address.

          A new entry must have values for all attributes that
          do not have default values before its RowStatus column
          can be set to active(1)."
     INDEX          { atmfM4TrapForwardingIndex }
     ::= { atmfM4TrapForwardingTable 1 }

AtmfM4TrapForwardingEntry ::= SEQUENCE {
     atmfM4TrapForwardingIndex     Integer32,
     atmfM4TrapForwardingDest      IpAddress,
     atmfM4ForwardedTrapId         OBJECT IDENTIFIER,
     atmfM4ForwardedTrapObject     RowPointer,
     atmfM4TrapForwardingPort      Integer32,
     atmfM4LowestForwardedSeverity AtmfM4AlarmSeverity,
     atmfM4ForwardedIndeterminate  TruthValue,
     atmfM4TrapForwardingRowStatus RowStatus
          }

atmfM4TrapForwardingIndex OBJECT-TYPE
     SYNTAX    Integer32 (1..2147483647)
     MAX-ACCESS     not-accessible
     STATUS    current
     DESCRIPTION
          "A unique number identifying the table entry."
     ::= { atmfM4TrapForwardingEntry 1 }

atmfM4TrapForwardingDest OBJECT-TYPE
     SYNTAX    IpAddress
     MAX-ACCESS     read-create
     STATUS    current
     DESCRIPTION
          "The IP address to which traps identified by this
          table entry should be sent."
     ::= { atmfM4TrapForwardingEntry 2 }

atmfM4ForwardedTrapId OBJECT-TYPE
     SYNTAX    OBJECT IDENTIFIER
     MAX-ACCESS     read-create
     STATUS    current
     DESCRIPTION
          "The ID of the trap type to which this entry applies."
     ::= { atmfM4TrapForwardingEntry 3 }

atmfM4ForwardedTrapObject OBJECT-TYPE
     SYNTAX    RowPointer
     MAX-ACCESS     read-create
     STATUS    current
     DESCRIPTION
          "The object to which this entry applies.
          By convention, this is the name of the first object in
          the row in the table referenced.

          The special value { 0 0 } indicates that
          traps of this type from all objects of the type that can
          generate it.  It should also be used when traps from the
          ATM NE are to be specified."
     ::= { atmfM4TrapForwardingEntry 4 }

atmfM4TrapForwardingPort OBJECT-TYPE
     SYNTAX    Integer32
     MAX-ACCESS     read-create
     STATUS    current
     DESCRIPTION
          "The UDP port on the specified management system to
          which traps identified by this entry should be sent."
     DEFVAL    { 162 }
     ::= { atmfM4TrapForwardingEntry 5 }

atmfM4LowestForwardedSeverity OBJECT-TYPE
     SYNTAX    AtmfM4AlarmSeverity
     MAX-ACCESS     read-create
     STATUS    current
     DESCRIPTION
          "The lowest severity of traps of this type from
          the specified object that should be sent to this
          address.
          This object has significance only if the trap type
          specified has a severity associated with it."
     DEFVAL    { minor }
     ::= { atmfM4TrapForwardingEntry 6 }

atmfM4ForwardedIndeterminate OBJECT-TYPE
     SYNTAX    TruthValue
     MAX-ACCESS     read-create
     STATUS    current
     DESCRIPTION
          "When this object has the value TRUE, traps with
          indeterminate severity will be forwarded to the
          specified event.
          This object has significance only if the trap type
          specified has a severity associated with it."
     DEFVAL    { false }
     ::= { atmfM4TrapForwardingEntry 7 }

atmfM4TrapForwardingRowStatus OBJECT-TYPE
     SYNTAX    RowStatus
     MAX-ACCESS     read-create
     STATUS    current
     DESCRIPTION
          "This object is used to create a new row or to delete
          an existing row in the table."
     ::= { atmfM4TrapForwardingEntry 8 }


-- ATM Forum M4 Trap Agent MIB Log Table

atmfM4TrapLogTable OBJECT-TYPE
     SYNTAX    SEQUENCE OF    AtmfM4TrapLogEntry
     MAX-ACCESS     not-accessible
     STATUS    current
     DESCRIPTION
          "The ATM Forum M4 Trap Agent log table.
          This table defines the trap logs currently maintained
          by the agent.
          The management system creates entries in this table to
          specify which types of traps, from which ATM network
          elements, should be logged.
          Deleting an entry in this table deletes all entries in
          the corresponding log."
     ::= { atmfM4MIBObjects 40 }

atmfM4TrapLogEntry OBJECT-TYPE
     SYNTAX    AtmfM4TrapLogEntry
     MAX-ACCESS     not-accessible
     STATUS    current
     DESCRIPTION
          "Information about a single trap log."
     INDEX          { atmfM4TrapLogSrc,
                    atmfM4TrapLogType }
     ::= { atmfM4TrapLogTable 1 }

AtmfM4TrapLogEntry ::= SEQUENCE {
     atmfM4TrapLogSrc              IpAddress,
     atmfM4TrapLogType             INTEGER,
     atmfM4TrapLogAdminStatus      INTEGER,
     atmfM4TrapLogOperStatus       INTEGER,
     atmfM4TrapLogFullAction       INTEGER,
     atmfM4TrapLogRowStatus        RowStatus
          }

atmfM4TrapLogSrc OBJECT-TYPE
     SYNTAX    IpAddress
     MAX-ACCESS     not-accessible
     STATUS    current
     DESCRIPTION
          "The IP address of the SNMP agent whose traps are
          stored in this log."
     ::= { atmfM4TrapLogEntry 1 }

atmfM4TrapLogType OBJECT-TYPE
     SYNTAX    INTEGER {
                    objectCreated(1),
                    objectDeleted(2),
                    configChange(3),
                    stateChange(4),
                    alarm(5)
                         }
     MAX-ACCESS     not-accessible
     STATUS    current
     DESCRIPTION
          "The type of traps stored in this log."
     ::= { atmfM4TrapLogEntry 2 }

atmfM4TrapLogAdminStatus OBJECT-TYPE
     SYNTAX    INTEGER {
                    up(1),
                    down(2)
                         }
     MAX-ACCESS     read-create
     STATUS    current
     DESCRIPTION
          "The management system uses this object to stop and
          start the operations of this object."
     DEFVAL    { up }
     ::= { atmfM4TrapLogEntry 3 }

atmfM4TrapLogOperStatus OBJECT-TYPE
     SYNTAX    INTEGER {
                    up(1),
                    down(2),
                    logFull(3)
                         }
     MAX-ACCESS     read-only
     STATUS    current
     DESCRIPTION
          "Indicates whether or not the log is capable of
          performing its normal operations."
     ::= { atmfM4TrapLogEntry 4 }

atmfM4TrapLogFullAction OBJECT-TYPE
     SYNTAX    INTEGER {
                    halt(1),
                    wrap(2)
                         }
     MAX-ACCESS     read-create
     STATUS    current
     DESCRIPTION
          "Indicates the action that should be performed when no
          more log entries can be created due to a log-full
          condition.  If the value of this object is wrap(2),
          each new log entry will cause the deletion of the oldest
          entry still in the log, for as long as the log is still
          full."
     DEFVAL    { wrap }
     ::= { atmfM4TrapLogEntry 5 }

atmfM4TrapLogRowStatus OBJECT-TYPE
     SYNTAX    RowStatus
     MAX-ACCESS     read-create
     STATUS    current
     DESCRIPTION
          "This object is used to create a new row or to delete
          an existing row in the table."
     ::= { atmfM4TrapLogEntry 6 }


-- ATM Forum M4 Trap Agent MIB Logged Trap Table

atmfM4LoggedTrapTable OBJECT-TYPE
     SYNTAX    SEQUENCE OF    AtmfM4LoggedTrapEntry
     MAX-ACCESS     not-accessible
     STATUS    current
     DESCRIPTION
          "The ATM Forum M4 Trap Agent logged trap table.
          This table is used to maintain the traps logged."
     ::= { atmfM4MIBObjects 41 }

atmfM4LoggedTrapEntry OBJECT-TYPE
     SYNTAX    AtmfM4LoggedTrapEntry
     MAX-ACCESS     not-accessible
     STATUS    current
     DESCRIPTION
          "Information about a single trap in the log.
          Entries in this table are created automatically but
          can be deleted by the management system.
          Entries that represent 'alarm' log types are augmented
          by the atmfM4LoggedAlarmEntry table."
     INDEX          { atmfM4TrapLogSrc,
                    atmfM4TrapLogType,
                    atmfM4LoggedTrapIndex }
     ::= { atmfM4LoggedTrapTable 1 }

AtmfM4LoggedTrapEntry ::= SEQUENCE {
     atmfM4LoggedTrapIndex         Unsigned32,
     atmfM4LoggedTrapTime          DateAndTime,
     atmfM4LoggedTrapID            Integer32,
     atmfM4LoggedTrapObject        RowPointer,
     atmfM4LoggedTrapRowStatus     RowStatus
          }

atmfM4LoggedTrapIndex OBJECT-TYPE
     SYNTAX    Unsigned32
     MAX-ACCESS     not-accessible
     STATUS    current
     DESCRIPTION
          "A unique number identifying this entry in the log.
          When the maximum value for this object has been reached,
          it will wrap around to 0."
     ::= { atmfM4LoggedTrapEntry 1 }

atmfM4LoggedTrapTime OBJECT-TYPE
     SYNTAX    DateAndTime
     MAX-ACCESS     read-only
     STATUS    current
     DESCRIPTION
          "The time at which this trap was logged."
     ::= { atmfM4LoggedTrapEntry 2 }

atmfM4LoggedTrapID OBJECT-TYPE
     SYNTAX    Integer32
     MAX-ACCESS     read-only
     STATUS    current
     DESCRIPTION
          "The type of trap to which this entry applies.
          Together with the logged trap ID object, this object
          specifies the entity to which this logged trap referred."
     ::= { atmfM4LoggedTrapEntry 3 }

atmfM4LoggedTrapObject OBJECT-TYPE
     SYNTAX    RowPointer
     MAX-ACCESS     read-only
     STATUS    current
     DESCRIPTION
          "The object to which this entry applies.
          By convention, this is the name of the first object in
          the row in the table referenced.
          Together with the logged trap ID object, this object
          specifies the entity to which this logged trap referred.

          The special value { 0 0 } indicates that the trap refers
          to the ATM NE entity itself."
     ::= { atmfM4LoggedTrapEntry 4 }

atmfM4LoggedTrapRowStatus OBJECT-TYPE
     SYNTAX    RowStatus
     MAX-ACCESS     read-write
     STATUS    current
     DESCRIPTION
          "This object is used to delete an existing row in the
          table.  Note that the only value to which a management
          system can set this object is destroy(6)."
     ::= { atmfM4LoggedTrapEntry 5 }


-- ATM Forum M4 Trap Agent MIB Logged Alarm Table

atmfM4LoggedAlarmTable OBJECT-TYPE
     SYNTAX    SEQUENCE OF    AtmfM4LoggedAlarmEntry
     MAX-ACCESS     not-accessible
     STATUS    current
     DESCRIPTION
          "The ATM Forum M4 Trap Agent logged alarm trap table.
          This table is used to maintain extra information for
          logged traps that represent alarm types."
     ::= { atmfM4MIBObjects 42 }

atmfM4LoggedAlarmEntry OBJECT-TYPE
     SYNTAX    AtmfM4LoggedAlarmEntry
     MAX-ACCESS     not-accessible
     STATUS    current
     DESCRIPTION
          "Information about the alarm-specific attributes of
          a single trap in the log."
     INDEX          { atmfM4TrapLogSrc,
                    atmfM4TrapLogType,
                    atmfM4LoggedTrapIndex }
     ::= { atmfM4LoggedAlarmTable 1 }

AtmfM4LoggedAlarmEntry ::= SEQUENCE {
     atmfM4LoggedAlarmSeverity     AtmfM4AlarmLogSeverity,
     atmfM4LoggedAlarmBackedUp     TruthValue,
     atmfM4LoggedAlarmBUObject     RowPointer,
     atmfM4LoggedAlarmSpecificProb DisplayString,
     atmfM4LoggedAlarmRepairAct    DisplayString
          }

atmfM4LoggedAlarmSeverity OBJECT-TYPE
     SYNTAX    AtmfM4AlarmLogSeverity
     MAX-ACCESS     read-only
     STATUS    current
     DESCRIPTION
          "The perceived severity of the alarm, as specified by
          the agent that generated it."
     ::= { atmfM4LoggedAlarmEntry 1 }

atmfM4LoggedAlarmBackedUp OBJECT-TYPE
     SYNTAX    TruthValue
     MAX-ACCESS     read-only
     STATUS    current
     DESCRIPTION
          "If the value of this object is true, the agent reported
          in this trap that the failed object had been backed up.

          This object is only present if it was included in the
          alarm trap corresponding to this log entry."
     ::= { atmfM4LoggedAlarmEntry 2 }

atmfM4LoggedAlarmBUObject OBJECT-TYPE
     SYNTAX    RowPointer
     MAX-ACCESS     read-only
     STATUS    current
     DESCRIPTION
          "Indicates the object that provided back-up services to
          the failed object.

          This object is only present if it was included in the
          alarm trap corresponding to this log entry."
     ::= { atmfM4LoggedAlarmEntry 3 }

atmfM4LoggedAlarmSpecificProb OBJECT-TYPE
     SYNTAX    DisplayString
     MAX-ACCESS     read-only
     STATUS    current
     DESCRIPTION
          "Indicates further refinements to the problem identified
          by the alarm type.  If more than one specific problem
          is described in this object, the problem descriptions are
          separated by newline characters.

          This object is only present if it was included in the
          alarm trap corresponding to this log entry."
     ::= { atmfM4LoggedAlarmEntry 4 }

atmfM4LoggedAlarmRepairAct OBJECT-TYPE
     SYNTAX    DisplayString
     MAX-ACCESS     read-only
     STATUS    current
     DESCRIPTION
          "Indicates proposed repair actions reported by the agent
          for the problem identified by the alarm.  If more than
          one action is described in this object, the problem
          descriptions are separated by newline characters.

          This object is only present if it was included in the
          alarm trap corresponding to this log entry."
     ::= { atmfM4LoggedAlarmEntry 5 }


-- ATM M4 MIB Notification types

-- Auxiliary definitions for alarms

-- Except for perceived severity, the following objects may be
-- optionally appended to any alarm notification.

atmfM4TrapAlarmSeverity OBJECT-TYPE
     SYNTAX    AtmfM4AlarmLogSeverity
     MAX-ACCESS     accessible-for-notify
     STATUS    current
     DESCRIPTION
          "The perceived severity of the alarm, as specified by
          the agent that generated it."
     ::= { atmfM4MIBObjects 43 }

atmfM4TrapAlarmBackedUp OBJECT-TYPE
     SYNTAX    TruthValue
     MAX-ACCESS     accessible-for-notify
     STATUS    current
     DESCRIPTION
          "If the value of this object is true, the failed object
          has been backed up."
     ::= { atmfM4MIBObjects 44 }

atmfM4TrapAlarmBUObject OBJECT-TYPE
     SYNTAX    RowPointer
     MAX-ACCESS     accessible-for-notify
     STATUS    current
     DESCRIPTION
          "Indicates the object that provided back-up services to
          the failed object."
     ::= { atmfM4MIBObjects 45 }

atmfM4TrapAlarmSpecificProb OBJECT-TYPE
     SYNTAX    DisplayString
     MAX-ACCESS     accessible-for-notify
     STATUS    current
     DESCRIPTION
          "Indicates further refinements to the problem identified
          by the alarm type.  If more than one specific problem
          is described in this object, the problem descriptions are
          separated by newline characters."
     ::= { atmfM4MIBObjects 46 }

atmfM4TrapAlarmRepairAct OBJECT-TYPE
     SYNTAX    DisplayString
     MAX-ACCESS     accessible-for-notify
     STATUS    current
     DESCRIPTION
          "Indicates proposed repair actions reported by the agent
          for the problem identified by the alarm.  If more than
          one action is described in this object, the problem
          descriptions are separated by newline characters."
     ::= { atmfM4MIBObjects 47 }


-- ATM M4 MIB Notifications

-- Note that index values for interfaces, hardware units, VPL TPs,
-- VCL TPs, etc. can be derived from the instance values of the
-- objects included in the notifications.  As examples, the ifIndex
-- value for an interface can be derived from the ifOperStatus
-- instance value, whereas the entPhysicalIndex value can be derived
-- from any of the entPhysicalContainedIn, entPhysicalParentRelPos,
-- and entPhysicalClass instance values.


-- Communications Alarms (interface)

atmfM4IfAisAlarm NOTIFICATION-TYPE
     OBJECTS   { ifOperStatus, atmfM4TrapAlarmSeverity }
     STATUS    current
     DESCRIPTION
          "Indicates that an AIS alarm condition has occurred
          on the physical path TP associated with the specified
          interface."
     ::= { atmfM4MIBTrapPrefix 1 }

atmfM4IfLcdAlarm NOTIFICATION-TYPE
     OBJECTS   { ifOperStatus, atmfM4TrapAlarmSeverity }
     STATUS    current
     DESCRIPTION
          "Indicates that an LCD (Loss of Cell Delineation)
          condition has occurred on the TC Adapter associated
          with the specified interface."
     ::= { atmfM4MIBTrapPrefix 2 }

atmfM4IfLofAlarm NOTIFICATION-TYPE
     OBJECTS   { ifOperStatus, atmfM4TrapAlarmSeverity }
     STATUS    current
     DESCRIPTION
          "Indicates that an LOF (Loss of Frame)
          condition has occurred on the physical path TP associated
          with the specified interface."
     ::= { atmfM4MIBTrapPrefix 3 }

atmfM4IfLopAlarm NOTIFICATION-TYPE
     OBJECTS   { ifOperStatus, atmfM4TrapAlarmSeverity }
     STATUS    current
     DESCRIPTION
          "Indicates that an LOP (Loss of Pointer)
          condition has occurred on the physical path TP associated
          with the specified interface."
     ::= { atmfM4MIBTrapPrefix 4 }

atmfM4IfLosAlarm NOTIFICATION-TYPE
     OBJECTS   { ifOperStatus, atmfM4TrapAlarmSeverity }
     STATUS    current
     DESCRIPTION
          "Indicates that an LOS (Loss of Signal)
          condition has occurred on the physical path TP associated
          with the specified interface."
     ::= { atmfM4MIBTrapPrefix 5 }

atmfM4IfPayloadMismatchAlarm NOTIFICATION-TYPE
     OBJECTS   { ifOperStatus, atmfM4TrapAlarmSeverity }
     STATUS    current
     DESCRIPTION
          "Indicates that a payload type mismatch condition has
          occurred on the physical path TP associated with the specified
          interface."
     ::= { atmfM4MIBTrapPrefix 6 }

atmfM4IfXmissionErrAlarm NOTIFICATION-TYPE
     OBJECTS   { ifOperStatus, atmfM4TrapAlarmSeverity }
     STATUS    current
     DESCRIPTION
          "Indicates that an transmission error condition has occurred
          on the physical path TP associated with the specified
          interface."
     ::= { atmfM4MIBTrapPrefix 7 }

atmfM4IfPathTraceMismatchAlarm NOTIFICATION-TYPE
     OBJECTS   { ifOperStatus, atmfM4TrapAlarmSeverity }
     STATUS    current
     DESCRIPTION
          "Indicates that path trace mismatch condition has occurred
          on the physical path TP associated with the specified
          interface."
     ::= { atmfM4MIBTrapPrefix 8 }

atmfM4IfRdiAlarm NOTIFICATION-TYPE
     OBJECTS   { ifOperStatus, atmfM4TrapAlarmSeverity }
     STATUS    current
     DESCRIPTION
          "Indicates that an RDI (Remote Defect Indication)
          condition has occurred on the physical path TP associated
          with the specified interface."
     ::= { atmfM4MIBTrapPrefix 9 }

atmfM4IfSignalLabelMismatchAlarm NOTIFICATION-TYPE
     OBJECTS   { ifOperStatus, atmfM4TrapAlarmSeverity }
     STATUS    current
     DESCRIPTION
          "Indicates that a signal label mismatch has occurred
          on the physical path TP associated with the specified
          interface."
     ::= { atmfM4MIBTrapPrefix 10 }


-- Communications alarms (VPL termination point)

atmfM4VplTpAisAlarm NOTIFICATION-TYPE
     OBJECTS   { ifOperStatus,
                 atmVplOperStatus,
                 atmfM4TrapAlarmSeverity
                 }
     STATUS    current
     DESCRIPTION
          "Indicates that an AIS alarm condition has occurred
          on the VPL TP associated with the specified
          interface and VPI."
     ::= { atmfM4MIBTrapPrefix 11 }

atmfM4VplTpRdiAlarm NOTIFICATION-TYPE
     OBJECTS   { ifOperStatus,
                 atmVplOperStatus,
                 atmfM4TrapAlarmSeverity
                 }
     STATUS    current
     DESCRIPTION
          "Indicates that an RDI (Remote Defect Indication)
          condition has occurred on the VPL TP associated
          with the specified interface and VPI."
     ::= { atmfM4MIBTrapPrefix 12 }


-- Communications alarms (VPC termination point)

atmfM4VpcTpAisAlarm NOTIFICATION-TYPE
     OBJECTS   { ifOperStatus,
                 atmVplOperStatus,
                 atmfM4TrapAlarmSeverity
                 }
     STATUS    current
     DESCRIPTION
          "Indicates that an AIS alarm condition has occurred
          on the VPC TP associated with the specified
          interface and VPI."
     ::= { atmfM4MIBTrapPrefix 13 }

atmfM4VpcTpRdiAlarm NOTIFICATION-TYPE
     OBJECTS   { ifOperStatus,
                 atmVplOperStatus,
                 atmfM4TrapAlarmSeverity
                 }
     STATUS    current
     DESCRIPTION
          "Indicates that an RDI (Remote Defect Indication)
          condition has occurred on the VPC TP associated
          with the specified interface and VPI."
     ::= { atmfM4MIBTrapPrefix 14 }


-- Communications alarms (VCL termination point)

atmfM4VclTpAisAlarm NOTIFICATION-TYPE
     OBJECTS   { ifOperStatus,
                 atmVclOperStatus,
                 atmfM4TrapAlarmSeverity
                 }
     STATUS    current
     DESCRIPTION
          "Indicates that an AIS alarm condition has occurred
          on the VCL TP associated with the specified
          interface, VPI, and VCI."
     ::= { atmfM4MIBTrapPrefix 15 }

atmfM4VclTpRdiAlarm NOTIFICATION-TYPE
     OBJECTS   { ifOperStatus,
                 atmVclOperStatus,
                 atmfM4TrapAlarmSeverity
                 }
     STATUS    current
     DESCRIPTION
          "Indicates that an RDI (Remote Defect Indication)
          condition has occurred on the VCL TP associated
          with the specified interface, VPI, and VCI."
     ::= { atmfM4MIBTrapPrefix 16 }


-- Communications alarms (VCC termination point)

atmfM4VccTpAisAlarm NOTIFICATION-TYPE
     OBJECTS   { ifOperStatus,
                 atmVclOperStatus,
                 atmfM4TrapAlarmSeverity
                 }
     STATUS    current
     DESCRIPTION
          "Indicates that an AIS alarm condition has occurred
          on the VCC TP associated with the specified
          interface, VPI, and VCI."
     ::= { atmfM4MIBTrapPrefix 17 }

atmfM4VccTpRdiAlarm NOTIFICATION-TYPE
     OBJECTS   { ifOperStatus,
                 atmVclOperStatus,
                 atmfM4TrapAlarmSeverity
                 }
     STATUS    current
     DESCRIPTION
          "Indicates that an RDI (Remote Defect Indication)
          condition has occurred on the VCC TP associated
          with the specified interface, VPI, and VCI."
     ::= { atmfM4MIBTrapPrefix 18 }


-- ATM NE and Hardware Unit Alarms

atmfM4HwBackPlaneAlarm NOTIFICATION-TYPE
     OBJECTS   { entPhysicalContainedIn,
                 entPhysicalParentRelPos,
                 entPhysicalClass,
                 atmfM4TrapAlarmSeverity
                 }
     STATUS    current
     DESCRIPTION
          "Indicates that a back-plane failure condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 19 }

atmfM4HwCallEstErrAlarm NOTIFICATION-TYPE
     OBJECTS   { entPhysicalContainedIn,
                 entPhysicalParentRelPos,
                 entPhysicalClass,
                 atmfM4TrapAlarmSeverity
                 }
     STATUS    current
     DESCRIPTION
          "Indicates that a call establishment error condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 20 }

atmfM4HwCongestionAlarm NOTIFICATION-TYPE
     OBJECTS   { entPhysicalContainedIn,
                 entPhysicalParentRelPos,
                 entPhysicalClass,
                 atmfM4TrapAlarmSeverity
                 }
     STATUS    current
     DESCRIPTION
          "Indicates that a congestion condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 21 }

atmfM4HwExtIfDevProbAlarm NOTIFICATION-TYPE
     OBJECTS   { entPhysicalContainedIn,
                 entPhysicalParentRelPos,
                 entPhysicalClass,
                 atmfM4TrapAlarmSeverity
                 }
     STATUS    current
     DESCRIPTION
          "Indicates that an external interface device problem
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 22 }

atmfM4HwLineCardAlarm NOTIFICATION-TYPE
     OBJECTS   { entPhysicalContainedIn,
                 entPhysicalParentRelPos,
                 entPhysicalClass,
                 atmfM4TrapAlarmSeverity
                 }
     STATUS    current
     DESCRIPTION
          "Indicates that a line-card problem condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 23 }

atmfM4HwMultiplexerAlarm NOTIFICATION-TYPE
     OBJECTS   { entPhysicalContainedIn,
                 entPhysicalParentRelPos,
                 entPhysicalClass,
                 atmfM4TrapAlarmSeverity
                 }
     STATUS    current
     DESCRIPTION
          "Indicates that a multiplexer problem condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 24 }

atmfM4HwPowerAlarm NOTIFICATION-TYPE
     OBJECTS   { entPhysicalContainedIn,
                 entPhysicalParentRelPos,
                 entPhysicalClass,
                 atmfM4TrapAlarmSeverity
                 }
     STATUS    current
     DESCRIPTION
          "Indicates that a power problem alarm condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 25 }

atmfM4HwProcessorAlarm NOTIFICATION-TYPE
     OBJECTS   { entPhysicalContainedIn,
                 entPhysicalParentRelPos,
                 entPhysicalClass,
                 atmfM4TrapAlarmSeverity
                 }
     STATUS    current
     DESCRIPTION
          "Indicates that a processor problem alarm condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 26 }

atmfM4HwProtectionPathAlarm NOTIFICATION-TYPE
     OBJECTS   { entPhysicalContainedIn,
                 entPhysicalParentRelPos,
                 entPhysicalClass,
                 atmfM4TrapAlarmSeverity
                 }
     STATUS    current
     DESCRIPTION
          "Indicates that a protection path problem condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 27 }

atmfM4HwReceiverFailAlarm NOTIFICATION-TYPE
     OBJECTS   { entPhysicalContainedIn,
                 entPhysicalParentRelPos,
                 entPhysicalClass,
                 atmfM4TrapAlarmSeverity
                 }
     STATUS    current
     DESCRIPTION
          "Indicates that a receiver failure condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 28 }

atmfM4HwPIUnitMissingAlarm NOTIFICATION-TYPE
     OBJECTS   { entPhysicalContainedIn,
                 entPhysicalParentRelPos,
                 entPhysicalClass,
                 atmfM4TrapAlarmSeverity
                 }
     STATUS    current
     DESCRIPTION
          "Indicates that a plug-in unit missing condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 29 }

atmfM4HwPIUnitProbAlarm NOTIFICATION-TYPE
     OBJECTS   { entPhysicalContainedIn,
                 entPhysicalParentRelPos,
                 entPhysicalClass,
                 atmfM4TrapAlarmSeverity
                 }
     STATUS    current
     DESCRIPTION
          "Indicates that a plug-in unit problem condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 30 }

atmfM4HwPIUnitMismatchAlarm NOTIFICATION-TYPE
     OBJECTS   { entPhysicalContainedIn,
                 entPhysicalParentRelPos,
                 entPhysicalClass,
                 atmfM4TrapAlarmSeverity
                 }
     STATUS    current
     DESCRIPTION
          "Indicates that a plug-in unit type mismatch condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 31 }

atmfM4HwTimingProbAlarm NOTIFICATION-TYPE
     OBJECTS   { entPhysicalContainedIn,
                 entPhysicalParentRelPos,
                 entPhysicalClass,
                 atmfM4TrapAlarmSeverity
                 }
     STATUS    current
     DESCRIPTION
          "Indicates that a timing problem alarm condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 32 }

atmfM4HwXmitterFailAlarm NOTIFICATION-TYPE
     OBJECTS   { entPhysicalContainedIn,
                 entPhysicalParentRelPos,
                 entPhysicalClass,
                 atmfM4TrapAlarmSeverity
                 }
     STATUS    current
     DESCRIPTION
          "Indicates that a transmitter failure condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 33 }

atmfM4HwTrunkCardAlarm NOTIFICATION-TYPE
     OBJECTS   { entPhysicalContainedIn,
                 entPhysicalParentRelPos,
                 entPhysicalClass,
                 atmfM4TrapAlarmSeverity
                 }
     STATUS    current
     DESCRIPTION
          "Indicates that a trunk-card problem condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 34 }

atmfM4HwStorageCapacityAlarm NOTIFICATION-TYPE
     OBJECTS   { entPhysicalContainedIn,
                 entPhysicalParentRelPos,
                 entPhysicalClass,
                 atmfM4TrapAlarmSeverity
                 }
     STATUS    current
     DESCRIPTION
          "Indicates that a storage capacity problem condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 35 }

atmfM4HwMemoryMismatchAlarm NOTIFICATION-TYPE
     OBJECTS   { entPhysicalContainedIn,
                 entPhysicalParentRelPos,
                 entPhysicalClass,
                 atmfM4TrapAlarmSeverity
                 }
     STATUS    current
     DESCRIPTION
          "Indicates that a memory mismatch alarm condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 36 }

atmfM4HwCorruptDataAlarm NOTIFICATION-TYPE
     OBJECTS   { entPhysicalContainedIn,
                 entPhysicalParentRelPos,
                 entPhysicalClass,
                 atmfM4TrapAlarmSeverity
                 }
     STATUS    current
     DESCRIPTION
          "Indicates that a corrupt data alarm condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 37 }

atmfM4HwSwEnvironAlarm NOTIFICATION-TYPE
     OBJECTS   { entPhysicalContainedIn,
                 entPhysicalParentRelPos,
                 entPhysicalClass,
                 atmfM4TrapAlarmSeverity
                 }
     STATUS    current
     DESCRIPTION
          "Indicates that a software environment problem
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 38 }

atmfM4HwSwDownloadFailAlarm NOTIFICATION-TYPE
     OBJECTS   { entPhysicalContainedIn,
                 entPhysicalParentRelPos,
                 entPhysicalClass,
                 atmfM4TrapAlarmSeverity
                 }
     STATUS    current
     DESCRIPTION
          "Indicates that a software download failure
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 39 }

atmfM4HwVersionMismatchAlarm NOTIFICATION-TYPE
     OBJECTS   { entPhysicalContainedIn,
                 entPhysicalParentRelPos,
                 entPhysicalClass,
                 atmfM4TrapAlarmSeverity
                 }
     STATUS    current
     DESCRIPTION
          "Indicates that a version mismatch condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 40 }

atmfM4HwFanFailAlarm NOTIFICATION-TYPE
     OBJECTS   { entPhysicalContainedIn,
                 entPhysicalParentRelPos,
                 entPhysicalClass,
                 atmfM4TrapAlarmSeverity
                 }
     STATUS    current
     DESCRIPTION
          "Indicates that a cooling fan failure condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 41 }

atmfM4HwDoorOpenAlarm NOTIFICATION-TYPE
     OBJECTS   { entPhysicalContainedIn,
                 entPhysicalParentRelPos,
                 entPhysicalClass,
                 atmfM4TrapAlarmSeverity
                 }
     STATUS    current
     DESCRIPTION
          "Indicates that an enclosure door open condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 42 }

atmfM4HwFuseFailAlarm NOTIFICATION-TYPE
     OBJECTS   { entPhysicalContainedIn,
                 entPhysicalParentRelPos,
                 entPhysicalClass,
                 atmfM4TrapAlarmSeverity
                 }
     STATUS    current
     DESCRIPTION
          "Indicates that a fuse failure alarm condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 43 }

atmfM4HwHighTempAlarm NOTIFICATION-TYPE
     OBJECTS   { entPhysicalContainedIn,
                 entPhysicalParentRelPos,
                 entPhysicalClass,
                 atmfM4TrapAlarmSeverity
                 }
     STATUS    current
     DESCRIPTION
          "Indicates that a high temperature condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 44 }


-- Software alarms

atmfM4SwVersionMismatchAlarm NOTIFICATION-TYPE
     OBJECTS   { entPhysicalContainedIn,
                 entPhysicalParentRelPos,
                 entPhysicalClass,
                 atmfM4HwInstalledSwSwIndex,
                 atmfM4TrapAlarmSeverity
                 }
     STATUS    current
     DESCRIPTION
          "Indicates that a version mismatch condition
          has occurred on the hardware unit associated
          with the specified index.

          An entPhysicalClass of unknown(2) along with
          both an entPhysicalContainedIn of 0 and an
          entPhysicalParentRelPos of -1 indicates that
          the error occurred in the ATM NE but not in any
          one hardware unit maintained in the MIB table."
     ::= { atmfM4MIBTrapPrefix 45 }


--  State change notification traps

atmfM4VplTpUp NOTIFICATION-TYPE
     OBJECTS   { ifOperStatus, atmVplOperStatus }
     STATUS    current
     DESCRIPTION
          "Indicates that the operational state of the specified
          VPL termination point has transitioned to 'up'."
     ::= { atmfM4MIBTrapPrefix 46 }

atmfM4VplTpDown NOTIFICATION-TYPE
     OBJECTS   { ifOperStatus, atmVplOperStatus }
     STATUS    current
     DESCRIPTION
          "Indicates that the operational state of the specified
          VPL termination point has transitioned to 'down'."
     ::= { atmfM4MIBTrapPrefix 47 }

atmfM4VclTpUp NOTIFICATION-TYPE
     OBJECTS   { ifOperStatus, atmVclOperStatus }
     STATUS    current
     DESCRIPTION
          "Indicates that the operational state of the specified
          VCL termination point has transitioned to 'up'."
     ::= { atmfM4MIBTrapPrefix 48 }

atmfM4VclTpDown NOTIFICATION-TYPE
     OBJECTS   { ifOperStatus, atmVclOperStatus }
     STATUS    current
     DESCRIPTION
          "Indicates that the operational state of the specified
          VCL termination point has transitioned to 'down'."
     ::= { atmfM4MIBTrapPrefix 49 }

atmfM4VplXConnUp NOTIFICATION-TYPE
     OBJECTS   { atmVpCrossConnectL2HOperStatus,
                 atmVpCrossConnectH2LOperStatus
                 }
     STATUS    current
     DESCRIPTION
          "Indicates that the operational state of the specified
          VPL cross-connection has transitioned to 'up'."
     ::= { atmfM4MIBTrapPrefix 50 }

atmfM4VplXConnDown NOTIFICATION-TYPE
     OBJECTS   { atmVpCrossConnectL2HOperStatus,
                 atmVpCrossConnectH2LOperStatus
                 }
     STATUS    current
     DESCRIPTION
          "Indicates that the operational state of the specified
          VPL cross-connection has transitioned to 'down'."
     ::= { atmfM4MIBTrapPrefix 51 }

atmfM4VclXConnUp NOTIFICATION-TYPE
     OBJECTS   { atmVcCrossConnectL2HOperStatus,
                 atmVcCrossConnectH2LOperStatus
                 }
     STATUS    current
     DESCRIPTION
          "Indicates that the operational state of the specified
          VCL cross-connection has transitioned to 'up'."
     ::= { atmfM4MIBTrapPrefix 52 }

atmfM4VclXConnDown NOTIFICATION-TYPE
     OBJECTS   { atmVcCrossConnectL2HOperStatus,
                 atmVcCrossConnectH2LOperStatus
                 }
     STATUS    current
     DESCRIPTION
          "Indicates that the operational state of the specified
          VCL cross-connection has transitioned to 'down'."
     ::= { atmfM4MIBTrapPrefix 53 }

atmfM4HwUnitUp NOTIFICATION-TYPE
     OBJECTS   { entPhysicalContainedIn,
                 entPhysicalParentRelPos,
                 entPhysicalClass
                 }
     STATUS    current
     DESCRIPTION
          "Indicates that the operational state of the specified
          hardware unit has transitioned to 'up'."
     ::= { atmfM4MIBTrapPrefix 54 }

atmfM4HwUnitDown NOTIFICATION-TYPE
     OBJECTS   { entPhysicalContainedIn,
                 entPhysicalParentRelPos,
                 entPhysicalClass
                 }
     STATUS    current
     DESCRIPTION
          "Indicates that the operational state of the specified
          hardware unit has transitioned to 'down'."
     ::= { atmfM4MIBTrapPrefix 55 }


-- Object creation and deletion notification traps

atmfM4AtmCellIfCreated NOTIFICATION-TYPE
     OBJECTS   { ifOperStatus, atmfM4IfType }
     STATUS    current
     DESCRIPTION
          "Indicates that an ATM cell layer interface has just
          been created on the interface."
     ::= { atmfM4MIBTrapPrefix 56 }

atmfM4AtmCellIfDeleted NOTIFICATION-TYPE
     OBJECTS   { ifOperStatus }
     STATUS    current
     DESCRIPTION
          "Indicates that the ATM cell layer interface has just
          been deleted."
     ::= { atmfM4MIBTrapPrefix 57 }

atmfM4VpcTpCreated NOTIFICATION-TYPE
     OBJECTS   { ifOperStatus, atmVplOperStatus }
     STATUS    current
     DESCRIPTION
          "Indicates that the VPC termination point has just
          been created."
     ::= { atmfM4MIBTrapPrefix 58 }

atmfM4VpcTpDeleted NOTIFICATION-TYPE
     OBJECTS   { ifOperStatus, atmVplOperStatus }
     STATUS    current
     DESCRIPTION
          "Indicates that the VPC termination point has just
          been deleted."
     ::= { atmfM4MIBTrapPrefix 59 }

atmfM4VccTpCreated NOTIFICATION-TYPE
     OBJECTS   { ifOperStatus, atmVclOperStatus }
     STATUS    current
     DESCRIPTION
          "Indicates that the VCC termination point has just
          been created."
     ::= { atmfM4MIBTrapPrefix 60 }

atmfM4VccTpDeleted NOTIFICATION-TYPE
     OBJECTS   { ifOperStatus, atmVclOperStatus }
     STATUS    current
     DESCRIPTION
          "Indicates that the VCC termination point has just
          been deleted."
     ::= { atmfM4MIBTrapPrefix 61 }

atmfM4VplXConnCreated NOTIFICATION-TYPE
     OBJECTS   { atmVpCrossConnectL2HOperStatus,
                 atmVpCrossConnectH2LOperStatus
                 }
     STATUS    current
     DESCRIPTION
          "Indicates that the VPL cross-connection has just
          been created.  When a cross-connection is created along
          with its VPL endpoints, this trap should be emitted
          to indicate the creation of the entire group of objects."
     ::= { atmfM4MIBTrapPrefix 62 }

atmfM4VplXConnDeleted NOTIFICATION-TYPE
     OBJECTS   { atmVpCrossConnectL2HOperStatus,
                 atmVpCrossConnectH2LOperStatus
                 }
     STATUS    current
     DESCRIPTION
          "Indicates that the VPL cross-connection has just
          been deleted.  When a cross-connection is deleted along
          with its VPL endpoints, this trap should be emitted
          to indicate the deletion of the entire group of objects."
     ::= { atmfM4MIBTrapPrefix 63 }

atmfM4VclXConnCreated NOTIFICATION-TYPE
     OBJECTS   { atmVcCrossConnectL2HOperStatus,
                 atmVcCrossConnectH2LOperStatus
                 }
     STATUS    current
     DESCRIPTION
          "Indicates that the VCL cross-connection has just
          been created.  When a cross-connection is created along
          with its VCL endpoints, this trap should be emitted
          to indicate the creation of the entire group of objects."
     ::= { atmfM4MIBTrapPrefix 64 }

atmfM4VclXConnDeleted NOTIFICATION-TYPE
     OBJECTS   { atmVcCrossConnectL2HOperStatus,
                 atmVcCrossConnectH2LOperStatus
                 }
     STATUS    current
     DESCRIPTION
          "Indicates that the VCL cross-connection has just
          been deleted.  When a cross-connection is deleted along
          with its VCL endpoints, this trap should be emitted
          to indicate the deletion of the entire group of objects."
     ::= { atmfM4MIBTrapPrefix 65 }

atmfM4HwUnitCreated NOTIFICATION-TYPE
     OBJECTS   { entPhysicalContainedIn,
                 entPhysicalParentRelPos,
                 entPhysicalClass
                 }
     STATUS    current
     DESCRIPTION
          "Indicates that the specified hardware unit has been
          installed at the specified location."
     ::= { atmfM4MIBTrapPrefix 66 }

atmfM4HwUnitDeleted NOTIFICATION-TYPE
     OBJECTS   { entPhysicalContainedIn,
                 entPhysicalParentRelPos,
                 entPhysicalClass
                 }
     STATUS    current
     DESCRIPTION
          "Indicates that the specified hardware unit has been
          removed or de-installed from the specified location."
     ::= { atmfM4MIBTrapPrefix 67 }

atmfM4InstalledSwCreated NOTIFICATION-TYPE
     OBJECTS   { atmfM4HwInstalledSwSwIndex,
                 hrSWInstalledIndex,
                 hrSWInstalledName
                 }
     STATUS    current
     DESCRIPTION
          "Indicates that the specified software package has been
          installed."
     ::= { atmfM4MIBTrapPrefix 68 }

atmfM4InstalledSwDeleted NOTIFICATION-TYPE
     OBJECTS   { atmfM4HwInstalledSwSwIndex,
                 hrSWInstalledIndex,
                 hrSWInstalledName
                 }
     STATUS    current
     DESCRIPTION
          "Indicates that the specified software package has been
          removed."
     ::= { atmfM4MIBTrapPrefix 69 }


--  Configuration change notification traps

atmfM4IfChanged NOTIFICATION-TYPE
     OBJECTS   { ifOperStatus }
     STATUS    current
     DESCRIPTION
          "Indicates that the configuration of the interface has
          been changed."
     ::= { atmfM4MIBTrapPrefix 70 }

atmfM4VplTpChanged NOTIFICATION-TYPE
     OBJECTS   { ifOperStatus, atmVplOperStatus }
     STATUS    current
     DESCRIPTION
          "Indicates that the VPL termination point configuration
          has been changed."
     ::= { atmfM4MIBTrapPrefix 71 }

atmfM4VclTpChanged NOTIFICATION-TYPE
     OBJECTS   { ifOperStatus, atmVclOperStatus }
     STATUS    current
     DESCRIPTION
          "Indicates that the VCL termination point configuration
          has been changed."
     ::= { atmfM4MIBTrapPrefix 72 }

atmfM4VplXConnChanged NOTIFICATION-TYPE
     OBJECTS   { atmVpCrossConnectL2HOperStatus,
                 atmVpCrossConnectH2LOperStatus
                 }
     STATUS    current
     DESCRIPTION
          "Indicates that the VPL cross-connection configuration
          has been changed."
     ::= { atmfM4MIBTrapPrefix 73 }

atmfM4VclXConnChanged NOTIFICATION-TYPE
     OBJECTS   { atmVcCrossConnectL2HOperStatus,
                 atmVcCrossConnectH2LOperStatus
                 }
     STATUS    current
     DESCRIPTION
          "Indicates that the VCL cross-connection configuration
          has been changed."
     ::= { atmfM4MIBTrapPrefix 74 }

atmfM4HwUnitChanged NOTIFICATION-TYPE
     OBJECTS   { entPhysicalContainedIn,
                 entPhysicalParentRelPos,
                 entPhysicalClass
                 }
     STATUS    current
     DESCRIPTION
          "Indicates that the specified hardware unit configuration
          has changed."
     ::= { atmfM4MIBTrapPrefix 75 }

atmfM4InstalledSwChanged NOTIFICATION-TYPE
     OBJECTS   { hrSWInstalledIndex }
     STATUS    current
     DESCRIPTION
          "Indicates that the specified software package configuration
          has changed."
     ::= { atmfM4MIBTrapPrefix 76 }


-- Conformance statements


atmfM4Groups      OBJECT IDENTIFIER ::= { atmfM4MIBConformance 1 }
atmfM4Compliances OBJECT IDENTIFIER ::= { atmfM4MIBConformance 2 }

-- compliance statements

atmfM4Compliance MODULE-COMPLIANCE
     STATUS    current
     DESCRIPTION
          "The compliance statements are listed as a set up conformance
          units that correspond to each table.  Support for all tables
          is mandatory."
     MODULE  -- this module
     MANDATORY-GROUPS {
          atmfM4General,
          atmfM4PhysPathTpGroup,
          atmfM4TcAdapterGroup,
          atmfM4AtmLayerGroup,
          atmfM4VplGroup,
          atmfM4VclGroup,
          atmfM4VpXConnGroup,
          atmfM4VcXConnGroup,
          atmfM4VpNextVpiGroup,
          atmfM4VcNextVciGroup,
          atmfM4CellProtoCurrGroup,
          atmfM4CellProtoHistGroup,
          atmfM4CellProtoErrorGroup,
          atmfM4TcProtoCurrGroup,
          atmfM4TcProtoHistGroup,
          atmfM4VpUpcNpcCurrGroup,
          atmfM4VpUpcNpcHistGroup,
          atmfM4VcUpcNpcCurrGroup,
          atmfM4VcUpcNpcHistGroup,
          atmfM4VpTestGroup,
          atmfM4VcTestGroup,
          atmfM4EquipGroup,
          atmfM4EquipHolderGroup,
          atmfM4PlugInUnitGroup,
          atmfM4HwRunningSwGroup,
          atmfM4HwInstalledSwGroup,
          atmfM4AlarmSevGroup,
          atmfM4TrapForwardingGroup,
          atmfM4TrapLogGroup,
          atmfM4LoggedTrapGroup,
          atmfM4LoggedAlarmGroup,
          atmfM4NotificationsGroup
          }

     OBJECT atmfM4TcACellScrambling
     MIN-ACCESS     not-accessible
     DESCRIPTION
          "Support for this object is required only for a TC Adapter
          which allows deactivation of cell scrambling."

     OBJECT atmfM4IfLoopbackLocationCode
     MIN-ACCESS     not-accessible
     DESCRIPTION
          "Support for this object is only required for an ATM cell
          layer interface whose atmfM4IfType is not none(0)."

     OBJECT atmfM4IfSubscriberAddress
     MIN-ACCESS     not-accessible
     DESCRIPTION
          "Support for this object is required only for an ATM cell
          layer interface whose atmfM4IfType is uni(1)."

     OBJECT atmfM4IfPreferredCarrier
     MIN-ACCESS     not-accessible
     DESCRIPTION
          "Support for this object is only required for an ATM cell
          layer interface whose atmfM4IfType is uni(1) and which
          supports SVC services."

     OBJECT atmfM4IfFarEndCarrierNetwork
     MIN-ACCESS     not-accessible
     DESCRIPTION
          "Support for this object is only required for an ATM cell
          layer interface whose atmfM4IfType is bici(2) and which
          supports SVC services."

     OBJECT atmfM4VpNextVpiValue
     MIN-ACCESS     not-accessible
     DESCRIPTION
          "Support for this object to supply unused VPI values for
          use in creating entries in the atmVplTable is optional."

     OBJECT atmfM4VcNextVciValue
     MIN-ACCESS     not-accessible
     DESCRIPTION
          "Support for this object to supply unused VCI values for
          use in creating entries in the atmVclTable is optional."

     OBJECT atmfM4VpUpcNpcCurrDiscardedClp0
     MIN-ACCESS     not-accessible
     DESCRIPTION
          "Support for this object is required only if CLP=0 traffic
          is separately policed."

     OBJECT atmfM4VpUpcNpcCurrPassedClp0
     MIN-ACCESS     not-accessible
     DESCRIPTION
          "Support for this object is required only if CLP=0 traffic
          is separately policed."

     OBJECT atmfM4VpUpcNpcHistDiscardedClp0
     MIN-ACCESS     not-accessible
     DESCRIPTION
          "Support for this object is required only if CLP=0 traffic
          is separately policed."

     OBJECT atmfM4VpUpcNpcHistPassedClp0
     MIN-ACCESS     not-accessible
     DESCRIPTION
          "Support for this object is required only if CLP=0 traffic
          is separately policed."

     OBJECT atmfM4VcUpcNpcCurrDiscardedClp0
     MIN-ACCESS     not-accessible
     DESCRIPTION
          "Support for this object is required only if CLP=0 traffic
          is separately policed."

     OBJECT atmfM4VcUpcNpcCurrPassedClp0
     MIN-ACCESS     not-accessible
     DESCRIPTION
          "Support for this object is required only if CLP=0 traffic
          is separately policed."

     OBJECT atmfM4VcUpcNpcHistDiscardedClp0
     MIN-ACCESS     not-accessible
     DESCRIPTION
          "Support for this object is required only if CLP=0 traffic
          is separately policed."

     OBJECT atmfM4VcUpcNpcHistPassedClp0
     MIN-ACCESS     not-accessible
     DESCRIPTION
          "Support for this object is required only if CLP=0 traffic
          is separately policed."

     OBJECT atmfM4EquipHolderAcceptableTypes
     MIN-ACCESS     not-accessible
     DESCRIPTION
          "Support for this object is required only for an Equipment
          Holder that represents a slot."

     OBJECT atmfM4EquipHolderSlotStatus
     MIN-ACCESS     not-accessible
     DESCRIPTION
          "Support for this object is required only for an Equipment
          Holder that represents a slot."

     OBJECT atmfM4EquipHolderSwLoad
     MIN-ACCESS     not-accessible
     DESCRIPTION
          "Support for this object is required only for an Equipment
          Holder that represents a slot."

     OBJECT atmfM4LoggedAlarmBackedUp
     MIN-ACCESS     not-accessible
     DESCRIPTION
          "Support for this object is required only for a logged alarm
          trap table entry whose corresponding alarm trap included the
          atmfM4TrapAlarmBackup object."

     OBJECT atmfM4LoggedAlarmBUObject
     MIN-ACCESS     not-accessible
     DESCRIPTION
          "Support for this object is required only for a logged alarm
          trap table entry whose corresponding alarm trap included the
          atmfM4TrapAlarmBUObject object."

     OBJECT atmfM4LoggedAlarmSpecificProb
     MIN-ACCESS     not-accessible
     DESCRIPTION
          "Support for this object is required only for a logged alarm
          trap table entry whose corresponding alarm trap included the
          atmfM4TrapAlarmSpecificProb object."

     OBJECT atmfM4LoggedAlarmRepairAct
     MIN-ACCESS     not-accessible
     DESCRIPTION
          "Support for this object is required only for a logged alarm
          trap table entry whose corresponding alarm trap included the
          atmfM4TrapAlarmRepairAct object."

     ::= { atmfM4Compliances 1 }

-- units of conformance

atmfM4General OBJECT-GROUP
     OBJECTS {
          atmfM4NeVendor,
          atmfM4NeVersion,
          atmfM4NeStartTime,
          atmfM4NeAlarmSeverityIndex,
          atmfM4NeSuppressZeroStats
          }
     STATUS    current
     DESCRIPTION
          "The ATM Forum M4 ATM NE high-level objects."
     ::= { atmfM4Groups 1}

atmfM4PhysPathTpGroup OBJECT-GROUP
     OBJECTS {
          atmfM4PhysPathTpHwUnitIndex,
          atmfM4PhysPathTpPortID,
          atmfM4PhysPathTpAlarmSeverityIndex
          }
     STATUS    current
     DESCRIPTION
          "The ATM Forum M4 interface Configuration table extensions
          for the physical path termination point."
     ::= { atmfM4Groups 2 }

atmfM4TcAdapterGroup OBJECT-GROUP
     OBJECTS {
          atmfM4TcACellScrambling,
          atmfM4TcAlarmSeverityIndex
          }
     STATUS    current
     DESCRIPTION
          "The ATM Forum M4 interface Configuration table extensions
          for the TC Adapter."
     ::= { atmfM4Groups 3 }

atmfM4AtmLayerGroup OBJECT-GROUP
     OBJECTS {
          atmfM4IfType,
          atmfM4IfLoopbackLocationCode,
          atmfM4IfSubscriberAddress,
          atmfM4IfPreferredCarrier,
          atmfM4IfFarEndCarrierNetwork
          }
     STATUS    current
     DESCRIPTION
          "The ATM Forum M4 interface Configuration table extensions
          for the ATM cell layer."
     ::= { atmfM4Groups 4 }

atmfM4VplGroup OBJECT-GROUP
     OBJECTS {
          atmfM4VplSegEndPt
          }
     STATUS    current
     DESCRIPTION
          "The ATM Forum M4 VPL Termination Point Configuration
          table extensions. "
     ::= { atmfM4Groups 5 }

atmfM4VclGroup OBJECT-GROUP
     OBJECTS {
          atmfM4VclSegEndPt
          }
     STATUS    current
     DESCRIPTION
          "The ATM Forum M4 VCL Termination Point Configuration
          table extensions."
     ::= { atmfM4Groups 6 }

atmfM4VpXConnGroup OBJECT-GROUP
     OBJECTS {
          atmfM4VpXConnRecover
          }
     STATUS    current
     DESCRIPTION
          "The ATM Forum M4 VP Cross-Connect Configuration table
          extensions."
     ::= { atmfM4Groups 7 }

atmfM4VcXConnGroup OBJECT-GROUP
     OBJECTS {
          atmfM4VcXConnRecover
          }
     STATUS    current
     DESCRIPTION
          "The ATM Forum M4 VC Cross-Connect Configuration table
          extensions."
     ::= { atmfM4Groups 8 }

atmfM4VpNextVpiGroup OBJECT-GROUP
     OBJECTS {
          atmfM4VpNextVpiValue
          }
     STATUS    current
     DESCRIPTION
          "The ATM Forum M4 VP Next VPI value table."
     ::= { atmfM4Groups 9 }

atmfM4VcNextVciGroup OBJECT-GROUP
     OBJECTS {
          atmfM4VcNextVciValue
          }
     STATUS    current
     DESCRIPTION
          "The ATM Forum M4 VC Next VCI value table."
     ::= { atmfM4Groups 10 }

atmfM4CellProtoCurrGroup OBJECT-GROUP
     OBJECTS {
          atmfM4CellProtoCurrSuspect,
          atmfM4CellProtoCurrElapsedTime,
          atmfM4CellProtoCurrSupprIntvls,
          atmfM4CellProtoCurrProtoErrors,
          atmfM4CellProtoCurrInOAMCells
          }
     STATUS    current
     DESCRIPTION
          "The ATM Forum M4 Cell Protocol Monitoring Current Data
          table."
     ::= { atmfM4Groups 11 }

atmfM4CellProtoHistGroup OBJECT-GROUP
     OBJECTS {
          atmfM4CellProtoHistSuspect,
          atmfM4CellProtoHistElapsedTime,
          atmfM4CellProtoHistSupprIntvls,
          atmfM4CellProtoHistProtoErrors,
          atmfM4CellProtoHistInOAMCells
          }
     STATUS    current
     DESCRIPTION
          "The ATM Forum M4 Cell Protocol Monitoring History Data
          table."
     ::= { atmfM4Groups 12 }

atmfM4CellProtoErrorGroup OBJECT-GROUP
     OBJECTS {
          atmfM4CellProtoErrorTime,
          atmfM4CellProtoErrorReason,
          atmfM4CellProtoErrorVpi,
          atmfM4CellProtoErrorVci
          }
     STATUS    current
     DESCRIPTION
          "The ATM Forum M4 Cell Protocol Monitoring Error Log table."
     ::= { atmfM4Groups 13 }

atmfM4TcProtoCurrGroup OBJECT-GROUP
     OBJECTS {
          atmfM4TcProtoCurrSuspect,
          atmfM4TcProtoCurrElapsedTime,
          atmfM4TcProtoCurrSupprIntvls,
          atmfM4TcProtoCurrDiscardHECViol
          }
     STATUS    current
     DESCRIPTION
          "The ATM Forum M4 TC Adapter Protocol Monitoring Current
          Data table."
     ::= { atmfM4Groups 14 }

atmfM4TcProtoHistGroup OBJECT-GROUP
     OBJECTS {
          atmfM4TcProtoHistSuspect,
          atmfM4TcProtoHistElapsedTime,
          atmfM4TcProtoHistSupprIntvls,
          atmfM4TcProtoHistDiscardHECViol
          }
     STATUS    current
     DESCRIPTION
          "The ATM Forum M4 TC Adapter Protocol Monitoring History
          Data table."
     ::= { atmfM4Groups 15 }

atmfM4VpUpcNpcCurrGroup OBJECT-GROUP
     OBJECTS {
          atmfM4VpUpcNpcCurrSuspect,
          atmfM4VpUpcNpcCurrElapsedTime,
          atmfM4VpUpcNpcCurrSupprIntvls,
          atmfM4VpUpcNpcCurrDiscardedCells,
          atmfM4VpUpcNpcCurrDiscardedClp0,
          atmfM4VpUpcNpcCurrPassedCells,
          atmfM4VpUpcNpcCurrPassedClp0
          }
     STATUS    current
     DESCRIPTION
          "The ATM Forum M4 UPC/NPC Disagreement Monitoring Current
          Data table for VPL termination points."
     ::= { atmfM4Groups 16 }

atmfM4VpUpcNpcHistGroup OBJECT-GROUP
     OBJECTS {
          atmfM4VpUpcNpcHistSuspect,
          atmfM4VpUpcNpcHistElapsedTime,
          atmfM4VpUpcNpcHistSupprIntvls,
          atmfM4VpUpcNpcHistDiscardedCells,
          atmfM4VpUpcNpcHistDiscardedClp0,
          atmfM4VpUpcNpcHistPassedCells,
          atmfM4VpUpcNpcHistPassedClp0
          }
     STATUS    current
     DESCRIPTION
          "The ATM Forum M4 UPC/NPC Disagreement Monitoring History
          Data table for VPL termination points."
     ::= { atmfM4Groups 17 }

atmfM4VcUpcNpcCurrGroup OBJECT-GROUP
     OBJECTS {
          atmfM4VcUpcNpcCurrSuspect,
          atmfM4VcUpcNpcCurrElapsedTime,
          atmfM4VcUpcNpcCurrSupprIntvls,
          atmfM4VcUpcNpcCurrDiscardedCells,
          atmfM4VcUpcNpcCurrDiscardedClp0,
          atmfM4VcUpcNpcCurrPassedCells,
          atmfM4VcUpcNpcCurrPassedClp0
          }
     STATUS    current
     DESCRIPTION
          "The ATM Forum M4 UPC/NPC Disagreement Monitoring Current
          Data table for VCL termination points."
     ::= { atmfM4Groups 18 }

atmfM4VcUpcNpcHistGroup OBJECT-GROUP
     OBJECTS {
          atmfM4VcUpcNpcHistSuspect,
          atmfM4VcUpcNpcHistElapsedTime,
          atmfM4VcUpcNpcHistSupprIntvls,
          atmfM4VcUpcNpcHistDiscardedCells,
          atmfM4VcUpcNpcHistDiscardedClp0,
          atmfM4VcUpcNpcHistPassedCells,
          atmfM4VcUpcNpcHistPassedClp0
          }
     STATUS    current
     DESCRIPTION
          "The ATM Forum M4 UPC/NPC Disagreement Monitoring History
          Data table for VCL termination points."
     ::= { atmfM4Groups 19 }

atmfM4VpTestGroup OBJECT-GROUP
     OBJECTS {
          atmfM4VpTestId,
          atmfM4VpTestStatus,
          atmfM4VpTestType,
          atmfM4VpTestResult,
          atmfM4VpTestCode,
          atmfM4VpTestOwner
          }
     STATUS    current
     DESCRIPTION
          "The ATM Forum M4 VP Termination Point Test table."
     ::= { atmfM4Groups 20 }

atmfM4VcTestGroup OBJECT-GROUP
     OBJECTS {
          atmfM4VcTestId,
          atmfM4VcTestStatus,
          atmfM4VcTestType,
          atmfM4VcTestResult,
          atmfM4VcTestCode,
          atmfM4VcTestOwner
          }
     STATUS    current
     DESCRIPTION
          "The ATM Forum M4 VC Termination Point Test table."
     ::= { atmfM4Groups 21 }

atmfM4EquipGroup OBJECT-GROUP
     OBJECTS {
          atmfM4EquipAdminStatus,
          atmfM4EquipLocation,
          atmfM4EquipOperStatus,
          atmfM4EquipVendor,
          atmfM4EquipVersion,
          atmfM4EquipUserLabel,
          atmfM4EquipAlarmSeverityIndex
          }
     STATUS    current
     DESCRIPTION
          "The ATM Forum M4 Equipment table."
     ::= { atmfM4Groups 22 }

atmfM4EquipHolderGroup OBJECT-GROUP
     OBJECTS {
          atmfM4EquipHolderType,
          atmfM4EquipHolderAcceptableTypes,
          atmfM4EquipHolderSlotStatus,
          atmfM4EquipHolderSwLoad
          }
     STATUS    current
     DESCRIPTION
          "The ATM Forum M4 Equipment Holder table."
     ::= { atmfM4Groups 23 }

atmfM4PlugInUnitGroup OBJECT-GROUP
     OBJECTS {
          atmfM4PlugInUnitAdminStatus,
          atmfM4PlugInUnitAvailStatus,
          atmfM4PlugInUnitOperStatus,
          atmfM4PlugInUnitVendor,
          atmfM4PlugInUnitVersion,
          atmfM4PlugInUnitAlarmSeverityIndex
          }
     STATUS    current
     DESCRIPTION
          "The ATM Forum M4 Plug-In Unit table."
     ::= { atmfM4Groups 24 }

atmfM4HwRunningSwGroup OBJECT-GROUP
     OBJECTS {
          atmfM4HwRunningSwSwIndex
          }
     STATUS    current
     DESCRIPTION
          "The ATM Forum M4 Hardware Unit/Running Software table."
     ::= { atmfM4Groups 25 }

atmfM4HwInstalledSwGroup OBJECT-GROUP
     OBJECTS {
          atmfM4HwInstalledSwSwIndex,
          atmfM4HwSwAlarmSeverityIndex
          }
     STATUS    current
     DESCRIPTION
          "The ATM Forum M4 Hardware Unit/Installed Software table."
     ::= { atmfM4Groups 26 }

atmfM4AlarmSevGroup OBJECT-GROUP
     OBJECTS {
          atmfM4AlarmSevProfileRowStatus,
          atmfM4AlarmSeverity,
          atmfM4AlarmSevDefault,
          atmfM4AlarmSevProfileIndexNext
          }
     STATUS    current
     DESCRIPTION
          "The ATM Forum M4 Alarm handling objects."
     ::= { atmfM4Groups 27 }

atmfM4TrapForwardingGroup OBJECT-GROUP
     OBJECTS {
          atmfM4TrapForwardingDest,
          atmfM4ForwardedTrapId,
          atmfM4ForwardedTrapObject,
          atmfM4TrapForwardingPort,
          atmfM4LowestForwardedSeverity,
          atmfM4ForwardedIndeterminate,
          atmfM4TrapForwardingRowStatus
          }
     STATUS    current
     DESCRIPTION
          "The ATM Forum M4 Trap forwarding table."
     ::= { atmfM4Groups 28 }

atmfM4TrapLogGroup OBJECT-GROUP
     OBJECTS {
          atmfM4TrapLogAdminStatus,
          atmfM4TrapLogOperStatus,
          atmfM4TrapLogFullAction,
          atmfM4TrapLogRowStatus
          }
     STATUS    current
     DESCRIPTION
          "The ATM Forum M4 Trap Agent log table."
     ::= { atmfM4Groups 29 }

atmfM4LoggedTrapGroup OBJECT-GROUP
     OBJECTS {
          atmfM4LoggedTrapTime,
          atmfM4LoggedTrapID,
          atmfM4LoggedTrapObject,
          atmfM4LoggedTrapRowStatus
          }
     STATUS    current
     DESCRIPTION
          "The ATM Forum M4 Trap Agent logged trap table."
     ::= { atmfM4Groups 30 }

atmfM4LoggedAlarmGroup OBJECT-GROUP
     OBJECTS {
          atmfM4LoggedAlarmSeverity,
          atmfM4LoggedAlarmBackedUp,
          atmfM4LoggedAlarmBUObject,
          atmfM4LoggedAlarmSpecificProb,
          atmfM4LoggedAlarmRepairAct,
          atmfM4TrapAlarmSeverity,
          atmfM4TrapAlarmBackedUp,
          atmfM4TrapAlarmBUObject,
          atmfM4TrapAlarmSpecificProb,
          atmfM4TrapAlarmRepairAct
          }
     STATUS    current
     DESCRIPTION
          "The ATM Forum M4 Trap Agent logged alarm trap table."
     ::= { atmfM4Groups 31 }

atmfM4NotificationsGroup NOTIFICATION-GROUP
     NOTIFICATIONS {
          atmfM4IfAisAlarm,
          atmfM4IfLcdAlarm,
          atmfM4IfLofAlarm,
          atmfM4IfLopAlarm,
          atmfM4IfLosAlarm,
          atmfM4IfPayloadMismatchAlarm,
          atmfM4IfXmissionErrAlarm,
          atmfM4IfPathTraceMismatchAlarm,
          atmfM4IfRdiAlarm,
          atmfM4IfSignalLabelMismatchAlarm,
          atmfM4VplTpAisAlarm,
          atmfM4VplTpRdiAlarm,
          atmfM4VpcTpAisAlarm,
          atmfM4VpcTpRdiAlarm,
          atmfM4VclTpAisAlarm,
          atmfM4VclTpRdiAlarm,
          atmfM4VccTpAisAlarm,
          atmfM4VccTpRdiAlarm,
          atmfM4HwBackPlaneAlarm,
          atmfM4HwCallEstErrAlarm,
          atmfM4HwCongestionAlarm,
          atmfM4HwExtIfDevProbAlarm,
          atmfM4HwLineCardAlarm,
          atmfM4HwMultiplexerAlarm,
          atmfM4HwPowerAlarm,
          atmfM4HwProcessorAlarm,
          atmfM4HwProtectionPathAlarm,
          atmfM4HwReceiverFailAlarm,
          atmfM4HwPIUnitMissingAlarm,
          atmfM4HwPIUnitProbAlarm,
          atmfM4HwPIUnitMismatchAlarm,
          atmfM4HwTimingProbAlarm,
          atmfM4HwXmitterFailAlarm,
          atmfM4HwTrunkCardAlarm,
          atmfM4HwStorageCapacityAlarm,
          atmfM4HwMemoryMismatchAlarm,
          atmfM4HwCorruptDataAlarm,
          atmfM4HwSwEnvironAlarm,
          atmfM4HwSwDownloadFailAlarm,
          atmfM4HwVersionMismatchAlarm,
          atmfM4HwFanFailAlarm,
          atmfM4HwDoorOpenAlarm,
          atmfM4HwFuseFailAlarm,
          atmfM4HwHighTempAlarm,
          atmfM4SwVersionMismatchAlarm,
          atmfM4VplTpUp,
          atmfM4VplTpDown,
          atmfM4VclTpUp,
          atmfM4VclTpDown,
          atmfM4VplXConnUp,
          atmfM4VplXConnDown,
          atmfM4VclXConnUp,
          atmfM4VclXConnDown,
          atmfM4HwUnitUp,
          atmfM4HwUnitDown,
          atmfM4AtmCellIfCreated,
          atmfM4AtmCellIfDeleted,
          atmfM4VpcTpCreated,
          atmfM4VpcTpDeleted,
          atmfM4VccTpCreated,
          atmfM4VccTpDeleted,
          atmfM4VplXConnCreated,
          atmfM4VplXConnDeleted,
          atmfM4VclXConnCreated,
          atmfM4VclXConnDeleted,
          atmfM4HwUnitCreated,
          atmfM4HwUnitDeleted,
          atmfM4InstalledSwCreated,
          atmfM4InstalledSwDeleted,
          atmfM4IfChanged,
          atmfM4VplTpChanged,
          atmfM4VclTpChanged,
          atmfM4VplXConnChanged,
          atmfM4VclXConnChanged,
          atmfM4HwUnitChanged,
          atmfM4InstalledSwChanged
          }
     STATUS    current
     DESCRIPTION
          "The ATM Forum M4 notification list."
     ::= { atmfM4Groups 32 }

END


IMA-MIB DEFINITIONS ::= BEGIN

IMPORTS
      MODULE-IDENTITY, OBJECT-TYPE, Integer32, Counter32, Gauge32,
      NOTIFICATION-TYPE, enterprises
        FROM SNMPv2-SMI
      MODULE-COMPLIANCE, OBJECT-GROUP, NOTIFICATION-GROUP
        FROM SNMPv2-CONF
      TEXTUAL-CONVENTION, DateAndTime, RowStatus
        FROM SNMPv2-TC
      InterfaceIndex, InterfaceIndexOrZero, ifIndex
        FROM IF-MIB;

atmfImaMib MODULE-IDENTITY
      LAST-UPDATED "9902111830Z"
      ORGANIZATION "The ATM Forum"
      CONTACT-INFO
        "ATM Forum
        World Headquarters
        2570 West El Camino Real
        Suite 304
        Mountain View, CA 94040-1313
        USA
        Phone: +1 415 949 6700
        Fax: +1 415 949 6705
        email: info@atmforum.com"
      DESCRIPTION
        "The MIB module for managing ATM Forum Inverse Multiplexing
        for ATM (IMA) interfaces."
      REVISION     "9902111830Z"
      DESCRIPTION
        "Updated and repaired version of the IMA-MIB released with the
        IMA v1.1 specification (af-phy-0086.001)."
      REVISION     "9701092245Z"
      DESCRIPTION
        "Initial incomplete version of the IMA-MIB as published in the
        IMA v1.0 specification (af-phy-0086.000)."
      ::= { atmfIma 1 }

-- The object identifier subtree for the IMA-MIB.

atmForum OBJECT IDENTIFIER ::= { enterprises 353 }
atmForumNetworkManagement OBJECT IDENTIFIER ::= { atmForum 5 }
atmfIma OBJECT IDENTIFIER ::= { atmForumNetworkManagement 7 }

atmfImaMibObjects OBJECT IDENTIFIER ::= { atmfImaMib 1 }
atmfImaMibTraps OBJECT IDENTIFIER ::= { atmfImaMib 2 }
atmfImaMibTrapPrefix OBJECT IDENTIFIER ::= { atmfImaMibTraps 0 }
atmfImaMibConformance OBJECT IDENTIFIER ::= { atmfImaMib 3 }

-- Textual conventions

MilliSeconds ::= TEXTUAL-CONVENTION
      STATUS      current
      DESCRIPTION
        "Time in milliseconds"
      SYNTAX      Integer32

ImaGroupState ::= TEXTUAL-CONVENTION
      STATUS      current
      DESCRIPTION
        "State of the IMA group."
      REFERENCE
        "ATM Forum IMA v1.1, Section 10.2.1 on page 55"
      SYNTAX      INTEGER {
        notConfigured(1),
        startUp(2),
        startUpAck(3),
        configAbortUnsupportedM(4),
        configAbortIncompatibleSymmetry(5),
        configAbortOther(6),
        insufficientLinks(7),
        blocked(8),
        operational(9),
        configAbortUnsupportedImaVersion(10) }

ImaGroupFailureStatus ::= TEXTUAL-CONVENTION
      STATUS      current
      DESCRIPTION
        "Failure reason of an IMA group."
      REFERENCE
        "ATM Forum IMA v1.1, Section 10.2.1, page 55"
      SYNTAX      INTEGER {
        noFailure(1), -- unit is up
        startUpNe(2),
        startUpFe(3),
        invalidMValueNe(4),
        invalidMValueFe(5),
        failedAssymetricNe(6),
        failedAssymetricFe(7),
        insufficientLinksNe(8),
        insufficientLinksFe(9),
        blockedNe(10),
        blockedFe(11),
        otherFailure(12),
        invalidImaVersionNe(13),
        invalidImaVersionFe(14) }

ImaAlarmStatus ::= TEXTUAL-CONVENTION
      STATUS      current
      DESCRIPTION
        "A qualification of the IMA trap which indicates if the
        condition causing the trap has been detected (declared)
        or is no longer present (cleared)."
      SYNTAX      INTEGER {
        cleared(1),
        declared(2) }

ImaAlarmType ::= TEXTUAL-CONVENTION
      STATUS      current
      DESCRIPTION
        "An identification of the event that caused the generation
        of the IMA trap."
      REFERENCE
        "ATM Forum IMA v1.1, Section 12.2.3 on page 79"
      SYNTAX      INTEGER {
        imaAlarmLinkLif(1),
        imaAlarmLinkLods(2),
        imaAlarmLinkRfi(3),
        imaAlarmLinkTxMisConnect(4),
        imaAlarmLinkRxMisConnect(5),
        imaAlarmLinkTxFault(6),
        imaAlarmLinkRxFault(7),
        imaAlarmLinkTxUnusableFe(8),
        imaAlarmLinkRxUnusableFe(9),
        imaAlarmGroupStartupFe(10),
        imaAlarmGroupCfgAbort(11),
        imaAlarmGroupCfgAbortFe(12),
        imaAlarmGroupInsuffLinks(13),
        imaAlarmGroupInsuffLinksFe(14),
        imaAlarmGroupBlockedFe(15),
        imaAlarmGroupTimingSynch(16) }

ImaGroupTxClkMode  ::= TEXTUAL-CONVENTION
      STATUS      current
      DESCRIPTION
        "Indicate the transmit clock mode of the IMA group.
        There are two possible modes: the Common Transmit
        Clock (CTC) and the Independent Transmit Clock (ITC).
        The CTC mode corresponds to the case when the transmit clock
        of all IMA links are derived from the same source.  The ITC
        configuration corresponds to the case where there is at least
        one IMA link whose transmit clock is derived from a source
        different than at least another link transmit clock."
      REFERENCE
        "ATM Forum IMA v1.1, Section 7 on page 38"
      SYNTAX      INTEGER {
        ctc(1),
        itc(2) }

ImaGroupSymmetry ::= TEXTUAL-CONVENTION
      STATUS      current
      DESCRIPTION
        "The group symmetry mode adjusted during the group start-up."
      REFERENCE
        "ATM Forum IMA v1.1, Section 5.2.2.7 on page 35"
      SYNTAX      INTEGER {
        symmetricOperation(1),
        asymmetricOperation(2),
        asymmetricConfiguration(3) }

ImaFrameLength ::= TEXTUAL-CONVENTION
      STATUS      current
      DESCRIPTION
        "Length of the IMA frames."
      REFERENCE
        "ATM Forum IMA v1.1, Section 5.2.2.4.2 on page 34"
      SYNTAX      INTEGER {
        m32(32),
        m64(64),
        m128(128),
        m256(256) }

ImaLinkState ::= TEXTUAL-CONVENTION
      STATUS      current
      DESCRIPTION
        "State of a link belonging to an IMA group."
      REFERENCE
        "ATM Forum IMA v1.1, Section 10.1.2 on page 48"
      SYNTAX      INTEGER {
        notInGroup(1),
        unusableNoGivenReason(2),
        unusableFault(3),
        unusableMisconnected(4),
        unusableInhibited(5),
        unusableFailed(6),
        usable(7),
        active(8) }

ImaLinkFailureStatus ::= TEXTUAL-CONVENTION
      STATUS      current
      DESCRIPTION
        "Local failure status of a link belonging to an IMA group."
      REFERENCE
        "ATM Forum IMA v1.1, Section 10.1.2 on page 48"
      SYNTAX      INTEGER {
        noFailure(1),
        imaLinkFailure(2),
        lifFailure(3),
        lodsFailure(4),
        misConnected(5),
        blocked(6),
        fault(7),
        farEndTxLinkUnusable(8),
        farEndRxLinkUnusable(9) }

ImaTestProcStatus ::= TEXTUAL-CONVENTION
      STATUS      current
      DESCRIPTION
        "States of the Test Pattern Procedure."
      REFERENCE
        "ATM Forum IMA v1.1, Section 13 on page 81"
      SYNTAX      INTEGER {
        disabled(1),
        operating(2),
        linkFail(3) }

--
-- The IMA Group subtree
--
-- The IMA Group subtree consists of the number of IMA groups and a
-- table of IMA groups.  Each entry in the table of IMA groups contains
-- information (configuration and status) specific to each group.
--

imaGroupNumber OBJECT-TYPE
      SYNTAX      INTEGER (0..2147483647)
      MAX-ACCESS  read-only
      STATUS      current
      DESCRIPTION
        "The number of IMA groups configured on this system."
      ::= { atmfImaMibObjects 1 }

imaGroupTable OBJECT-TYPE
      SYNTAX      SEQUENCE OF ImaGroupEntry
      MAX-ACCESS  not-accessible
      STATUS      current
      DESCRIPTION
        "The IMA Group Configuration table."
      ::= { atmfImaMibObjects 2 }

imaGroupEntry OBJECT-TYPE
      SYNTAX      ImaGroupEntry
      MAX-ACCESS  not-accessible
      STATUS      current
      DESCRIPTION
        "An entry in the IMA Group table."
      INDEX       { imaGroupIndex }
      ::= { imaGroupTable 1 }

ImaGroupEntry ::= SEQUENCE {
      imaGroupIndex               INTEGER (1..2147483647),
      imaGroupRowStatus           RowStatus,
      imaGroupIfIndex             InterfaceIndex,
      imaGroupNeState             ImaGroupState,
      imaGroupFeState             ImaGroupState,
      imaGroupFailureStatus       ImaGroupFailureStatus,
      imaGroupSymmetry            ImaGroupSymmetry,
      imaGroupMinNumTxLinks       INTEGER (1..32),
      imaGroupMinNumRxLinks       INTEGER (1..32),
      imaGroupNeTxClkMode         ImaGroupTxClkMode,
      imaGroupFeTxClkMode         ImaGroupTxClkMode,
      imaGroupTxTimingRefLink     InterfaceIndexOrZero,
      imaGroupRxTimingRefLink     InterfaceIndexOrZero,
      imaGroupLastChange          DateAndTime,
      imaGroupTxImaId             INTEGER (0..255),
      imaGroupRxImaId             INTEGER (0..255),
      imaGroupTxFrameLength       ImaFrameLength,
      imaGroupRxFrameLength       ImaFrameLength,
      imaGroupDiffDelayMax        MilliSeconds,
      imaGroupLeastDelayLink      InterfaceIndexOrZero,
      imaGroupDiffDelayMaxObs     MilliSeconds,
      imaGroupAlphaValue          INTEGER (1..2),
      imaGroupBetaValue           INTEGER (1..5),
      imaGroupGammaValue          INTEGER (1..5),
      imaGroupRunningSecs         Gauge32,
      imaGroupUnavailSecs         Counter32,
      imaGroupNeNumFailures       Counter32,
      imaGroupFeNumFailures       Counter32,
      imaGroupTxAvailCellRate     Gauge32,
      imaGroupRxAvailCellRate     Gauge32,
      imaGroupNumTxCfgLinks       Gauge32,
      imaGroupNumRxCfgLinks       Gauge32,
      imaGroupNumTxActLinks       Gauge32,
      imaGroupNumRxActLinks       Gauge32,
      imaGroupTestLinkIfIndex     InterfaceIndexOrZero,
      imaGroupTestPattern         INTEGER (-1..255),
      imaGroupTestProcStatus      ImaTestProcStatus,
      imaGroupValidIntervals      INTEGER (0..96),
      imaGroupInvalidIntervals    INTEGER (0..96),
      imaGroupTimeElapsed         INTEGER (0..899),
      imaGroupTxOamLabelValue     INTEGER (1..255),
      imaGroupRxOamLabelValue     INTEGER (0..255) }

imaGroupIndex OBJECT-TYPE
      SYNTAX      INTEGER (1..2147483647)
      MAX-ACCESS  not-accessible
      STATUS      current
      DESCRIPTION
        "A unique value for the IMA Group."
      ::= { imaGroupEntry 1 }

imaGroupRowStatus OBJECT-TYPE
      SYNTAX      RowStatus
      MAX-ACCESS  read-create
      STATUS      current
      DESCRIPTION
        "The imaGroupRowStatus object allows create, change, and delete
        operations on imaGroupTable entries.

        To create a new conceptual row (or instance) of the imaGroupTable,
        imaGroupRowStatus must be set to 'createAndWait' or 'createAndGo'.
        If settable, a successful set of the following objects must be
        performed before the imaGroupRowStatus of a new conceptual row can
        be set to 'active':

          imaGroupMinNumTxLinks
          imaGroupMinNumRxLinks
          imaGroupTxImaId

        Some objects in the imaGroupTable control settings which can only
        be established or changed at group start-up time.  These objects
        include:

          imaGroupTxImaId
          imaGroupSymmetry
          imaGroupTxFrameLength

        To change (modify) the imaGroupTxImaId object, the manager must
        first set imaGroupRowStatus to 'notInService'.  However, changes
        to the following two objects can be optionally allowed while the
        imaGroupRowStatus is 'active':

          imaGroupSymmetry
          imaGroupTxFrameLength

        These two objects can be changed when the imaGroupRowStatus is
        'active' in order to allow the far-end to recover from its
        Config-Aborted state without having to force the near-end Group
        State machine to go to the 'Not Configured' state.  Changing
        these object values after group start-up has completed causes a
        restart of the IMA group.

        Alternatively, as noted above, the agent implementation may
        simply require the imaGroupRowStatus object to first be set to
        'notInService' before allowing changes to either of these two
        objects.

        To remove (delete) an imaGroupTable entry from this table, set
        imaGroupRowStatus to 'destroy'.

        Setting the imaGroupRowStatus to 'active' has the effect of
        activating the Group Startup Procedure.  The Group Startup
        Procedure uses provisioned links that have imaLinkRowStatus set
        to 'active' and imaLinkGroupIndex set to the imaGroupIndex in
        this conceptual row.

        When the imaGroupRowStatus is not in 'active' state, the Group
        State machine is in its 'Not Configured' state."
      ::= { imaGroupEntry 2 }

imaGroupIfIndex OBJECT-TYPE
      SYNTAX      InterfaceIndex
      MAX-ACCESS  read-only
      STATUS      current
      DESCRIPTION
        "This object identifies the logical interface number ('ifIndex')
        assigned to this IMA group, and is used to identify corresponding
        rows in the Interfaces MIB.

        Note that re-initialization of the management agent may cause
        a client's 'imaGroupIfIndex' to change."
      ::= { imaGroupEntry 3 }

imaGroupNeState OBJECT-TYPE
      SYNTAX      ImaGroupState
      MAX-ACCESS  read-only
      STATUS      current
      DESCRIPTION
        "The current operational state of the near-end IMA Group State
        Machine."
      REFERENCE
        "ATM Forum IMA v1.1, Section 10.2.1 on page 55"
      ::= { imaGroupEntry 4 }

imaGroupFeState OBJECT-TYPE
      SYNTAX      ImaGroupState
      MAX-ACCESS  read-only
      STATUS      current
      DESCRIPTION
        "The current operational state of the far-end IMA Group State
        Machine."
      REFERENCE
        "ATM Forum IMA v1.1, Section 10.2.1 on page 55"
      ::= { imaGroupEntry 5 }

imaGroupFailureStatus OBJECT-TYPE
      SYNTAX      ImaGroupFailureStatus
      MAX-ACCESS  read-only
      STATUS      current
      DESCRIPTION
        "The current failure status of the IMA group (the reason why
        the GTSM is in the down state)."
      REFERENCE
        "ATM Forum IMA v1.1, Section 10.2.1 on page 55"
      ::= { imaGroupEntry 6 }

imaGroupSymmetry OBJECT-TYPE
      SYNTAX      ImaGroupSymmetry
      MAX-ACCESS  read-create
      STATUS      current
      DESCRIPTION
        "Symmetry of the IMA group."
      REFERENCE
        "ATM Forum IMA v1.1, Section 5.2.2.7 on page 35"
      DEFVAL { symmetricOperation }
      ::= { imaGroupEntry 7 }

imaGroupMinNumTxLinks OBJECT-TYPE
      SYNTAX      INTEGER (1..32)
      MAX-ACCESS  read-create
      STATUS      current
      DESCRIPTION
        "Minimum number of transmit links required to be Active for
        the IMA group to be in the Operational state."
      REFERENCE
        "ATM Forum IMA v1.1, Section 10.2.1.1 on page 55"
      ::= { imaGroupEntry 8 }

imaGroupMinNumRxLinks OBJECT-TYPE
      SYNTAX      INTEGER (1..32)
      MAX-ACCESS  read-create
      STATUS      current
      DESCRIPTION
        "Minimum number of receive links required to be Active for
        the IMA group to be in the Operational state."
      REFERENCE
        "ATM Forum IMA v1.1, Section 10.2.1.1 on page 55"
      ::= { imaGroupEntry 9 }

imaGroupNeTxClkMode OBJECT-TYPE
      SYNTAX      ImaGroupTxClkMode
      MAX-ACCESS  read-create
      STATUS      current
      DESCRIPTION
        "Transmit clocking mode used by the near-end IMA group."
      REFERENCE
        "ATM Forum IMA v1.1, Section 7 on page 38"
      DEFVAL { ctc }
      ::= { imaGroupEntry 10 }

imaGroupFeTxClkMode OBJECT-TYPE
      SYNTAX      ImaGroupTxClkMode
      MAX-ACCESS  read-only
      STATUS      current
      DESCRIPTION
        "Transmit clocking mode used by the far-end IMA group."
      REFERENCE
        "ATM Forum IMA v1.1, Section 7 on page 38"
      ::= { imaGroupEntry 11 }

imaGroupTxTimingRefLink OBJECT-TYPE
      SYNTAX      InterfaceIndexOrZero
      MAX-ACCESS  read-only
      STATUS      current
      DESCRIPTION
        "The ifIndex of the transmit timing reference link to be
        used by the near-end for IMA data cell clock recovery from
        the ATM layer.  The distinguished value of zero may be used
        if no link has been configured in the IMA group, or if the
        transmit timing reference link has not yet been selected."
      REFERENCE
        "ATM Forum IMA v1.1, Section 8.1.1 on page 41"
      ::= { imaGroupEntry 12 }

imaGroupRxTimingRefLink OBJECT-TYPE
      SYNTAX      InterfaceIndexOrZero
      MAX-ACCESS  read-only
      STATUS      current
      DESCRIPTION
        "The ifIndex of the receive timing reference link to be
        used by near-end for IMA data cell clock recovery toward
        the ATM layer.  The distinguished value of zero may be used
        if no link has been configured in the IMA group, or if the
        receive timing reference link has not yet been detected."
      REFERENCE
        "ATM Forum IMA v1.1, Section 8.1.1 on page 41"
      ::= { imaGroupEntry 13 }

imaGroupLastChange OBJECT-TYPE
      SYNTAX      DateAndTime
      MAX-ACCESS  read-only
      STATUS      current
      DESCRIPTION
        "The time-of-day the IMA group last changed operational
        state (i.e., value of imaGroupNeState changed)."
      ::= { imaGroupEntry 14 }

imaGroupTxImaId OBJECT-TYPE
      SYNTAX      INTEGER (0..255)
      MAX-ACCESS  read-create
      STATUS      current
      DESCRIPTION
        "The IMA ID currently in use by the near-end IMA function."
      REFERENCE
        "ATM Forum IMA v1.1, Section 5.2.2.6 on page 35"
      ::= { imaGroupEntry 15 }

imaGroupRxImaId OBJECT-TYPE
      SYNTAX      INTEGER (0..255)
      MAX-ACCESS  read-only
      STATUS      current
      DESCRIPTION
        "The IMA ID currently in use by the far-end IMA function."
      REFERENCE
        "ATM Forum IMA v1.1, Section 5.2.2.6 on page 35"
      ::= { imaGroupEntry 16 }

imaGroupTxFrameLength OBJECT-TYPE
      SYNTAX      ImaFrameLength
      MAX-ACCESS  read-create
      STATUS      current
      DESCRIPTION
        "The frame length to be used by the IMA group in the transmit
        direction.  Can only be set when the IMA group is startup."
      REFERENCE
        "ATM Forum IMA v1.1, Section 5.2.2.4.2 on page 34"
      DEFVAL { m128 }
      ::= { imaGroupEntry 17 }

imaGroupRxFrameLength OBJECT-TYPE
      SYNTAX      ImaFrameLength
      MAX-ACCESS  read-only
      STATUS      current
      DESCRIPTION
        "Value of IMA frame length as received from remote IMA function."
      REFERENCE
        "ATM Forum IMA v1.1, Section 5.2.2.4.2 on page 34"
      ::= { imaGroupEntry 18 }

imaGroupDiffDelayMax OBJECT-TYPE
      SYNTAX      MilliSeconds
      MAX-ACCESS  read-create
      STATUS      current
      DESCRIPTION
        "The maximum number of milliseconds of differential delay among
        the links that will be tolerated on this interface."
      REFERENCE
        "ATM Forum IMA v1.1, Section 9.2 on page 45"
      DEFVAL { 25 }
      ::= { imaGroupEntry 19 }

imaGroupLeastDelayLink OBJECT-TYPE
      SYNTAX      InterfaceIndexOrZero
      MAX-ACCESS  read-only
      STATUS      current
      DESCRIPTION
        "The ifIndex of the link configured in the IMA group which has
        the smallest link propagation delay.  The distinguished value of
        zero may be used if no link has been configured in the IMA group,
        or if the link with the smallest link propagation delay has not
        yet been determined."
      REFERENCE
        "ATM Forum IMA v1.1, Section 9.2 on page 45"
      ::= { imaGroupEntry 20 }

imaGroupDiffDelayMaxObs OBJECT-TYPE
      SYNTAX      MilliSeconds
      MAX-ACCESS  read-only
      STATUS      current
      DESCRIPTION
        "The latest maximum differential delay observed (in milliseconds)
        between the links having the least and most link propagation delay,
        among the receive links that are currently configured in the IMA
        group."
      REFERENCE
        "ATM Forum IMA v1.1, Section 9.2 on page 45"
      ::= { imaGroupEntry 21 }

imaGroupAlphaValue OBJECT-TYPE
      SYNTAX      INTEGER (1..2)
      MAX-ACCESS  read-create
      STATUS      current
      DESCRIPTION
        "This indicates the 'alpha' value used to specify the number
        of consecutive invalid ICP cells to be detected before moving
        to the IMA Hunt state from the IMA Sync state."
      REFERENCE
        "ATM Forum IMA v1.1, Section 11 on page 68"
      DEFVAL { 2 }
      ::= { imaGroupEntry 22 }

imaGroupBetaValue OBJECT-TYPE
      SYNTAX      INTEGER (1..5)
      MAX-ACCESS  read-create
      STATUS      current
      DESCRIPTION
        "This indicates the 'beta' value used to specify the number
        of consecutive errored ICP cells to be detected before moving
        to the IMA Hunt state from the IMA Sync state."
      REFERENCE
        "ATM Forum IMA v1.1, Section 11 on page 68"
      DEFVAL { 2 }
      ::= { imaGroupEntry 23 }

imaGroupGammaValue OBJECT-TYPE
      SYNTAX      INTEGER (1..5)
      MAX-ACCESS  read-create
      STATUS      current
      DESCRIPTION
        "This indicates the 'gamma' value used to specify the number
        of consecutive valid ICP cells to be detected before moving
        to the IMA Sync state from the IMA PreSync state."
      REFERENCE
        "ATM Forum IMA v1.1, Section 11 on page 68"
      DEFVAL { 1 }
      ::= { imaGroupEntry 24 }

imaGroupRunningSecs OBJECT-TYPE
      SYNTAX      Gauge32
      MAX-ACCESS  read-only
      STATUS      current
      DESCRIPTION
        "The amount of time (in seconds) since this IMA group has
        been in the Operational state."
      REFERENCE
        "ATM Forum IMA v1.1, Section 10.2.1 on page 55"
      ::= { imaGroupEntry 25 }

imaGroupUnavailSecs OBJECT-TYPE
      SYNTAX      Counter32
      MAX-ACCESS  read-only
      STATUS      current
      DESCRIPTION
        "Count of one second intervals where the IMA Group Traffic
        State Machine is Down."
      REFERENCE
        "ATM Forum IMA v1.1, Section 10.2.1 on page 55 and (R-136) in Section
        12.2.2.2 on page 77"
      ::= { imaGroupEntry 26 }

imaGroupNeNumFailures OBJECT-TYPE
      SYNTAX      Counter32
      MAX-ACCESS  read-only
      STATUS      current
      DESCRIPTION
        "The number of times a near-end group failure (Config-Aborted,
        Insufficient-Links) has been reported since power-up or reboot."
      REFERENCE
        "ATM Forum IMA v1.1, (R-137) in Section 12.2.2.2 on page 77"
      ::= { imaGroupEntry 27 }

imaGroupFeNumFailures OBJECT-TYPE
      SYNTAX      Counter32
      MAX-ACCESS  read-only
      STATUS      current
      DESCRIPTION
        "The number of times a far-end group failure (Config-Aborted-FE,
        Insufficient-Links-FE, Blocked-FE) has been reported since
        power-up or reboot.  This is an optional attribute."
      REFERENCE
        "ATM Forum IMA v1.1, (O-25) in Section 12.2.2.2 on page 77"
      ::= { imaGroupEntry 28 }

imaGroupTxAvailCellRate OBJECT-TYPE
      SYNTAX      Gauge32
      MAX-ACCESS  read-only
      STATUS      current
      DESCRIPTION
        "The current cell rate (truncated value in cells per second)
        provided by this IMA group in the transmit direction,
        considering all the transmit links in the Active state."
      ::= { imaGroupEntry 29 }

imaGroupRxAvailCellRate OBJECT-TYPE
      SYNTAX      Gauge32
      MAX-ACCESS  read-only
      STATUS      current
      DESCRIPTION
        "The current cell rate (truncated value in cells per second)
        provided by this IMA group in the receive direction,
        considering all the receive links in the Active state."
      ::= { imaGroupEntry 30 }

-- imaGroupNumTxCfgLinks is used by a network operator to tell how many
-- links are configured for transmit in the IMA group.

imaGroupNumTxCfgLinks OBJECT-TYPE
      SYNTAX      Gauge32
      MAX-ACCESS  read-only
      STATUS      current
      DESCRIPTION
        "The number of links that are configured to transmit in this IMA
        group. This attribute overwrites the value of the
        imaGroupNumRxActLinks attribute when the IMA group is configured
        in the Symmetrical Configuration group symmetry mode."
      ::= { imaGroupEntry 31 }

-- imaGroupNumRxCfgLinks is used by a network operator to tell how many
-- links are configured for receive in the IMA group.

imaGroupNumRxCfgLinks OBJECT-TYPE
      SYNTAX      Gauge32
      MAX-ACCESS  read-only
      STATUS      current
      DESCRIPTION
        "The number of links that are configured to receive in this IMA
        group. This attribute is overwritten by the value of the
        imaGroupNumTxActLinks attribute when the IMA group is configured
        in the Symmetrical Configuration group symmetry mode."
      ::= { imaGroupEntry 32 }

-- imaGroupNumTxActLinks is used by a network operator to tell how many
-- links which are configured for transmit are also Active.

imaGroupNumTxActLinks OBJECT-TYPE
      SYNTAX      Gauge32
      MAX-ACCESS  read-only
      STATUS      current
      DESCRIPTION
        "The number of links which are configured to transmit and are
        currently Active in this IMA group."
      ::= { imaGroupEntry 33 }

-- imaGroupNumRxActLinks is used by a network operator to tell how many
-- links which are configured for receive are also Active.

imaGroupNumRxActLinks OBJECT-TYPE
      SYNTAX      Gauge32
      MAX-ACCESS  read-only
      STATUS      current
      DESCRIPTION
        "The number of links which are configured to receive and are
        currently Active in this IMA group."
      ::= { imaGroupEntry 34 }

--
-- Test Pattern Procedure control objects.  These objects are implemented
-- if the IMA implements the Test Pattern Procedure.  In this case all
-- test pattern procedure related objects must be implemented.  Specifically,
-- these objects are:
--
--   imaGroupTestLinkIfIndex
--   imaGroupTestPattern
--   imaGroupTestProcStatus
--   imaLinkRxTestPattern
--   imaLinkTestProcStatus
--

imaGroupTestLinkIfIndex OBJECT-TYPE
      SYNTAX      InterfaceIndexOrZero
      MAX-ACCESS  read-create
      STATUS      current
      DESCRIPTION
        "This object is used to designate an interface as the test link
        for use in the Test Pattern Procedure.  The distinguished value of
        zero specifies that the implementation may choose the Test Link,
        in which case, the implementation may also choose the value of
        'imaGroupTestPattern'.  The value zero may also be used if no link
        has yet been added to the group.

        Note that this value is NOT the same as the Tx LID value, but
        instead either identifies the ifIndex value of the test link to be
        used by the Test Pattern Procedure (i.e., the link whose LID value
        is inserted in the Tx LID field of the transmitted ICP cells),
        or identifies that the implementation may choose the test link (if
        the value is zero)."
      REFERENCE
        "ATM Forum IMA v1.1, Section 13 on page 81"
      DEFVAL { 0 }
      ::= { imaGroupEntry 35 }

imaGroupTestPattern OBJECT-TYPE
      SYNTAX      INTEGER (-1..255)
      MAX-ACCESS  read-create
      STATUS      current
      DESCRIPTION
        "The value of this object is used to specify the Tx Test Pattern
        in an IMA group loopback operation.  A value in the range 0 to
        255 designates a specific pattern.  The distinguished value of
        -1 specifies that the implementation may choose the value.  In
        this case, the implementation may also choose the value of
        'imaGroupTestLinkIfIndex'.

        It is recommended that the specific value 255 not be used for
        testing, since by (R-137) the IMA interface is required to
        transmit 0xFF (i.e., 255) when the incoming test command is
        inactive or the test link is not detected, and thus it cannot
        be established for certain whether 255 was received due to an
        actual loopback operation or due to the normal operation of an
        IMA that is not performing (or else cannot perform) the test
        pattern procedure."
      REFERENCE
        "ATM Forum IMA v1.1, Section 13 on page 81"
      DEFVAL { -1 }
      ::= { imaGroupEntry 36 }

imaGroupTestProcStatus OBJECT-TYPE
      SYNTAX      ImaTestProcStatus
      MAX-ACCESS  read-create
      STATUS      current
      DESCRIPTION
        "This object is used to enable or disable the
        Test Pattern Procedure, and to note whether at least one
        link failed the test.

        The test is started by setting operating(2) status.  If any
        link should fail the test, the IMA will set the status to
        linkFail(3).  The linkFail(3) state will persist until
        either the disabled(1) state is set or until no instance
        of imaLinkTestProcStatus has the value linkFail(3).

        Only the values disabled(1) and operating(2) may be written.
        Writing the operating(2) value will not cause clearing of
        the linkFail(3) state."
      REFERENCE
        "ATM Forum IMA v1.1, Section 13 on page 81"
      DEFVAL { disabled }
      ::= { imaGroupEntry 37 }

--
-- Objects for use with the IMA Group Current Table, the IMA Group
-- Interval Table, and the IMA Group Total Table.
--
-- Implementation of these objects is optional, dependent on whether
-- the tables mentioned above are implemented.
--

imaGroupValidIntervals OBJECT-TYPE
      SYNTAX      INTEGER (0..96)
      MAX-ACCESS  read-only
      STATUS      current
      DESCRIPTION
        "The number of previous 15 minute intervals for which valid data
        was collected.  The value will be 96 unless the IMA group table
        entry was created within the last 24 hours, in which case the value
        will be the number of complete 15 minute intervals since the IMA
        group table entry was created.  In the case where the agent is a
        proxy, it is possible that some intervals are unavailable.  In this
        case, this value is the maximum interval number for which valid
        data is available.  This attribute is only mandatory when the IMA
        Group Interval Statistics and/or IMA Group Total Statistics objects
        are implemented."
      REFERENCE
        "ATM Forum IMA v1.1, (O-26) in Section 12.2.2.2 on page 77"
      ::= { imaGroupEntry 38 }

imaGroupInvalidIntervals OBJECT-TYPE
      SYNTAX      INTEGER (0..96)
      MAX-ACCESS  read-only
      STATUS      current
      DESCRIPTION
        "The number of intervals for which no valid data is available.
        This attribute is only mandatory when the IMA Group Interval
        Statistics and/or IMA Group Total Statistics objects are
        implemented."
      REFERENCE
        "ATM Forum IMA v1.1, (O-26) in Section 12.2.2.2 on page 77"
      ::= { imaGroupEntry 39 }

imaGroupTimeElapsed OBJECT-TYPE
      SYNTAX      INTEGER (0..899)
      MAX-ACCESS  read-only
      STATUS      current
      DESCRIPTION
        "The number of seconds that have elapsed since the beginning of
        the current measurement period.  This attribute is only mandatory
        when the IMA Group Current Statistics are implemented."
      REFERENCE
        "ATM Forum IMA v1.1, (O-26) in Section 12.2.2.2 on page 77"
      ::= { imaGroupEntry 40 }

--
-- Objects to report the IMA OAM Label values transmitted and
-- received by the IMA group. 
--

imaGroupTxOamLabelValue OBJECT-TYPE
      SYNTAX      INTEGER (1..255)
      MAX-ACCESS  read-only
      STATUS      current
      DESCRIPTION
        "IMA OAM Label value transmitted by the NE IMA unit."
      REFERENCE
        "ATM Forum IMA v1.1, Section 5.2.2.3 on page 32"            
      ::= { imaGroupEntry 41 }

imaGroupRxOamLabelValue OBJECT-TYPE
      SYNTAX      INTEGER (0..255)
      MAX-ACCESS  read-only
      STATUS      current
      DESCRIPTION
        "IMA OAM Label value transmitted by the FE IMA unit.  The value 0
        likely means that the IMA unit has not received an OAM Label 
        from the FE IMA unit at this time."
      REFERENCE
        "ATM Forum IMA v1.1, Section 5.2.2.3 on page 32"
      ::= { imaGroupEntry 42 }

--
-- The IMA Group Mapping Table subtree
--
-- The IMA Group Mapping Table subtree consists of a table of mappings
-- from 'ifIndex' values of IMA groups to their 'imaGroupIndex' values.
-- This table allows the Unit Management to perform easy look-ups (no
-- searches and sorts).
--
-- Note that the Group Index is different than the ifIndex.
--

imaGroupMappingTable OBJECT-TYPE
      SYNTAX      SEQUENCE OF ImaGroupMappingEntry
      MAX-ACCESS  not-accessible
      STATUS      current
      DESCRIPTION
        "A table mapping the 'ifIndex' values of 'imaGroupIfIndex'
        to the 'imaGroupIndex' values of the corresponding IMA group."
      ::= { atmfImaMibObjects 3 }

imaGroupMappingEntry OBJECT-TYPE
      SYNTAX      ImaGroupMappingEntry
      MAX-ACCESS  not-accessible
      STATUS      current
      DESCRIPTION
        "Each row describes one ifIndex to imaGroupIndex mapping."
      INDEX       { ifIndex }
      ::= { imaGroupMappingTable 1 }

ImaGroupMappingEntry ::= SEQUENCE {
      imaGroupMappingIndex    Integer32 }

imaGroupMappingIndex OBJECT-TYPE
      SYNTAX      Integer32
      MAX-ACCESS  read-only
      STATUS      current
      DESCRIPTION
        "The imaGroupIndex of the IMA Group which implements the
        specified interface."
      ::= { imaGroupMappingEntry 1 }

--
-- The IMA Link subtree
--
-- The IMA Link subtree consists of a table of IMA links.  Each entry
-- in the table contains status information about a link which is part
-- of an IMA group, and also contains a configuration object to select
-- to which IMA group the link belongs.
--

imaLinkTable OBJECT-TYPE
      SYNTAX      SEQUENCE OF ImaLinkEntry
      MAX-ACCESS  not-accessible
      STATUS      current
      DESCRIPTION
        "The IMA group Link Status and Configuration table."
      ::= { atmfImaMibObjects 4 }

imaLinkEntry OBJECT-TYPE
      SYNTAX      ImaLinkEntry
      MAX-ACCESS  not-accessible
      STATUS      current
      DESCRIPTION
        "An entry in the IMA Group Link table."
      INDEX       { imaLinkIfIndex }
      ::= { imaLinkTable 1 }

ImaLinkEntry ::= SEQUENCE {
      imaLinkIfIndex              InterfaceIndex,
      imaLinkRowStatus            RowStatus,
      imaLinkGroupIndex           Integer32,
      imaLinkNeTxState            ImaLinkState,
      imaLinkNeRxState            ImaLinkState,
      imaLinkFeTxState            ImaLinkState,
      imaLinkFeRxState            ImaLinkState,
      imaLinkNeRxFailureStatus    ImaLinkFailureStatus,
      imaLinkFeRxFailureStatus    ImaLinkFailureStatus,
      imaLinkTxLid                INTEGER (0..31),
      imaLinkRxLid                INTEGER (0..31),
      imaLinkRelDelay             MilliSeconds,
      imaLinkImaViolations        Counter32,
      imaLinkOifAnomalies         Counter32,
      imaLinkNeSevErroredSecs     Counter32,
      imaLinkFeSevErroredSecs     Counter32,
      imaLinkNeUnavailSecs        Counter32,
      imaLinkFeUnavailSecs        Counter32,
      imaLinkNeTxUnusableSecs     Counter32,
      imaLinkNeRxUnusableSecs     Counter32,
      imaLinkFeTxUnusableSecs     Counter32,
      imaLinkFeRxUnusableSecs     Counter32,
      imaLinkNeTxNumFailures      Counter32,
      imaLinkNeRxNumFailures      Counter32,
      imaLinkFeTxNumFailures      Counter32,
      imaLinkFeRxNumFailures      Counter32,
      imaLinkTxStuffs             Counter32,
      imaLinkRxStuffs             Counter32,
      imaLinkRxTestPattern        INTEGER (0..255),
      imaLinkTestProcStatus       ImaTestProcStatus,
      imaLinkValidIntervals       INTEGER (0..96),
      imaLinkInvalidIntervals     INTEGER (0..96),
      imaLinkTimeElapsed          INTEGER (0..899) }

imaLinkIfIndex OBJECT-TYPE
      SYNTAX      InterfaceIndex
      MAX-ACCESS  not-accessible
      STATUS      current
      DESCRIPTION
        "This corresponds to the 'ifIndex' of the MIB-II interface
        on which this link is established.  This object also
        corresponds to the logical number ('ifIndex') assigned to
        this IMA link."
      ::= { imaLinkEntry 1 }

imaLinkRowStatus OBJECT-TYPE
      SYNTAX      RowStatus
      MAX-ACCESS  read-create
      STATUS      current
      DESCRIPTION
        "The imaLinkRowStatus object allows create, change, and delete
        operations on imaLinkTable entries.

        To create a new conceptual row (or instance) of the imaLinkTable,
        imaLinkRowStatus must be set to 'createAndWait' or 'createAndGo'.
        A successful set of the imaLinkGroupIndex object must be performed
        before the imaLinkRowStatus of a new conceptual row can be set to
        'active'.

        To change (modify) the imaLinkGroupIndex in an imaLinkTable entry,
        the imaLinkRowStatus object must first be set to 'notInService'.
        Only then can this object in the conceptual row be modified.
        This is due to the fact that the imaLinkGroupIndex object provides
        the association between a physical IMA link and the IMA group to
        which it belongs, and setting the imaLinkGroupIndex object to a
        different value has the effect of changing the association between
        a physical IMA link and an IMA group.  To place the link 'in group',
        the imaLinkRowStatus object is set to 'active'.  While the row is
        not in 'active' state, both the Transmit and Receive IMA link state
        machines are in the 'Not In Group' state.

        To remove (delete) an imaLinkTable entry from this table, set
        this object to 'destroy'."
      ::= { imaLinkEntry 2 }

imaLinkGroupIndex OBJECT-TYPE
      SYNTAX      Integer32
      MAX-ACCESS  read-create
      STATUS      current
      DESCRIPTION
        "The value which identifies the IMA group (imaGroupIndex)
        of which this link is a member."
      ::= { imaLinkEntry 3 }

imaLinkNeTxState OBJECT-TYPE
      SYNTAX      ImaLinkState
      MAX-ACCESS  read-only
      STATUS      current
      DESCRIPTION
        "The current state of the near-end transmit link."
      REFERENCE
        "ATM Forum IMA v1.1, Section 10.1.2 on page 48"
      ::= { imaLinkEntry 4 }

imaLinkNeRxState OBJECT-TYPE
      SYNTAX      ImaLinkState
      MAX-ACCESS  read-only
      STATUS      current
      DESCRIPTION
        "The current state of the near-end receive link."
      REFERENCE
        "ATM Forum IMA v1.1, Section 10.1.2 on page 48"
      ::= { imaLinkEntry 5 }

imaLinkFeTxState OBJECT-TYPE
      SYNTAX      ImaLinkState
      MAX-ACCESS  read-only
      STATUS      current
      DESCRIPTION
        "The current state of the far-end transmit link as reported
        via ICP cells."
      REFERENCE
        "ATM Forum IMA v1.1, Section 10.1.2 on page 48"
      ::= { imaLinkEntry 6 }

imaLinkFeRxState OBJECT-TYPE
      SYNTAX      ImaLinkState
      MAX-ACCESS  read-only
      STATUS      current
      DESCRIPTION
        "The current state of the far-end receive link as reported
        via ICP cells."
      REFERENCE
        "ATM Forum IMA v1.1, Section 10.1.2 on page 48"
      ::= { imaLinkEntry 7 }

imaLinkNeRxFailureStatus OBJECT-TYPE
      SYNTAX      ImaLinkFailureStatus
      MAX-ACCESS  read-only
      STATUS      current
      DESCRIPTION
        "The current link failure status of the near-end receive link."
      REFERENCE
        "ATM Forum IMA v1.1, Section 10.1.2 on page 48"
      ::= { imaLinkEntry 8 }

imaLinkFeRxFailureStatus OBJECT-TYPE
      SYNTAX      ImaLinkFailureStatus
      MAX-ACCESS  read-only
      STATUS      current
      DESCRIPTION
        "The current link failure status of the far-end receive link
        as reported via ICP cells."
      REFERENCE
        "ATM Forum IMA v1.1, Section 10.1.2 on page 48"
      ::= { imaLinkEntry 9 }

imaLinkTxLid OBJECT-TYPE
      SYNTAX      INTEGER (0..31)
      MAX-ACCESS  read-only
      STATUS      current
      DESCRIPTION
        "The outgoing LID used currently on the link by the local end.
        This value has meaning only if the link belongs to an IMA group."
      REFERENCE
        "ATM Forum IMA v1.1, Section 5.2.2.1 on page 26"
      ::= { imaLinkEntry 10 }

imaLinkRxLid OBJECT-TYPE
      SYNTAX      INTEGER (0..31)
      MAX-ACCESS  read-only
      STATUS      current
      DESCRIPTION
        "The incoming LID used currently on the link by the remote
        end as reported via ICP cells.  This value has meaning only
        if the link belongs to an IMA group."
      REFERENCE
        "ATM Forum IMA v1.1, Section 5.2.2.1 on page 26"
      ::= { imaLinkEntry 11 }

imaLinkRelDelay OBJECT-TYPE
      SYNTAX      MilliSeconds
      MAX-ACCESS  read-only
      STATUS      current
      DESCRIPTION
        "The latest measured delay on this link relative to the link, in
        the same IMA group, with the least delay."
      REFERENCE
        "ATM Forum IMA v1.1, Section 9.2 on page 45"
      ::= { imaLinkEntry 12 }

imaLinkImaViolations OBJECT-TYPE
      SYNTAX      Counter32
      MAX-ACCESS  read-only
      STATUS      current
      DESCRIPTION
        "ICP violations: count of errored, invalid or missing ICP cells,
        except during SES-IMA or UAS-IMA conditions."
      REFERENCE
        "ATM Forum IMA v1.1, (R-125) in Section 12.2.2.2 on page 77"
      ::= { imaLinkEntry 13 }

imaLinkOifAnomalies OBJECT-TYPE
      SYNTAX      Counter32
      MAX-ACCESS  read-only
      STATUS      current
      DESCRIPTION
        "The number of OIF anomalies, except during SES-IMA or UAS-IMA
        conditions, at the near-end.  This is an optional attribute."
      REFERENCE
        "ATM Forum IMA v1.1, (O-20) in Section 12.2.2.2 on page 77"
      ::= { imaLinkEntry 14 }

imaLinkNeSevErroredSecs OBJECT-TYPE
      SYNTAX      Counter32
      MAX-ACCESS  read-only
      STATUS      current
      DESCRIPTION
        "Count of one second intervals containing &gt;= 30% of the ICP cells
        counted as IV-IMAs, or one or more link defects (e.g., LOS, OOF/LOF,
        AIS, or LCD), LIF defects, or LODS defects, except during UAS-IMA
        condition."
      REFERENCE
        "ATM Forum IMA v1.1, (R-126) in Section 12.2.2.2 on page 77"
      ::= { imaLinkEntry 15 }

imaLinkFeSevErroredSecs OBJECT-TYPE
      SYNTAX      Counter32
      MAX-ACCESS  read-only
      STATUS      current
      DESCRIPTION
        "Count of one second intervals containing one or more RDI-IMA
        defects, except during UAS-IMA-FE condition."
      REFERENCE
        "ATM Forum IMA v1.1, (R-127) in Section 12.2.2.2 on page 77"
      ::= { imaLinkEntry 16 }

imaLinkNeUnavailSecs OBJECT-TYPE
      SYNTAX      Counter32
      MAX-ACCESS  read-only
      STATUS      current
      DESCRIPTION
        "Count of unavailable seconds at near-end: unavailability begins
        at the onset of 10 contiguous SES-IMA and ends at the onset
        of 10 contiguous seconds with no SES-IMA."
      REFERENCE
        "ATM Forum IMA v1.1, (R-128) in Section 12.2.2.2 on page 77"
      ::= { imaLinkEntry 17 }

imaLinkFeUnavailSecs OBJECT-TYPE
      SYNTAX      Counter32
      MAX-ACCESS  read-only
      STATUS      current
      DESCRIPTION
        "Count of unavailable seconds at far-end: unavailability begins
        at the onset of 10 contiguous SES-IMA-FE and ends at the onset of
        10 contiguous seconds with no SES-IMA-FE."
      REFERENCE
        "ATM Forum IMA v1.1, (R-129) in Section 12.2.2.2 on page 77"
      ::= { imaLinkEntry 18 }

imaLinkNeTxUnusableSecs OBJECT-TYPE
      SYNTAX      Counter32
      MAX-ACCESS  read-only
      STATUS      current
      DESCRIPTION
        "Tx Unusable seconds: count of Tx Unusable seconds at the near-end
        Tx LSM."
      REFERENCE
        "ATM Forum IMA v1.1, (R-130) in Section 12.2.2.2 on page 77"
      ::= { imaLinkEntry 19 }

imaLinkNeRxUnusableSecs OBJECT-TYPE
      SYNTAX      Counter32
      MAX-ACCESS  read-only
      STATUS      current
      DESCRIPTION
        "Rx Unusable seconds: count of Rx Unusable seconds at the near-end
        Rx LSM."
      REFERENCE
        "ATM Forum IMA v1.1, (R-131) in Section 12.2.2.2 on page 77"
      ::= { imaLinkEntry 20 }

imaLinkFeTxUnusableSecs OBJECT-TYPE
      SYNTAX      Counter32
      MAX-ACCESS  read-only
      STATUS      current
      DESCRIPTION
        "Tx Unusable seconds at far-end: count of seconds with Tx Unusable
        indications from the far-end Tx LSM."
      REFERENCE
        "ATM Forum IMA v1.1, (R-132) in Section 12.2.2.2 on page 77"
      ::= { imaLinkEntry 21 }

imaLinkFeRxUnusableSecs OBJECT-TYPE
      SYNTAX      Counter32
      MAX-ACCESS  read-only
      STATUS      current
      DESCRIPTION
        "Rx Unusable seconds at far-end: count of seconds with Rx Unusable
        indications from the far-end Rx LSM."
      REFERENCE
        "ATM Forum IMA v1.1, (R-133) in Section 12.2.2.2 on page 77"
      ::= { imaLinkEntry 22 }

imaLinkNeTxNumFailures OBJECT-TYPE
      SYNTAX      Counter32
      MAX-ACCESS  read-only
      STATUS      current
      DESCRIPTION
        "The number of times a near-end transmit failure alarm condition
        has been entered on this link (i.e., some form of implementation
        specific transmit fault)."
      REFERENCE
        "ATM Forum IMA v1.1, (R-134) in Section 12.2.2.2 on page 77"
      ::= { imaLinkEntry 23 }

imaLinkNeRxNumFailures OBJECT-TYPE
      SYNTAX      Counter32
      MAX-ACCESS  read-only
      STATUS      current
      DESCRIPTION
        "The number of times a near-end receive failure alarm condition
        has been entered on this link (i.e., LIF, LODS, 
        RFI-IMA, Mis-Connected or some form of implementation specific receive
        fault)."
      REFERENCE
        "ATM Forum IMA v1.1, (R-135) in Section 12.2.2.2 on page 77"
      ::= { imaLinkEntry 24 }

imaLinkFeTxNumFailures OBJECT-TYPE
      SYNTAX      Counter32
      MAX-ACCESS  read-only
      STATUS      current
      DESCRIPTION
        "The number of times a far-end transmit failure alarm condition
        has been entered on this link (i.e., Tx-Unusable-FE).  This is an
        optional attribute."
      REFERENCE
        "ATM Forum IMA v1.1, (O-21) in Section 12.2.2.2 on page 77"
      ::= { imaLinkEntry 25 }

imaLinkFeRxNumFailures OBJECT-TYPE
      SYNTAX      Counter32
      MAX-ACCESS  read-only
      STATUS      current
      DESCRIPTION
        "The number of times a far-end receive failure alarm condition
        has been entered on this link (i.e., Rx-Unusable-FE).  This is an
        optional attribute."
      REFERENCE
        "ATM Forum IMA v1.1, (O-22) in Section 12.2.2.2 on page 77"
      ::= { imaLinkEntry 26 }

imaLinkTxStuffs OBJECT-TYPE
      SYNTAX      Counter32
      MAX-ACCESS  read-only
      STATUS      current
      DESCRIPTION
        "Count of stuff events inserted in the transmit direction.
        This is an optional attribute."
      REFERENCE
        "ATM Forum IMA v1.1, (O-23) in Section 12.2.2.2 on page 77"
      ::= { imaLinkEntry 27 }

imaLinkRxStuffs OBJECT-TYPE
      SYNTAX      Counter32
      MAX-ACCESS  read-only
      STATUS      current
      DESCRIPTION
        "Count of stuff events detected in the receive direction.
        This is an optional attribute."
      REFERENCE
        "ATM Forum IMA v1.1, (O-24) in Section 12.2.2.2 on page 77"
      ::= { imaLinkEntry 28 }

--
-- Test Pattern Procedure control objects.  These objects are implemented
-- if the IMA implements the Test Pattern Procedure.  In this case all
-- test pattern procedure related objects must be implemented.  Specifically,
-- these objects are:
--
--   imaGroupTestLinkIfIndex
--   imaGroupTestPattern
--   imaGroupTestProcStatus
--   imaLinkRxTestPattern
--   imaLinkTestProcStatus
--

imaLinkRxTestPattern OBJECT-TYPE
      SYNTAX      INTEGER (0..255)
      MAX-ACCESS  read-only
      STATUS      current
      DESCRIPTION
        "This object identifies the test pattern received in the
        ICP Cell (octet 17) on the link during the IMA Test Pattern
        Procedure.  This value may then be compared to the transmitted
        test pattern."
      ::= { imaLinkEntry 29 }

imaLinkTestProcStatus OBJECT-TYPE
      SYNTAX      ImaTestProcStatus
      MAX-ACCESS  read-only
      STATUS      current
      DESCRIPTION
        "This value indicates the current state of the Test Pattern
        Procedure.  If the value is disabled(1), the test is not
        running.  A value of operating(2) means the test is running
        and no error has been found on this interface.  A value of
        linkFail(3) means an error has been detected on this link
        during the test.

        Once an error is detected, the linkFail(3) value is latched until
        either this object is read or until the imaGroupTestProcStatus
        is moved to disabled(1).  Once read, if the error no longer
        persists, a subsequent read will report the value operating(2)."
      ::= { imaLinkEntry 30 }

--
-- Objects for use with the IMA Link Current Table, the IMA Link
-- Interval Table, and the IMA Link Total Table.
--
-- Implementation of these objects is optional, dependent on whether
-- the tables mentioned above are implemented.
--

imaLinkValidIntervals OBJECT-TYPE
      SYNTAX      INTEGER (0..96)
      MAX-ACCESS  read-only
      STATUS      current
      DESCRIPTION
        "The number of previous 15 minute intervals for which valid data
        was collected.  The value will be 96 unless the IMA group table
        entry was created within the last 24 hours, in which case the value
        will be the number of complete 15 minute intervals since the IMA
        group table entry was created.  In the case where the agent is a
        proxy, it is possible that some intervals are unavailable.  In this
        case, this value is the maximum interval number for which valid
        data is available.  This attribute is only mandatory when the IMA
        Link Interval Statistics and/or IMA Link Total Statistics objects
        are implemented."
      REFERENCE
        "ATM Forum IMA v1.1, (O-26) in Section 12.2.2.2 on page 77"
      ::= { imaLinkEntry 31 }

imaLinkInvalidIntervals OBJECT-TYPE
      SYNTAX      INTEGER (0..96)
      MAX-ACCESS  read-only
      STATUS      current
      DESCRIPTION
        "The number of intervals for which no valid data is available.
        This attribute is only mandatory when the IMA Link Interval
        Statistics and/or IMA Link Total Statistics objects are
        implemented."
      REFERENCE
        "ATM Forum IMA v1.1, (O-26) in Section 12.2.2.2 
         on page 77"
      ::= { imaLinkEntry 32 }

imaLinkTimeElapsed OBJECT-TYPE
      SYNTAX      INTEGER (0..899)
      MAX-ACCESS  read-only
      STATUS      current
      DESCRIPTION
        "The number of seconds that have elapsed since the beginning of
        the current measurement period.  This attribute is only mandatory
        when the IMA Link Current Statistics are implemented."
      REFERENCE
        "ATM Forum IMA v1.1, (O-26) in Section 12.2.2.2 
         on page 77"
      ::= { imaLinkEntry 33 }

--
-- IMA Failure Alarms
--
-- Implementation of the imaFailureAlarm Trap is optional.
--

imaAlarmStatus OBJECT-TYPE
      SYNTAX      ImaAlarmStatus
      MAX-ACCESS  accessible-for-notify
      STATUS      current
      DESCRIPTION
        "Status of the IMA alarm."
       ::= { atmfImaMibObjects 5 }

imaAlarmType OBJECT-TYPE
      SYNTAX      ImaAlarmType
      MAX-ACCESS  accessible-for-notify
      STATUS      current
      DESCRIPTION
        "The Type of IMA alarm declared or cleared.  The value of
        ImaAlarmType identifies the type of alarm according to the
        definitions in the IMA specification."
      REFERENCE
        "ATM Forum IMA v1.1, Section 12.2.3 on page 79"
       ::= { atmfImaMibObjects 6 }

imaFailureAlarm NOTIFICATION-TYPE
      OBJECTS {
        ifIndex,
        imaAlarmStatus,
        imaAlarmType }
      STATUS      current
      DESCRIPTION
        "The imaFailureAlarm provides a method for an agent implementing IMA
        to notify an NMS of an alarm condition."
      REFERENCE
        "ATM Forum IMA v1.1, Section 12.2.3 on page 79"
      ::= { atmfImaMibTrapPrefix 1 }

--
-- The IMA Group Current Statistics subtree
--
-- The IMA Group Current Statistics subtree consists of a single table:
-- the IMA Group Current Table.  This table contains various statistics
-- collected by each IMA group for the current 15 minute interval.
--
-- Implementation of IMA Group Current Table is optional.
--

imaGroupCurrentTable OBJECT-TYPE
      SYNTAX      SEQUENCE OF ImaGroupCurrentEntry
      MAX-ACCESS  not-accessible
      STATUS      current
      DESCRIPTION
        "The IMA Group Current table."
      ::= { atmfImaMibObjects 7 }

imaGroupCurrentEntry OBJECT-TYPE
      SYNTAX      ImaGroupCurrentEntry
      MAX-ACCESS  not-accessible
      STATUS      current
      DESCRIPTION
        "An entry in the IMA Group Current table."
      INDEX       { imaGroupIndex }
      ::= { imaGroupCurrentTable 1 }

ImaGroupCurrentEntry ::= SEQUENCE {
      imaGroupCurrentUnavailSecs     Gauge32,
      imaGroupCurrentNeNumFailures   Gauge32,
      imaGroupCurrentFeNumFailures   Gauge32 }

imaGroupCurrentUnavailSecs OBJECT-TYPE
      SYNTAX      Gauge32
      MAX-ACCESS  read-only
      STATUS      current
      DESCRIPTION
        "Count of one second intervals where the IMA Group Traffic
        State Machine is Down in the current 15 minutes interval."
      REFERENCE
        "ATM Forum IMA v1.1, Section 10.2.1 on page 55, (R-136) and
        (O-26) in Section 12.2.2.2 on page 77"
      ::= { imaGroupCurrentEntry 1 }

imaGroupCurrentNeNumFailures OBJECT-TYPE
      SYNTAX      Gauge32
      MAX-ACCESS  read-only
      STATUS      current
      DESCRIPTION
        "The number of times a near-end group failure (Config-Aborted,
        Insufficient-Links) has been reported in the current 15
        minutes interval."
      REFERENCE
        "ATM Forum IMA v1.1, (R-137) and (O-26) in Section 12.2.2.2 
        on page 77"
      ::= { imaGroupCurrentEntry 2 }

imaGroupCurrentFeNumFailures OBJECT-TYPE
      SYNTAX      Gauge32
      MAX-ACCESS  read-only
      STATUS      current
      DESCRIPTION
        "The number of times a far-end group failure (Config-Aborted-FE,
        Insufficient-Links-FE, Blocked-FE) has been reported in the
        current 15 minutes interval.  This is an optional attribute."
      REFERENCE
        "ATM Forum IMA v1.1, (O-25) and (O-26) in Section 12.2.2.2
        on page 77"
      ::= { imaGroupCurrentEntry 3 }

--
-- The IMA Group Interval Statistics subtree
--
-- The IMA Group Interval Statistics subtree consists of a single table:
-- the IMA Group Interval Table.  This table contains various statistics
-- collected by each IMA group over the previous 24 hours of operation.
-- The past 24 hours are broken into 96 completed 15 minute intervals.
--
-- Implementation of IMA Group Interval Table is optional.
--

imaGroupIntervalTable OBJECT-TYPE
      SYNTAX      SEQUENCE OF ImaGroupIntervalEntry
      MAX-ACCESS  not-accessible
      STATUS      current
      DESCRIPTION
        "The IMA Group Interval table."
      ::= { atmfImaMibObjects 8 }

imaGroupIntervalEntry OBJECT-TYPE
      SYNTAX      ImaGroupIntervalEntry
      MAX-ACCESS  not-accessible
      STATUS      current
      DESCRIPTION
        "An entry in the IMA Group Interval table."
      INDEX       { imaGroupIndex, imaGroupIntervalNumber }
      ::= { imaGroupIntervalTable 1 }

ImaGroupIntervalEntry ::= SEQUENCE {
      imaGroupIntervalNumber          INTEGER (1..96),
      imaGroupIntervalUnavailSecs     Gauge32,
      imaGroupIntervalNeNumFailures   Gauge32,
      imaGroupIntervalFeNumFailures   Gauge32 }

imaGroupIntervalNumber OBJECT-TYPE
      SYNTAX      INTEGER (1..96)
      MAX-ACCESS  not-accessible
      STATUS      current
      DESCRIPTION
        "A number between 1 and 96, where 1 is the most
         recently completed 15 minute interval and 96 is the least
         recently completed 15 minutes interval (assuming that all
         96 intervals are valid)."
      ::= { imaGroupIntervalEntry 1 }

imaGroupIntervalUnavailSecs OBJECT-TYPE
      SYNTAX      Gauge32
      MAX-ACCESS  read-only
      STATUS      current
      DESCRIPTION
        "Count of one second intervals where the IMA Group Traffic
        State Machine is Down in one of the previous 96, individual 15
        minute, intervals."
      REFERENCE
        "ATM Forum IMA v1.1, Section 10.2.1 on page 55, (R-136) and 
        (O-26) in Section 12.2.2.2 on page 77"
      ::= { imaGroupIntervalEntry 2 }

imaGroupIntervalNeNumFailures OBJECT-TYPE
      SYNTAX      Gauge32
      MAX-ACCESS  read-only
      STATUS      current
      DESCRIPTION
        "The number of times a near-end group failure (Config-Aborted,
        Insufficient-Links) has been reported in one of the previous
        96, individual 15 minute, intervals."
      REFERENCE
        "ATM Forum IMA v1.1, (R-137) and (O-26) in Section 12.2.2.2 
        on page 77"
      ::= { imaGroupIntervalEntry 3 }

imaGroupIntervalFeNumFailures OBJECT-TYPE
      SYNTAX      Gauge32
      MAX-ACCESS  read-only
      STATUS      current
      DESCRIPTION
        "The number of times a far-end group failure (Config-Aborted-FE,
        Insufficient-Links-FE, Blocked-FE) has been reported in one of
        the previous 96, individual 15 minute, intervals.  This is an
        optional attribute."
      REFERENCE
        "ATM Forum IMA v1.1, (O-25) and (O-26) in Section 12.2.2.2 
        on page 77"
      ::= { imaGroupIntervalEntry 4 }

--
-- The IMA Group Total Statistics subtree
--
-- The IMA Group Total Statistics subtree consists of a single table:
-- the IMA Group Total Table.  This table contains the cumulative sum
-- of the various statistics collected by each IMA group for the 24 hour
-- period preceding the current interval.
--
-- Implementation of IMA Group Total Table is optional.
--

imaGroupTotalTable OBJECT-TYPE
      SYNTAX      SEQUENCE OF ImaGroupTotalEntry
      MAX-ACCESS  not-accessible
      STATUS      current
      DESCRIPTION
        "The IMA Group Total table."
      ::= { atmfImaMibObjects 9 }

imaGroupTotalEntry OBJECT-TYPE
      SYNTAX      ImaGroupTotalEntry
      MAX-ACCESS  not-accessible
      STATUS      current
      DESCRIPTION
        "An entry in the IMA Group Total table."
      INDEX       { imaGroupIndex }
      ::= { imaGroupTotalTable 1 }

ImaGroupTotalEntry ::= SEQUENCE {
      imaGroupTotalUnavailSecs     Gauge32,
      imaGroupTotalNeNumFailures   Gauge32,
      imaGroupTotalFeNumFailures   Gauge32 }

imaGroupTotalUnavailSecs OBJECT-TYPE
      SYNTAX      Gauge32
      MAX-ACCESS  read-only
      STATUS      current
      DESCRIPTION
        "Count of one second intervals where the IMA Group Traffic
        State Machine is Down in the previous 24 hour interval.
        Invalid 15 minute intervals count as 0."
      REFERENCE
        "ATM Forum IMA v1.1, Section 10.2.1 on page 55, (R-136) and 
        (O-27) in Section 12.2.2.2 on page 77"
      ::= { imaGroupTotalEntry 1 }

imaGroupTotalNeNumFailures OBJECT-TYPE
      SYNTAX      Gauge32
      MAX-ACCESS  read-only
      STATUS      current
      DESCRIPTION
        "The number of times a near-end group failure (Config-Aborted,
        Insufficient-Links) has been reported in the previous 24 hour
        interval.  Invalid 15 minute intervals count as 0."
      REFERENCE
        "ATM Forum IMA v1.1, (R-137) and (O-27) in Section 12.2.2.2 
        on page 77"
      ::= { imaGroupTotalEntry 2 }

imaGroupTotalFeNumFailures OBJECT-TYPE
      SYNTAX      Gauge32
      MAX-ACCESS  read-only
      STATUS      current
      DESCRIPTION
        "The number of times a far-end group failure (Config-Aborted-FE,
        Insufficient-Links-FE, Blocked-FE) has been reported in the
        previous 24 hour interval.  Invalid 15 minute intervals count
        as 0.  This is an optional attribute."
      REFERENCE
        "ATM Forum IMA v1.1, (O-25) and (O-27) in Section 12.2.2.2 
        on page 77"
      ::= { imaGroupTotalEntry 3 }

--
-- The IMA Link Current Statistics subtree
--
-- The IMA Link Current Statistics subtree consists of a single table:
-- the IMA Link Current Table.  This table contains various statistics
-- collected by each IMA link for the current 15 minute interval.
--
-- Implementation of IMA Link Current Table is optional.
--

imaLinkCurrentTable OBJECT-TYPE
      SYNTAX      SEQUENCE OF ImaLinkCurrentEntry
      MAX-ACCESS  not-accessible
      STATUS      current
      DESCRIPTION
        "The IMA Link Current table."
      ::= { atmfImaMibObjects 10 }

imaLinkCurrentEntry OBJECT-TYPE
      SYNTAX      ImaLinkCurrentEntry
      MAX-ACCESS  not-accessible
      STATUS      current
      DESCRIPTION
        "An entry in the IMA Link Current table."
      INDEX       { ifIndex }
      ::= { imaLinkCurrentTable 1 }

ImaLinkCurrentEntry ::= SEQUENCE {
      imaLinkCurrentImaViolations     Gauge32,
      imaLinkCurrentOifAnomalies      Gauge32,
      imaLinkCurrentNeSevErroredSecs  Gauge32,
      imaLinkCurrentFeSevErroredSecs  Gauge32,
      imaLinkCurrentNeUnavailSecs     Gauge32,
      imaLinkCurrentFeUnavailSecs     Gauge32,
      imaLinkCurrentNeTxUnusableSecs  Gauge32,
      imaLinkCurrentNeRxUnusableSecs  Gauge32,
      imaLinkCurrentFeTxUnusableSecs  Gauge32,
      imaLinkCurrentFeRxUnusableSecs  Gauge32,
      imaLinkCurrentNeTxNumFailures   Gauge32,
      imaLinkCurrentNeRxNumFailures   Gauge32,
      imaLinkCurrentFeTxNumFailures   Gauge32,
      imaLinkCurrentFeRxNumFailures   Gauge32,
      imaLinkCurrentTxStuffs          Gauge32,
      imaLinkCurrentRxStuffs          Gauge32 }

imaLinkCurrentImaViolations OBJECT-TYPE
      SYNTAX      Gauge32
      MAX-ACCESS  read-only
      STATUS      current
      DESCRIPTION
        "ICP violations: count of errored, invalid or missing ICP cells,
        except during SES-IMA or UAS-IMA conditions, in the current
        15 minute interval."
      REFERENCE
        "ATM Forum IMA v1.1, (R-125) and (O-26) in Section 12.2.2.2 
        on page 77"
      ::= { imaLinkCurrentEntry 1 }

imaLinkCurrentOifAnomalies OBJECT-TYPE
      SYNTAX      Gauge32
      MAX-ACCESS  read-only
      STATUS      current
      DESCRIPTION
        "The number of OIF anomalies, except during SES-IMA or UAS-IMA
        conditions, at the near-end in the current 15 minute interval.
        This is an optional attribute."
      REFERENCE
        "ATM Forum IMA v1.1, (O-20) and (O-26) in Section 12.2.2.2 
        on page 77"
      ::= { imaLinkCurrentEntry 2 }

imaLinkCurrentNeSevErroredSecs OBJECT-TYPE
      SYNTAX      Gauge32
      MAX-ACCESS  read-only
      STATUS      current
      DESCRIPTION
        "Count of one second intervals containing &gt;= 30% of the ICP cells
        counted as IV-IMAs, or one or more link defects (e.g., LOS, OOF/LOF,
        AIS, or LCD), LIF defects, or LODS defects, except during UAS-IMA
        condition, in the current 15 minute interval."
      REFERENCE
        "ATM Forum IMA v1.1, (R-126) and (O-26) in Section 12.2.2.2 
        on page 77"
      ::= { imaLinkCurrentEntry 3 }

imaLinkCurrentFeSevErroredSecs OBJECT-TYPE
      SYNTAX      Gauge32
      MAX-ACCESS  read-only
      STATUS      current
      DESCRIPTION
        "Count of one second intervals containing one or more RDI-IMA
        defects, except during UAS-IMA-FE condition, in the current 15
        minute interval."
      REFERENCE
        "ATM Forum IMA v1.1, (R-127) and (O-26) in Section 12.2.2.2 
        on page 77"
      ::= { imaLinkCurrentEntry 4 }

imaLinkCurrentNeUnavailSecs OBJECT-TYPE
      SYNTAX      Gauge32
      MAX-ACCESS  read-only
      STATUS      current
      DESCRIPTION
        "Count of unavailable seconds at near-end in the current 15 minute
        interval: unavailability begins at the onset of 10 contiguous
        SES-IMA and ends at the onset of 10 contiguous seconds with no
        SES-IMA."
      REFERENCE
        "ATM Forum IMA v1.1, (R-128) and (O-26) in Section 12.2.2.2 
        on page 77"
      ::= { imaLinkCurrentEntry 5 }

imaLinkCurrentFeUnavailSecs OBJECT-TYPE
      SYNTAX      Gauge32
      MAX-ACCESS  read-only
      STATUS      current
      DESCRIPTION
        "Count of unavailable seconds at far-end in the current 15 minute
        interval: unavailability begins at the onset of 10 contiguous
        SES-IMA-FE and ends at the onset of 10 contiguous seconds with no
        SES-IMA-FE."
      REFERENCE
        "ATM Forum IMA v1.1, (R-129) and (O-26) in Section 12.2.2.2 
        on page 77"
      ::= { imaLinkCurrentEntry 6 }

imaLinkCurrentNeTxUnusableSecs OBJECT-TYPE
      SYNTAX      Gauge32
      MAX-ACCESS  read-only
      STATUS      current
      DESCRIPTION
        "Tx Unusable seconds: count of Unusable seconds at the near-end
        Tx LSM in the current 15 minute interval."
      REFERENCE
        "ATM Forum IMA v1.1, (R-130) and (O-26) in Section 12.2.2.2 
        on page 77"
      ::= { imaLinkCurrentEntry 7 }

imaLinkCurrentNeRxUnusableSecs OBJECT-TYPE
      SYNTAX      Gauge32
      MAX-ACCESS  read-only
      STATUS      current
      DESCRIPTION
        "Rx Unusable seconds: count of Unusable seconds at the near-end
        Rx LSM in the current 15 minute interval."
      REFERENCE
        "ATM Forum IMA v1.1, (R-131) and (O-26) in Section 12.2.2.2 
        on page 77"
      ::= { imaLinkCurrentEntry 8 }

imaLinkCurrentFeTxUnusableSecs OBJECT-TYPE
      SYNTAX      Gauge32
      MAX-ACCESS  read-only
      STATUS      current
      DESCRIPTION
        "Tx Unusable seconds at far-end: count of seconds with Tx Unusable
        indications from the far-end Tx LSM in the current 15 minute
        interval."
      REFERENCE
        "ATM Forum IMA v1.1, (R-132) and (O-26) in Section 12.2.2.2 
        on page 77"
      ::= { imaLinkCurrentEntry 9 }

imaLinkCurrentFeRxUnusableSecs OBJECT-TYPE
      SYNTAX      Gauge32
      MAX-ACCESS  read-only
      STATUS      current
      DESCRIPTION
        "Rx Unusable seconds at far-end: count of seconds with Rx Unusable
        indications from the far-end Rx LSM in the current 15 minute
        interval."
      REFERENCE
        "ATM Forum IMA v1.1, (R-133) and (O-26) in Section 12.2.2.2 
        on page 77"
      ::= { imaLinkCurrentEntry 10 }

imaLinkCurrentNeTxNumFailures OBJECT-TYPE
      SYNTAX      Gauge32
      MAX-ACCESS  read-only
      STATUS      current
      DESCRIPTION
        "The number of times a near-end transmit failure alarm condition
        has been entered on this link (i.e., some form of implementation
        specific transmit fault) in the current 15 minute interval."
      REFERENCE
        "ATM Forum IMA v1.1, (R-134) and (O-26) in Section 12.2.2.2 
        on page 77"
      ::= { imaLinkCurrentEntry 11 }

imaLinkCurrentNeRxNumFailures OBJECT-TYPE
      SYNTAX      Gauge32
      MAX-ACCESS  read-only
      STATUS      current
      DESCRIPTION
        "The number of times a near-end receive failure alarm condition
        has been entered on this link (i.e., LIF, LODS, RFI-IMA, Mis-Connected,
        or some form of implementation specific receive fault)
        in the current 15 minute interval."
      REFERENCE
        "ATM Forum IMA v1.1, (R-135) and (O-26) in Section 12.2.2.2 
        on page 77"
      ::= { imaLinkCurrentEntry 12 }

imaLinkCurrentFeTxNumFailures OBJECT-TYPE
      SYNTAX      Gauge32
      MAX-ACCESS  read-only
      STATUS      current
      DESCRIPTION
        "The number of times a far-end transmit failure alarm condition
        has been entered on this link (i.e., Tx-Unusable-FE) in the
        current 15 minute interval.  This is an optional attribute."
      REFERENCE
        "ATM Forum IMA v1.1, (O-21) and (O-26) in Section 12.2.2.2 
        on page 77"
      ::= { imaLinkCurrentEntry 13 }

imaLinkCurrentFeRxNumFailures OBJECT-TYPE
      SYNTAX      Gauge32
      MAX-ACCESS  read-only
      STATUS      current
      DESCRIPTION
        "The number of times a far-end receive failure alarm condition
        has been entered on this link (i.e., Rx-Unusable-FE) in the
        current 15 minute interval.  This is an optional attribute."
      REFERENCE
        "ATM Forum IMA v1.1, (O-22) and (O-26) in Section 12.2.2.2 
        on page 77"
      ::= { imaLinkCurrentEntry 14 }

imaLinkCurrentTxStuffs OBJECT-TYPE
      SYNTAX      Gauge32
      MAX-ACCESS  read-only
      STATUS      current
      DESCRIPTION
        "Count of stuff events inserted in the transmit direction in
        the current 15 minute interval.  This is an optional attribute."
      REFERENCE
        "ATM Forum IMA v1.1, (O-23) and (O-26) in Section 12.2.2.2 
        on page 77"
      ::= { imaLinkCurrentEntry 15 }

imaLinkCurrentRxStuffs OBJECT-TYPE
      SYNTAX      Gauge32
      MAX-ACCESS  read-only
      STATUS      current
      DESCRIPTION
        "Count of stuff events detected in the receive direction in
        the current 15 minute interval.  This is an optional attribute."
      REFERENCE
        "ATM Forum IMA v1.1, (O-24) and (O-26) in Section 12.2.2.2 
        on page 77"
      ::= { imaLinkCurrentEntry 16 }

--
-- The IMA Link Interval Statistics subtree
--
-- The IMA Link Interval Statistics subtree consists of a single table:
-- the IMA Link Interval Table.  This table contains various statistics
-- collected by each IMA link over the previous 24 hours of operation.
-- The past 24 hours are broken into 96 completed 15 minute intervals.
--
-- Implementation of IMA Link Interval Table is optional.
--

imaLinkIntervalTable OBJECT-TYPE
      SYNTAX      SEQUENCE OF ImaLinkIntervalEntry
      MAX-ACCESS  not-accessible
      STATUS      current
      DESCRIPTION
        "The IMA Link Interval table."
      ::= { atmfImaMibObjects 11 }

imaLinkIntervalEntry OBJECT-TYPE
      SYNTAX      ImaLinkIntervalEntry
      MAX-ACCESS  not-accessible
      STATUS      current
      DESCRIPTION
        "An entry in the IMA Link Interval table."
      INDEX       { ifIndex, imaLinkIntervalNumber }
      ::= { imaLinkIntervalTable 1 }

ImaLinkIntervalEntry ::= SEQUENCE {
      imaLinkIntervalNumber            INTEGER (1..96),
      imaLinkIntervalImaViolations     Gauge32,
      imaLinkIntervalOifAnomalies      Gauge32,
      imaLinkIntervalNeSevErroredSecs  Gauge32,
      imaLinkIntervalFeSevErroredSecs  Gauge32,
      imaLinkIntervalNeUnavailSecs     Gauge32,
      imaLinkIntervalFeUnavailSecs     Gauge32,
      imaLinkIntervalNeTxUnusableSecs  Gauge32,
      imaLinkIntervalNeRxUnusableSecs  Gauge32,
      imaLinkIntervalFeTxUnusableSecs  Gauge32,
      imaLinkIntervalFeRxUnusableSecs  Gauge32,
      imaLinkIntervalNeTxNumFailures   Gauge32,
      imaLinkIntervalNeRxNumFailures   Gauge32,
      imaLinkIntervalFeTxNumFailures   Gauge32,
      imaLinkIntervalFeRxNumFailures   Gauge32,
      imaLinkIntervalTxStuffs          Gauge32,
      imaLinkIntervalRxStuffs          Gauge32 }

imaLinkIntervalNumber OBJECT-TYPE
      SYNTAX      INTEGER (1..96)
      MAX-ACCESS  not-accessible
      STATUS      current
      DESCRIPTION
        "A number between 1 and 96, where 1 is the most
         recently completed 15 minute interval and 96 is the least
         recently completed 15 minutes interval (assuming that all
         96 intervals are valid)."
      ::= { imaLinkIntervalEntry 1 }

imaLinkIntervalImaViolations OBJECT-TYPE
      SYNTAX      Gauge32
      MAX-ACCESS  read-only
      STATUS      current
      DESCRIPTION
        "ICP violations: count of errored, invalid or missing ICP cells,
        except during SES-IMA or UAS-IMA conditions, in one of the
        previous 96, individual 15 minute, intervals."
      REFERENCE
        "ATM Forum IMA v1.1, (R-125) and (O-26) in Section 12.2.2.2 
        on page 77"
      ::= { imaLinkIntervalEntry 2 }

imaLinkIntervalOifAnomalies OBJECT-TYPE
      SYNTAX      Gauge32
      MAX-ACCESS  read-only
      STATUS      current
      DESCRIPTION
        "The number of OIF anomalies, except during SES-IMA or UAS-IMA
        conditions, at the near-end in one of the previous 96, individual
        15 minute, intervals.  This is an optional attribute."
      REFERENCE
        "ATM Forum IMA v1.1, (O-20) and (O-26) in Section 12.2.2.2 
        on page 77"
      ::= { imaLinkIntervalEntry 3 }

imaLinkIntervalNeSevErroredSecs OBJECT-TYPE
      SYNTAX      Gauge32
      MAX-ACCESS  read-only
      STATUS      current
      DESCRIPTION
        "Count of one second intervals containing &gt;= 30% of the ICP cells
        counted as IV-IMAs, or one or more link defects (e.g., LOS, OOF/LOF,
        AIS, or LCD), LIF defects, or LODS defects, except during UAS-IMA
        condition, in one of the previous 96, individual 15 minute,
        intervals."
      REFERENCE
        "ATM Forum IMA v1.1, (R-126) and (O-26) in Section 12.2.2.2 
        on page 77"
      ::= { imaLinkIntervalEntry 4 }

imaLinkIntervalFeSevErroredSecs OBJECT-TYPE
      SYNTAX      Gauge32
      MAX-ACCESS  read-only
      STATUS      current
      DESCRIPTION
        "Count of one second intervals containing one or more RDI-IMA
        defects, except during UAS-IMA-FE condition, in one of the previous
        96, individual 15 minute, intervals."
      REFERENCE
        "ATM Forum IMA v1.1, (R-127) and (O-26) in Section 12.2.2.2 
        on page 77"
      ::= { imaLinkIntervalEntry 5 }

imaLinkIntervalNeUnavailSecs OBJECT-TYPE
      SYNTAX      Gauge32
      MAX-ACCESS  read-only
      STATUS      current
      DESCRIPTION
        "Count of unavailable seconds at near-end in one of the previous
        96, individual 15 minute, intervals: unavailability begins at the
        onset of 10 contiguous SES-IMA and ends at the onset of 10
        contiguous seconds with no SES-IMA."
      REFERENCE
        "ATM Forum IMA v1.1, (R-128) and (O-26) in Section 12.2.2.2 
        on page 77"
      ::= { imaLinkIntervalEntry 6 }

imaLinkIntervalFeUnavailSecs OBJECT-TYPE
      SYNTAX      Gauge32
      MAX-ACCESS  read-only
      STATUS      current
      DESCRIPTION
        "Count of unavailable seconds at far-end in one of the previous
        96, individual 15 minute, intervals: unavailability begins at the
        onset of 10 contiguous SES-IMA-FE and ends at the onset of 10
        contiguous seconds with no SES-IMA-FE."
      REFERENCE
        "ATM Forum IMA v1.1, (R-129) and (O-26) in Section 12.2.2.2 
        on page 77"
      ::= { imaLinkIntervalEntry 7 }

imaLinkIntervalNeTxUnusableSecs OBJECT-TYPE
      SYNTAX      Gauge32
      MAX-ACCESS  read-only
      STATUS      current
      DESCRIPTION
        "Tx Unusable seconds: count of Unusable seconds at the near-end
        Tx LSM in one of the previous 96, individual 15 minute, intervals."
      REFERENCE
        "ATM Forum IMA v1.1, (R-130) and (O-26) in Section 12.2.2.2 
        on page 77"
      ::= { imaLinkIntervalEntry 8 }

imaLinkIntervalNeRxUnusableSecs OBJECT-TYPE
      SYNTAX      Gauge32
      MAX-ACCESS  read-only
      STATUS      current
      DESCRIPTION
        "Rx Unusable seconds: count of Unusable seconds at the near-end
        Rx LSM in one of the previous 96, individual 15 minute, intervals."
      REFERENCE
        "ATM Forum IMA v1.1, (R-131) and (O-26) in Section 12.2.2.2 
        on page 77"
      ::= { imaLinkIntervalEntry 9 }

imaLinkIntervalFeTxUnusableSecs OBJECT-TYPE
      SYNTAX      Gauge32
      MAX-ACCESS  read-only
      STATUS      current
      DESCRIPTION
        "Tx Unusable seconds at far-end: count of seconds with Tx Unusable
        indications from the far-end Tx LSM in one of the previous 96,
        individual 15 minute, intervals."
      REFERENCE
        "ATM Forum IMA v1.1, (R-132) and (O-26) in Section 12.2.2.2 
        on page 77"
      ::= { imaLinkIntervalEntry 10 }

imaLinkIntervalFeRxUnusableSecs OBJECT-TYPE
      SYNTAX      Gauge32
      MAX-ACCESS  read-only
      STATUS      current
      DESCRIPTION
        "Rx Unusable seconds at far-end: count of seconds with Rx Unusable
        indications from the far-end Rx LSM in one of the previous 96,
        individual 15 minute, intervals."
      REFERENCE
        "ATM Forum IMA v1.1, (R-133) and (O-26) in Section 12.2.2.2 
        on page 77"
      ::= { imaLinkIntervalEntry 11 }

imaLinkIntervalNeTxNumFailures OBJECT-TYPE
      SYNTAX      Gauge32
      MAX-ACCESS  read-only
      STATUS      current
      DESCRIPTION
        "The number of times a near-end transmit failure alarm condition
        has been entered on this link (i.e., some form of implementation
        specific transmit fault) in one of the previous 96, individual
        15 minute, intervals."
      REFERENCE
        "ATM Forum IMA v1.1, (R-134) and (O-26) in Section 12.2.2.2 
        on page 77"
      ::= { imaLinkIntervalEntry 12 }

imaLinkIntervalNeRxNumFailures OBJECT-TYPE
      SYNTAX      Gauge32
      MAX-ACCESS  read-only
      STATUS      current
      DESCRIPTION
        "The number of times a near-end receive failure alarm condition
        has been entered on this link (i.e., LIF, LODS, RFI-IMA, 
        Mis-Connected, or some form of implementation specific 
        receive fault) in one of the previous 96, individual 15 minute,
        intervals."
      REFERENCE
        "ATM Forum IMA v1.1, (R-135) and (O-26) in Section 12.2.2.2 
        on page 77"
      ::= { imaLinkIntervalEntry 13 }

imaLinkIntervalFeTxNumFailures OBJECT-TYPE
      SYNTAX      Gauge32
      MAX-ACCESS  read-only
      STATUS      current
      DESCRIPTION
        "The number of times a far-end transmit failure alarm condition
        has been entered on this link (i.e., Tx-Unusable-FE) in one of the
        previous 96, individual 15 minute, intervals.  This is an optional
        attribute."
      REFERENCE
        "ATM Forum IMA v1.1, (O-21) and (O-26) in Section 12.2.2.2 
        on page 77"
      ::= { imaLinkIntervalEntry 14 }

imaLinkIntervalFeRxNumFailures OBJECT-TYPE
      SYNTAX      Gauge32
      MAX-ACCESS  read-only
      STATUS      current
      DESCRIPTION
        "The number of times a far-end receive failure alarm condition
        has been entered on this link (i.e., Rx-Unusable-FE) in one of
        the previous 96, individual 15 minute, intervals.  This is an
        optional attribute."
      REFERENCE
        "ATM Forum IMA v1.1, (O-22) and (O-26) in Section 12.2.2.2 
        on page 77"
      ::= { imaLinkIntervalEntry 15 }

imaLinkIntervalTxStuffs OBJECT-TYPE
      SYNTAX      Gauge32
      MAX-ACCESS  read-only
      STATUS      current
      DESCRIPTION
        "Count of stuff events inserted in the transmit direction in
        one of the previous 96, individual 15 minute, intervals.  This
        is an optional attribute."
      REFERENCE
        "ATM Forum IMA v1.1, (O-23) and (O-26) in Section 12.2.2.2 
        on page 77"
      ::= { imaLinkIntervalEntry 16 }

imaLinkIntervalRxStuffs OBJECT-TYPE
      SYNTAX      Gauge32
      MAX-ACCESS  read-only
      STATUS      current
      DESCRIPTION
        "Count of stuff events detected in the receive direction in
        one of the previous 96, individual 15 minute, intervals.  This
        is an optional attribute."
      REFERENCE
        "ATM Forum IMA v1.1, (O-24) and (O-26) in Section 12.2.2.2 
        on page 77"
      ::= { imaLinkIntervalEntry 17 }

--
-- The IMA Link Total Statistics subtree
--
-- The IMA Link Total Statistics subtree consists of a single table:
-- the IMA Link Total Table.  This table contains the cumulative sum
-- of the various statistics collected by each IMA link for the 24 hour
-- period preceding the current interval.
--
-- Implementation of IMA Link Total Table is optional.
--

imaLinkTotalTable OBJECT-TYPE
      SYNTAX      SEQUENCE OF ImaLinkTotalEntry
      MAX-ACCESS  not-accessible
      STATUS      current
      DESCRIPTION
        "The IMA Link Total table."
      ::= { atmfImaMibObjects 12 }

imaLinkTotalEntry OBJECT-TYPE
      SYNTAX      ImaLinkTotalEntry
      MAX-ACCESS  not-accessible
      STATUS      current
      DESCRIPTION
        "An entry in the IMA Link Total table."
      INDEX       { ifIndex }
      ::= { imaLinkTotalTable 1 }

ImaLinkTotalEntry ::= SEQUENCE {
      imaLinkTotalImaViolations     Gauge32,
      imaLinkTotalOifAnomalies      Gauge32,
      imaLinkTotalNeSevErroredSecs  Gauge32,
      imaLinkTotalFeSevErroredSecs  Gauge32,
      imaLinkTotalNeUnavailSecs     Gauge32,
      imaLinkTotalFeUnavailSecs     Gauge32,
      imaLinkTotalNeTxUnusableSecs  Gauge32,
      imaLinkTotalNeRxUnusableSecs  Gauge32,
      imaLinkTotalFeTxUnusableSecs  Gauge32,
      imaLinkTotalFeRxUnusableSecs  Gauge32,
      imaLinkTotalNeTxNumFailures   Gauge32,
      imaLinkTotalNeRxNumFailures   Gauge32,
      imaLinkTotalFeTxNumFailures   Gauge32,
      imaLinkTotalFeRxNumFailures   Gauge32,
      imaLinkTotalTxStuffs          Gauge32,
      imaLinkTotalRxStuffs          Gauge32 }

imaLinkTotalImaViolations OBJECT-TYPE
      SYNTAX      Gauge32
      MAX-ACCESS  read-only
      STATUS      current
      DESCRIPTION
        "ICP violations: count of errored, invalid or missing ICP cells,
        except during SES-IMA or UAS-IMA conditions, in the previous 24
        hour interval.  Invalid 15 minute intervals count as 0."
      REFERENCE
        "ATM Forum IMA v1.1, (R-125) and (O-27) in Section 12.2.2.2 
        on page 77"
      ::= { imaLinkTotalEntry 1 }

imaLinkTotalOifAnomalies OBJECT-TYPE
      SYNTAX      Gauge32
      MAX-ACCESS  read-only
      STATUS      current
      DESCRIPTION
        "The number of OIF anomalies, except during SES-IMA or UAS-IMA
        conditions, at the near-end in the previous 24 hour interval.
        Invalid 15 minute intervals count as 0.  This is an optional
        attribute."
      REFERENCE
        "ATM Forum IMA v1.1, (O-20) and (O-27) in Section 12.2.2.2 
        on page 77"
      ::= { imaLinkTotalEntry 2 }

imaLinkTotalNeSevErroredSecs OBJECT-TYPE
      SYNTAX      Gauge32
      MAX-ACCESS  read-only
      STATUS      current
      DESCRIPTION
        "Count of one second intervals containing &gt;= 30% of the ICP cells
        counted as IV-IMAs, or one or more link defects (e.g., LOS, OOF/LOF,
        AIS, or LCD), LIF defects, or LODS defects, except during UAS-IMA
        condition, in the previous 24 hour interval.  Invalid 15 minute
        intervals count as 0."
      REFERENCE
        "ATM Forum IMA v1.1, (R-126) and (O-27) in Section 12.2.2.2 
        on page 77"
      ::= { imaLinkTotalEntry 3 }

imaLinkTotalFeSevErroredSecs OBJECT-TYPE
      SYNTAX      Gauge32
      MAX-ACCESS  read-only
      STATUS      current
      DESCRIPTION
        "Count of one second intervals containing one or more RDI-IMA
        defects, except during UAS-IMA-FE condition, in the previous 24
        hour interval.  Invalid 15 minute intervals count as 0."
      REFERENCE
        "ATM Forum IMA v1.1, (R-127) and (O-27) in Section 12.2.2.2 
        on page 77"
      ::= { imaLinkTotalEntry 4 }

imaLinkTotalNeUnavailSecs OBJECT-TYPE
      SYNTAX      Gauge32
      MAX-ACCESS  read-only
      STATUS      current
      DESCRIPTION
        "Count of unavailable seconds at near-end in the previous 24 hour
        interval: unavailability begins at the onset of 10 contiguous
        SES-IMA and ends at the onset of 10 contiguous seconds with no
        SES-IMA.  Invalid 15 minute intervals count as 0."
      REFERENCE
        "ATM Forum IMA v1.1, (R-128) and (O-27) in Section 12.2.2.2 
        on page 77"
      ::= { imaLinkTotalEntry 5 }

imaLinkTotalFeUnavailSecs OBJECT-TYPE
      SYNTAX      Gauge32
      MAX-ACCESS  read-only
      STATUS      current
      DESCRIPTION
        "Count of unavailable seconds at far-end in the previous 24 hour
        interval: unavailability begins at the onset of 10 contiguous
        SES-IMA-FE and ends at the onset of 10 contiguous seconds with no
        SES-IMA-FE.  Invalid 15 minute intervals count as 0."
      REFERENCE
        "ATM Forum IMA v1.1, (R-129) and (O-27) in Section 12.2.2.2 
        on page 77"
      ::= { imaLinkTotalEntry 6 }

imaLinkTotalNeTxUnusableSecs OBJECT-TYPE
      SYNTAX      Gauge32
      MAX-ACCESS  read-only
      STATUS      current
      DESCRIPTION
        "Tx Unusable seconds: count of Unusable seconds at the near-end
        Tx LSM in the previous 24 hour interval.  Invalid 15 minute
        intervals count as 0."
      REFERENCE
        "ATM Forum IMA v1.1, (R-130) and (O-27) in Section 12.2.2.2 
        on page 77"
      ::= { imaLinkTotalEntry 7 }

imaLinkTotalNeRxUnusableSecs OBJECT-TYPE
      SYNTAX      Gauge32
      MAX-ACCESS  read-only
      STATUS      current
      DESCRIPTION
        "Rx Unusable seconds: count of Unusable seconds at the near-end
        Rx LSM in the previous 24 hour interval.  Invalid 15 minute
        intervals count as 0."
      REFERENCE
        "ATM Forum IMA v1.1, (R-131) and (O-27) in Section 12.2.2.2 
        on page 77"
      ::= { imaLinkTotalEntry 8 }

imaLinkTotalFeTxUnusableSecs OBJECT-TYPE
      SYNTAX      Gauge32
      MAX-ACCESS  read-only
      STATUS      current
      DESCRIPTION
        "Tx Unusable seconds at far-end: count of seconds with Tx Unusable
        indications from the far-end Tx LSM in the previous 24 hour
        interval.  Invalid 15 minute intervals count as 0."
      REFERENCE
        "ATM Forum IMA v1.1, (R-132) and (O-27) in Section 12.2.2.2 
        on page 77"
      ::= { imaLinkTotalEntry 9 }

imaLinkTotalFeRxUnusableSecs OBJECT-TYPE
      SYNTAX      Gauge32
      MAX-ACCESS  read-only
      STATUS      current
      DESCRIPTION
        "Rx Unusable seconds at far-end: count of seconds with Rx Unusable
        indications from the far-end Rx LSM in the previous 24 hour
        interval.  Invalid 15 minute intervals count as 0."
      REFERENCE
        "ATM Forum IMA v1.1, (R-133) and (O-27) in Section 12.2.2.2 
        on page 77"
      ::= { imaLinkTotalEntry 10 }

imaLinkTotalNeTxNumFailures OBJECT-TYPE
      SYNTAX      Gauge32
      MAX-ACCESS  read-only
      STATUS      current
      DESCRIPTION
        "The number of times a near-end transmit failure alarm condition
        has been entered on this link (i.e., some form of implementation
        specific transmit fault) in the previous 24 hour interval.
        Invalid 15 minute intervals count as 0."
      REFERENCE
        "ATM Forum IMA v1.1, (R-134) and (O-27) in Section 12.2.2.2 
        on page 77"
      ::= { imaLinkTotalEntry 11 }

imaLinkTotalNeRxNumFailures OBJECT-TYPE
      SYNTAX      Gauge32
      MAX-ACCESS  read-only
      STATUS      current
      DESCRIPTION
        "The number of times a near-end receive failure alarm condition
        has been entered on this link (i.e., LIF, LODS, RFI-IMA, 
        Mis-Connected, or some form of implementation specific receive fault)
        in the previous 24 hour interval. Invalid 15 minute intervals
        count as 0."
      REFERENCE
        "ATM Forum IMA v1.1, (R-135) and (O-27) in Section 12.2.2.2 
        on page 77"
      ::= { imaLinkTotalEntry 12 }

imaLinkTotalFeTxNumFailures OBJECT-TYPE
      SYNTAX      Gauge32
      MAX-ACCESS  read-only
      STATUS      current
      DESCRIPTION
        "The number of times a far-end transmit failure alarm condition
        has been entered on this link (i.e., Tx-Unusable-FE) in the
        previous 24 hour interval.  Invalid 15 minute intervals count
        as 0.  This is an optional attribute."
      REFERENCE
        "ATM Forum IMA v1.1, (O-21) and (O-27) in Section 12.2.2.2 
        on page 77"
      ::= { imaLinkTotalEntry 13 }

imaLinkTotalFeRxNumFailures OBJECT-TYPE
      SYNTAX      Gauge32
      MAX-ACCESS  read-only
      STATUS      current
      DESCRIPTION
        "The number of times a far-end receive failure alarm condition
        has been entered on this link (i.e., Rx-Unusable-FE) in the
        previous 24 hour interval.  Invalid 15 minute intervals count
        as 0.  This is an optional attribute."
      REFERENCE
        "ATM Forum IMA v1.1, (O-22) and (O-27) in Section 12.2.2.2 
        on page 77"
      ::= { imaLinkTotalEntry 14 }

imaLinkTotalTxStuffs OBJECT-TYPE
      SYNTAX      Gauge32
      MAX-ACCESS  read-only
      STATUS      current
      DESCRIPTION
        "Count of stuff events inserted in the transmit direction in
        the previous 24 hour interval.  Invalid 15 minute intervals
        count as 0.  This is an optional attribute."
      REFERENCE
        "ATM Forum IMA v1.1, (O-23) and (O-27) in Section 12.2.2.2 
        on page 77"
      ::= { imaLinkTotalEntry 15 }

imaLinkTotalRxStuffs OBJECT-TYPE
      SYNTAX      Gauge32
      MAX-ACCESS  read-only
      STATUS      current
      DESCRIPTION
        "Count of stuff events detected in the receive direction in
        the previous 24 hour interval.  Invalid 15 minute intervals
        count as 0.  This is an optional attribute."
      REFERENCE
        "ATM Forum IMA v1.1, (O-24) and (O-27) in Section 12.2.2.2 
        on page 77"
      ::= { imaLinkTotalEntry 16 }

-- Conformance Information

atmfImaMibGroups OBJECT IDENTIFIER ::= { atmfImaMibConformance 1 }
atmfImaMibCompliances OBJECT IDENTIFIER ::= { atmfImaMibConformance 2 }

-- Compliance Statements

atmfImaMibCompliance MODULE-COMPLIANCE
      STATUS      current
      DESCRIPTION
        "The compliance statement for network elements implementing
        ATM Forum Inverse Multiplexing for ATM (IMA) interfaces."
      MODULE -- this module

-- Mandatory Part

      MANDATORY-GROUPS {
        imaGroupGroup,
        imaLinkGroup,
        imaGroupMappingTableGroup,
        imaAlarmGroup,
        imaNotificationsGroup }

      GROUP imaTestPatternGroup
      DESCRIPTION
        "This group is mandatory only for implementations that support
        the Test Pattern Procedure."

      GROUP imaGroupIntervalGroup
      DESCRIPTION
        "This group is mandatory only for implementations that support
        interval statistics."

      GROUP imaLinkIntervalGroup
      DESCRIPTION
        "This group is mandatory only for implementations that support
        interval statistics."

-- Compliance Part

      OBJECT imaGroupSymmetry
      MIN-ACCESS read-only
      DESCRIPTION
        "Write access is not required."

      OBJECT imaGroupMinNumTxLinks
      MIN-ACCESS read-only
      DESCRIPTION
        "Write access is not required."

      OBJECT imaGroupMinNumRxLinks
      MIN-ACCESS read-only
      DESCRIPTION
        "Write access is not required."

      OBJECT imaGroupTxImaId
      MIN-ACCESS read-only
      DESCRIPTION
        "Write access is not required."

      OBJECT imaGroupTxFrameLength
      MIN-ACCESS read-only
      DESCRIPTION
        "Write access is not required."

      OBJECT imaGroupDiffDelayMax
      MIN-ACCESS read-only
      DESCRIPTION
        "Write access is not required."

      OBJECT imaGroupAlphaValue
      MIN-ACCESS read-only
      DESCRIPTION
        "Write access is not required."

      OBJECT imaGroupBetaValue
      MIN-ACCESS read-only
      DESCRIPTION
        "Write access is not required."

      OBJECT imaGroupGammaValue
      MIN-ACCESS read-only
      DESCRIPTION
        "Write access is not required."

      OBJECT imaGroupFeNumFailures
      MIN-ACCESS not-accessible
      DESCRIPTION
        "This is an optional attribute."

      OBJECT imaGroupTestLinkIfIndex
      MIN-ACCESS read-only
      DESCRIPTION
        "Write access is not required."

      OBJECT imaGroupTestPattern
      MIN-ACCESS read-only
      DESCRIPTION
        "Write access is not required."

      OBJECT imaLinkOifAnomalies
      MIN-ACCESS not-accessible
      DESCRIPTION
        "This is an optional attribute."

      OBJECT imaLinkFeTxNumFailures
      MIN-ACCESS not-accessible
      DESCRIPTION
        "This is an optional attribute."

      OBJECT imaLinkFeRxNumFailures
      MIN-ACCESS not-accessible
      DESCRIPTION
        "This is an optional attribute."

      OBJECT imaLinkTxStuffs
      MIN-ACCESS not-accessible
      DESCRIPTION
        "This is an optional attribute."

      OBJECT imaLinkRxStuffs
      MIN-ACCESS not-accessible
      DESCRIPTION
        "This is an optional attribute."

      OBJECT imaGroupCurrentFeNumFailures
      MIN-ACCESS not-accessible
      DESCRIPTION
        "This is an optional attribute."

      OBJECT imaGroupIntervalFeNumFailures
      MIN-ACCESS not-accessible
      DESCRIPTION
        "This is an optional attribute."

      OBJECT imaGroupTotalFeNumFailures
      MIN-ACCESS not-accessible
      DESCRIPTION
        "This is an optional attribute."

      OBJECT imaLinkCurrentOifAnomalies
      MIN-ACCESS not-accessible
      DESCRIPTION
        "This is an optional attribute."

      OBJECT imaLinkCurrentFeTxNumFailures
      MIN-ACCESS not-accessible
      DESCRIPTION
        "This is an optional attribute."

      OBJECT imaLinkCurrentFeRxNumFailures
      MIN-ACCESS not-accessible
      DESCRIPTION
        "This is an optional attribute."

      OBJECT imaLinkCurrentTxStuffs
      MIN-ACCESS not-accessible
      DESCRIPTION
        "This is an optional attribute."

      OBJECT imaLinkCurrentRxStuffs
      MIN-ACCESS not-accessible
      DESCRIPTION
        "This is an optional attribute."

      OBJECT imaLinkIntervalOifAnomalies
      MIN-ACCESS not-accessible
      DESCRIPTION
        "This is an optional attribute."

      OBJECT imaLinkIntervalFeTxNumFailures
      MIN-ACCESS not-accessible
      DESCRIPTION
        "This is an optional attribute."

      OBJECT imaLinkIntervalFeRxNumFailures
      MIN-ACCESS not-accessible
      DESCRIPTION
        "This is an optional attribute."

      OBJECT imaLinkIntervalTxStuffs
      MIN-ACCESS not-accessible
      DESCRIPTION
        "This is an optional attribute."

      OBJECT imaLinkIntervalRxStuffs
      MIN-ACCESS not-accessible
      DESCRIPTION
        "This is an optional attribute."

      OBJECT imaLinkTotalOifAnomalies
      MIN-ACCESS not-accessible
      DESCRIPTION
        "This is an optional attribute."

      OBJECT imaLinkTotalFeTxNumFailures
      MIN-ACCESS not-accessible
      DESCRIPTION
        "This is an optional attribute."

      OBJECT imaLinkTotalFeRxNumFailures
      MIN-ACCESS not-accessible
      DESCRIPTION
        "This is an optional attribute."

      OBJECT imaLinkTotalTxStuffs
      MIN-ACCESS not-accessible
      DESCRIPTION
        "This is an optional attribute."

      OBJECT imaLinkTotalRxStuffs
      MIN-ACCESS not-accessible
      DESCRIPTION
        "This is an optional attribute."

   ::= { atmfImaMibCompliances 1 }

-- Units of Conformance

imaGroupGroup OBJECT-GROUP
      OBJECTS {
        imaGroupNumber,
        imaGroupRowStatus,
        imaGroupIfIndex,
        imaGroupNeState,
        imaGroupFeState,
        imaGroupFailureStatus,
        imaGroupSymmetry,
        imaGroupMinNumTxLinks,
        imaGroupMinNumRxLinks,
        imaGroupNeTxClkMode,
        imaGroupFeTxClkMode,
        imaGroupTxTimingRefLink,
        imaGroupRxTimingRefLink,
        imaGroupLastChange,
        imaGroupTxImaId,
        imaGroupRxImaId,
        imaGroupTxFrameLength,
        imaGroupRxFrameLength,
        imaGroupDiffDelayMax,
        imaGroupLeastDelayLink,
        imaGroupDiffDelayMaxObs,
        imaGroupAlphaValue,
        imaGroupBetaValue,
        imaGroupGammaValue,
        imaGroupRunningSecs,
        imaGroupUnavailSecs,
        imaGroupNeNumFailures,
        imaGroupFeNumFailures,
        imaGroupTxAvailCellRate,
        imaGroupRxAvailCellRate,
        imaGroupNumTxCfgLinks,
        imaGroupNumRxCfgLinks,
        imaGroupNumTxActLinks,
        imaGroupNumRxActLinks,
        imaGroupTxOamLabelValue,
        imaGroupRxOamLabelValue }
      STATUS     current
      DESCRIPTION
        "A set of objects providing configuration and status information for
        an IMA group definition."
      ::= { atmfImaMibGroups 1 }

imaLinkGroup OBJECT-GROUP
      OBJECTS {
        imaLinkRowStatus,
        imaLinkGroupIndex,
        imaLinkNeTxState,
        imaLinkNeRxState,
        imaLinkFeTxState,
        imaLinkFeRxState,
        imaLinkNeRxFailureStatus,
        imaLinkFeRxFailureStatus,
        imaLinkTxLid,
        imaLinkRxLid,
        imaLinkRelDelay,
        imaLinkImaViolations,
        imaLinkOifAnomalies,
        imaLinkNeSevErroredSecs,
        imaLinkFeSevErroredSecs,
        imaLinkNeUnavailSecs,
        imaLinkFeUnavailSecs,
        imaLinkNeTxUnusableSecs,
        imaLinkNeRxUnusableSecs,
        imaLinkFeTxUnusableSecs,
        imaLinkFeRxUnusableSecs,
        imaLinkNeTxNumFailures,
        imaLinkNeRxNumFailures,
        imaLinkFeTxNumFailures,
        imaLinkFeRxNumFailures,
        imaLinkTxStuffs,
        imaLinkRxStuffs }
      STATUS     current
      DESCRIPTION
        "A set of objects providing status information for an IMA link."
      ::= { atmfImaMibGroups 2 }

imaGroupMappingTableGroup OBJECT-GROUP
      OBJECTS {
        imaGroupMappingIndex }
      STATUS     current
      DESCRIPTION
        "A table mapping the 'ifIndex' values of 'imaGroupIfIndex'
        to the 'imaGroupIndex' values of the corresponding
        IMA group."
      ::= { atmfImaMibGroups 3 }

imaTestPatternGroup OBJECT-GROUP
      OBJECTS {
        imaGroupTestLinkIfIndex,
        imaGroupTestPattern,
        imaGroupTestProcStatus,
        imaLinkRxTestPattern,
        imaLinkTestProcStatus }
      STATUS     current
      DESCRIPTION
        "Objects in the imaGroupTable and imaLinkTable which control and
        report on the Test Pattern Procedure.  These objects must be
        implemented if the IMA Test Pattern Procedure is supported."
      ::= { atmfImaMibGroups 4 }

imaAlarmGroup OBJECT-GROUP
      OBJECTS {
        imaAlarmStatus,
        imaAlarmType }
      STATUS     current
      DESCRIPTION
        "Objects used in the imaFailureAlarm notification."
      ::= { atmfImaMibGroups 5 }

imaGroupIntervalGroup OBJECT-GROUP
      OBJECTS {
        imaGroupValidIntervals,
        imaGroupInvalidIntervals,
        imaGroupTimeElapsed,
        imaGroupCurrentUnavailSecs,
        imaGroupCurrentNeNumFailures,
        imaGroupCurrentFeNumFailures,
        imaGroupIntervalUnavailSecs,
        imaGroupIntervalNeNumFailures,
        imaGroupIntervalFeNumFailures,
        imaGroupTotalUnavailSecs,
        imaGroupTotalNeNumFailures,
        imaGroupTotalFeNumFailures }
      STATUS     current
      DESCRIPTION
        "Objects containing interval statistics for an IMA group."
      ::= { atmfImaMibGroups 6 }

imaLinkIntervalGroup OBJECT-GROUP
      OBJECTS {
        imaLinkValidIntervals,
        imaLinkInvalidIntervals,
        imaLinkTimeElapsed,
        imaLinkCurrentImaViolations,
        imaLinkCurrentOifAnomalies,
        imaLinkCurrentNeSevErroredSecs,
        imaLinkCurrentFeSevErroredSecs,
        imaLinkCurrentNeUnavailSecs,
        imaLinkCurrentFeUnavailSecs,
        imaLinkCurrentNeTxUnusableSecs,
        imaLinkCurrentNeRxUnusableSecs,
        imaLinkCurrentFeTxUnusableSecs,
        imaLinkCurrentFeRxUnusableSecs,
        imaLinkCurrentNeTxNumFailures,
        imaLinkCurrentNeRxNumFailures,
        imaLinkCurrentFeTxNumFailures,
        imaLinkCurrentFeRxNumFailures,
        imaLinkCurrentTxStuffs,
        imaLinkCurrentRxStuffs,
        imaLinkIntervalImaViolations,
        imaLinkIntervalOifAnomalies,
        imaLinkIntervalNeSevErroredSecs,
        imaLinkIntervalFeSevErroredSecs,
        imaLinkIntervalNeUnavailSecs,
        imaLinkIntervalFeUnavailSecs,
        imaLinkIntervalNeTxUnusableSecs,
        imaLinkIntervalNeRxUnusableSecs,
        imaLinkIntervalFeTxUnusableSecs,
        imaLinkIntervalFeRxUnusableSecs,
        imaLinkIntervalNeTxNumFailures,
        imaLinkIntervalNeRxNumFailures,
        imaLinkIntervalFeTxNumFailures,
        imaLinkIntervalFeRxNumFailures,
        imaLinkIntervalTxStuffs,
        imaLinkIntervalRxStuffs,
        imaLinkTotalImaViolations,
        imaLinkTotalOifAnomalies,
        imaLinkTotalNeSevErroredSecs,
        imaLinkTotalFeSevErroredSecs,
        imaLinkTotalNeUnavailSecs,
        imaLinkTotalFeUnavailSecs,
        imaLinkTotalNeTxUnusableSecs,
        imaLinkTotalNeRxUnusableSecs,
        imaLinkTotalFeTxUnusableSecs,
        imaLinkTotalFeRxUnusableSecs,
        imaLinkTotalNeTxNumFailures,
        imaLinkTotalNeRxNumFailures,
        imaLinkTotalFeTxNumFailures,
        imaLinkTotalFeRxNumFailures,
        imaLinkTotalTxStuffs,
        imaLinkTotalRxStuffs }
      STATUS     current
      DESCRIPTION
        "Objects containing interval statistics for an IMA link."
      ::= { atmfImaMibGroups 7 }

imaNotificationsGroup NOTIFICATION-GROUP
      NOTIFICATIONS {
        imaFailureAlarm }
      STATUS     current
      DESCRIPTION
        "Notifications that must be implemented for IMA groups and links."
      ::= { atmfImaMibGroups 8 }

END


PDN-HEADER-MIB DEFINITIONS ::= BEGIN

IMPORTS
     enterprises
         FROM RFC1155-SMI;

--     Copyright (C) 1994-2003, Paradyne.  All rights reserved.
--
--     Title: Paradyne Top Level Enterprise Definitions
--
-- =========================================================
-- PdnHeader Version: 8/28/2003
-- =========================================================
--
--     This file may be freely copied and distributed as
--     long as no changes are made to it.
--

pdyn                 OBJECT IDENTIFIER ::= { enterprises 1795 }
pdn-products         OBJECT IDENTIFIER ::= { pdyn 1 }
pdn-mgmt             OBJECT IDENTIFIER ::= { pdyn 2 }

--
--  The NMS/pdnP products subtrees are used for enterprise OIDs
--

-- ========== NMS products ==========

paradyneNMS-products      OBJECT IDENTIFIER ::= { pdn-products 13 }

-- nms-6800-products      OBJECT IDENTIFIER ::= { paradyneNMS-products }

nms-6700-products         OBJECT IDENTIFIER ::= { paradyneNMS-products 2 }

nms-dce-products          OBJECT IDENTIFIER ::= { paradyneNMS-products 3 }

nms-gem-products          OBJECT IDENTIFIER ::= { paradyneNMS-products 4 }
gem-aac-341               OBJECT IDENTIFIER ::= { nms-gem-products 1 }

nms-logical-products      OBJECT IDENTIFIER ::= { paradyneNMS-products 5 }
iso-physical              OBJECT IDENTIFIER ::= { nms-logical-products 1 }
iso-link                  OBJECT IDENTIFIER ::= { nms-logical-products 2 }
iso-network               OBJECT IDENTIFIER ::= { nms-logical-products 3 }
access-router               OBJECT IDENTIFIER ::= { iso-network 1 }
iso-transport             OBJECT IDENTIFIER ::= { nms-logical-products 4 }
iso-session               OBJECT IDENTIFIER ::= { nms-logical-products 5 }
iso-presentation          OBJECT IDENTIFIER ::= { nms-logical-products 6 }
iso-application           OBJECT IDENTIFIER ::= { nms-logical-products 7 }
chassis-manager             OBJECT IDENTIFIER ::= { iso-application 1 }

-- ========== PDN products ==========

paradyne-products         OBJECT IDENTIFIER ::= { pdn-products 14 }

pdn-cellRelay-products   OBJECT IDENTIFIER ::= { paradyne-products 1 }

-- 3000/9000/7000 Series
pdn-snmp-products        OBJECT IDENTIFIER ::= { paradyne-products 2 }

csu                       OBJECT IDENTIFIER ::= { pdn-snmp-products 1 }
t1-3150                     OBJECT IDENTIFIER ::= { csu 1 }
t1-3151                     OBJECT IDENTIFIER ::= { csu 2 }

dsu-csu                   OBJECT IDENTIFIER ::= { pdn-snmp-products 2 }
t1-3160                     OBJECT IDENTIFIER ::= { dsu-csu 1 }
t1-3164                     OBJECT IDENTIFIER ::= { dsu-csu 2 }
t1-3165                     OBJECT IDENTIFIER ::= { dsu-csu 3 }
t1-3161                     OBJECT IDENTIFIER ::= { dsu-csu 4 }
e1-3172                     OBJECT IDENTIFIER ::= { dsu-csu 5 }
e1-3174                     OBJECT IDENTIFIER ::= { dsu-csu 6 }
t1-3162                     OBJECT IDENTIFIER ::= { dsu-csu 7 }
t1-3166                     OBJECT IDENTIFIER ::= { dsu-csu 8 }

ntu                       OBJECT IDENTIFIER ::= { pdn-snmp-products 3 }
e1-3350                     OBJECT IDENTIFIER ::= { ntu 1 }
e1-3360                     OBJECT IDENTIFIER ::= { ntu 2 }
e1-3364                     OBJECT IDENTIFIER ::= { ntu 3 }
e1-3365                     OBJECT IDENTIFIER ::= { ntu 4 }

dev9XXX                   OBJECT IDENTIFIER ::= { pdn-snmp-products 4 }
fr-96XX                   OBJECT IDENTIFIER ::= { dev9XXX 1 }
fr-9620                     OBJECT IDENTIFIER ::= { fr-96XX 1 }
fr-2slot                    OBJECT IDENTIFIER ::= { fr-96XX 2 }
fr-naf                      OBJECT IDENTIFIER ::= { fr-96XX 3 }
fr-nac                      OBJECT IDENTIFIER ::= { fr-96XX 4 }
fr-9624                     OBJECT IDENTIFIER ::= { fr-96XX 5 }
fr-9626                     OBJECT IDENTIFIER ::= { fr-96XX 6 }
fr-9623                     OBJECT IDENTIFIER ::= { fr-96XX 7 }
fr-9624-OS                  OBJECT IDENTIFIER ::= { fr-96XX 8 }

bonaire                   OBJECT IDENTIFIER ::= { dev9XXX 2 }
bonaire-1slot               OBJECT IDENTIFIER ::= { bonaire 1 }
bonaire-2slot               OBJECT IDENTIFIER ::= { bonaire 2 }
bonaire-naf                 OBJECT IDENTIFIER ::= { bonaire 3 }
bonaire-nac                 OBJECT IDENTIFIER ::= { bonaire 4 }

t1-916X                   OBJECT IDENTIFIER ::= { dev9XXX 3 }
t1-1slot                    OBJECT IDENTIFIER ::= { t1-916X 1 }
t1-9162                     OBJECT IDENTIFIER ::= { t1-916X 2 }
t1-9165                     OBJECT IDENTIFIER ::= { t1-916X 3 }
t1-nac                      OBJECT IDENTIFIER ::= { t1-916X 4 }
t1-9262                     OBJECT IDENTIFIER ::= { t1-916X 5 }
t1-9265                     OBJECT IDENTIFIER ::= { t1-916X 6 }
t1-9161                     OBJECT IDENTIFIER ::= { t1-916X 7 }
t1-9261                     OBJECT IDENTIFIER ::= { t1-916X 8 }

t1fr-912X                 OBJECT IDENTIFIER ::= { dev9XXX 4 }
t1fr-9121                   OBJECT IDENTIFIER ::= { t1fr-912X 1 }
t1fr-2slot                  OBJECT IDENTIFIER ::= { t1fr-912X 2 }
t1fr-naf                    OBJECT IDENTIFIER ::= { t1fr-912X 3 }
t1fr-nac                    OBJECT IDENTIFIER ::= { t1fr-912X 4 }
t1fr-9124                   OBJECT IDENTIFIER ::= { t1fr-912X 5 }
t1fr-9124-NNI               OBJECT IDENTIFIER ::= { t1fr-912X 6 }
t1fr-9126                   OBJECT IDENTIFIER ::= { t1fr-912X 7 }
t1fr-9128                   OBJECT IDENTIFIER ::= { t1fr-912X 8 }
t1fr-9124-II                OBJECT IDENTIFIER ::= { t1fr-912X 9 }
t1fr-9124-L                 OBJECT IDENTIFIER ::= { t1fr-912X 10 }
t1fr-9123                   OBJECT IDENTIFIER ::= { t1fr-912X 11 }
t1fr-9124-OS                OBJECT IDENTIFIER ::= { t1fr-912X 12 }

atm-95XX                  OBJECT IDENTIFIER ::= { dev9XXX 5 }
atm-9580                    OBJECT IDENTIFIER ::= { atm-95XX 1 }
atm-9520-ilm                OBJECT IDENTIFIER ::= { atm-95XX 2 }
atm-9520                    OBJECT IDENTIFIER ::= { atm-95XX 3 }

msa-919X                  OBJECT IDENTIFIER ::= { dev9XXX 6 }
msa-9192                    OBJECT IDENTIFIER ::= { msa-919X 1 }
msa-9195                    OBJECT IDENTIFIER ::= { msa-919X 2 }
msa-9292                    OBJECT IDENTIFIER ::= { msa-919X 3 }
msa-9295                    OBJECT IDENTIFIER ::= { msa-919X 4 }

int-98XX                  OBJECT IDENTIFIER ::= { dev9XXX 7 }
int-9820                    OBJECT IDENTIFIER ::= { int-98XX 1 }
int-9820-C                  OBJECT IDENTIFIER ::= { int-98XX 2 }
int-9820-8M                 OBJECT IDENTIFIER ::= { int-98XX 3 }
int-9820-45M                OBJECT IDENTIFIER ::= { int-98XX 4 }

nni-9XXX                  OBJECT IDENTIFIER ::= { dev9XXX 8 }
nni-9110                    OBJECT IDENTIFIER ::= { nni-9XXX 1 }

msdsl-9XXX                OBJECT IDENTIFIER ::= { dev9XXX 9 }
msdsl-9723                  OBJECT IDENTIFIER ::= { msdsl-9XXX 1 }
msdsl-9783                  OBJECT IDENTIFIER ::= { msdsl-9XXX 2 }
msdsl-9720                  OBJECT IDENTIFIER ::= { msdsl-9XXX 3 }
msdsl-9788                  OBJECT IDENTIFIER ::= { msdsl-9XXX 4 }

isdn-9XXX                 OBJECT IDENTIFIER ::= { dev9XXX 10 }
isdn-9664                   OBJECT IDENTIFIER ::= { isdn-9XXX 1 }

rtr-9XXX                  OBJECT IDENTIFIER ::= { dev9XXX 11 }
rtr-9783                    OBJECT IDENTIFIER ::= { rtr-9XXX 1 }
rtr-9720                    OBJECT IDENTIFIER ::= { rtr-9XXX 2 }
rtr-9788                    OBJECT IDENTIFIER ::= { rtr-9XXX 3 }
rtr-9126                    OBJECT IDENTIFIER ::= { rtr-9XXX 4 }
rtr-9123                    OBJECT IDENTIFIER ::= { rtr-9XXX 5 }
rtr-9623                    OBJECT IDENTIFIER ::= { rtr-9XXX 6 }

t1-7XXX                   OBJECT IDENTIFIER ::= { dev9XXX 12 }
t1-7123                     OBJECT IDENTIFIER ::= { t1-7XXX 1 }
 
dev7XXX                   OBJECT IDENTIFIER ::= { pdn-snmp-products 5 }
dds-76XX                    OBJECT IDENTIFIER ::= { dev7XXX 1 }
dds-7610                      OBJECT IDENTIFIER ::= { dds-76XX 1 }
dds-7612                      OBJECT IDENTIFIER ::= { dds-76XX 2 }
dds-7613                      OBJECT IDENTIFIER ::= { dds-76XX 3 }
t1-71XX                     OBJECT IDENTIFIER ::= { dev7XXX 2 }
t1-7110                       OBJECT IDENTIFIER ::= { t1-71XX 1 }
t1-7112                       OBJECT IDENTIFIER ::= { t1-71XX 2 }

-- 3600 Series
pdn-36xx-products        OBJECT IDENTIFIER ::= { paradyne-products 3 }

-- ACCULINK Access Controller
pdn-aac-products         OBJECT IDENTIFIER ::= { paradyne-products 4 }
aac-34                    OBJECT IDENTIFIER ::= { pdn-aac-products 1 }

aac-34X                   OBJECT IDENTIFIER ::= { pdn-aac-products 2 }
aac-FL                      OBJECT IDENTIFIER ::= { aac-34X 1 }
aac-UE                      OBJECT IDENTIFIER ::= { aac-34X 2 }
aac-FP                      OBJECT IDENTIFIER ::= { aac-34X 3 }
aac-300                     OBJECT IDENTIFIER ::= { aac-34X 4 }

aac-cards                 OBJECT IDENTIFIER ::= { pdn-aac-products 3 }
aac-frs                     OBJECT IDENTIFIER ::= { aac-cards 1 }
aac-ipc                     OBJECT IDENTIFIER ::= { aac-cards 2 }
aac-atm                     OBJECT IDENTIFIER ::= { aac-cards 3 }

aac-4X                    OBJECT IDENTIFIER ::= { pdn-aac-products 4 }
aac-4XFL                    OBJECT IDENTIFIER ::= { aac-4X 1 }
aac-4XUE                    OBJECT IDENTIFIER ::= { aac-4X 2 }
aac-4XFP                    OBJECT IDENTIFIER ::= { aac-4X 3 }
aac-4X300                   OBJECT IDENTIFIER ::= { aac-4X 4 }

-- Common
pdn-common-products      OBJECT IDENTIFIER ::= { paradyne-products 5 }
pdn-testOIDs               OBJECT IDENTIFIER ::= { pdn-common-products 1 }
pdnLoopbackTest            OBJECT IDENTIFIER ::= { pdn-testOIDs 1 }
pdnBertTest                OBJECT IDENTIFIER ::= { pdn-testOIDs 2 }
pdnPingTest                OBJECT IDENTIFIER ::= { pdn-testOIDs 3 }
pdnTraceRouteTest          OBJECT IDENTIFIER ::= { pdn-testOIDs 4 }
pdnBlertTest	           OBJECT IDENTIFIER ::= { pdn-testOIDs 5 }

-- Eagle
pdn-eagle-products       OBJECT IDENTIFIER ::= { paradyne-products 6 }

-- Access Router
pdn-ar-products          OBJECT IDENTIFIER ::= { paradyne-products 7 }
ar-541                      OBJECT IDENTIFIER ::= { pdn-ar-products 1 }
ar-611                      OBJECT IDENTIFIER ::= { pdn-ar-products 2 }
ar-621                      OBJECT IDENTIFIER ::= { pdn-ar-products 3 }
ar-641                      OBJECT IDENTIFIER ::= { pdn-ar-products 4 }
ar-712                      OBJECT IDENTIFIER ::= { pdn-ar-products 5 }
ar-722                      OBJECT IDENTIFIER ::= { pdn-ar-products 6 }
ar-928                      OBJECT IDENTIFIER ::= { pdn-ar-products 7 }
ar-711                      OBJECT IDENTIFIER ::= { pdn-ar-products 8 }

-- Access Server
pdn-as-products          OBJECT IDENTIFIER ::= { paradyne-products 8 }
as-4                        OBJECT IDENTIFIER ::= { pdn-as-products 1 }
as-8                        OBJECT IDENTIFIER ::= { pdn-as-products 2 }
as-24                       OBJECT IDENTIFIER ::= { pdn-as-products 3 }

-- xDSL
pdn-xdsl-products        OBJECT IDENTIFIER ::= { paradyne-products 9 }
xdsl-5100                   OBJECT IDENTIFIER ::= { pdn-xdsl-products 1 }
xdsl-unused1                OBJECT IDENTIFIER ::= { pdn-xdsl-products 2 }
xdsl-8800-old               OBJECT IDENTIFIER ::= { pdn-xdsl-products 3 }
xdsl-unused2                OBJECT IDENTIFIER ::= { pdn-xdsl-products 4 }
xdsl-8600-old               OBJECT IDENTIFIER ::= { pdn-xdsl-products 5 }
xdsl-ipc                    OBJECT IDENTIFIER ::= { pdn-xdsl-products 6 }
xdsl-8100                     OBJECT IDENTIFIER ::= { xdsl-ipc 1 }
xdsl-8200                     OBJECT IDENTIFIER ::= { xdsl-ipc 2 }
xdsl-chassis                OBJECT IDENTIFIER ::= { pdn-xdsl-products 8 }
xdsl-8600                     OBJECT IDENTIFIER ::= { xdsl-chassis 1 }
xdsl-8800                     OBJECT IDENTIFIER ::= { xdsl-chassis 2 }
xdsl-8610                     OBJECT IDENTIFIER ::= { xdsl-chassis 3 }
xdsl-8810                     OBJECT IDENTIFIER ::= { xdsl-chassis 4 }
xdsl-8820                     OBJECT IDENTIFIER ::= { xdsl-chassis 5 }
xdsl-8610-X                   OBJECT IDENTIFIER ::= { xdsl-chassis 6 }
xdsl-8810-X                   OBJECT IDENTIFIER ::= { xdsl-chassis 7 }
xdsl-8820-X                   OBJECT IDENTIFIER ::= { xdsl-chassis 8 }
xdsl-8620                     OBJECT IDENTIFIER ::= { xdsl-chassis 9 }
xdsl-remote                 OBJECT IDENTIFIER ::= { pdn-xdsl-products 9 }
xdsl-5446                     OBJECT IDENTIFIER ::= { xdsl-remote 1 }
xdsl-7914                     OBJECT IDENTIFIER ::= { xdsl-remote 2 }
xdsl-5246                     OBJECT IDENTIFIER ::= { xdsl-remote 3 }
xdsl-5216                     OBJECT IDENTIFIER ::= { xdsl-remote 4 }
xdsl-5170                     OBJECT IDENTIFIER ::= { xdsl-remote 5 }
xdsl-5171                     OBJECT IDENTIFIER ::= { xdsl-remote 6 }
xdsl-5546                     OBJECT IDENTIFIER ::= { xdsl-remote 7 }
xdsl-5620                     OBJECT IDENTIFIER ::= { xdsl-remote 8 }
xdsl-6310                     OBJECT IDENTIFIER ::= { xdsl-remote 9 }
xdsl-7975                     OBJECT IDENTIFIER ::= { xdsl-remote 10 }
xdsl-7976                     OBJECT IDENTIFIER ::= { xdsl-remote 11 }
xdsl-7974                     OBJECT IDENTIFIER ::= { xdsl-remote 12 }
xdsl-7986                     OBJECT IDENTIFIER ::= { xdsl-remote 13 }
xdsl-7985                     OBJECT IDENTIFIER ::= { xdsl-remote 14 }
xdsl-7984                     OBJECT IDENTIFIER ::= { xdsl-remote 15 }
xdsl-6341                     OBJECT IDENTIFIER ::= { xdsl-remote 16 }
xdsl-6342                     OBJECT IDENTIFIER ::= { xdsl-remote 17 }
xdsl-6331                     OBJECT IDENTIFIER ::= { xdsl-remote 18 }
xdsl-6332                     OBJECT IDENTIFIER ::= { xdsl-remote 19 }
xdsl-6371                     OBJECT IDENTIFIER ::= { xdsl-remote 20 }
xdsl-6372                     OBJECT IDENTIFIER ::= { xdsl-remote 21 }
xdsl-6321                     OBJECT IDENTIFIER ::= { xdsl-remote 23 }
xdsl-6322                     OBJECT IDENTIFIER ::= { xdsl-remote 24 }
xdsl-6341R2                   OBJECT IDENTIFIER ::= { xdsl-remote 25 }
xdsl-6342R2                   OBJECT IDENTIFIER ::= { xdsl-remote 26 }
xdsl-6331R2                   OBJECT IDENTIFIER ::= { xdsl-remote 27 }
xdsl-6332R2                   OBJECT IDENTIFIER ::= { xdsl-remote 28 }
xdsl-6371R2                   OBJECT IDENTIFIER ::= { xdsl-remote 29 }
xdsl-6372R2                   OBJECT IDENTIFIER ::= { xdsl-remote 30 }
xdsl-6321R2                   OBJECT IDENTIFIER ::= { xdsl-remote 31 }
xdsl-6322R2                   OBJECT IDENTIFIER ::= { xdsl-remote 32 }
xdsl-6328                     OBJECT IDENTIFIER ::= { xdsl-remote 33 } -- unused
xdsl-6329                     OBJECT IDENTIFIER ::= { xdsl-remote 34 } -- unused
xdsl-6301R2                   OBJECT IDENTIFIER ::= { xdsl-remote 35 }
xdsl-6302R2                   OBJECT IDENTIFIER ::= { xdsl-remote 36 }
xdsl-6350                     OBJECT IDENTIFIER ::= { xdsl-remote 38 }
xdsl-6351                     OBJECT IDENTIFIER ::= { xdsl-remote 39 }
xdsl-6385                     OBJECT IDENTIFIER ::= { xdsl-remote 40 }
xdsl-7994                     OBJECT IDENTIFIER ::= { xdsl-remote 41 }
xdsl-7995                     OBJECT IDENTIFIER ::= { xdsl-remote 42 }
xdsl-7996                     OBJECT IDENTIFIER ::= { xdsl-remote 43 }
xdsl-cards                    OBJECT IDENTIFIER ::= { pdn-xdsl-products 10 }
card-mcc                      OBJECT IDENTIFIER ::= { xdsl-cards 1 }
card-adsl                     OBJECT IDENTIFIER ::= { xdsl-cards 2 } -- unused
card-radsl                    OBJECT IDENTIFIER ::= { xdsl-cards 3 }
card-sdsl                     OBJECT IDENTIFIER ::= { xdsl-cards 4 } -- unused
card-vdsl                     OBJECT IDENTIFIER ::= { xdsl-cards 5 } -- unused
card-8774                     OBJECT IDENTIFIER ::= { xdsl-cards 6 }
card-8540                     OBJECT IDENTIFIER ::= { xdsl-cards 7 }
card-8775                     OBJECT IDENTIFIER ::= { xdsl-cards 8 }
card-8776                     OBJECT IDENTIFIER ::= { xdsl-cards 9 }
card-8786                     OBJECT IDENTIFIER ::= { xdsl-cards 10 }
card-8946                     OBJECT IDENTIFIER ::= { xdsl-cards 11 }
card-8510                     OBJECT IDENTIFIER ::= { xdsl-cards 12 }
card-8310                     OBJECT IDENTIFIER ::= { xdsl-cards 13 }
card-e1-sdsl                  OBJECT IDENTIFIER ::= { xdsl-cards 14 }
card-mcc2                     OBJECT IDENTIFIER ::= { xdsl-cards 15 }
card-8785                     OBJECT IDENTIFIER ::= { xdsl-cards 16 }
card-8784                     OBJECT IDENTIFIER ::= { xdsl-cards 17 }
card-8312                     OBJECT IDENTIFIER ::= { xdsl-cards 18 }
card-8344                     OBJECT IDENTIFIER ::= { xdsl-cards 19 }
card-mcc-plus                 OBJECT IDENTIFIER ::= { xdsl-cards 20 }
card-mcp                      OBJECT IDENTIFIER ::= { xdsl-cards 21 }
card-8334                     OBJECT IDENTIFIER ::= { xdsl-cards 22 }
card-xxxx                     OBJECT IDENTIFIER ::= { xdsl-cards 23 }
card-8343                     OBJECT IDENTIFIER ::= { xdsl-cards 24 }
card-8333                     OBJECT IDENTIFIER ::= { xdsl-cards 25 }
card-8719                     OBJECT IDENTIFIER ::= { xdsl-cards 26 }
card-8747                     OBJECT IDENTIFIER ::= { xdsl-cards 27 }
card-8777                     OBJECT IDENTIFIER ::= { xdsl-cards 28 }
card-8779                     OBJECT IDENTIFIER ::= { xdsl-cards 29 }
card-8021                     OBJECT IDENTIFIER ::= { xdsl-cards 30 }
card-8022                     OBJECT IDENTIFIER ::= { xdsl-cards 31 }
card-8373                     OBJECT IDENTIFIER ::= { xdsl-cards 32 }
card-8374                     OBJECT IDENTIFIER ::= { xdsl-cards 33 }
card-8323                     OBJECT IDENTIFIER ::= { xdsl-cards 34 }
card-8324                     OBJECT IDENTIFIER ::= { xdsl-cards 35 }
card-8023                     OBJECT IDENTIFIER ::= { xdsl-cards 36 }
card-8024                     OBJECT IDENTIFIER ::= { xdsl-cards 37 }
card-8335                     OBJECT IDENTIFIER ::= { xdsl-cards 38 }
card-8365                     OBJECT IDENTIFIER ::= { xdsl-cards 39 }
card-83xx                     OBJECT IDENTIFIER ::= { xdsl-cards 40 }
card-8314                     OBJECT IDENTIFIER ::= { xdsl-cards 41 }
card-8328                     OBJECT IDENTIFIER ::= { xdsl-cards 42 }
card-8329                     OBJECT IDENTIFIER ::= { xdsl-cards 43 }
card-8303                     OBJECT IDENTIFIER ::= { xdsl-cards 44 }
card-8304                     OBJECT IDENTIFIER ::= { xdsl-cards 45 }
card-8025                     OBJECT IDENTIFIER ::= { xdsl-cards 46 }
card-8026                     OBJECT IDENTIFIER ::= { xdsl-cards 47 }
card-8027                     OBJECT IDENTIFIER ::= { xdsl-cards 48 }
card-8028                     OBJECT IDENTIFIER ::= { xdsl-cards 49 }
card-8379                     OBJECT IDENTIFIER ::= { xdsl-cards 50 }
card-8312-ReachDSL            OBJECT IDENTIFIER ::= { xdsl-cards 51 }
card-8314-ReachDSL            OBJECT IDENTIFIER ::= { xdsl-cards 52 }
card-8385                     OBJECT IDENTIFIER ::= { xdsl-cards 53 }
card-8395                     OBJECT IDENTIFIER ::= { xdsl-cards 54 }
card-8396                     OBJECT IDENTIFIER ::= { xdsl-cards 55 }
card-8797                     OBJECT IDENTIFIER ::= { xdsl-cards 56 }
card-8799                     OBJECT IDENTIFIER ::= { xdsl-cards 57 }
card-8355                     OBJECT IDENTIFIER ::= { xdsl-cards 58 }
card-mcp8900                  OBJECT IDENTIFIER ::= { xdsl-cards 59 }
xdsl-ports                  OBJECT IDENTIFIER ::= { pdn-xdsl-products 11 }
port-dsl                      OBJECT IDENTIFIER ::= { xdsl-ports 1 }
port-mvl                      OBJECT IDENTIFIER ::= { xdsl-ports 2 }
port-eth10                    OBJECT IDENTIFIER ::= { xdsl-ports 3 }
port-eth100                   OBJECT IDENTIFIER ::= { xdsl-ports 4 }
port-oc3                      OBJECT IDENTIFIER ::= { xdsl-ports 5 }
port-ds3                      OBJECT IDENTIFIER ::= { xdsl-ports 6 }
port-sar                      OBJECT IDENTIFIER ::= { xdsl-ports 7 }
port-hdlc                     OBJECT IDENTIFIER ::= { xdsl-ports 8 }
port-e3                       OBJECT IDENTIFIER ::= { xdsl-ports 9 }
port-ds1                      OBJECT IDENTIFIER ::= { xdsl-ports 10 }
port-e1                       OBJECT IDENTIFIER ::= { xdsl-ports 11 }
port-ima                      OBJECT IDENTIFIER ::= { xdsl-ports 12 }
port-reachDsl                 OBJECT IDENTIFIER ::= { xdsl-ports 13 }
port-reachDslV3		      OBJECT IDENTIFIER ::= { xdsl-ports 14 }
xdsl-slots                  OBJECT IDENTIFIER ::= { pdn-xdsl-products 12 }
slot-std                      OBJECT IDENTIFIER ::= { xdsl-slots 1 }
xdsl-components             OBJECT IDENTIFIER ::= { pdn-xdsl-products 13 }
comp-powerA                   OBJECT IDENTIFIER ::= { xdsl-components 1 }
comp-powerB                   OBJECT IDENTIFIER ::= { xdsl-components 2 }
comp-fan                      OBJECT IDENTIFIER ::= { xdsl-components 3 }
comp-mgmt                     OBJECT IDENTIFIER ::= { xdsl-components 4 }
comp-atm                      OBJECT IDENTIFIER ::= { xdsl-components 5 }
comp-pld                      OBJECT IDENTIFIER ::= { xdsl-components 6 }
comp-sensor                   OBJECT IDENTIFIER ::= { xdsl-components 7 }

-- SME  -begin

xdsl-sme	       	OBJECT IDENTIFIER ::= { pdn-xdsl-products 14 }

sme-scp-cards		 OBJECT IDENTIFIER ::= { xdsl-sme 1}
sme-scp-8412-card	  OBJECT IDENTIFIER ::= { sme-scp-cards 1}
sme-scp-8413-card	  OBJECT IDENTIFIER ::= { sme-scp-cards 2}
sme-scp-8414-card	  OBJECT IDENTIFIER ::= { sme-scp-cards 3}
sme-scp-8416-card	  OBJECT IDENTIFIER ::= { sme-scp-cards 4}
sme-scp-8417-card	  OBJECT IDENTIFIER ::= { sme-scp-cards 5}
sme-scp-8418-card	  OBJECT IDENTIFIER ::= { sme-scp-cards 6}

sme-childcards		 OBJECT IDENTIFIER ::= { xdsl-sme 2}
sme-t1e1-uplink-child	  OBJECT IDENTIFIER ::= { sme-childcards 1}

sme-ports		 OBJECT IDENTIFIER ::= { xdsl-sme 3}
sme-reachDsl-port	  OBJECT IDENTIFIER ::= { sme-ports 1}
sme-adsl-a-port		  OBJECT IDENTIFIER ::= { sme-ports 2}
sme-adsl-b-port		  OBJECT IDENTIFIER ::= { sme-ports 3}
sme-shdsl-port		  OBJECT IDENTIFIER ::= { sme-ports 4}
sme-t1e1-port		  OBJECT IDENTIFIER ::= { sme-ports 5}
sme-oc3-port		  OBJECT IDENTIFIER ::= { sme-ports 6}
sme-rs232-port		  OBJECT IDENTIFIER ::= { sme-ports 7}
sme-eth-port		  OBJECT IDENTIFIER ::= { sme-ports 8}
sme-ds3-port              OBJECT IDENTIFIER ::= { sme-ports 9}

sme-portcards		 OBJECT IDENTIFIER ::= { xdsl-sme 4}
sme-8965-card	  	  OBJECT IDENTIFIER ::= { sme-portcards 1}
sme-8955-card	  	  OBJECT IDENTIFIER ::= { sme-portcards 2}
sme-8985-card	  	  OBJECT IDENTIFIER ::= { sme-portcards 3}

sme-chassis		 OBJECT IDENTIFIER ::= { xdsl-sme 5}
sme-chassis-8820	 OBJECT IDENTIFIER ::= { sme-chassis 1}
sme-chassis-8620	 OBJECT IDENTIFIER ::= { sme-chassis 2}

sme-components		 OBJECT IDENTIFIER ::= { xdsl-sme 6}
sme-comp-fan		 OBJECT IDENTIFIER ::= { sme-components 1}
sme-comp-pld		 OBJECT IDENTIFIER ::= { sme-components 2}
sme-comp-sensor		 OBJECT IDENTIFIER ::= { sme-components 3}
sme-comp-powersupply	 OBJECT IDENTIFIER ::= { sme-components 4}
sme-comp-spf		 OBJECT IDENTIFIER ::= { sme-components 5}


sme-container		 OBJECT IDENTIFIER ::= { xdsl-sme 7}

-- SME -end

-- Compression
pdn-comp-products        OBJECT IDENTIFIER ::= { paradyne-products 10 }
comp-9028                   OBJECT IDENTIFIER ::= { pdn-comp-products 1 }

-- PTC
pdn-ptc-products         OBJECT IDENTIFIER ::= { paradyne-products 11 }
xdsl-xdsl                   OBJECT IDENTIFIER ::= { pdn-ptc-products 1 }

-- DSL Router Endpoint (not used?)
pdnDslEndpoint           OBJECT IDENTIFIER ::= { paradyne-products 12 }

-- (reserved)
reserved13               OBJECT IDENTIFIER ::= { paradyne-products 13 }
reserved14               OBJECT IDENTIFIER ::= { paradyne-products 14 }

-- CellSaver
pdn-cellsaver            OBJECT IDENTIFIER ::= { paradyne-products 15 }
cellsaver-9510              OBJECT IDENTIFIER ::= { pdn-cellsaver 1 }
cellsaver-9550              OBJECT IDENTIFIER ::= { pdn-cellsaver 2 }

-- Cornet
pdn-cornet              OBJECT IDENTIFIER ::= { paradyne-products 16 }
cornet-xxxx                 OBJECT IDENTIFIER ::= { pdn-cornet 1 }

--
-- IP Stackable  i.e. Speedway/Bitstorm
--    ips refers to IP Stackable
--
ip-stackable            OBJECT IDENTIFIER ::= { paradyne-products 17 }
ips-stack                 OBJECT IDENTIFIER ::= { ip-stackable 1 }
ips-4800                    OBJECT IDENTIFIER ::= { ips-stack 1 }
ips-2600                    OBJECT IDENTIFIER ::= { ips-stack 2 }
ips-4200                    OBJECT IDENTIFIER ::= { ips-stack 3 }

ips-chassis               OBJECT IDENTIFIER ::= { ip-stackable 2 }
ips-4821                    OBJECT IDENTIFIER ::= { ips-chassis 1 }
ips-2611                    OBJECT IDENTIFIER ::= { ips-chassis 2 }
ips-2621                    OBJECT IDENTIFIER ::= { ips-chassis 3 }
ips-4219                    OBJECT IDENTIFIER ::= { ips-chassis 4 }
ips-4229                    OBJECT IDENTIFIER ::= { ips-chassis 5 }

ips-fixed-cards           OBJECT IDENTIFIER ::= { ip-stackable 3 }
ips-24port-adsl-main-card          OBJECT IDENTIFIER ::= { ips-fixed-cards 1 }
ips-24port-adsl-child-card         OBJECT IDENTIFIER ::= { ips-fixed-cards 2 }
ips-maui-card                      OBJECT IDENTIFIER ::= { ips-fixed-cards 3 }
ips-pots-splitter-child-card       OBJECT IDENTIFIER ::= { ips-fixed-cards 4 }
ips-24port-reachDsl-main-card      OBJECT IDENTIFIER ::= { ips-fixed-cards 5 }
ips-24port-reachDsl-child-card     OBJECT IDENTIFIER ::= { ips-fixed-cards 6 }

ips-pluggable-cards       OBJECT IDENTIFIER ::= { ip-stackable 4 }
ips-mgmt-no-wan                 OBJECT IDENTIFIER ::= { ips-pluggable-cards 1 }
ips-mgmt-with-v35x21-wan        OBJECT IDENTIFIER ::= { ips-pluggable-cards 2 }
ips-mgmt-with-t1e1-mlppp-wan    OBJECT IDENTIFIER ::= { ips-pluggable-cards 3 }
ips-mgmt-with-t1e1-ima-wan      OBJECT IDENTIFIER ::= { ips-pluggable-cards 4 }

ips-ports                 OBJECT IDENTIFIER ::= { ip-stackable 5 }
ips-rs232-dte-port          OBJECT IDENTIFIER ::= { ips-ports 1 }
ips-rs232-dce-port          OBJECT IDENTIFIER ::= { ips-ports 2 }
ips-v35-dte-port            OBJECT IDENTIFIER ::= { ips-ports 3 }
ips-adsl-port               OBJECT IDENTIFIER ::= { ips-ports 4 }
ips-ethernet-port           OBJECT IDENTIFIER ::= { ips-ports 5 }
ips-t1e1-port               OBJECT IDENTIFIER ::= { ips-ports 6 }
ips-adsl-a-port             OBJECT IDENTIFIER ::= { ips-ports 7 }
ips-reachDslPort            OBJECT IDENTIFIER ::= { ips-ports 8 }

ips-components            OBJECT IDENTIFIER ::= { ip-stackable 6 }
ips-fan                     OBJECT IDENTIFIER ::= { ips-components 1 }
                            -- Probably should use ips-speed-sensor
ips-temperature-sensor      OBJECT IDENTIFIER ::= { ips-components 2 }
ips-processor               OBJECT IDENTIFIER ::= { ips-components 3 }
ips-pld                     OBJECT IDENTIFIER ::= { ips-components 4 }
ips-speed-sensor            OBJECT IDENTIFIER ::= { ips-components 5 }
ips-alarm-relay-contact     OBJECT IDENTIFIER ::= { ips-components 6 }

ips-dot1dBasePortCircuit OBJECT IDENTIFIER ::= { ip-stackable 7 }
                           -- Priority Interworking Groups (PIWGs)
ips-piwg-1                 OBJECT IDENTIFIER ::= { ips-dot1dBasePortCircuit 1 }
ips-piwg-2                 OBJECT IDENTIFIER ::= { ips-dot1dBasePortCircuit 2 }
ips-piwg-3                 OBJECT IDENTIFIER ::= { ips-dot1dBasePortCircuit 3 }
ips-piwg-4                 OBJECT IDENTIFIER ::= { ips-dot1dBasePortCircuit 4 }
ips-piwg-5                 OBJECT IDENTIFIER ::= { ips-dot1dBasePortCircuit 5 }
ips-piwg-6                 OBJECT IDENTIFIER ::= { ips-dot1dBasePortCircuit 6 }
ips-piwg-7                 OBJECT IDENTIFIER ::= { ips-dot1dBasePortCircuit 7 }
ips-piwg-8                 OBJECT IDENTIFIER ::= { ips-dot1dBasePortCircuit 8 }


--
-- New Tree for EtherLoop
--

etherloop             OBJECT IDENTIFIER ::= { paradyne-products 18 }
eloop-shelf             OBJECT IDENTIFIER ::= { etherloop 1 }
eloop-2400                OBJECT IDENTIFIER ::= { eloop-shelf 1 }

eloop-unit            OBJECT IDENTIFIER ::= { etherloop 2 }
eloop-2461              OBJECT IDENTIFIER ::= { eloop-unit 1 }

eloop-modem-stick     OBJECT IDENTIFIER ::= { etherloop 3 }

eloop-intf-card       OBJECT IDENTIFIER ::= { etherloop 4 }

eloop-switch-card     OBJECT IDENTIFIER ::= { etherloop 5 }

--
-- ATM Stackable  i.e. 4200
--    atm-stk refers to ATM Stackable
--
atm-stackable          OBJECT IDENTIFIER ::= { paradyne-products 19 }

atmstk-stack            OBJECT IDENTIFIER ::= { atm-stackable 1 }
atmstk-4200                OBJECT IDENTIFIER ::= { atmstk-stack 1 }

atmstk-chassis          OBJECT IDENTIFIER ::= { atm-stackable 2 }
atmstk-4216                OBJECT IDENTIFIER ::= { atmstk-chassis 1 }
atmstk-4218                OBJECT IDENTIFIER ::= { atmstk-chassis 2 }
atmstk-4210                OBJECT IDENTIFIER ::= { atmstk-chassis 3 }
atmstk-4211                OBJECT IDENTIFIER ::= { atmstk-chassis 4 }
atmstk-4212                OBJECT IDENTIFIER ::= { atmstk-chassis 5 }
atmstk-4213                OBJECT IDENTIFIER ::= { atmstk-chassis 6 }
atmstk-4221                OBJECT IDENTIFIER ::= { atmstk-chassis 7 }
atmstk-4222                OBJECT IDENTIFIER ::= { atmstk-chassis 8 }
atmstk-4223                OBJECT IDENTIFIER ::= { atmstk-chassis 9 }
atmstk-4231                OBJECT IDENTIFIER ::= { atmstk-chassis 10 }
atmstk-4232                OBJECT IDENTIFIER ::= { atmstk-chassis 11 }
atmstk-4233                OBJECT IDENTIFIER ::= { atmstk-chassis 12 }

atmstk-cards            OBJECT IDENTIFIER ::= { atm-stackable 3 }
atmstk-24Port-main-reach   OBJECT IDENTIFIER ::= { atmstk-cards 1 }
atmstk-24Port-main-adsl-a  OBJECT IDENTIFIER ::= { atmstk-cards 2 }
atmstk-24Port-main-adsl-b  OBJECT IDENTIFIER ::= { atmstk-cards 3 }

atmstk-child-cards      OBJECT IDENTIFIER ::= { atm-stackable 4 }
atmstk-4201-t1-uplink       OBJECT IDENTIFIER ::= { atmstk-child-cards 1 }
atmstk-4202-e1-uplink       OBJECT IDENTIFIER ::= { atmstk-child-cards 2 }
atmstk-4203-t1e1-ima-uplink OBJECT IDENTIFIER ::= { atmstk-child-cards 3 }
atmstk-oc3-uplink           OBJECT IDENTIFIER ::= { atmstk-child-cards 4 }
atmstk-splitter             OBJECT IDENTIFIER ::= { atmstk-child-cards 5 }
atmstk-24Port-ext           OBJECT IDENTIFIER ::= { atmstk-child-cards 6 }

atmstk-ports     	OBJECT IDENTIFIER ::= { atm-stackable 5 }
atmstk-reachDsl-port       OBJECT IDENTIFIER ::= { atmstk-ports 1 }
atmstk-t1e1-port     	   OBJECT IDENTIFIER ::= { atmstk-ports 2 }
atmstk-rs232-dce-port      OBJECT IDENTIFIER ::= { atmstk-ports 3 }
atmstk-ethernet-port       OBJECT IDENTIFIER ::= { atmstk-ports 4 }
atmstk-ADSL-annexa-port    OBJECT IDENTIFIER ::= { atmstk-ports 5 }
atmstk-ADSL-annexb-port    OBJECT IDENTIFIER ::= { atmstk-ports 6 }

atmstk-components     	OBJECT IDENTIFIER ::= { atm-stackable 6 }
atmstk-comp-fan       	   OBJECT IDENTIFIER ::= { atmstk-components 1 }
atmstk-comp-temp-sensor    OBJECT IDENTIFIER ::= { atmstk-components 2 }
atmstk-comp-pld            OBJECT IDENTIFIER ::= { atmstk-components 3 }

--
--  The NMS/pdn mgmt subtrees are used for MIB objects
--

-- ========== NMS mgmt ==========

paradyneNMS           OBJECT IDENTIFIER ::= { pdn-mgmt 23 }

-- nms-6800           OBJECT IDENTIFIER ::= { paradyneNMS 1 thru 4}
nms-6700              OBJECT IDENTIFIER ::= { paradyneNMS 5 }

-- ========== pdn mgmt ==========

paradyne              OBJECT IDENTIFIER ::= { pdn-mgmt 24 }

pdn-cellRelay        OBJECT IDENTIFIER ::= { paradyne 1 } 

pdn-common           OBJECT IDENTIFIER ::= { paradyne 2 }
pdn-frontPanel       OBJECT IDENTIFIER ::= { pdn-common 1 }
pdn-chassis          OBJECT IDENTIFIER ::= { pdn-common 2 } -- unused
pdn-callDir          OBJECT IDENTIFIER ::= { pdn-common 3 }
pdn-devStatus        OBJECT IDENTIFIER ::= { pdn-common 4 }
pdn-devID            OBJECT IDENTIFIER ::= { pdn-common 5 }
pdn-interfaces       OBJECT IDENTIFIER ::= { pdn-common 6 }
-- ifMap                  OBJECT IDENTIFIER ::= { pdn-interfaces 1 }
-- dds                    OBJECT IDENTIFIER ::= { pdn-interfaces 2 }
-- portUsage              OBJECT IDENTIFIER ::= { pdn-interfaces 3 }
-- voice                  OBJECT IDENTIFIER ::= { pdn-interfaces 4 }
ent-ds1                   OBJECT IDENTIFIER ::= { pdn-interfaces 5 }
-- devDS1Tests              OBJECT IDENTIFIER ::= { ent-ds1 1 }
-- ds1PerfStats             OBJECT IDENTIFIER ::= { ent-ds1 4 }
-- pdnDs1Ext                OBJECT IDENTIFIER ::= { ent-ds1 5 }
--syncPort                  OBJECT IDENTIFIER ::= { pdn-interfaces 6 }
-- syncDataPortConfigTbl    OBJECT IDENTIFIER ::= { syncPort 1 }
-- devSyncPortTest          OBJECT IDENTIFIER ::= { syncPort 2 }
-- edlPerfStats             OBJECT IDENTIFIER ::= { syncPort 4 }
crossConnect              OBJECT IDENTIFIER ::= { pdn-interfaces 7 }
-- devDs1FracTable          OBJECT IDENTIFIER ::= { crossConnect 1 }
-- devSyncDataPortAssignTbl OBJECT IDENTIFIER ::= { crossConnect 2 }
-- pvcXconnect              OBJECT IDENTIFIER ::= { crossConnect 3 }
xdsl                      OBJECT IDENTIFIER ::= { pdn-interfaces 8 }
-- xdsl                     OBJECT IDENTIFIER ::= { xdsl 1 }
-- dhcp                     OBJECT IDENTIFIER ::= { xdsl 2 }
-- pdsl                     OBJECT IDENTIFIER ::= { xdsl 3 }
pdnFrameRelay             OBJECT IDENTIFIER ::= { pdn-interfaces 9 }
-- frame-relay-clear-stat   OBJECT IDENTIFIER ::= { pdnFrameRelay 1 }
-- frNetDcp                 OBJECT IDENTIFIER ::= { pdnFrameRelay 2 }
-- devPVCTest               OBJECT IDENTIFIER ::= { pdnFrameRelay 3 }
-- ocuPort                OBJECT IDENTIFIER ::= { pdn-interfaces 10 }
pdnAtm                    OBJECT IDENTIFIER ::= { pdn-interfaces 11 }
-- devAtmSlv                OBJECT IDENTIFIER ::= { pdnAtm 1 }
-- devAtmPVCTest            OBJECT IDENTIFIER ::= { pdnAtm 2 }
-- devAtmStatsMIB           OBJECT IDENTIFIER ::= { pdnAtm 3 }
-- devAtmSCM                OBJECT IDENTIFIER ::= { pdnAtm 4 }
-- pdnAtmExtMIB             OBJECT IDENTIFIER ::= { pdnAtm 5 }
-- pdnAtmM4ExtMIB           OBJECT IDENTIFIER ::= { pdnAtm 6 }
pdnIfExt                  OBJECT IDENTIFIER ::= { pdn-interfaces 12 }
-- pdnIfExtConfig           OBJECT IDENTIFIER ::= { pdnIfExt 1 }
-- pdnIfExtTestConfig       OBJECT IDENTIFIER ::= { pdnIfExt 2 }
-- pdnIfExtEncapConfig      OBJECT IDENTIFIER ::= { pdnIfExt 3 }
pdnSonetMIB               OBJECT IDENTIFIER ::= { pdn-interfaces 13 }
pdnDs3MIB                 OBJECT IDENTIFIER ::= { pdn-interfaces 14 }
pdnmsdsl                  OBJECT IDENTIFIER ::= { pdn-interfaces 15 }
-- pdnShdsl                 OBJECT IDENTIFIER ::= { pdnmsdsl 1 }
pdnIsdn                   OBJECT IDENTIFIER ::= { pdn-interfaces 16 }
pdnMgmtLink               OBJECT IDENTIFIER ::= { pdn-interfaces 17 }
pdnDiagPortal             OBJECT IDENTIFIER ::= { pdn-interfaces 18 }
-- pdnSpectrumMgmt           OBJECT IDENTIFIER ::= { pdn-interfaces 19 }
pdnReachDSL             OBJECT IDENTIFIER ::= { pdn-interfaces 20 }
-- pdnMgmtIpMIB              OBJECT IDENTIFIER ::= { pdn-interfaces 21 }
--rs232ExtPort                  OBJECT IDENTIFIER ::= { pdn-interfaces 22 }
-- rs232PortExtMIBObject    OBJECT IDENTIFIER ::= { rs232ExtPort 1 }
-- rs232ExtPortGroups         OBJECT IDENTIFIER ::= { rs232ExtPort 2 }


pdn-devConfig        OBJECT IDENTIFIER ::= { pdn-common 7 }
pdn-security         OBJECT IDENTIFIER ::= { pdn-common 8 }
pdn-traps            OBJECT IDENTIFIER ::= { pdn-common 9 }
-- pdn-control          OBJECT IDENTIFIER ::= { pdn-common 10 }
pdn-ipInjection      OBJECT IDENTIFIER ::= { pdn-common 11 }
pdn-ip               OBJECT IDENTIFIER ::= { pdn-common 12 }
-- pdnRmon             OBJECT IDENTIFIER ::= { pdn-common 13 }
pdn-fileXfer         OBJECT IDENTIFIER ::= { pdn-common 14 } 
pdn-feature          OBJECT IDENTIFIER ::= { pdn-common 15 }
pdn-diagnostics      OBJECT IDENTIFIER ::= { pdn-common 16 }
-- diagTestMIBObjects    OBJECT IDENTIFIER ::= { pdn-diagnostics 1  }
-- diagTestMIBTraps      OBJECT IDENTIFIER ::= { pdn-diagnostics 2 }

pdn-dns              OBJECT IDENTIFIER ::= { pdn-common 17 }
-- pdnDNSMIBObjects      OBJECT IDENTIFIER ::= { pdn-dns 1 }
-- pdnDNSMIBTraps        OBJECT IDENTIFIER ::= { pdn-dns 2 }

pdn-ether            OBJECT IDENTIFIER ::= { pdn-common 18 }
-- pdnPortConfigMIBObjects  OBJECT IDENTIFIER ::= { pdn-ether 1 }
-- pdnPortConfigMIBTraps    OBJECT IDENTIFIER ::= { pdn-ether 2 }


pdn-socket           OBJECT IDENTIFIER ::= { pdn-common 19 }
-- devSocketStatsMIBObjects  OBJECT IDENTIFIER ::= { pdn-socket 1 }
-- devSocketStatsMIBTraps    OBJECT IDENTIFIER ::= { pdn-socket 2 }


pdn-time             OBJECT IDENTIFIER ::= { pdn-common 20 }
-- devTimeMIBObjects       OBJECT IDENTIFIER ::= { pdn-time 1 }
-- devTimeMIBTraps         OBJECT IDENTIFIER ::= { pdn-time 2 }


pdn-bridge           OBJECT IDENTIFIER ::= { pdn-common 21 }
-- pdnBridgeGenericMIBObjects OBJECT IDENTIFIER ::= { pdn-bridge 1 }
-- pdnBridgeMIBTraps OBJECT IDENTIFIER ::= { pdn-bridge 2 }

pdn-domain           OBJECT IDENTIFIER ::= { pdn-common 22 }
-- pdnDomainMIBObjects   OBJECT IDENTIFIER ::= { pdn-domain 1 }
-- pdnDomainMIBTraps     OBJECT IDENTIFIER ::= { pdn-domain 2 }

pdn-filter           OBJECT IDENTIFIER ::= { pdn-common 23 }
-- sysDevFilterMIBObjects OBJECT IDENTIFIER ::= { pdn-filter 1 }
-- sysDevFilterMIBTraps   OBJECT IDENTIFIER ::= { pdn-filter 2 }

pdn-dslam            OBJECT IDENTIFIER ::= { pdn-common 24 }
-- sysDevDslamMIBObjects OBJECT IDENTIFIER ::= { pdn-dslam 1 }
-- sysDevDslamMIBTraps   OBJECT IDENTIFIER ::= { pdn-dslam 2 }

pdn-radius           OBJECT IDENTIFIER ::= { pdn-common 25 }
-- sysDevRadiusMIBObjects OBJECT IDENTIFIER ::= { pdn-radius 1 }
-- sysDevRadiusMIBTraps   OBJECT IDENTIFIER ::= { pdn-radius 2 }


pdn-inet             OBJECT IDENTIFIER ::= { pdn-common 26 }
-- pdnInetMIBObjects   OBJECT IDENTIFIER ::= { pdn-inet 1 }
-- pdnInetMIBTraps     OBJECT IDENTIFIER ::= { pdn-inet 2 }


pdn-arp              OBJECT IDENTIFIER ::= { pdn-common 27 }
-- pdnNetToMediaGenericMIBObjects  OBJECT IDENTIFIER ::= { pdn-arp 1 }
-- pdnNetToMediaMIBTraps OBJECT IDENTIFIER ::= { pdn-arp 2 }

pdn-devStats         OBJECT IDENTIFIER ::= { pdn-common 28 }
-- devStatsMIBObjects    OBJECT IDENTIFIER ::= { pdn-devStats 1 }
-- devStatsMIBTraps      OBJECT IDENTIFIER ::= { pdn-devStats 2 }

pdn-dhcp             OBJECT IDENTIFIER ::= { pdn-common 29 }
pdn-nat              OBJECT IDENTIFIER ::= { pdn-common 30 }
pdn-syslog           OBJECT IDENTIFIER ::= { pdn-common 31 }
pdn-dialControl      OBJECT IDENTIFIER ::= { pdn-common 32 }

pdn-devNetTiming     OBJECT IDENTIFIER ::= { pdn-common 33 }
-- pdnDevNetTimingMIB            OBJECT IDENTIFIER ::= { pdn-devTiming 1 }
-- pdnDevNetTimingMIBObjects     OBJECT IDENTIFIER ::= { pdnDevNetTimingMIB 1 }
-- pdnDevNetTimingMIBTraps       OBJECT IDENTIFIER ::= { pdnDevNetTimingMIB 2 }
-- pdnDevNetTimingMIBConformance OBJECT IDENTIFIER ::= { pdnDevNetTimingMIB 3 }

pdnIPSec             OBJECT IDENTIFIER ::= { pdn-common 34 }
mpeEntitySensor      OBJECT IDENTIFIER ::= { pdn-common 35 }
pdnStackable	     OBJECT IDENTIFIER ::= { pdn-common 36 }
pdnUplinkTagging     OBJECT IDENTIFIER ::= { pdn-common 37 }
pdnSpectrumMgr       OBJECT IDENTIFIER ::= { pdn-common 38 }
pdn-dot1q            OBJECT IDENTIFIER ::= { pdn-common 39 } 
pdnLinkFaultMgmt     OBJECT IDENTIFIER ::= { pdn-common 40 } 
pdnEntityRedundancy  OBJECT IDENTIFIER ::= { pdn-common 41 } 
pdnLinkLoadSharing   OBJECT IDENTIFIER ::= { pdn-common 42 } 
pdnAtmBridgeIwfMIB   OBJECT IDENTIFIER ::= { pdn-common 43 } 
pdnMpdExt   	     OBJECT IDENTIFIER ::= { pdn-common 44 } 
pdnEntitySensorExtMIB OBJECT IDENTIFIER ::= { pdn-common 45 } 
pdnVlanMIB            OBJECT IDENTIFIER ::= { pdn-common 46 } 
pdnIgmpStdExtMIB      OBJECT IDENTIFIER ::= { pdn-common 47 } 
pdnIpMcastMIB         OBJECT IDENTIFIER ::= { pdn-common 48 } 

pdn-snmp         OBJECT IDENTIFIER ::= { paradyne 3 }
ent-9XXX              OBJECT IDENTIFIER ::= { pdn-snmp 1 }
ent-96XX              OBJECT IDENTIFIER ::= { ent-9XXX 1 } -- unused
ent-bonaire           OBJECT IDENTIFIER ::= { ent-9XXX 2 } -- unused
ent-91XX              OBJECT IDENTIFIER ::= { ent-9XXX 3 } -- unused

pdn-36xx             OBJECT IDENTIFIER ::= { paradyne 4 } -- unused

pdn-aac              OBJECT IDENTIFIER ::= { paradyne 5 } -- unused

pdn-eagle            OBJECT IDENTIFIER ::= { paradyne 6 } -- unused

pdn-ar               OBJECT IDENTIFIER ::= { paradyne 7 } -- unused

pdn-as               OBJECT IDENTIFIER ::= { paradyne 8 } -- unused

pdn-xdsl             OBJECT IDENTIFIER ::= { paradyne 9 }
ent-5100                OBJECT IDENTIFIER ::= { pdn-xdsl 1 }
-- xdslIfConfigMIBObjects        OBJECT IDENTIFIER ::= { pdn-xdsl 2 }
ent-8800                OBJECT IDENTIFIER ::= { pdn-xdsl 3 } 
-- sysDevStats            OBJECT IDENTIFIER ::= { ent-8800 1 } 
-- sysDevConfig           OBJECT IDENTIFIER ::= { ent-8800 2 } 
-- sysDevFilter           OBJECT IDENTIFIER ::= { ent-8800 3 } 
-- diagTests              OBJECT IDENTIFIER ::= { ent-8800 4 } 
-- pdnDot1dBridge         OBJECT IDENTIFIER ::= { ent-8800 5 } 
-- pdnDomain              OBJECT IDENTIFIER ::= { ent-8800 6 } 
-- sysDevRadiusAuth       OBJECT IDENTIFIER ::= { ent-8800 7 } 
-- sysDevUserAccount      OBJECT IDENTIFIER ::= { ent-8800 8 } 
-- xdslIfConfigMIBTraps          OBJECT IDENTIFIER ::= { pdn-xdsl 4 }
ent-8600                OBJECT IDENTIFIER ::= { pdn-xdsl 5 } -- unused
pdn-sle                 OBJECT IDENTIFIER ::= { pdn-xdsl 6 }

pdn-comp             OBJECT IDENTIFIER ::= { paradyne 10 }
ent-9028                OBJECT IDENTIFIER ::= { pdn-comp 1 } -- unused

pdn-ptc              OBJECT IDENTIFIER ::= { paradyne 11 }
ent-ptc                 OBJECT IDENTIFIER ::= { pdn-ptc 1 } -- unused

pdn-mpe              OBJECT IDENTIFIER ::= { paradyne 12 }

mpe-mib2         OBJECT IDENTIFIER ::= { pdn-mpe 4 }
-- mpeMib2MIBObjects OBJECT IDENTIFIER ::= { mpe-mib2 1 }
-- mpeMib2MIBTraps   OBJECT IDENTIFIER ::= { mpe-mib2 2 }


mpe-devHealth    OBJECT IDENTIFIER ::= { pdn-mpe 7 }
-- mpeDevHealthAndStatusMIBObjects  OBJECT IDENTIFIER ::= { mpe-devHealth  1 }
-- mpeDevHealthAndStatusMIBTraps    OBJECT IDENTIFIER ::= { mpe-devHealth  2 }

-- mpeDevControl    OBJECT IDENTIFIER ::= { pdn-mpe 10 }
-- mpeDevControlMIBObjects      OBJECT IDENTIFIER ::= { mpe-devControl 1  }
-- mpeDevControlMIBTraps        OBJECT IDENTIFIER ::= { mpe-devControl 2  }

mpe-bridge         OBJECT IDENTIFIER ::= { pdn-mpe 21 }
-- mpePdnBridgeGenericMIBObjects OBJECT IDENTIFIER ::= { mpe-bridge 1 }
-- mpePdnBridgeMIBTraps OBJECT IDENTIFIER ::= { mpe-bridge 2 }

mpe-domain       OBJECT IDENTIFIER ::= { pdn-mpe 22 }
-- mpePdnDomainMIBObjects   OBJECT IDENTIFIER ::= { mpe-domain 1 }
-- mpePdnDomainMIBTraps     OBJECT IDENTIFIER ::= { mpe-domain 2 }

mpe-filter         OBJECT IDENTIFIER ::= { pdn-mpe 23 }
-- mpeSysDevFilterMIBObjects OBJECT IDENTIFIER ::= { mpe-filter 1 }
-- mpeSysDevFilterMIBTraps   OBJECT IDENTIFIER ::= { mpe-filter 2 }

mpe-dslam         OBJECT IDENTIFIER ::= { pdn-mpe 24 }
-- mpeSysDevDslamMIBObjects OBJECT IDENTIFIER ::= { mpe-dslam 1 }
-- mpeSysDevDslamMIBTraps   OBJECT IDENTIFIER ::= { mpe-dslam 2 }

mpe-arp            OBJECT IDENTIFIER ::= { pdn-mpe 27 }
-- mpePdnNetToMediaGenericMIBObjects      OBJECT IDENTIFIER ::= { mpe-arp 1 } 
-- mpePdnNetToMediaGenericMIBTraps        OBJECT IDENTIFIER ::= { mpe-arp 2 }

mpe-devStats     OBJECT IDENTIFIER ::= { pdn-mpe 28 }
-- mpeDevStatsMIBObjects    OBJECT IDENTIFIER ::= { mpe-devStats 1 }
-- mpeDevStatsMIBTraps      OBJECT IDENTIFIER ::= { mpe-devStats 2 }

mpe-devConfig     OBJECT IDENTIFIER ::= { pdn-mpe 29 }
-- mpeDevConfigMIB            OBJECT IDENTIFIER ::= { mpe-devConfig 1 }
-- mpeDevConfigMIBObjects     OBJECT IDENTIFIER ::= { mpeDevConfigMIB 1 }
-- mpeDevConfigMIBTraps       OBJECT IDENTIFIER ::= { mpeDevConfigMIB 2 }
-- mpeDevConfigMIBConformance OBJECT IDENTIFIER ::= { mpeDevConfigMIB 3 }

mpe-atm     OBJECT IDENTIFIER ::= { pdn-mpe 30 }
-- mpeAtmConfMIB             OBJECT IDENTIFIER ::= { mpe-atm 1 }
-- mpeAtmConfMIBObjects      OBJECT IDENTIFIER ::= { mpeAtmConfMIB 1 }
-- mpeAtmConfMIBTraps        OBJECT IDENTIFIER ::= { mpeAtmConfMIB 2 }
-- mpeAtmConfMIBConformance  OBJECT IDENTIFIER ::= { mpeAtmConfMIB 3 }

pdn-experimental     OBJECT IDENTIFIER ::= { paradyne 13 }


pdn-ietf-drafts      OBJECT IDENTIFIER ::= { paradyne 14 }
-- draft-ietf-frnetmib-frsi-00  OBJECT IDENTIFER ::= { pdn-ietf-drafts 1 }
-- draft-ietf-atommib-sonetaps-mib-08 OBJECT IDENTIFER ::= { pdn-ietf-drafts 2 }
-- pdnSfp  OBJECT IDENTIFER ::= { pdn-ietf-drafts 3 }

cellsaver-mibs       OBJECT IDENTIFIER ::= { paradyne 15 }
-- cellsaver-common          OBJECT IDENTIFER ::= { cellsaver-mibs 1 }
-- mib-9510                  OBJECT IDENTIFER ::= { cellsaver-mibs 2 }
-- mib-9550                  OBJECT IDENTIFER ::= { cellsaver-mibs 3 }

cornet-mibs          OBJECT IDENTIFIER ::= { paradyne 16 }
-- cornet-common       OBJECT IDENTIFER ::= { cornet-mibs 1 }
-- mib-xxxx            OBJECT IDENTIFER ::= { cornet-mibs 2 }

ip-stackable-mibs      OBJECT IDENTIFIER ::= { paradyne 17 }
-- ip-stackable-common OBJECT IDENTIFIER ::= { ip-stackable-mibs 1 }
-- mib-xxxx            OBJECT IDENTIFIER ::= { ip-stackable-mibs 2 }

etherloop-mib        OBJECT IDENTIFIER ::= { paradyne 18 }

END

PDN-TC DEFINITIONS ::=  BEGIN

-- Copyright (C) 2002 Paradyne Corporation.
-- Enterprise Textual Convention MIB
-- Version : 0.2 DRAFT 

-- Last Updated Sue Alfano 08/13/2002
-- Last Updated Sue Alfano 05/7/2002
-- Last Updated Wayne Jadoo 10/7/1999
-- Last Updated Wayne Jadoo 10/4/1999
-- Last Update Wayne Jadoo 09/28/1999
-- Last Updated Wayne Jadoo 09/27/1999
-- Last Updated : Wayne Jadoo 08/31/99

-- The textual Conversion MIB contains the definitions of objects that  are used
-- for defining  objects in other MIBs. This file can be imported by the other  
-- MIBs in order to use the pre-defined objects. Textual conventions for new  
-- objects can  be added to this file.

-- History
-- 08/25/1999  Wayne Jadoo
--   Initial Version.
-- 09/27/1999  Wayne Jadoo
--   Commented out textual conventions so 
--   to be compatible to SNMP-V1 
-- 09/28/99 Wayne Jadoo
--   Added TC for TAddress , MacAddress and TruthValue
-- 10/04/99 Wayne Jadoo
--   Removed TC for Tadddress, MacAddress and TruthValue 
--   DateAndTime and SnmpAdminString and moved to rfc1901v1.mi
-- Wayne Jadoo 10/7/99
--   Imported PDN-HEADER-HEADER mib 
--   and added TC for SnmpAdminString.
-- Kevin Baughman 10/27/99
--   Converted back to smiv2
-- Rajesh Raghavan 9/21/2000
--   Added TC for TimeOfDay
-- Sue Alfano 5/7/2002
--   Added new enum to NTPMode, removed reference to DisplayString
--   (MIB compile doesn't allow definition in TC to use syntax
--   from another TC)
-- 
-- Jesus Pinto 8/13/2002
--   Added TC for ContactState. 
-- 

IMPORTS 

TEXTUAL-CONVENTION
  FROM SNMPv2-TC 
enterprises
  FROM RFC1155-SMI;

-- Not having an object defined causes errors for HP OpenView
pdyn           OBJECT IDENTIFIER ::= { enterprises 1795 }

-- ==========================================================

VnidMode ::= TEXTUAL-CONVENTION
     STATUS       current
     DESCRIPTION
	"This object describes the configuration mode
  	for VNIDs and ports. "

     SYNTAX INTEGER { implicit(1), explicit(2), notagging(3) }

ClientState ::= TEXTUAL-CONVENTION
     STATUS current
     DESCRIPTION
       " The configuration type for a client."
     SYNTAX INTEGER { static(1), dynamic(2)}

VnidTaggingState ::=  TEXTUAL-CONVENTION
     STATUS current
     DESCRIPTION
        " This object indicates whether VNID tagging 
        is activated or de-activated."
     SYNTAX	INTEGER { enabled(1), disabled(2)}

VnidRange ::= TEXTUAL-CONVENTION
     STATUS current
     DESCRIPTION
        " The valid range for VNID IDs"
     SYNTAX INTEGER ( 2..4000 )

SwitchState ::= TEXTUAL-CONVENTION
     STATUS current
     DESCRIPTION
        " This object indicates whether an object state is 
        in the enabled or disabled state "
     SYNTAX INTEGER { enabled(1), disabled(2)}

ResetStates ::= TEXTUAL-CONVENTION
     STATUS current
     DESCRIPTION
        "This object defines the enumerations
        of values that can be applied to the reset
        object"
     SYNTAX INTEGER { 
                      noOp(1), 
		      reset(2), 
		      resetToFactoryDefaults(3), 
		      resetToNewActiveConfig(4) 
     }

ResultTypes ::=  TEXTUAL-CONVENTION
     STATUS current
     DESCRIPTION
        "This object defines the enumerations
        for the result of an operation "
     SYNTAX INTEGER {
                none(1),
                success(2),
                failure(3),
                inProgress(4)
     }

InitiatorTypes ::=  TEXTUAL-CONVENTION
     STATUS current
     DESCRIPTION
        "This object defines the enumerations
        for the result of an operation "
     SYNTAX INTEGER {
             noop(1),
             telnet(2),
             console(3),
             snmp(4)
           }

NTPMode ::= TEXTUAL-CONVENTION
     STATUS current
     DESCRIPTION
           "This object describes the mode in which NTP/SNTP will operate."
     SYNTAX INTEGER {
                  unicast(1),
                  broadcast(2),
                  multicast(3)
          }

DNSServerType ::= TEXTUAL-CONVENTION
    STATUS  current
    DESCRIPTION
           "This object describes the DNS server Type"
	SYNTAX  INTEGER {
                  primary(1),
                  secondary(2)
                 }


MibOidType ::=  TEXTUAL-CONVENTION
    STATUS  current
    DESCRIPTION
        "This Object describes the type of a mib object
              Scalar - Single Instance Object
              Table - Multi-instance Object
              Mib - A Mib.
                 Section - A Section Within A MIB"
    SYNTAX INTEGER {
                    scalar (1),
                    table (2),
                    mib (3),
                    section (4)
                 }

SocketType ::=  TEXTUAL-CONVENTION
    STATUS  current
    DESCRIPTION
           "This object describes the type of socket"
    SYNTAX INTEGER {
                    unknown(1),
                    stream(2),
                    datagram(3),
                    rawProtocol(4),
                    reliableMessageDelivery(5),
                    sequencedPacket(6)
                   }


SocketFamily ::=  TEXTUAL-CONVENTION
     STATUS  current
     DESCRIPTION
            "This object describes the socket Family"
     SYNTAX  INTEGER {
                           unknown(1),
                           unix(2),
                           darpaInternet(3),
                           darpaIMP(4),
                           pUP(5),
                           cHAOSFamily(6),
                           xeroxNovell(7),
                           nBS(8),
                           eCMA(9),
                           dATAKIT(10),
                           cCITT(11),
                           sNA(12),
                           dECnet(13),
                           directDataLinkInterface(14),
                           dECLAT(15),
                           nSCHyperChannel(16),
                           appleTalk(17),
                           netqorkInterfaceTap(18),
                           iEEE8020ISO8802(19),
                           oSI(20),
                           x25(21),
                           oSIAFI47IDI4(22),
                           uSGovermentOSI(23)
                   }

SocketState ::=  TEXTUAL-CONVENTION
       STATUS  current
       DESCRIPTION
              "This object describes the state of a stream socket"
       SYNTAX INTEGER {
                          closed (1),
                          listen (2),
                          sYNSent(3),
                          sYNRCVD(4),
                          established(5),
                          closeWait(6),
                          fINWait(7),
                          closing(8),
                          lastAck(9),
                          fINWait2(10),
                          timeWait(11)
                 }

DomainName ::=  TEXTUAL-CONVENTION
       STATUS  current
       DESCRIPTION
            "The domain name space is a tree structure.  Each node and 
            leaf on the tree corresponds to a resource set (which may be 
            empty).  The domain system makes no distinctions between the 
            uses of the interior nodes and leaves, and this memo uses the 
            term 'node' to refer to both. Each node has a label, which is 
            zero to 63 octets in length.  Brother nodes may not have the 
            same label, although the same label can be used for nodes 
            which are not brothers.  One label is reserved, and that is
            the null (i.e., zero length) label used for the root.
            The domain name of a node is the list of the labels on the 
            path from the node to the root of the tree.  By convention, 
            the labels that compose a domain name are printed or read 
            left to right, from the most specific (lowest, farthest from 
            the root) to the least specific (highest, closest to the 
            root).
 
            Internally, programs that manipulate domain names should 
            represent them as sequences of labels, where each label is a 
            length octet followed by  an octet string.  Because all domain 
            names end at the root, which has a null string for a label, 
            these internal representations can use a length byte of zero 
            to terminate a domain name.
 
            By convention, domain names can be stored with arbitrary case, but
            domain name comparisons for all present domain functions are done in 
            a case-insensitive manner, assuming an ASCII character set, and a 
            high order zero bit.  This means that you are free to create a node 
            with label 'A' or a node with label 'a', but not both as brothers; 
            you could refer to either using 'a' or 'A'.  When you receive a 
            domain name or label, you should preserve its case.  The rationale 
            for this  choice is that we may someday need to add full binary 
            domain names for  new services; existing services would not be 
            changed.
 
            When a user needs to type a domain name, the length of each label is
            omitted and the labels are separated by dots ('.').  Since a complete
            domain name ends with the root label, this leads to a printed form 
            which ends in a dot.  We use this property to distinguish between:
 
            character string which represents a complete domain name
            (often called 'absolute').  For example, 'poneria.ISI.EDU.'
 
           - a character string that represents the starting labels of a
           domain name which is incomplete, and should be completed by
           local software using knowledge of the local domain (often
           called 'relative').  For example, 'poneria' used in the
           ISI.EDU domain.
 
           Relative names are either taken relative to a well known 
           origin, or to a list of domains used as a search list.  Relative 
           names appear mostly at the user interface, where their interpretation 
           varies  from implementation to implementation, and in master files, 
           where they  are  relative to a single origin domain name.  The most 
           common interpretation uses the root '.' as either the single origin 
           or as one of the members of the search list, so a multi-label relative 
           name is often one where the trailing dot has been omitted to save 
           typing.
 
           To simplify implementations, the total number of octets that represent  a
           domain name (i.e., the sum of all label octets and label lengths) is
           limited to 255.
 
           A domain is identified by a domain name, and consists of that part of
           the domain name space that is at or below the domain name which
           specifies the domain.  A domain is a subdomain of another domain if it
           is contained within that domain.  This relationship can be tested by
           seeing if the subdomain's name ends with the containing domain's name.
           For example, A.B.C.D is a subdomain of B.C.D, C.D, D, and  '.' "
        SYNTAX OCTET STRING (SIZE (1..64))

   SnmpAdminString ::= TEXTUAL-CONVENTION
        DISPLAY-HINT "255a"
        STATUS       current
        DESCRIPTION "An octet string containing administrative
           information, preferably in human-readable form.
 
           To facilitate internationalization, this
           information is represented using the ISO/IEC
           IS 10646-1 character set, encoded as an octet
           string using the UTF-8 transformation format
           described in [RFC2044].
 
           Since additional code points are added by
           amendments to the 10646 standard from time
           to time, implementations must be prepared to
           encounter any code point from 0x00000000 to
           0x7fffffff.
 
           The use of control codes should be avoided.
 
           When it is necessary to represent a newline,
           the control code sequence CR LF should be used.
 
 
           The use of leading or trailing white space should
           be avoided.
 
           For code points not directly supported by user
           interface hardware or software, an alternative
           means of entry and display, such as hexadecimal,
           may be provided.
 
           For information encoded in 7-bit US-ASCII,
           the UTF-8 encoding is identical to the
           US-ASCII encoding.
 
           Note that when this TC is used for an object that
           is used or envisioned to be used as an index, then
           a SIZE restriction must be specified so that the
           number of sub-identifiers for any object instance
           does not exceed the limit of 128, as defined by
           [RFC1905].
                "
    SYNTAX OCTET STRING (SIZE (0..255))

InetAddressType ::= TEXTUAL-CONVENTION
  STATUS       current
  DESCRIPTION
    "This object describes the type of address configured 
     for a interface"
  SYNTAX INTEGER { primary (1), secondary (2) }

ManagementType ::= TEXTUAL-CONVENTION
	STATUS current
	DESCRIPTION
	"This object is used to specify the type of
	management. This can be either Inband
	Management or OutBand Management."
	SYNTAX INTEGER
	{
		inband  (1),
		outband (2)
	}

ContactState ::= TEXTUAL-CONVENTION
	STATUS current
	DESCRIPTION
	"This convension can be used to indicate the
	state of a switch, door, connector, etc. that
	can be by nature opened or closed."
	SYNTAX INTEGER
	{
		open  (1),
		close (2)
	}

IdslClockMode ::= TEXTUAL-CONVENTION
	STATUS current
	DESCRIPTION
    "This object indicates the network clock mode set
    for the secondary network clock. IDSL portcards with a
    port configured as an NT will be set to
    portCardDriveClockOnboard(4), both driving the backplane
    and using the clock for the other Local Timing transceivers
    on the card. Port cards with only LT ports configured will
    receive a clock from the backplane using portCardSinkClock(2).
    portCardDriveClock(3) will drive the backplane alone."
   SYNTAX INTEGER 
   {
      triState(1),
      portCardSinkClock(2),
      portCardDriveClock(3),
      portCardDriveClockOnboard(4)
   }

TimeOfDay ::= TEXTUAL-CONVENTION
    DISPLAY-HINT "1d:1d"
    STATUS	current
    DESCRIPTION
	"A time of day specification

	field	octets	contents	range
	-----	------	--------	-----
	  1	   1	hour		0..23
	  2	   2	minutes		0..59"

    SYNTAX	OCTET STRING(SIZE(2))

DayOfWeek ::= TEXTUAL-CONVENTION
    STATUS	current
    DESCRIPTION
	"This object indicates the day of the week, with
	an additional option 'Daily' to work with interfaces
	that use this convention to schedule events."
    SYNTAX	INTEGER { sunday(1), monday(2), tuesday(3), wednesday(4),
			thursday(5), friday(6), saturday(7), daily(8) }

END


PDN-DSLAM-SYSTEM-MIB DEFINITIONS ::= BEGIN

-- Version :  1.1 APPROVED
-- Enterprise pdn DSLAM mib
-- Copyright (C) 2002 Paradyne Corporation.

 
 IMPORTS
 TAddress,
 RowStatus,DisplayString
 FROM SNMPv2-TC
 IdslClockMode, SwitchState
 FROM PDN-TC
 Counter32,IpAddress,TimeTicks,
 Integer32, OBJECT-TYPE, NOTIFICATION-TYPE,
 MODULE-IDENTITY
 FROM SNMPv2-SMI
 OBJECT-GROUP, NOTIFICATION-GROUP
 FROM SNMPv2-CONF
 ifIndex, sysObjectID
 FROM RFC1213-MIB
 entPhysicalIndex
 FROM ENTITY-MIB
 pdn-common
 FROM PDN-HEADER-MIB 
 ;


pdn-dslam MODULE-IDENTITY

   LAST-UPDATED    "0206050000Z"
   ORGANIZATION    "Paradyne Corporation
		    MIB Working Group"

   CONTACT-INFO    "Paradyne Corporation
		    8545 126th Avenue North
		    Largo, FL 33733
		    www.paradyne.com

		    General Comments to: mibwg_team@paradyne.com

		    Editors
		    Prakash Easwar
		    Jesus Pinto
		    Dragana Gough"

   DESCRIPTION
    	"The DSLAM MIB. This MIB is specific to portcards and
 	DSLAM configuration/stats for MCC and the portcards.
 	The objects defined in this mib are specific to some
 	products and donot apply to all paradyne devices."

   REVISION "0206200000Z"
   DESCRIPTION "J. Pinto
    o Added IMPLIED modifier to the INDEX clause in:
	entCommunityTableEntry and sysDevUserAccountEntry.
   "

   REVISION "0206050000Z"
   DESCRIPTION "J. Pinto
    o Changed  sysDevUserAccountUserPassword to read-create
    o Expanded sysDevUserAccountPrivilege options
   "

   REVISION "0202220000Z"
   DESCRIPTION "Initial Release"


   ::= { pdn-common 24 }

sysDevDslamMIBObjects OBJECT IDENTIFIER ::= { pdn-dslam 1 }
sysDevDslamMIBTraps   OBJECT IDENTIFIER ::= { pdn-dslam 2 }


sysDevStats 				OBJECT IDENTIFIER ::= { sysDevDslamMIBObjects 1 }
sysDevConfig				OBJECT IDENTIFIER ::= { sysDevDslamMIBObjects 2 }

-- The statistics group. The implementation of this group
-- is mandatory.
 
 loginHistTable OBJECT-TYPE
   SYNTAX SEQUENCE OF LoginHistTableEntry
   MAX-ACCESS  not-accessible
   STATUS current
   DESCRIPTION
     "This table shows the most recent 10 logins and all active users 
	  currently accessing the device. It is indexed by userId
	  and loginTime."
 ::= { sysDevStats 1 }

 loginHistTableEntry OBJECT-TYPE
   SYNTAX  LoginHistTableEntry
   MAX-ACCESS  not-accessible
   STATUS  current
   DESCRIPTION
   		"This object corresponds to an entry in the login history table."
   INDEX { loginUserId, loginTime }
 ::= { loginHistTable 1 }

 LoginHistTableEntry ::=
   SEQUENCE {
   loginUserId 		DisplayString,
   loginTime 	TimeTicks,
   loginAccessApp 	INTEGER,
   loginAccessHost	IpAddress,
   loginUserPriv	 	INTEGER,
   loginStatus 	INTEGER
   }
 
 loginUserId OBJECT-TYPE
   SYNTAX DisplayString
   MAX-ACCESS read-only
   STATUS current
   DESCRIPTION
     "This object containes the user login id."
 ::= { loginHistTableEntry 1 }
 
 loginTime OBJECT-TYPE
   SYNTAX TimeTicks 
   MAX-ACCESS read-only
   STATUS current
   DESCRIPTION
     "This object containes the login time in seconds 
	 when the login session is established."
 ::= { loginHistTableEntry 2 }

 loginAccessApp OBJECT-TYPE
   SYNTAX INTEGER {
	console (1),
	telnet (2),
	ftp (3),
	web (4),
	modem (5)
   }
   MAX-ACCESS read-only
   STATUS current
   DESCRIPTION
     "This object describes the access application used 
	 by the end user to access the device. This can be 
	 done through console, using telnet, modem, web, or using ftp."
 ::= { loginHistTableEntry 3 }

 loginAccessHost OBJECT-TYPE
   SYNTAX IpAddress
   MAX-ACCESS read-only
   STATUS current
   DESCRIPTION
     "This object containes the ip address of the network
	 management station when the access application is
	 telnet or ftp. In case of console, this object contains
	 0.0.0.0."
 ::= { loginHistTableEntry 4 }

 loginUserPriv OBJECT-TYPE
   SYNTAX INTEGER {
	administrator (1),
	operator (2)
   }
   MAX-ACCESS read-only
   STATUS current
   DESCRIPTION
     "This object containes the access privileges of the user."
 ::= { loginHistTableEntry 5 }

 loginStatus OBJECT-TYPE
   SYNTAX INTEGER {
	active (1),
	inactive (2)
   }
   MAX-ACCESS read-only
   STATUS current
   DESCRIPTION
     "This object indicates whether the user is still accessing the
	 device."
 ::= { loginHistTableEntry 6 }

 loginFailureCountTable OBJECT-TYPE
   SYNTAX SEQUENCE OF LoginFailureCountTableEntry
   MAX-ACCESS  not-accessible
   STATUS current
   DESCRIPTION
     "This table containes the statistics for login failures. It
	  is indexed by access type i.e console, telnet or ftp."
 ::= { sysDevStats 2 }

 loginFailureCountTableEntry OBJECT-TYPE
   SYNTAX  LoginFailureCountTableEntry
   MAX-ACCESS  not-accessible
   STATUS  current
   DESCRIPTION
   "This object corresponds to an entry in the login failure count table."
   INDEX {loginFailureAccessApp}
 ::= { loginFailureCountTable 1 }

 LoginFailureCountTableEntry ::=
   SEQUENCE {
   loginFailureAccessApp INTEGER,
   loginFailureCount Counter32
   }

 loginFailureAccessApp OBJECT-TYPE
   SYNTAX INTEGER {
	console (1),
	telnet (2),
	ftp (3)
   }
   MAX-ACCESS read-only
   STATUS current
   DESCRIPTION
     "This object describes the access application used 
	 by the end user to access the device. This can be 
	 done through console, using telnet or using ftp."
 ::= { loginFailureCountTableEntry 1 }

 loginFailureCount OBJECT-TYPE
   SYNTAX Counter32
   MAX-ACCESS read-only
   STATUS current
   DESCRIPTION
     "This object containes the number of unsuccesful logins for console,
	 ftp or telnet."
 ::= { loginFailureCountTableEntry 2 }

 -- The configuration group. The implementation of this group
 -- is optional.

 enablePowerSourceFailureAlarm OBJECT-TYPE
   SYNTAX INTEGER {
     disable (1),
     enable (2)
   }
   MAX-ACCESS read-write
   STATUS current
   DESCRIPTION
     "This objects corresponds to enabling/disabling the 
      power source failure alarm - for both A and B power sources
      This object is for the MCC only.
      The default value of this object should be 1."
    ::= {sysDevConfig 1 }

 devIfTable OBJECT-TYPE
   SYNTAX SEQUENCE OF DevIfTableEntry
   MAX-ACCESS  not-accessible
   STATUS current
   DESCRIPTION
       "This table is used to configure information  for a
    particular interface"
    ::= {sysDevConfig 2 }

devIfTableEntry OBJECT-TYPE
    SYNTAX  DevIfTableEntry
    MAX-ACCESS  not-accessible
    STATUS  current
    DESCRIPTION
      "This object corresponds to an entry in the DevifTable "
    INDEX { ifIndex }
    ::= { devIfTable 1 }
 
DevIfTableEntry ::=
    SEQUENCE {
      devPacketDiscardPolicy INTEGER,
      devLinkIntegrity        INTEGER
      }
devPacketDiscardPolicy OBJECT-TYPE
    SYNTAX INTEGER {
	 noOp (1),
     mrrp (2),
     lrrp (3)
   }
   MAX-ACCESS read-create
   STATUS current
   DESCRIPTION
     "This object corresponds to the policy for packet discards
      during periods of congestion :
      mrrp - most recently received packets are discarded.
      lrrp - least recently received packets are discarded.
      The default value of this object should be 2"
    ::= { devIfTableEntry 1 }

devLinkIntegrity OBJECT-TYPE
     SYNTAX INTEGER {
     enable (1),
     disable (2),
     none (3)
       }
     MAX-ACCESS read-create
     STATUS current
     DESCRIPTION
         "This object corresponds to the enabling or disabling of
          the ethernet link integrity :
           enable - enable link integrity
           disable - disable link integrity
           none - for interfaces that do not support link integrity
           The default value of this object should be 1"
    ::= { devIfTableEntry 2 }

communityTrapAddressInfoTable OBJECT-TYPE
      SYNTAX SEQUENCE OF CommunityTrapAddressInfoTableEntry
      MAX-ACCESS  not-accessible
      STATUS current
      DESCRIPTION
        "This table is used to set the trap destination address
         for a particular community."
    ::= {sysDevConfig 3 }
 
communityTrapAddressInfoTableEntry OBJECT-TYPE
   SYNTAX  CommunityTrapAddressInfoTableEntry
   MAX-ACCESS  not-accessible
   STATUS current
   DESCRIPTION
     "This object corresponds to an entry in the community
      trap address info table."
   INDEX { trapCommunityName, trapDestAndPort}
 ::= { communityTrapAddressInfoTable 1 }
 
CommunityTrapAddressInfoTableEntry ::=
   SEQUENCE {
     trapCommunityName DisplayString (SIZE(1..32)),
     trapDestAndPort   TAddress,
     trapsEnable       INTEGER,
     trapRowStatus     RowStatus
 }
 
trapCommunityName OBJECT-TYPE
   SYNTAX  DisplayString (SIZE(1..32))
   MAX-ACCESS not-accessible
   STATUS current
   DESCRIPTION
     "This object corresponds to the name of the SNMP Community."
   ::= { communityTrapAddressInfoTableEntry 1 }
    
trapDestAndPort OBJECT-TYPE
   SYNTAX TAddress
   MAX-ACCESS not-accessible
   STATUS current
   DESCRIPTION
     "The IP Address and Port of the destination to which a trap
      must be sent."
   ::= { communityTrapAddressInfoTableEntry 2 }
 
trapsEnable OBJECT-TYPE
   SYNTAX INTEGER {
     enable (1),
     disable (2)
   }
   MAX-ACCESS read-create
   STATUS current
   DESCRIPTION
     "This object corresponds to turning traps on/off for a
      particular destination.
      enable (1) - traps will be sent to the specified destination.
      disable (2)- traps will not be sent to the specified 
      destination.
      The default value of this object should be 2."
 ::= { communityTrapAddressInfoTableEntry 3 }

trapRowStatus OBJECT-TYPE
   SYNTAX RowStatus 
   MAX-ACCESS read-only
   STATUS current
   DESCRIPTION
     "This object is used to add or delete a
       a row from the table."
   ::= { communityTrapAddressInfoTableEntry 4 }

entCommunityTable OBJECT-TYPE
   SYNTAX SEQUENCE OF EntCommunityTableEntry
   MAX-ACCESS  not-accessible
   STATUS current
   DESCRIPTION
     "This table is used to set the various configuration
      parameters for a particular community."
    ::= { sysDevConfig 4 }

entCommunityTableEntry OBJECT-TYPE
   SYNTAX  EntCommunityTableEntry
   MAX-ACCESS  not-accessible
   STATUS  current
   DESCRIPTION
     "This object corresponds to an entry in the community
      table."
   INDEX { IMPLIED entCommunityName }
   ::= { entCommunityTable 1 }

EntCommunityTableEntry ::=
   SEQUENCE {
     entCommunityName
       DisplayString (SIZE(1..32)),
     entCommunityType
       INTEGER,
     entCommunityRowStatus
	    RowStatus
 }
 
entCommunityName OBJECT-TYPE
   SYNTAX  DisplayString (SIZE(1..32))
   MAX-ACCESS not-accessible
   STATUS current
   DESCRIPTION
     "This object corresponds to the name of the SNMP Community"
 ::= { entCommunityTableEntry 1 }

entCommunityType OBJECT-TYPE
   SYNTAX INTEGER {
     readOnly (1),
     readWrite (2)
   }
   MAX-ACCESS read-create
   STATUS current
   DESCRIPTION
     "The type of the community
       readOnly - this community is only allowed to do get's
       readWrite - this community is allowed to do get's and 
                   set's
      The default value of this object should be 1"
 ::= { entCommunityTableEntry 2 }

entCommunityRowStatus OBJECT-TYPE
   SYNTAX RowStatus 
   MAX-ACCESS read-create
   STATUS current
   DESCRIPTION
     "This object is used to add or delete a
       a row from the table."
   ::= { entCommunityTableEntry 3 }


-- MCC-rq 200-210: A new user account group is added into the Hotwire System MIB
 
sysDevUserAccountTable OBJECT-TYPE
    SYNTAX  SEQUENCE OF SysDevUserAccountEntry
    MAX-ACCESS  not-accessible
    STATUS current
    DESCRIPTION
        "This table contains the user accounts."
    ::= { sysDevConfig 5}
 
sysDevUserAccountEntry OBJECT-TYPE
    SYNTAX  SysDevUserAccountEntry
    MAX-ACCESS  not-accessible
    STATUS  current
    DESCRIPTION
        "An entry containing user account information."
    INDEX { IMPLIED sysDevUserAccountUserId }
    ::= { sysDevUserAccountTable 1 }
 
SysDevUserAccountEntry  ::= SEQUENCE {
    sysDevUserAccountUserId   DisplayString (SIZE(6..15)),
    sysDevUserAccountPrivilege INTEGER,
    sysDevUserAccountUserPassword DisplayString (SIZE(6..15)),
    sysDevUserAccountAccessPartition DisplayString (SIZE(0..50)),
    sysDevUserAccountRowStatus RowStatus
	}
 
sysDevUserAccountUserId OBJECT-TYPE
    SYNTAX  DisplayString (SIZE(6..15))
    MAX-ACCESS  not-accessible
    STATUS  current
    DESCRIPTION
        "This object corresponds to the login ID of the
         user account."
    ::= { sysDevUserAccountEntry 1 }
 
sysDevUserAccountPrivilege OBJECT-TYPE
    SYNTAX  INTEGER {
        operator (1),
        administrator (2),
	maintenance (3),
	provisioning (4),
	manufacturing (5)
    }
    MAX-ACCESS  read-create
    STATUS  current
    DESCRIPTION
        "This object corresponds to the access privilege
         of the user account.  1 = Operator, 2 = Administrator,
	 3 = maintenance, 4 = provisioning, 5 = manufacturing."
    ::= { sysDevUserAccountEntry 2 }

sysDevUserAccountUserPassword OBJECT-TYPE
    SYNTAX  DisplayString (SIZE(6..15))
    MAX-ACCESS  read-create
    STATUS  current
    DESCRIPTION
        "This object corresponds to the password of the
         user account."
    ::= { sysDevUserAccountEntry 3 }
 
sysDevUserAccountAccessPartition  OBJECT-TYPE
    SYNTAX  DisplayString (SIZE(0..50))
    MAX-ACCESS  read-create
    STATUS current
    DESCRIPTION
    "This object corresponds to the access partition of the
     user account. The default value of this object is 'all'"
    ::= { sysDevUserAccountEntry 4 }

sysDevUserAccountRowStatus OBJECT-TYPE
	SYNTAX  RowStatus
	MAX-ACCESS  read-create
	STATUS current
	DESCRIPTION
	"This object corresponds to create or delete a row in
	sysDevUserAccountTable."
    ::= {sysDevUserAccountEntry 5 }

-- A new user account config group is added
 
sysDevConfigUserAccountTable OBJECT-TYPE
    SYNTAX  SEQUENCE OF SysDevConfigUserAccountEntry
    MAX-ACCESS  not-accessible
    STATUS current
    DESCRIPTION
        "This table contains the user accounts."
    ::= { sysDevConfig 8}
 
sysDevConfigUserAccountEntry OBJECT-TYPE
    SYNTAX  SysDevConfigUserAccountEntry
    MAX-ACCESS  not-accessible
    STATUS  current
    DESCRIPTION
        "An entry containing user account information."
    INDEX { sysDevConfigUserAccountIndex }
    ::= { sysDevConfigUserAccountTable 1 }
 
SysDevConfigUserAccountEntry  ::= SEQUENCE {
    sysDevConfigUserAccountIndex   Integer32,
    sysDevConfigUserAccountUserId   DisplayString (SIZE(1..15)),
    sysDevConfigUserAccountPrivilegedPassword DisplayString (SIZE(0..15)),
    sysDevConfigUserAccountUserPassword DisplayString (SIZE(0..15)),
    sysDevConfigUserAccountRowStatus RowStatus
	}
 

 sysDevConfigUserAccountIndex OBJECT-TYPE
   SYNTAX Integer32
   MAX-ACCESS not-accessible
   STATUS current
   DESCRIPTION
     "The value of this object is an index of the account config
      table. This object is used by sysDevConfigUserAccountTable
      to identify the row in the table. When creating new
      row of this table the value of this object may be
      obtained by retreiving the value of
      sysDevConfigUserAccountIndexNext."
 ::= { sysDevConfigUserAccountEntry 1 }

sysDevConfigUserAccountUserId OBJECT-TYPE
    SYNTAX  DisplayString (SIZE(1..15))
    MAX-ACCESS  read-create
    STATUS current
    DESCRIPTION
        "This object corresponds to the login ID of the
         user account."
    ::= { sysDevConfigUserAccountEntry 2 }
 
sysDevConfigUserAccountPrivilegedPassword OBJECT-TYPE
    SYNTAX  DisplayString (SIZE(0..15))
    MAX-ACCESS  read-create
    STATUS current
    DESCRIPTION
        "This object corresponds to the access privilege password
         of the user account.  If user is configured
	 with this password in addition to a UserPassword 
	 than the user is Administrator. In a case that user
	 is Operator and does not supply this password 
	 upon user configuration this value should be null string"
    ::= { sysDevConfigUserAccountEntry 3 }

sysDevConfigUserAccountUserPassword OBJECT-TYPE
    SYNTAX  DisplayString (SIZE(0..15))
    MAX-ACCESS  read-create
    STATUS  current
    DESCRIPTION
        "This object corresponds to the password of the
         user account."
    ::= { sysDevConfigUserAccountEntry 4 }
 
sysDevConfigUserAccountRowStatus OBJECT-TYPE
	SYNTAX  RowStatus
	MAX-ACCESS  read-create
	STATUS  current
	DESCRIPTION
	"This object corresponds to create or delete a row in
	sysDevConfigUserAccountTable."
    ::= {sysDevConfigUserAccountEntry 5 }

 sysDevConfigUserAccountIndexNext OBJECT-TYPE
   SYNTAX  Integer32
   MAX-ACCESS  read-only 
   STATUS current
   DESCRIPTION
	" This object contains an appropriate value to be
	  used for sysDevConfigUserAccountTable.
	  The value of 0 indicates that no unassigned 
	  entries are available.  To obtain 
	  sysDevConfigUserAccountIndex value for the new entry 
	  the manager issues a management protocol retrieval 
	  operation to obtain a current value of this object.
	  After each retrieval, the agent should modify the value
	  to the next unassigned index.  "
 ::= { sysDevConfig 9 }

-- the sysDevIDSLConfig group on the MCC

sysDevIDSLConfigTable OBJECT-TYPE
   SYNTAX  SEQUENCE OF SysDevIDSLConfigEntry
   MAX-ACCESS  not-accessible
   STATUS  current
    DESCRIPTION
         "A table that contains configuration information about
          IDSL Card."
    ::= { sysDevConfig 6 }

sysDevIDSLConfigEntry OBJECT-TYPE
   SYNTAX  SysDevIDSLConfigEntry
   MAX-ACCESS  not-accessible
   STATUS current
   DESCRIPTION
         "A list of information for IDSL device Configuration."
   INDEX  { entPhysicalIndex }
    ::= { sysDevIDSLConfigTable 1 }

SysDevIDSLConfigEntry ::=
    SEQUENCE {
            sysDevIDSLConfigPrimaryNetClockMode  IdslClockMode,
            sysDevIDSLConfigSecondaryNetClockMode  IdslClockMode
             }

sysDevIDSLConfigPrimaryNetClockMode  OBJECT-TYPE
    SYNTAX IdslClockMode
    MAX-ACCESS read-create
    STATUS current
    DESCRIPTION
        "This object indicates the network clock mode set
    for the primary network clock. IDSL portcards with a
    port configured as an NT will be set to
    portCardDriveClockOnboard(4), both driving the backplane
    and using the clock for the other Local Timing transceivers
    on the card. Port cards with only LT ports configured will
    receive a clock from the backplane using portCardSinkClock(2).
    portCardDriveClock(3) will drive the backplane alone. The 
    default value of this object is triState(1)."
    DEFVAL { triState }
::= { sysDevIDSLConfigEntry 1 }

sysDevIDSLConfigSecondaryNetClockMode  OBJECT-TYPE
    SYNTAX IdslClockMode
    MAX-ACCESS read-create
    STATUS current
    DESCRIPTION
        "This object indicates the network clock mode set
    for the secondary network clock. IDSL portcards with a
    port configured as an NT will be set to
    portCardDriveClockOnboard(4), both driving the backplane
    and using the clock for the other Local Timing transceivers
    on the card. Port cards with only LT ports configured will
    receive a clock from the backplane using portCardSinkClock(2).
    portCardDriveClock(3) will drive the backplane alone. The 
    default value of this object is triState(1)."
    DEFVAL { triState }
::= { sysDevIDSLConfigEntry 2 }

-- The syslog Group
sysDevDslamSyslog OBJECT IDENTIFIER ::= { sysDevConfig 7 }

sysDevSyslogFtpServerXferStatsEnable OBJECT-TYPE
  SYNTAX SwitchState
  MAX-ACCESS read-write
  STATUS current
  DESCRIPTION
    "This object allows the network manager to enable and disable 
     syslog messages for FTP server file transfer statistics"
  DEFVAL { disabled }
::= { sysDevDslamSyslog 1 }

sysDevSyslogTftpServerXferStatsEnable OBJECT-TYPE
  SYNTAX SwitchState
  MAX-ACCESS read-write
  STATUS current
  DESCRIPTION
    "This object allows the network manager to enable and disable 
     syslog messages for TFTP server file transfer statistics"
  DEFVAL { disabled }
::= { sysDevDslamSyslog 2 }




--Traps

cCN NOTIFICATION-TYPE
  OBJECTS { ifIndex }
  STATUS		current
  DESCRIPTION
    "This trap signifies a Configuration change  or 
     software upgrade in the xDSL card. This trap 
     is of 'warning' class"
 ::= { sysDevDslamMIBTraps 7}

authenticationFailureTrap NOTIFICATION-TYPE
 OBJECTS { loginFailureAccessApp, loginFailureCount }
 STATUS		current
 DESCRIPTION 
  "This trap signifies an authentication  failure. 
   Authentication failures can be telnet based or 
  terminal based. This trap is in addition to the
  SNMP based authentication failure trap, which
  is a generic trap."
  ::= { sysDevDslamMIBTraps 8}

-- the following traps are sent by the MCC *******

 fanModuleFailure NOTIFICATION-TYPE
  STATUS		current
   DESCRIPTION
   "This trap indicates the indicates the failure of 
    the fan module on the device." 
 ::= {sysDevDslamMIBTraps 9}

 fanModuleOperational NOTIFICATION-TYPE
  STATUS		current
   DESCRIPTION
   "This trap indicates the indicates the fan module on the 
    device is operational."  
 ::=  {sysDevDslamMIBTraps 109}



 powerSourceAFailure NOTIFICATION-TYPE
   STATUS		current
   DESCRIPTION
     "This trap indicates that power source A
      has failed. This is sent only by the MCC card. This 
      trap is of 'minor' class."
 ::= {sysDevDslamMIBTraps 10}

 powerSourceAOperational NOTIFICATION-TYPE
   STATUS		current
   DESCRIPTION
     "This trap indicates that the power source A
      is operational. This is sent only by the MCC card. 
      This trap is of 'minor' class. This trap compliments
      powerSourceAFailure trap."
 ::={ sysDevDslamMIBTraps 110}

slotPollFailure NOTIFICATION-TYPE
  OBJECTS { entPhysicalIndex }
  STATUS		current
  DESCRIPTION
   "This trap indicates a slot poll failure.
    This is sent only by the MCC card. this trap is
    of 'major' class."
 ::=  { sysDevDslamMIBTraps 11}

 newCardDetected NOTIFICATION-TYPE
   OBJECTS { entPhysicalIndex }
   STATUS		current
   DESCRIPTION
   "This trap indicates that a new card was detected 
    in a slot. This is sent only by the MCC card. this trap
    is of 'warning' class."
 ::=  {sysDevDslamMIBTraps 111}

-- ****************************

 ethernetJabber NOTIFICATION-TYPE
   OBJECTS { ifIndex }
   STATUS		current
   DESCRIPTION
     "This trap indicates that a jabber condition  has been 
      detected on the ethernet interface. This trap is of 
      'major' class."
 ::=  { sysDevDslamMIBTraps 12}

 ethernetJabberClear NOTIFICATION-TYPE
 
   OBJECTS { ifIndex }
   STATUS		current
   DESCRIPTION
     "This trap indicates that the jabber condition that was 
      detected no longer exists. This trap is of 'major' 
      class."
 ::= { sysDevDslamMIBTraps 112}

 ethernetJumbos NOTIFICATION-TYPE
   OBJECTS { ifIndex }
   STATUS		current
   DESCRIPTION
     "This trap indicates ethernet jumbos. this trap
      is of 'minor' class"
 ::=   { sysDevDslamMIBTraps 13}

 ethernetRunts NOTIFICATION-TYPE
   OBJECTS { ifIndex }
   STATUS		current
   DESCRIPTION
     "This trap indicates ethernet runts. this trap is of 'minor'"
 ::=  {sysDevDslamMIBTraps 14}

 powerSourceBFailure NOTIFICATION-TYPE
   STATUS		current
   DESCRIPTION
     "This trap indicates that power source B
      has failed. This is sent only by the MCC card. This 
      trap is of 'minor' class."
 ::= { sysDevDslamMIBTraps 17}

 powerSourceBOperational NOTIFICATION-TYPE
   STATUS		current
   DESCRIPTION
     "This trap indicates that the power source B
      is operational. This is sent only by the MCC card. 
      This trap is of 'minor' class. This trap compliments
      powerSourceBFailure trap."
 ::=  {sysDevDslamMIBTraps 117}

 nonIpConservativeCardDetected NOTIFICATION-TYPE
   OBJECTS { entPhysicalIndex }
   STATUS		current
   DESCRIPTION
     "This trap indicates that a non ip conservative DSL card
      exist in the chassis at the slot 'slotNumber'.This is
      sent only by the MCC card. This trap is of warning class."
 ::={ sysDevDslamMIBTraps 18}

nonSupportedMCC NOTIFICATION-TYPE
  OBJECTS { sysObjectID }
  STATUS		current
  DESCRIPTION
    "AN has detected MCC firmware release too low to support
     this device"
::={ sysDevDslamMIBTraps 20 }

nonSupportedChassis NOTIFICATION-TYPE
  OBJECTS { sysObjectID }
  STATUS		current
  DESCRIPTION
    "AN in slot xx has been installed in a chassis that cannot
     support one or more of its features. "
::=  {sysDevDslamMIBTraps 21}

 fanEntityModuleFailure NOTIFICATION-TYPE
   OBJECTS { entPhysicalIndex }
  STATUS		current
   DESCRIPTION
   "This trap indicates the indicates the failure of 
    the fan module on the device." 
 ::= {sysDevDslamMIBTraps 22}

 fanEntityModuleOperational NOTIFICATION-TYPE
   OBJECTS { entPhysicalIndex }
  STATUS		current
   DESCRIPTION
   "This trap indicates the indicates the fan module on the 
    device is operational."  
 ::=  {sysDevDslamMIBTraps 122}
END

PDN-XDSL-INTERFACE-MIB DEFINITIONS ::= BEGIN

-- Version : 1.0
-- Added xdslDevGenericIfConfigSnType.
-- Removed unused IMPORTS to clear compile warnings.
-- Updated by Jesus A. Pinto, January 3th 2002

-- Version : 0.9
-- Changed description for xdslDevMVLSpecificIfConfigOnHookPowerAttenuation
-- to include new permissable values for this object as described by the
-- NMS Spec and as implemented.
-- Changed description for xdslDevMVLSpecificIfConfigOffHookPowerAttenuation
-- to include new permissable values for this object as described by the
-- NMS Spec and as implemented.
-- Updated by Jesus A. Pinto, June 29th 2001

-- Version : 0.8
-- deprecated xdslDevMVLSpecificIfConfigMaxPortSpeed
-- Added xdslDevMVLSpecificIfConfigMaxUpStreamPortSpeed
-- Added xdslDevMVLSpecificIfConfigMaxDownStreamPortSpeed
-- Changed the description for xdslDevMVLSpecificIfConfigMaxPortSpeed
-- Updated by Mohan Mohankumar, June 20th 2001

-- Version : 0.7
-- Added xdslDevGenericIfConfigLineEncapType
-- Updated by Dragana Gough, March 22nd 2001

-- Version : 0.6
-- Added xdslDevGenericIfConfigLineEncodeType
-- xdslDevMVLSpecificIfConfigOnHookPC and SN Voltage Drop ThresholdValue
-- restored xdslDevIDSLSpecificChannel
-- Updated by Dragana Gough, March 22nd 2001

-- Version :  0.5
-- Added xdslDevSDSLSpecificIfConfigMinSnrMargin in 
-- 	xdslDevSDSLSpecificIfConfigTable
-- Removed xdslDevGenericIfConfigMaxSnrMargin in xdslDevGenericIfConfigTable
-- Added xdslDevSDSLSpecificIfConfigTargetSnrMargin in 
--	xdslDevSDSLSpecificIfConfigTable
-- Updated by R.A.Bowhall, March 9th, 2001

-- Version :  0.4
-- Added xdslDevGenericIfConfigMinSnrMargin in xdslDevGenericIfConfigTable
-- Added xdslDevGenericIfConfigMaxSnrMargin in xdslDevGenericIfConfigTable
-- Added xdslDevGenericIfConfigTargetSnrMargin in xdslDevGenericIfConfigTable
-- Updated by R.A.Bowhall, March 8th, 2001

-- Version :  0.3
-- Added xdslLinkUpDownTransitions TRAP (under protest in that it already is defined
--       in the HOT MIB for Mirror objects)
-- Version :  0.2
-- Added xdslDevGenericIfConfigLineRateMode in xdslDevGenericIfConfigTable
-- Added xdslDevSDSLSpecificIfConfigFixedPortSpeedNx128Mode and
--       xdslDevSDSLSpecificIfConfigMaxPortSpeedNx128Mode
-- Updated by Z. Pan

-- Version :  0.1 DRAFT
-- Enterprise Time mib
-- Copyright (C) 1999 Paradyne Corporation.

-- Created by : Rajesh Gowda

IMPORTS
     
   DisplayString
    FROM SNMPv2-TC
   OBJECT-TYPE
     FROM RFC-1212
   TRAP-TYPE
     FROM RFC-1215
   ifIndex
     FROM RFC1213-MIB
   pdn-xdsl
     FROM PDN-HEADER-MIB
     ;

 xdslIfConfigMIBObjects        OBJECT IDENTIFIER ::= { pdn-xdsl 2 }
 xdslIfConfigMIBTraps          OBJECT IDENTIFIER ::= { pdn-xdsl 4 }
 xdslDevGenericIfConfig        OBJECT IDENTIFIER ::= { xdslIfConfigMIBObjects 1 }
 xdslDevRADSLSpecificIfConfig  OBJECT IDENTIFIER ::= { xdslIfConfigMIBObjects 2 }
 xdslDevMVLSpecificIfConfig    OBJECT IDENTIFIER ::= { xdslIfConfigMIBObjects 3 }
 xdslDevSDSLSpecificIfConfig   OBJECT IDENTIFIER ::= { xdslIfConfigMIBObjects 4 }
 xdslDevIDSLSpecificIfConfig   OBJECT IDENTIFIER ::= { xdslIfConfigMIBObjects 5 }

 -- The xdslDevGenericIfConfig group. Implementation of this group is
 -- mandatory for all type of DSL.

 xdslDevGenericIfConfigTable OBJECT-TYPE
   SYNTAX SEQUENCE OF XdslDevGenericIfConfigEntry
   ACCESS not-accessible
   STATUS mandatory
   DESCRIPTION
     "The xdslDevGenericIfConfigTable provides config information 
      generic to a xDSL device, or system. The table is indexed by an 
      object which corresponds to ifIndex. These ifIndex entries, 
      themselves, denote and identify specific xdsl interfaces on
      the board or module. Also the configuration parameters are
      grouped into two broad categories, 'up' and 'down'. 'up'
      reflects the upstream direction (from the customer premises
      to the central office). 'Down' reflects the downstream
      direction (from the central office to the customer premises)"
 ::= { xdslDevGenericIfConfig 1 }

 xdslDevGenericIfConfigEntry OBJECT-TYPE
   SYNTAX XdslDevGenericIfConfigEntry
   ACCESS not-accessible
   STATUS mandatory
   DESCRIPTION
     "Describes a specific xDSL interface entry."
   INDEX { ifIndex }
 ::= { xdslDevGenericIfConfigTable 1 }

 XdslDevGenericIfConfigEntry ::=
   SEQUENCE {
     xdslDevGenericIfConfigPortSpeedBehaviour
       INTEGER,
     xdslDevGenericIfConfigMarginThreshold 
       INTEGER,
     xdslDevGenericIfConfigPortID
       DisplayString (SIZE (1..40)),
     xdslDevGenericIfConfigLinkUpDownTransitionThreshold
       INTEGER,
     xdslDevGenericIfConfigLineEncodeType
       INTEGER,
     xdslDevGenericIfConfigLineRateMode
       INTEGER,
     xdslDevGenericIfConfigLinkEncapType
       INTEGER,
     xdslDevGenericIfConfigSnType
       OBJECT IDENTIFIER
  }

 xdslDevGenericIfConfigPortSpeedBehaviour OBJECT-TYPE
   SYNTAX INTEGER {
     fixed (1),
     adaptive (2)
   }
   ACCESS read-write
   STATUS mandatory
   DESCRIPTION
     "The value of this object corresponds to the
      behaviour of the specified port. The default
      value for this object is fixed (1). "
 ::= { xdslDevGenericIfConfigEntry 1 }

 xdslDevGenericIfConfigMarginThreshold OBJECT-TYPE
   SYNTAX INTEGER 
   ACCESS read-write
   STATUS mandatory
   DESCRIPTION
    "The value of this object corresponds to the offset from
     the startup margin. The threshold margin is calculated
     by subtracting the offset from the startup margin. 
     Permissible range of values are between -7 and 14.
     A value of -9999 disables the threshold check. The default
     value of this object is 3"
 ::= { xdslDevGenericIfConfigEntry 2 }

 xdslDevGenericIfConfigPortID OBJECT-TYPE
   SYNTAX DisplayString (SIZE (1..40))
   ACCESS read-write
   STATUS mandatory
   DESCRIPTION
     "The value of this object corresponds to  40 character
      information only field that identifies what the DSL
      port is connected to (Circuit ID, MDF location, 
      Customer name, etc.)"
 ::= { xdslDevGenericIfConfigEntry 3 }

 xdslDevGenericIfConfigLinkUpDownTransitionThreshold OBJECT-TYPE
   SYNTAX INTEGER
   ACCESS read-write
   STATUS mandatory
   DESCRIPTION
     "The value of this object corresponds to the threshold
      value for link up-down transitions. If link up-down's exceed
      this threshold value a xdslLinkupDownTransitions
      trap is generated. This value would represent the number
      of link up-down transitions in a 15 minute interval. A value
      of -9999 disables the threshold check. The default value for this
      object is 0"
 ::= { xdslDevGenericIfConfigEntry 4 }
 
 xdslDevGenericIfConfigLineEncodeType OBJECT-TYPE
   SYNTAX INTEGER {
       other  (1),
       cap    (2),
       twoB1q (3),
       mvl    (4),
       g-lite (5),
       dmt    (6)
    }
   ACCESS read-only
   STATUS mandatory
   DESCRIPTION
     "The value of this object corresponds to the line
      encoding technology used for data transmission over
      the the dsl link."
 ::= { xdslDevGenericIfConfigEntry 5 }
     
 xdslDevGenericIfConfigLineRateMode OBJECT-TYPE
   SYNTAX INTEGER {
       standard (1),
       nx128    (2)
    }
   ACCESS read-write
   STATUS mandatory
   DESCRIPTION
     "The value of this object is used to choose the line
      rate list for data transmission over the dsl link.
      The default value is standard(1). "
 ::= { xdslDevGenericIfConfigEntry 6 }

 xdslDevGenericIfConfigLinkEncapType OBJECT-TYPE
   SYNTAX INTEGER {
       linkNone   (1),
       ethernet   (2),
       ppp 	  (3),
       slip       (4),
       frameRelay-PLL (5),
       x23PVC    (6),
       x25SVC	  (7),
       hdlc      (8),
       etherHDLC  (9),
       rfc1483-MPOA (10),
       funi-MPOA    (11),
       frf5	  (12),
       frf8	  (13),
       pppoAVC-Mux (14),
       pppoALLC  (15)
    }
   ACCESS read-write
   STATUS mandatory
   DESCRIPTION
     "The value of this object corresponds to the link
      encapsulation type. Following are valid settings:
       linkNone   (1)
       ethernet   (2)
       ppp 	  (3)
       slip       (4)
       frameRelay-PLL (5)
       x23PVC    (6)
       x25SVC	  (7)
       hdlc      (8)
       etherHDLC  (9)
       rfc1483-MPOA (10)
       funi-MPOA    (11)
       frf5	  (12)
       frf8	  (13)
       pppoAVC-Mux (14)
       pppoALLC  (15) "
 ::= { xdslDevGenericIfConfigEntry 7 }

 xdslDevGenericIfConfigSnType OBJECT-TYPE
   SYNTAX OBJECT IDENTIFIER
   ACCESS read-write
   STATUS mandatory
   DESCRIPTION
     "The value of this object is used to choose a valid 
      Service Node Type to be configured in the port. The
      configurable values are the object identifiers of the
      remote endpoints as defined in the xdsl-remote group
      of the pdn-xdsl-products.
      The following are examples of valid endpoints for the
      8312 Reach port card:
	xdsl_6350,
	xdsl_6351,
	xdsl_6310
      By default, this object will be set to the default
      service node associated with the portcard."
 ::= { xdslDevGenericIfConfigEntry 8 }
 
 -- The xdslDevRADSLSpecificIfConfig group. Implementation of this
 -- group is mandatory for RADSL.

 xdslDevRADSLSpecificIfConfigTable OBJECT-TYPE
   SYNTAX SEQUENCE OF XdslDevRADSLSpecificIfConfigEntry
   ACCESS not-accessible
   STATUS mandatory
   DESCRIPTION
     "The xdslDevRADSLSpecificIfConfigTable provides config information
      specific to a xDSL device, or system. The table is indexed by
      an object which corresponds to ifIndex. These ifIndex entries, 
      themselves, denote and identify specific xdsl interfaces on
      the board or module. Also the configuration parameters are
      grouped into two broad categories, 'up' and 'down'. 'up'
      reflects the upstream direction (from the customer premises
      to the central office). 'Down' reflects the downstream
      direction (from the central office to the customer premises)"
 ::= { xdslDevRADSLSpecificIfConfig 1 }

 xdslDevRADSLSpecificIfConfigEntry OBJECT-TYPE
   SYNTAX XdslDevRADSLSpecificIfConfigEntry
   ACCESS not-accessible
   STATUS mandatory
   DESCRIPTION
     "Describes a specific xDSL interface entry."
   INDEX { ifIndex }
 ::= { xdslDevRADSLSpecificIfConfigTable 1 }

 XdslDevRADSLSpecificIfConfigEntry ::=
   SEQUENCE {
     xdslDevRADSLSpecificIfConfigUpFixedPortSpeed 
       INTEGER,
     xdslDevRADSLSpecificIfConfigDownFixedPortSpeed 
       INTEGER,
     xdslDevRADSLSpecificIfConfigUpAdaptiveUpperBoundPortSpeed 
       INTEGER,
     xdslDevRADSLSpecificIfConfigUpAdaptiveLowerBoundPortSpeed 
       INTEGER,
     xdslDevRADSLSpecificIfConfigDownAdaptiveUpperBoundPortSpeed 
       INTEGER,
     xdslDevRADSLSpecificIfConfigDownAdaptiveLowerBoundPortSpeed 
       INTEGER,
     xdslDevRADSLSpecificIfConfigReedSolomonDownFwdErrCorrection 
       INTEGER,
     xdslDevRADSLSpecificIfConfigStartUpMargin
       INTEGER (-3..9),
     xdslDevRADSLSpecificIfConfigTxPowerAttenuation
       INTEGER,
     xdslDevRADSLSpecificIfConfigSnTxPowerAttenuation
       INTEGER
  }

 xdslDevRADSLSpecificIfConfigUpFixedPortSpeed OBJECT-TYPE
   SYNTAX INTEGER 
   ACCESS read-write
   STATUS mandatory
   DESCRIPTION
     "The value of this object corresponds to the upstream
      speed of the specified port for fixed port speed
      behaviour. All the speeds are in kbps.
      If the port speed behaviour is adaptive an error
      of noSuchName will be returned by the agent."
 ::= { xdslDevRADSLSpecificIfConfigEntry 1 }

 xdslDevRADSLSpecificIfConfigDownFixedPortSpeed OBJECT-TYPE
   SYNTAX INTEGER
   ACCESS read-write
   STATUS mandatory
   DESCRIPTION
     "The value of this object corresponds to the downstream
      speed of the specified port for fixed port speed
      behaviour. All the speeds are in kbps. 
      If the port speed behaviour is adaptive an error of noSuchName
      will be returned by the agent.  "
 ::= { xdslDevRADSLSpecificIfConfigEntry 2 }

 xdslDevRADSLSpecificIfConfigUpAdaptiveUpperBoundPortSpeed OBJECT-TYPE
   SYNTAX INTEGER
   ACCESS read-write
   STATUS mandatory
   DESCRIPTION
     "The value of this object corresponds to the 
      upper bound for the upstream port speed of the specified port
      for adaptive port speed behaviour. The speeds are measured
      in kbps. If the port speed behaviour is fixed
      an error of noSuchName will be returned by the agent."
 ::= { xdslDevRADSLSpecificIfConfigEntry 3 }

 xdslDevRADSLSpecificIfConfigUpAdaptiveLowerBoundPortSpeed OBJECT-TYPE
   SYNTAX INTEGER
   ACCESS read-write
   STATUS mandatory
   DESCRIPTION
     "The value of this object corresponds to the
      lower bound for the upstream port speed of the 
      specified port for adaptive port speed behaviour
      in kbps. If the port speed behaviour is fixed an 
	  error of noSuchName will be returned by the agent.  
	  The value -9999 should be used to disable the lower
      bound threshold check. The default value for this 
	  object is -9999 "
 ::= { xdslDevRADSLSpecificIfConfigEntry 4 }

 xdslDevRADSLSpecificIfConfigDownAdaptiveUpperBoundPortSpeed OBJECT-TYPE
   SYNTAX INTEGER
   ACCESS read-write
   STATUS mandatory
   DESCRIPTION
     "The value of this object corresponds to 
      the upper bound allowed for the downstream port speed 
      of the specified port for adaptive port speed 
      behaviour. The speeds are measured in kbps. 
      If the port speed behaviour is fixed an error of noSuchName
      will be returned by the agent."
 ::= { xdslDevRADSLSpecificIfConfigEntry 5 }

 xdslDevRADSLSpecificIfConfigDownAdaptiveLowerBoundPortSpeed OBJECT-TYPE
   SYNTAX INTEGER
   ACCESS read-write
   STATUS mandatory
   DESCRIPTION
     "The value of this object corresponds to the
      Minimum lower bound allowed for the downstream port speed 
      of the specified port for adaptive port speed behaviour.
      If the port speed behaviour is fixed an error of noSuchName
      will be returned by the agent.  The speeds are measured in kbps.
      The value -9999 is used to disable the lower bound threshold 
      check.The default value for this object is -9999"
 ::= { xdslDevRADSLSpecificIfConfigEntry 6 }

 xdslDevRADSLSpecificIfConfigReedSolomonDownFwdErrCorrection OBJECT-TYPE
   SYNTAX INTEGER {
     minimizeError (1),
     minimizeDelay (2),
     reedSolomonNotSupported(3)
   }
   ACCESS read-write
   STATUS mandatory
   DESCRIPTION
     "The value of this object corresponds to the
      Reed-Solomon forward error correction in the downstream
      direction. The default value of this object should be 
      minimizeError (1)."
 ::= { xdslDevRADSLSpecificIfConfigEntry 7 }

 xdslDevRADSLSpecificIfConfigStartUpMargin OBJECT-TYPE
   SYNTAX INTEGER (-3..9)
   ACCESS read-write
   STATUS mandatory
   DESCRIPTION
     " The value of this object corresponds to the startup value
       of the margin for a DSL interface (specified by ifIndex).
       The unit is db (decibels. The higher the margin the better
       the quality of the line. The default value of this object is 3."
 ::= { xdslDevRADSLSpecificIfConfigEntry 8 }

 xdslDevRADSLSpecificIfConfigTxPowerAttenuation OBJECT-TYPE
   SYNTAX INTEGER
   ACCESS read-write
   STATUS mandatory
   DESCRIPTION
     " This value corresponds to the Transmitt Power Attenuation in
       dB for the access node. This value represents the downstream
       power level in dB. Permissible values are -6, -3 and 0.
       The default value of this object is 0 dB. The power levels +3
       and +6 may be used in future."
 ::= { xdslDevRADSLSpecificIfConfigEntry 9 }

 xdslDevRADSLSpecificIfConfigSnTxPowerAttenuation OBJECT-TYPE
   SYNTAX INTEGER
   ACCESS read-write
   STATUS mandatory
   DESCRIPTION
     " This value corresponds to the Transmitt Power Attenuation in dB
       for the service node. This value represents the upstream power
       level in dB. Permissible values are -9, -6, -3 and 0. The 
       default value of this object is -6 dB."

 ::= { xdslDevRADSLSpecificIfConfigEntry 10 }

 -- The xdslDevMVLSpecificConfig group. Implementation of this group is
 -- mandatory for MVL 

 xdslDevMVLSpecificIfConfigTable OBJECT-TYPE
   SYNTAX SEQUENCE OF XdslDevMVLSpecificIfConfigEntry
   ACCESS not-accessible
   STATUS mandatory
   DESCRIPTION
     "The xdslDevMVLSpecificIfConfigTable provides config information specific 
      to a xDSL(MVL) device, or system. The table is indexed by an 
      object which corresponds to ifIndex. These ifIndex entries, 
      themselves, denote and identify specific xdsl(Mvl) interfaces on
      the board or module. "
 ::= { xdslDevMVLSpecificIfConfig 1 }

 xdslDevMVLSpecificIfConfigEntry OBJECT-TYPE
   SYNTAX XdslDevMVLSpecificIfConfigEntry
   ACCESS not-accessible
   STATUS mandatory
   DESCRIPTION
     "Describes a specific xDSL(MVL) interface entry."
   INDEX { ifIndex }
 ::= { xdslDevMVLSpecificIfConfigTable 1 }

 XdslDevMVLSpecificIfConfigEntry ::=
   SEQUENCE {
     xdslDevMVLSpecificIfConfigMaxPortSpeed 
       INTEGER,
     xdslDevMVLSpecificIfConfigOnHookTxPowerAttenuation
       INTEGER,
     xdslDevMVLSpecificIfConfigOffHookTxPowerAttenuation
       INTEGER,
     xdslDevMVLSpecificIfConfigOnHookPCVoltageDropThresholdValue
       INTEGER,
     xdslDevMVLSpecificIfConfigOnHookSNVoltageDropThresholdValue
       INTEGER,
     xdslDevMVLSpecificIfConfigMaxDownStreamPortSpeed
       INTEGER,
     xdslDevMVLSpecificIfConfigMaxUpStreamPortSpeed
       INTEGER
  }

 xdslDevMVLSpecificIfConfigMaxPortSpeed OBJECT-TYPE
   SYNTAX INTEGER 
   ACCESS read-write
   STATUS deprecated
   DESCRIPTION
     "The value of this object corresponds to the upper bound 
      port speed of the specified port. The speeds are measured 
      in kbps.
      Prior to GrandSlam 2.3, this object was used for both upstream and downstream
      port speeds. Now there are 2 new objects created for downstream and upstream
      port speeds. 
      Setting this value will also set the same value for the objects
      xdslDevMVLSpecificIfConfigMaxDownStreamPortSpeed and
      xdslDevMVLSpecificIfConfigMaxUpStreamPortSpeed."

 ::= { xdslDevMVLSpecificIfConfigEntry 1 }

 xdslDevMVLSpecificIfConfigOnHookTxPowerAttenuation OBJECT-TYPE
   SYNTAX INTEGER
   ACCESS read-write
   STATUS mandatory
   DESCRIPTION
     " This value corresponds to the On-hook Transmitt Power Attenuation 
       in dB for the access node and the service node. This value represents
       both downstream and upstream power level in dB while the phone is
       On-hook. Permissible values are -2, 1, 4, 7, 10, and +12. The
       default value of this object is 12 dB."
 ::= { xdslDevMVLSpecificIfConfigEntry 2 }

 xdslDevMVLSpecificIfConfigOffHookTxPowerAttenuation OBJECT-TYPE
   SYNTAX INTEGER
   ACCESS read-write
   STATUS mandatory
   DESCRIPTION
     " This value corresponds to the Off-hook Transmitt Power Attenuation 
       in dB for the access node and the service node. This value represents
       both downstream and upstream power level in dB while the phone is
       Off-hook. Permissible values are -11, -8, -5, -2, 1, 4, 7, 10
       and +12. The default value of this object is 12 dB. "
 ::= { xdslDevMVLSpecificIfConfigEntry 3 }

 xdslDevMVLSpecificIfConfigOnHookPCVoltageDropThresholdValue OBJECT-TYPE
   SYNTAX INTEGER
   ACCESS read-write
   STATUS mandatory
   DESCRIPTION
	"This value correspond to the portcard Voltage Drop
	 Threshold Value and valid settings are 0 and 6.
	 If the corresponding value at the endpoint is
	 set for Max (255) than only valid value for this
	 object is 0. This only applies for MVL configuration
	 If Reach configuration is used only valid value is 6
	 which is a default value."
 ::= { xdslDevMVLSpecificIfConfigEntry 4 }

 xdslDevMVLSpecificIfConfigOnHookSNVoltageDropThresholdValue OBJECT-TYPE
   SYNTAX INTEGER
   ACCESS read-write
   STATUS mandatory
   DESCRIPTION
	"This corresponds to the endpoint Voltage Drop
	Threshold Value and valid settings are 17, 34 and 255(Max).
	If Reach is used than only valid value is 34 - default."
	
 ::= { xdslDevMVLSpecificIfConfigEntry 5 }

 xdslDevMVLSpecificIfConfigMaxDownStreamPortSpeed OBJECT-TYPE
   SYNTAX INTEGER 
   ACCESS read-write
   STATUS mandatory
   DESCRIPTION
     "The value of this object corresponds to the upper bound downstream
      port speed of the specified port. The speeds are measured 
      in kbps.
      Setting the value of this object will also set the same value to the object
      xdslDevMVLSpecificIfConfigMaxPortSpeed.
      Prior to GrandSlam 2.3, the object xdslDevMVLSpecificIfConfigMaxPortSpeed 
      was used for both upstream and downstream port speeds. Now there are 
      two different objects for upstream and downstream port speeds."
      
 ::= { xdslDevMVLSpecificIfConfigEntry 6 }
      
 xdslDevMVLSpecificIfConfigMaxUpStreamPortSpeed OBJECT-TYPE
   SYNTAX INTEGER 
   ACCESS read-write
   STATUS mandatory
   DESCRIPTION
     "The value of this object corresponds to the upper bound upstream
      port speed of the specified port. The speeds are measured 
      in kbps.
      Prior to GrandSlam 2.3, the object MaxPortSpeed was used for both upstream 
      and downstream port speeds. Now there are two different objects for
      upstream and downstream port speeds."
      
 ::= { xdslDevMVLSpecificIfConfigEntry 7 }


 -- The xdslDevSDSLSpecificIfConfig group. Implementation of this group is
 -- mandatory for SDSL 

 xdslDevSDSLSpecificIfConfigTable OBJECT-TYPE
   SYNTAX SEQUENCE OF XdslDevSDSLSpecificIfConfigEntry
   ACCESS not-accessible
   STATUS mandatory
   DESCRIPTION
     "The xdslDevSDSLSpecificIfConfigTable provides configuration 
      specific to the SDSL link."
 ::= { xdslDevSDSLSpecificIfConfig 1 }

 xdslDevSDSLSpecificIfConfigEntry OBJECT-TYPE
   SYNTAX XdslDevSDSLSpecificIfConfigEntry
   ACCESS not-accessible
   STATUS mandatory
   DESCRIPTION
     "Describes a specific SDSL configuration entry."
   INDEX { ifIndex }
 ::= { xdslDevSDSLSpecificIfConfigTable 1 }

 XdslDevSDSLSpecificIfConfigEntry ::=
   SEQUENCE {
     xdslDevSDSLSpecificIfConfigFixedPortSpeed
       INTEGER,
    xdslDevSDSLSpecificIfConfigMaxPortSpeed
       INTEGER,
    xdslDevSDSLSpecificIfConfigFixedPortSpeedNx128Mode
       INTEGER,
    xdslDevSDSLSpecificIfConfigMaxPortSpeedNx128Mode
       INTEGER,
    xdslDevSDSLSpecificIfConfigMinSnrMargin
       INTEGER,
    xdslDevSDSLSpecificIfConfigTargetSnrMargin
       INTEGER
 }

 xdslDevSDSLSpecificIfConfigFixedPortSpeed OBJECT-TYPE
   SYNTAX INTEGER
   ACCESS read-write
   STATUS mandatory
   DESCRIPTION
     "The value of this object corresponds to both upstream
      and downstream speed of the specified port. All the
      speeds are in kbps. The value of this  object is used
      only when the port behaviour is fixed."
 ::= { xdslDevSDSLSpecificIfConfigEntry 1 }

 xdslDevSDSLSpecificIfConfigMaxPortSpeed OBJECT-TYPE
   SYNTAX INTEGER
   ACCESS read-write
   STATUS mandatory
   DESCRIPTION
     "The value of this object corresponds to the upper bound
      port speed of the specified port when the port behaviour
      is adaptive. The speeds are measured in kbps."
 ::= { xdslDevSDSLSpecificIfConfigEntry 2 }

 xdslDevSDSLSpecificIfConfigFixedPortSpeedNx128Mode OBJECT-TYPE
   SYNTAX INTEGER (0..2147483647)
   ACCESS read-write
   STATUS mandatory
   DESCRIPTION
     "The value of this object applies to both upstream
      and downstream speed of the specified port when the 
      line rate mode is configured as Nx128 mode. All the 
      speeds are in kbps. The value of this object is used
      only when the port behaviour is fixed and the line rate
      is Nx128 mode, and doesn't take effect in the standard mode."
 ::= { xdslDevSDSLSpecificIfConfigEntry 3 }

 xdslDevSDSLSpecificIfConfigMaxPortSpeedNx128Mode OBJECT-TYPE
   SYNTAX INTEGER (0..2147483647)
   ACCESS read-write
   STATUS mandatory
   DESCRIPTION
     "The value of this object corresponds to the upper bound
      port speed of the specified port when the port behaviour
      is adaptive and the line rate is Nx128 mode, and doesn't
      take effect in the standard mode. The speeds are measured
      in kbps."
 ::= { xdslDevSDSLSpecificIfConfigEntry 4 }

 xdslDevSDSLSpecificIfConfigMinSnrMargin OBJECT-TYPE
   SYNTAX INTEGER (0..15)
   ACCESS read-write
   STATUS mandatory
   DESCRIPTION
        "Configured Minimum acceptable Signal/Noise Margin."
 ::= { xdslDevSDSLSpecificIfConfigEntry 5 }

 xdslDevSDSLSpecificIfConfigTargetSnrMargin OBJECT-TYPE
   SYNTAX INTEGER (0..15)
   ACCESS read-write
   STATUS mandatory
   DESCRIPTION
        "Configured Target Signal/Noise Margin."
 ::= { xdslDevSDSLSpecificIfConfigEntry 6 }
 
 -- The xdslDevIDSLSpecificIfConfig group. Implementation of this group is
 -- mandatory for IDSL 

 xdslDevIDSLSpecificIfConfigTable OBJECT-TYPE
   SYNTAX SEQUENCE OF XdslDevIDSLSpecificIfConfigEntry
   ACCESS not-accessible
   STATUS mandatory
   DESCRIPTION
     "The xdslDevIDSLSpecificIfConfigTable provides configuration 
      specific to the IDSL link."
 ::= { xdslDevIDSLSpecificIfConfig 1 }

 xdslDevIDSLSpecificIfConfigEntry OBJECT-TYPE
   SYNTAX XdslDevIDSLSpecificIfConfigEntry
   ACCESS not-accessible
   STATUS mandatory
   DESCRIPTION
     "Describes a specific IDSL configuration entry."
   INDEX { ifIndex }
 ::= { xdslDevIDSLSpecificIfConfigTable 1 }

 XdslDevIDSLSpecificIfConfigEntry ::=
   SEQUENCE {
     xdslDevIDSLSpecificIfConfigPortSpeed
       INTEGER,
     xdslDevIDSLSpecificIfConfigTimingPortTransceiverMode
       INTEGER,
     xdslDevIDSLSpecificChannel
       INTEGER
 }

 xdslDevIDSLSpecificIfConfigPortSpeed OBJECT-TYPE
   SYNTAX INTEGER
   ACCESS read-write
   STATUS mandatory
   DESCRIPTION
     "The value of this object corresponds to both upstream
      and downstream speed of the specified port. All the
      speeds are in kbps. Allowed speeds are 64, 128 and 144
      kbps. The default value for this object is 128 kbps."
 ::= { xdslDevIDSLSpecificIfConfigEntry 1 }

 xdslDevIDSLSpecificIfConfigTimingPortTransceiverMode OBJECT-TYPE
   SYNTAX INTEGER {
          networkTiming (1),
          localTiming (2)
   }
   ACCESS read-write
   STATUS mandatory
   DESCRIPTION
     "The transceiver mode selected on the timing source port.
      Only one IDSL port can be set to NT mode. This timing
      will then be distributed to all other IDSL ports in the
      chassis that are set to LT.

      The selected xdslDevIDSLPrimaryTimingSourcePort provides clocking
      signals to the DSLAM when the transceiver mode is set to Network
      timing. The port selected for Network Timing mode will probably not
      used for customer data, but will receive a 2.048 Mhz Network clocking
      signal from a central office timing source and distribute this timing
      to other IDSL port cards."
 ::= { xdslDevIDSLSpecificIfConfigEntry 2 }

 xdslDevIDSLSpecificChannel	OBJECT-TYPE
   SYNTAX INTEGER {
          b1 (1),
          b2 (2),
	  noOp (3)
   }
   ACCESS read-write
   STATUS mandatory
   DESCRIPTION
	" The channel type for 64 Kbps. Default value is B1."
 ::= { xdslDevIDSLSpecificIfConfigEntry 3 }
 -- Trap definitions
 -- All traps sent from the DSL cards will have the MCC card's address 
 -- (in the NAP domain) in the ip-address field of the TRAP PDU.

-- NOTE: This trap obsoletes the xdslLinkUpDownTransitions trap of hot_xdsl.mib
xdslLinkUpDownTransitions TRAP-TYPE
   ENTERPRISE xdslIfConfigMIBTraps
   VARIABLES { ifIndex }
   DESCRIPTION
     "This trap signifies that the sending protocol
      entity recognizes that one of the xDSL communication 
      links is in a fluctuating state."
 ::= 1

END

PDN-DEVICE-TIME-MIB DEFINITIONS ::= BEGIN

-- Last Updated: 6/3/02

-- Enterprise Time MIB
-- Copyright (C) 1999-2002 Paradyne Corporation.

-- Created by : Prakash Easwar

-- REVISION HISTORY:
-- Date of Chg  Revision (Most Recent First)                            By
--
-- 06/03/02     Removed unneeded devNTPIf object.                       alfano
-- 05/07/02     Added new objects for SNTP support.  Changed/corrected  alfano
--              existing object descriptions to reflect SNTP support.
--

IMPORTS
IpAddress
FROM RFC1155-SMI
OBJECT-TYPE
FROM RFC-1212
DateAndTime
FROM SNMPv2-TC
NTPMode
FROM PDN-TC
pdn-time
FROM PDN-HEADER-MIB

;
devTimeMIBObjects       OBJECT IDENTIFIER ::= { pdn-time 1 }
devTimeMIBTraps         OBJECT IDENTIFIER ::= { pdn-time 2 }
devTimeAndDate          OBJECT IDENTIFIER ::= { devTimeMIBObjects 1 }
devNTP                  OBJECT IDENTIFIER ::= { devTimeMIBObjects 2 }


-- Time And Date Group

devDateAndTime OBJECT-TYPE
    SYNTAX  DateAndTime
    ACCESS  read-write
    STATUS  mandatory
    DESCRIPTION
       "This object displays the date and time on the entity.
       It allows an NMS to set the date and time in the appropriate
       timezone."
    ::= { devTimeAndDate 1 }

-- [S]NTP ([Simple] Network Time Protocol) group

devNTPServerIP OBJECT-TYPE
    SYNTAX  IpAddress
    ACCESS  read-write
    STATUS  mandatory
    DESCRIPTION
        "The IP address of the NTP/SNTP server."
    ::= { devNTP 1 }

devNTPMode OBJECT-TYPE
    SYNTAX  NTPMode
    ACCESS  read-write
    STATUS  mandatory
    DESCRIPTION
        "This object allows an NMS to configure the mode in which NTP/SNTP
        will operate.  In unicast(1) mode, NTP/SNTP polls the server
        specified via the devNTPServerIP object.  In broadcast(2) mode,
        NTP/SNTP polls by broadcasting a request so that any NTP/SNTP
        server could respond.  Alternatively, in broadcast(2) mode, the
        client only listens for messages broadcasted by any server.  In
        multicast(3) mode, the client listens for messages from any server
        sent to the multicast group defined for NTP/SNTP (224.0.1.1).
        Default value is broadcast(2)."
    ::= { devNTP 2 }

devNTPSynchronised OBJECT-TYPE
    SYNTAX  INTEGER (1 .. 24)
    ACCESS  read-write
    STATUS  mandatory
    DESCRIPTION
        "This object allows an NMS to configure the poll interval (hours)    
        for the NTP/SNTP client to use to send requests to an NTP/SNTP
        server to synchronize the local clock for the device.
        Default value is 1 hour."
    ::= { devNTP 3 }

devNTPEnable OBJECT-TYPE
    SYNTAX  INTEGER { enabled(1), disabled(2) }
    ACCESS  read-write
    STATUS  mandatory
    DESCRIPTION
        "Indicates whether or not the local clock is synchronized
        via NTP/SNTP.  When set to enabled(1), NTP/SNTP is operational
        and will attempt to synchronize the local clock based on the
        message(s) received from an NTP/SNTP server.
        Default value is enabled(1)."
    ::= { devNTP 4 }

devNTPOffsetFromUTC OBJECT-TYPE
    SYNTAX  INTEGER
    ACCESS  read-write
    STATUS  mandatory
    DESCRIPTION
        "Offset (minutes) from the coordinated universal time (UTC), also
        known as Greenwich mean time (GMT), to local time represented as a
        signed integer.  The sign of the integer denotes the direction of local
        time from UTC (e.g., offsets for local times west of the zero meridian
        to the international date line are negative).
        Default value is 0 (i.e., at UTC)."
    ::= { devNTP 5 }

END

--
-- Copyright (C) 2003 Paradyne Corporation.
--
PDN-SYSLOG-MIB DEFINITIONS ::= BEGIN 

IMPORTS 
	MODULE-IDENTITY, OBJECT-TYPE, Integer32, IpAddress
	 FROM SNMPv2-SMI
	entPhysicalIndex
	FROM ENTITY-MIB
	MODULE-COMPLIANCE, OBJECT-GROUP
        FROM SNMPv2-CONF
	pdn-syslog
          FROM PDN-HEADER-MIB; 

    pdnSyslog MODULE-IDENTITY 
        LAST-UPDATED "200302130000Z" -- February 13, 2003
        ORGANIZATION "Paradyne Networks
                      MIB Working Group"
                     
        CONTACT-INFO "Paradyne Networks, Inc. 
                      8545 126th Avenue North 
                      Largo, FL 33733 
                      www.paradyne.com 
		      
                      General Comments to: mibwg_team@eng.paradyne.com 
                      Editor: Dragana Gough 	- Original Author
		      Editor: Mike Himelstein 	- Updated Mib
		      Editor: Jesus Pinto 	- Updated Mib
                      " 
	DESCRIPTION "1)Added pdnEntitySyslogTable to be used for entities
	             2)Added conformance statements."
        REVISION "200302130000Z" -- February 13, 2003

	DESCRIPTION "4 changes:
	             1)Add to the description of pdnSyslogIpAddr
	             2)Rewording the description of pdnSyslogNumber.
	             3)Expanding the pdnSyslogMessage size from 255 to
			       1024
		     4)Adding a new object: pdnSyslogRateLimiting"
		     
        REVISION "200111150000Z" -- November 15, 2001
	DESCRIPTION "Changing pdn-common 31 to pdn-syslog 1"
        REVISION "200104100000Z" -- October 4, 2001
        DESCRIPTION 
	     "Added new object pdnSyslogMsgToConsole, and
	      changed comments to reflects the change status of a referenced
	      ietf draft. This draft ( draft-ietf-syslog-syslog-12)
	      is now RFC 3164."

        REVISION "200108090000Z" -- August 9, 2001
        DESCRIPTION 
	    "This mib defines a collection of objects  for managing 
	     syslog messages.  The objects are used to configure both syslog 
	     functions and syslog daemons.
	     This mib also allows one to retrieve syslog message
	     from a device. 
             The modifications to this mib include
	     * making mib snmp v2
	     * deprecated pdnSyslogLevel
             * adding pdnSyslogSeverityThreshold
             * adding pdnSyslogRemoteDaemon
             * adding pdnSyslogTable
             * adding pdnSyslogNumOfMsgInTable 
             * adding pdnSyslogMaxTableSize
             * adding pdnSyslogClearTable"

        REVISION "200004240000Z" -- April 24, 2000
        DESCRIPTION "Editor: Dragana Gough
                     Initial Version" 
        REVISION "200002050000Z"   -- May 02, 2000
        DESCRIPTION "Editor: Dragana Gough
                     Updated OBJECT IDENTIFIER to pdn-syslog" 
	::= { pdn-syslog 1 }

pdnSyslogConformance OBJECT IDENTIFIER ::= 
	{ pdn-syslog 14 }

--+++++++++++++++++++++++++++++++++++++++++++++++++++++++++++++++++++++++++++++

-- Syslog Configuration Group
pdnSyslogStatus  OBJECT-TYPE
    SYNTAX       INTEGER { disable (1), enable (2) }
    MAX-ACCESS   read-write
    STATUS       current
    DESCRIPTION
		 " This value allows user to
		 disable or enable syslog event generation. "
    ::= { pdnSyslog 1 }

pdnSyslogIPAddr  OBJECT-TYPE
    SYNTAX       IpAddress
    MAX-ACCESS   read-write
    STATUS       current
    DESCRIPTION
		 " This value is the IP address of a syslog server.
		 If the ip address is known then this can be used for
		 the remote syslog daemon" 
    ::= { pdnSyslog 2 }

-- The following object has been deprecated
-- It is still valid on older products that use this mib, 
--     i.e. DSL Router endpoints
-- All new products should use pdnSyslogSeverityThreshold which uses 
-- the severity values in the RFC 3164

pdnSyslogLevel   OBJECT-TYPE
    SYNTAX       INTEGER 
                 {  emerg (1), err   (2), norm  (3), info  (4) }
    MAX-ACCESS   read-write
    STATUS       deprecated
    DESCRIPTION
		" This value corresponds to a minimum severity level
		of events that will be logged.  "
    DEFVAL { norm }
    ::= { pdnSyslog 3 }

    
pdnSyslogPort    OBJECT-TYPE
    SYNTAX       Integer32 
    MAX-ACCESS   read-write
    STATUS       current
    DESCRIPTION
		 "This value corresponds to a UDP port number to which
		  system events are sent. The default is 514. "
    DEFVAL { 514 }
    ::= { pdnSyslog 4 }

-- The extension to this mib are below, they include the 
-- * pdnSyslogSeverityThreshold
-- * pdnSyslogRemoteDaemon
-- * pdnSyslogTable
-- * pdnSyslogNumOfMsgInTable 
-- * pdnSyslogMaxTableSize
-- * pdnSyslogClearTable
-- * pdnSyslogMsgToConsole 
	
pdnSyslogSeverityThreshold OBJECT-TYPE
    SYNTAX       INTEGER 
                 { 
                    emerg     (0),
                    alert     (1),
                    critical  (2),
                    error     (3),
                    warning   (4),
                    notice    (5),
                    info      (6),
                    debug     (7)
		 }
    MAX-ACCESS   read-write
    STATUS       current
    DESCRIPTION
		"This value corresponds to a minimum severity level
		 that a syslog messages can be set.  All syslog message
		 with an enum value greater than the threshold will not be
		 sent.  The values are obtain from the 
		 RFC 3164 The BSD Syslog Protocol:
		 
		 emerg    (0) - Emergency: system is unusable
		 alert    (1) - Alert: action must be taken immediately
		 critical (2) - Critical: critical conditions
		 error    (3) - Error: error conditions 
		 warning  (4) - Warning: warning conditions
		 notice   (5) - Notice: normal but significant condition
		 info     (6) - Informational: informational messages
		 debug    (7) - Debug: debug-level messages

		 For a more complete description of the severity levels, 
		 please reference your Operation Specification Manual
		 for details pertaining to that product."
    ::= { pdnSyslog 5 }

pdnSyslogRemoteDaemon OBJECT-TYPE
    SYNTAX       INTEGER { disable (1), enable (2) }
    MAX-ACCESS   read-write
    STATUS       current
    DESCRIPTION
		 "This value allows user to
		  disable or enable syslog messages going to a remote daemon."
    ::= { pdnSyslog 6 }
 
--
-- Syslog Table and supporting objects.
--

pdnSyslogTable   OBJECT-TYPE
    SYNTAX       SEQUENCE OF PdnSyslogEntry
    MAX-ACCESS   not-accessible
    STATUS       current
    DESCRIPTION
                 "This table supports retrieval of the syslog messages."
    ::= { pdnSyslog 7 }

pdnSyslogEntry   OBJECT-TYPE 
    SYNTAX       PdnSyslogEntry
    MAX-ACCESS   not-accessible
    STATUS       current
    DESCRIPTION
	        "An entry in the pdnSyslogTable."
    INDEX { pdnSyslogNumber }
    ::= { pdnSyslogTable 1 }

PdnSyslogEntry ::=
    SEQUENCE
    {
	pdnSyslogNumber        Integer32,
	pdnSyslogMessage       OCTET STRING
    }

pdnSyslogNumber  OBJECT-TYPE
    SYNTAX       Integer32
    MAX-ACCESS   not-accessible
    STATUS       current
    DESCRIPTION
	         "This is a sequentially increasing index of syslog messages
                  starting at 1.  When the table reaches its maximum size
		  (as defined by pdnSyslogMaxTableSize) then the oldest 
		  message will be dropped without renumbering any messages 
		  that remain.  The index is reset to 1 on a device reset or 
		  when the table is cleared (using pdnSyslogClearTable)."	
    ::= { pdnSyslogEntry 1}

pdnSyslogMessage OBJECT-TYPE
    SYNTAX       OCTET STRING(SIZE(1024))
    MAX-ACCESS   read-only
    STATUS       current
    DESCRIPTION
		 "The text of the syslog message."
    ::= { pdnSyslogEntry 2 }

--
-- Entity syslog table and supporting objects.
--
-- This table should be used in a system that
-- needs to clasify syslog messages per entities.
--

pdnEntitySyslogTable   OBJECT-TYPE
    SYNTAX       SEQUENCE OF PdnEntitySyslogEntry
    MAX-ACCESS   not-accessible
    STATUS       current
    DESCRIPTION
        "This table supports retrieval of the syslog messages.
	Each entry corresponds to a message being generated by
	(or on behalf of) an entity (e.g. port card)."

    ::= { pdnSyslog 13 }

pdnEntitySyslogEntry   OBJECT-TYPE 
    SYNTAX       PdnEntitySyslogEntry
    MAX-ACCESS   not-accessible
    STATUS       current
    DESCRIPTION
	        "An entry in the pdnEntitySyslogTable "
    INDEX { entPhysicalIndex, pdnEntitySyslogNumber }
    ::= { pdnEntitySyslogTable 1 }

PdnEntitySyslogEntry ::=
    SEQUENCE
    {
	pdnEntitySyslogNumber        Integer32,
	pdnEntitySyslogMessage       OCTET STRING
    }

pdnEntitySyslogNumber  OBJECT-TYPE
    SYNTAX       Integer32
    MAX-ACCESS   not-accessible
    STATUS       current
    DESCRIPTION
	         "This is a sequentially increasing index of syslog messages
                  starting at 1.  When the table reaches its maximum size
		  (as defined by pdnSyslogMaxTableSize) then the oldest 
		  message will be dropped without renumbering any messages 
		  that remain.  The index is reset to 1 on a device reset or 
		  when the table is cleared (using pdnSyslogClearTable)."	
    ::= { pdnEntitySyslogEntry 1}

pdnEntitySyslogMessage OBJECT-TYPE
    SYNTAX       OCTET STRING(SIZE(1024))
    MAX-ACCESS   read-only
    STATUS       current
    DESCRIPTION
		 "The text of the syslog message."
    ::= { pdnEntitySyslogEntry 2 }



pdnSyslogNumOfMsgInTable OBJECT-TYPE 
    SYNTAX       Integer32 
    MAX-ACCESS   read-only
    STATUS       current 
    DESCRIPTION
                 "This value let the users know how many syslog messages are
		  currently in the syslog table."
    ::= { pdnSyslog 8 }

pdnSyslogMaxTableSize OBJECT-TYPE 
    SYNTAX       Integer32 
    MAX-ACCESS   read-only
    STATUS       current 
    DESCRIPTION
                 "The maximum number of syslog message the syslog table
		 can hold."
    ::= { pdnSyslog 9 }

pdnSyslogClearTable OBJECT-TYPE 
    SYNTAX       INTEGER { noOp(1), clear(2) }
    MAX-ACCESS   read-write
    STATUS       current 
    DESCRIPTION
                 "Clears all the entries in the syslog message table."
    ::= { pdnSyslog 10 }

pdnSyslogMsgToConsole OBJECT-TYPE 
    SYNTAX       INTEGER { disable (1), enable (2) }
    MAX-ACCESS   read-write
    STATUS       current 
    DESCRIPTION
                 "This allows messages to be sent to the device's console port.
		  Note this is intended for debug use only!
		  It is not recommended to be used to monitor syslog message
		  on a regular bases.  If one needs to constantly monitor 
		  the syslog messages, then they should use the remote syslog 
		  daemon, or other user interfaces."
    ::= { pdnSyslog 11 }

pdnSyslogRateLimiting OBJECT-TYPE 
    SYNTAX       INTEGER { disable (1), enable (2) }
    MAX-ACCESS   read-write
    STATUS       current 
    DESCRIPTION
                 "This allows one to enable or disable rate limitiming. When
		  rate limiting is enabled, it prevents the exact same message 
		  from being resent within a fixed amount of time.  "
    ::= { pdnSyslog 12 }

--
-- Conformance Information
--

pdnSyslogCompliances OBJECT IDENTIFIER
     ::= { pdnSyslogConformance 1 }

pdnSyslogGroups OBJECT IDENTIFIER
     ::= { pdnSyslogConformance 2 }

pdnSyslogCompliance MODULE-COMPLIANCE
     STATUS  current
     DESCRIPTION
             "The compliance statement for configurable
	      attributes for syslog manager."
     MODULE
     MANDATORY-GROUPS {	pdnSyslogGroup }

     OBJECT pdnSyslogStatus
     MIN-ACCESS read-only
     DESCRIPTION
	     "Write access is not required."

     OBJECT pdnSyslogIPAddr
     MIN-ACCESS read-only
     DESCRIPTION
	     "Write access is not required."

     OBJECT pdnSyslogPort
     MIN-ACCESS read-only
     DESCRIPTION
	     "Write access is not required."

     OBJECT pdnSyslogSeverityThreshold
     MIN-ACCESS read-only
     DESCRIPTION
	     "Write access is not required."

     OBJECT pdnSyslogRemoteDaemon
     MIN-ACCESS read-only
     DESCRIPTION
	     "Write access is not required."

     OBJECT pdnSyslogClearTable
     MIN-ACCESS read-only
     DESCRIPTION
	     "Write access is not required."

     OBJECT pdnSyslogMsgToConsole
     MIN-ACCESS read-only
     DESCRIPTION
	     "Write access is not required."

     OBJECT pdnSyslogRateLimiting
     MIN-ACCESS read-only
     DESCRIPTION
	     "Write access is not required."

-- Optional groups

     GROUP pdnSyslogOptionalGroup
     DESCRIPTION
	     "Implementation of this group is optional for the
	      syslog manager implementation."

     ::= { pdnSyslogCompliances 1 }

-- units of conformance

pdnSyslogGroup	OBJECT-GROUP
     OBJECTS
     {
	pdnSyslogStatus,
	pdnSyslogIPAddr,
	pdnSyslogPort,
	pdnSyslogSeverityThreshold,
	pdnSyslogRemoteDaemon,
	pdnSyslogMessage,
	pdnSyslogNumOfMsgInTable,
	pdnSyslogMaxTableSize,
	pdnSyslogClearTable,
	pdnSyslogMsgToConsole,
	pdnSyslogRateLimiting
     }
     STATUS current
     DESCRIPTION
             "A collection of objects that permits configuration
              and display of syslog messages generated."
     ::= { pdnSyslogGroups 1 }

pdnSyslogOptionalGroup	OBJECT-GROUP
     OBJECTS
     {
	pdnEntitySyslogMessage
     }	
     STATUS current
     DESCRIPTION
             " A collection of syslog messages classified 
	      per entities."
     ::= { pdnSyslogGroups 2 }

pdnSyslogDeprecatedGroup OBJECT-GROUP
	OBJECTS
	{
	  pdnSyslogLevel
	}
	STATUS deprecated
	DESCRIPTION
		"Objects being deprecated should be added to this group"
       ::= {pdnSyslogGroups 3 }

END 

PDN-DIAGNOSTICS-MIB DEFINITIONS ::= BEGIN

-- Version :  4.0 
-- Enterprise diagnostic mib
-- Copyright (C) 2000 Paradyne Corporation.

-- Created by : Prakash Easwar
-- Last Updated 05/02/2000
-- Last Updated 06/07/2000 Dragana Gough
-- Last Updated 10/05/2001 Jesus A. Pinto


IMPORTS
IpAddress
	FROM RFC1155-SMI
OBJECT-TYPE
	FROM RFC-1212
TRAP-TYPE
	FROM RFC-1215
ifIndex
	FROM RFC1213-MIB
RowStatus, DisplayString, AutonomousType
	FROM SNMPv2-TC
pdn-diagnostics
	FROM PDN-HEADER-MIB
ifTestId
	FROM IF-MIB
;

--
--    The  HotWire Diagnostics MIB
--
--    This MIB provides an NMS to trigger a diagnostic test 
--    The tests that can be performed are grouped into the following
--    categories :
--       1. Device Tests ( Self, Test Reset ...) 
--       2. interface related tests (bert test, packet loopback ...)
--       3. application based diagnostic tests (Ping, TraceRoute ...)
--
--    Interface related tests (2) are an exception. An NMS will use
--    the ifTestTable of RFC1573 to start these tests. However if any 
--    of the interface related tests need to have inputs. those tests
--    will use the objects defined under the ifTestInput group.
--    Hence in these cases implementation of the following groups
--    are mandatory.
--       ifDeviceInput
--       ifDeviceResults - This group is mandatory if more specific 
--                         information about the results is required
--                         (other than ifTestResult - RFC 1573,ifTestTable) 
--                         to be sent back to an NMS.
--                         Hence in these cases it is left to the 
--                         implementor of the device to put
--                         the OID of the object or results table
--                         containing such specifics to be put
--                         in ifTestCode (RFC 1573, ifTestTable).
--       Note  that the above mentioned groups compliment the ifTestTable
--       of RFC 1573
--
--    if the device supports device tests (1), the devControl.mib needs
--    to be implemented. In addition the following group needs to be 
--    implemented 
--       deviceTestInput
--       deviceTestResults
--
--    if the device supports application tests (1). implementation of the
--    following groups are mandatory.
--       applTests
--

-- History
--
-- 05/02/2000
--
-- Removed integer ranges as those should be designated in the
-- product documentation
--
-- 06/07/2000
--
-- Corrected spelling errors in Probe1,2,3, etc.
--
-- 10/04/2001
--
-- Added a new Interface test called BLERT (Block Error Rate Test)
-- which is intended for MVL.


diagTestMIBObjects    OBJECT IDENTIFIER ::= { pdn-diagnostics 1  }
diagTestMIBTraps      OBJECT IDENTIFIER ::= { pdn-diagnostics 2 }
diagIfTest            OBJECT IDENTIFIER ::= { diagTestMIBObjects 1 }
diagApplTest          OBJECT IDENTIFIER ::= { diagTestMIBObjects 2 }
diagTest              OBJECT IDENTIFIER ::= { diagTestMIBObjects 3 }

-- Table objects under diagIfTest
-- The Loopback Test Objects

ifLoopbackTestTable   OBJECT-TYPE
  SYNTAX       SEQUENCE OF IfLoopbackTestEntry
  ACCESS       not-accessible
  STATUS       mandatory
  DESCRIPTION
    "This table contains input and results of a packet loopback
     test. This table is indexed by ifIndex. This is a interface
     related test. There can be only one test running per 
     interface. This table should be used in conjunction with 
     ifTestTable(Rfc 1573) with all the semantics of ifTestTable."
::= { diagIfTest 1 }

ifLoopbackTestEntry OBJECT-TYPE
  SYNTAX       IfLoopbackTestEntry
  ACCESS       not-accessible
  STATUS       mandatory
  DESCRIPTION
    "An entry containing objects for test input and result
     for packet loopback test"
  INDEX { ifIndex }
::= { ifLoopbackTestTable 1 }

IfLoopbackTestEntry ::=
  SEQUENCE {
    loopbackTestInputNumCycles       INTEGER,
    loopbackTestResultsPktsSent      INTEGER,
    loopbackTestResultsPktsRcvdOK    INTEGER,
    loopbackTestResultsPktsRcvdErr   INTEGER,
    loopbackTestResultsPktsNotRcvd   INTEGER,
    loopbackTestResultsPktErrorRate  DisplayString,
    loopbackTestResultsErrSecs       INTEGER,
    loopbackTestResultsSvrErrSecs    INTEGER,
    loopbackTestResultsElpTime       INTEGER
  }

loopbackTestInputNumCycles OBJECT-TYPE
  SYNTAX       INTEGER
  ACCESS       read-write
  STATUS       mandatory
  DESCRIPTION
    "This object corresponds the number of cycles the test 
     to be run for. One cycle corresponds to a 15 second 
     interval. The default value for this object is 40."
::= { ifLoopbackTestEntry 1 }

loopbackTestResultsPktsSent OBJECT-TYPE
  SYNTAX        INTEGER
  ACCESS        read-only
  STATUS        mandatory
  DESCRIPTION
    "This object corresponds to the number of packets sent"
::= { ifLoopbackTestEntry 2 }

loopbackTestResultsPktsRcvdOK OBJECT-TYPE
  SYNTAX        INTEGER
  ACCESS        read-only
  STATUS        mandatory
  DESCRIPTION
    "This object corresponds to the number of packets which were received
     without any error"
::= { ifLoopbackTestEntry 3 }

loopbackTestResultsPktsRcvdErr OBJECT-TYPE
  SYNTAX        INTEGER
  ACCESS        read-only
  STATUS        mandatory
  DESCRIPTION
    "This object corresponds to the number of packets which were received
     with errors"
::= { ifLoopbackTestEntry 4 }

loopbackTestResultsPktsNotRcvd OBJECT-TYPE
  SYNTAX        INTEGER
  ACCESS        read-only
  STATUS        mandatory
  DESCRIPTION
    "This object corresponds to the number of packets which were sent
     but not received"
::= { ifLoopbackTestEntry 5 }

loopbackTestResultsPktErrorRate OBJECT-TYPE
  SYNTAX        DisplayString (SIZE (1..32))
  ACCESS        read-only
  STATUS        mandatory
  DESCRIPTION
     "Reflects the error rate of the loopback test. this string 
      will represent a floating point number of the form 
      [ErrRate][eE][+-][ErrRateBase] where ErrRate and ErrRateBase
      are integers. In Other Words 
      ErrRate * [10^ -ErrRateBase]
      shown below are example of the values returned.
            123456E-5 = 1.23456
            344567e-6 = 0.344567"
::= { ifLoopbackTestEntry 6 }

loopbackTestResultsErrSecs OBJECT-TYPE
  SYNTAX        INTEGER
  ACCESS        read-only
  STATUS        mandatory
  DESCRIPTION
    "This object corresponds to the number of errored seconds"
::= { ifLoopbackTestEntry 7 }

loopbackTestResultsSvrErrSecs OBJECT-TYPE
  SYNTAX        INTEGER
  ACCESS        read-only
  STATUS        mandatory
  DESCRIPTION
    "This object corresponds to the number of severely errored seconds"
::= { ifLoopbackTestEntry 8 }

loopbackTestResultsElpTime OBJECT-TYPE
  SYNTAX        INTEGER
  ACCESS        read-only
  STATUS        mandatory
  DESCRIPTION
    "This object corresponds to the number of seconds elapsed since the
     start of the test."
::= { ifLoopbackTestEntry 9 }

-- The BERT group

ifBERTObjectsTable OBJECT-TYPE
    SYNTAX  SEQUENCE OF IfBERTObjectsEntry
    ACCESS  not-accessible
    STATUS  mandatory
    DESCRIPTION
    "This table contains the objects for Bit Error Rate Test. This table
     is indexed by ifIndex."
::= { diagIfTest 2 }

ifBERTObjectsEntry  OBJECT-TYPE
    SYNTAX  IfBERTObjectsEntry
    ACCESS  not-accessible
    STATUS  mandatory
    DESCRIPTION
    "An Entry containing objects of BERT."
    INDEX   { ifIndex }
::= { ifBERTObjectsTable 1 }

IfBERTObjectsEntry ::=
    SEQUENCE {
        ifBERTTestDuration          INTEGER,
        ifBERTElapsedTime           INTEGER,
        ifBERTDownSyncUP            INTEGER,
        ifBERTUpSyncUP              INTEGER,
        ifBERTSegmentsSent          INTEGER,
        ifBERTDownMBitsRcvd         INTEGER,
        ifBERTUpMBitsRcvd           INTEGER,
        ifBERTDownBitErrDetected    INTEGER,
        ifBERTUpBitErrDetected      INTEGER,
        ifBERTDownBitErrRate        DisplayString,
        ifBERTUpBitErrRate          DisplayString,
        ifBERTDownErroredSecs       INTEGER,
        ifBERTUpErroredSecs         INTEGER,
        ifBERTDownLineRate          INTEGER,
        ifBERTUpLineRate            INTEGER,
        ifBERTDownMargin            INTEGER,
        ifBERTUpMargin              INTEGER
    }

ifBERTTestDuration  OBJECT-TYPE
SYNTAX              INTEGER
ACCESS              read-write
STATUS              mandatory
DESCRIPTION
   "This object represents the test duration in seconds."
::= {ifBERTObjectsEntry 1}

ifBERTElapsedTime       OBJECT-TYPE
SYNTAX              INTEGER
ACCESS              read-only
STATUS              mandatory
DESCRIPTION
   "This object represents the elapsed time in seconds."
::= {ifBERTObjectsEntry 2}

ifBERTDownSyncUP    OBJECT-TYPE
SYNTAX              INTEGER {
                        yes (1),
                        no (2)
                            }
ACCESS              read-only
STATUS              mandatory
DESCRIPTION
	"This object indicates whether Downstream sync is enabled ."
::= {ifBERTObjectsEntry 3}

ifBERTUpSyncUP      OBJECT-TYPE
SYNTAX              INTEGER {
                        yes (1),
                        no (2)
                            }
ACCESS              read-only
STATUS              mandatory
DESCRIPTION
	"This object indicates whether upstream sync is enabled."
::= {ifBERTObjectsEntry 4}

ifBERTSegmentsSent  OBJECT-TYPE
SYNTAX              INTEGER
ACCESS              read-only
STATUS              mandatory
DESCRIPTION
	"This object represents the number of segments sent during the test"
::= {ifBERTObjectsEntry 5}

ifBERTDownMBitsRcvd OBJECT-TYPE
SYNTAX              INTEGER
ACCESS              read-only
STATUS              mandatory
DESCRIPTION
	"This represents the number of million bits rcvd downstream."
::= {ifBERTObjectsEntry 6}

ifBERTUpMBitsRcvd   OBJECT-TYPE
SYNTAX              INTEGER
ACCESS              read-only
STATUS              mandatory
DESCRIPTION
	"This represents the number of million bits rcvd upstream."
::= {ifBERTObjectsEntry 7}

ifBERTDownBitErrDetected    OBJECT-TYPE
SYNTAX                      INTEGER
ACCESS                      read-only
STATUS                      mandatory
DESCRIPTION
	"This represents the number of bit errors detected downstream."
::= {ifBERTObjectsEntry 8}

ifBERTUpBitErrDetected      OBJECT-TYPE
SYNTAX                      INTEGER
ACCESS                      read-only
STATUS                      mandatory
DESCRIPTION
	"This represents the number of bit errors detected upstream."
::= {ifBERTObjectsEntry 9}

ifBERTDownBitErrRate    OBJECT-TYPE
SYNTAX                  DisplayString (SIZE (1..32))
ACCESS                  read-only
STATUS                  mandatory
DESCRIPTION
	  "This string will represent a floating point number of the 
               form [Er rRate] [eE] [+-] [ErrRatebase] where ErrTare and
               errRateBase are integers."
::= {ifBERTObjectsEntry 10}

ifBERTUpBitErrRate  OBJECT-TYPE
SYNTAX              DisplayString (SIZE (1..32))
ACCESS              read-only
STATUS              mandatory
DESCRIPTION
	  "This object reflects the error rate of BERT in Upstream direction. 
               This string will represent a floating point number of the form
               [ErrRate] [eE] [+-] [ErrRatebase]
               where ErrTare and errRateBase are integers."
::= {ifBERTObjectsEntry 11}

ifBERTDownErroredSecs   OBJECT-TYPE
SYNTAX                  INTEGER
ACCESS                  read-only
STATUS                  mandatory
DESCRIPTION
	"This represents number of errored seconds downstream. Errored second 
             is a second in which there is at least 1 block error."
::= {ifBERTObjectsEntry 12}


ifBERTUpErroredSecs OBJECT-TYPE
SYNTAX              INTEGER
ACCESS              read-only
STATUS              mandatory
DESCRIPTION
	"This represents number of errored seconds upstream. 
             Errored second is a second in which there is at least 1 block error."
::= {ifBERTObjectsEntry 13}

ifBERTDownLineRate  OBJECT-TYPE
SYNTAX              INTEGER
ACCESS              read-only
STATUS              mandatory
DESCRIPTION
	"This represents the downstream line rate in KBPS"
::= {ifBERTObjectsEntry 14}

ifBERTUpLineRate    OBJECT-TYPE
SYNTAX              INTEGER
ACCESS              read-only
STATUS              mandatory
DESCRIPTION
	"This represents the Upstream line rate in KBPS"
::= {ifBERTObjectsEntry 15}

ifBERTDownMargin    OBJECT-TYPE
SYNTAX              INTEGER
ACCESS              read-only
STATUS              mandatory
DESCRIPTION
	"This represents the Downstream margin in decibels (DB)."
::= {ifBERTObjectsEntry 16}

ifBERTUpMargin  OBJECT-TYPE
SYNTAX          INTEGER
ACCESS          read-only
STATUS          mandatory
DESCRIPTION
	"This represents the upstream margin in decibels (DB)."
::= {ifBERTObjectsEntry 17}

-- The BLERT group

ifBLERTObjectsTable OBJECT-TYPE
    SYNTAX  SEQUENCE OF IfBLERTObjectsEntry
    ACCESS  not-accessible
    STATUS  mandatory
    DESCRIPTION
    "This table contains the objects for Block Error Rate Test (BLERT).
     This table is indexed by ifIndex."
::= { diagIfTest 3 }

ifBLERTObjectsEntry  OBJECT-TYPE
    SYNTAX  IfBLERTObjectsEntry
    ACCESS  not-accessible
    STATUS  mandatory
    DESCRIPTION
    "An Entry containing objects of BLERT."
    INDEX   { ifIndex }
::= { ifBLERTObjectsTable 1 }

IfBLERTObjectsEntry ::=
    SEQUENCE {
        ifBLERTTestDuration          INTEGER,
        ifBLERTElapsedTime           INTEGER,
        ifBLERTTxSeqCount            INTEGER,
        ifBLERTRxSeqCount            INTEGER,
        ifBLERTRxGoodFrames          INTEGER,
        ifBLERTTxGoodFrames          INTEGER,
        ifBLERTRxBadFrames	     INTEGER,
        ifBLERTTxBadFrames           INTEGER,
        ifBLERTDnLineRate            INTEGER,
        ifBLERTUpLineRate            INTEGER
    }

ifBLERTTestDuration  OBJECT-TYPE
SYNTAX              INTEGER
ACCESS              read-write
STATUS              mandatory
DESCRIPTION
   "This object represents the test duration in seconds."
::= {ifBLERTObjectsEntry 1}

ifBLERTElapsedTime       OBJECT-TYPE
SYNTAX              INTEGER
ACCESS              read-only
STATUS              mandatory
DESCRIPTION
   "This object represents the elapsed time in seconds since the test started."
::= {ifBLERTObjectsEntry 2}

ifBLERTTxSeqCount    OBJECT-TYPE
SYNTAX              INTEGER
ACCESS              read-only
STATUS              mandatory
DESCRIPTION
   "This object indicates the next Tx sequence."
::= {ifBLERTObjectsEntry 3}

ifBLERTRxSeqCount    OBJECT-TYPE
SYNTAX              INTEGER
ACCESS              read-only
STATUS              mandatory
DESCRIPTION
   "This object indicates the next Rx sequence."
::= {ifBLERTObjectsEntry 4}

ifBLERTRxGoodFrames  OBJECT-TYPE
SYNTAX              INTEGER
ACCESS              read-only
STATUS              mandatory
DESCRIPTION
   "This object indicates the number of good frames received."
::= {ifBLERTObjectsEntry 5}

ifBLERTTxGoodFrames  OBJECT-TYPE
SYNTAX              INTEGER
ACCESS              read-only
STATUS              mandatory
DESCRIPTION
   "This object indicates the number of good frames transmitted."
::= {ifBLERTObjectsEntry 6}

ifBLERTRxBadFrames  OBJECT-TYPE
SYNTAX              INTEGER
ACCESS              read-only
STATUS              mandatory
DESCRIPTION
   "This object indicates the number of bad frames received."
::= {ifBLERTObjectsEntry 7}

ifBLERTTxBadFrames  OBJECT-TYPE
SYNTAX      	    INTEGER
ACCESS              read-only
STATUS              mandatory
DESCRIPTION
   "This object indicates the number of bad frames transmitted."
::= {ifBLERTObjectsEntry 8}

ifBLERTDnLineRate   OBJECT-TYPE
SYNTAX              INTEGER
ACCESS              read-only
STATUS              mandatory
DESCRIPTION
   "This object indicates the downstream line rate."
::= {ifBLERTObjectsEntry 9}

ifBLERTUpLineRate   OBJECT-TYPE
SYNTAX      	    INTEGER
ACCESS              read-only
STATUS              mandatory
DESCRIPTION
   "This object indicates the upstream line rate."
::= {ifBLERTObjectsEntry 10}

-- The applTests group. Implementation of all objects in this group is
-- is mandatory

applMaxNumberOfTests OBJECT-TYPE
  SYNTAX        INTEGER
  ACCESS        read-only
  STATUS        mandatory
  DESCRIPTION
    "This object identifies the maximum number of application based
     tests that can be simultaneously instantiated on the device."
::= { diagApplTest 1 }

applCurrentNumberOfTests OBJECT-TYPE
  SYNTAX        INTEGER
  ACCESS        read-only
  STATUS        mandatory
  DESCRIPTION
    "This object identifies the current number of application based
     tests that are running on the device."
::= { diagApplTest 2 }

applStopAllTests  OBJECT-TYPE
  SYNTAX INTEGER {
    noOp (1),
    stop (2),
    stopAndClear (3)
  }
  ACCESS       read-write
  STATUS       mandatory
  DESCRIPTION
    "The value of this object corresponds to stop all
     application based tests on the device.
     noOp -- no operation
     stop -- all the application tests will be stopped
             but current test results are still available
     stopAndClear -- all the application tests will be stoped
             and the results are cleared also"
::= { diagApplTest 3 }

applNewTestId OBJECT-TYPE
  SYNTAX        INTEGER
  ACCESS        read-only
  STATUS        mandatory
  DESCRIPTION
    "This value of this object corresponds to getting a
     magic number to start an application based test.
     The magic number is used as an index to create a
     row for the diagApplTestTable.  If no new rows
     can be created, this object will have a value of 0."
::= { diagApplTest 4 }

-- applTestStatusTable: This table controls all the application tests

applTestStatusTable OBJECT-TYPE
  SYNTAX       SEQUENCE OF ApplTestStatusEntry
  ACCESS       not-accessible
  STATUS       mandatory
  DESCRIPTION
    "This table controls all the application tests.  It defines a test type,
     starts a test, and clears a test."
::= { diagApplTest 5 }

applTestStatusEntry OBJECT-TYPE
  SYNTAX       ApplTestStatusEntry
  ACCESS       not-accessible
  STATUS       mandatory
  DESCRIPTION
    "An entry containing objects for invoking application based tests"
  INDEX { applTestId }
::= { applTestStatusTable 1 }

ApplTestStatusEntry ::=
  SEQUENCE {
    applTestId                 INTEGER,
    applTestType               AutonomousType,
    applTestStatus             INTEGER,
    applTestErrorCode          INTEGER,
    applTestOwner              DisplayString,
    applTestRowStatus          RowStatus
  }

applTestId OBJECT-TYPE
  SYNTAX        INTEGER
  ACCESS        read-only
  STATUS        mandatory
  DESCRIPTION
    "A unique ID to identify each application test."
::= { applTestStatusEntry 1 }

applTestType OBJECT-TYPE
  SYNTAX        AutonomousType
  ACCESS        read-write
  STATUS        mandatory
  DESCRIPTION
    "This object defines the application test type."
::= { applTestStatusEntry 2 }

applTestStatus OBJECT-TYPE
  SYNTAX        INTEGER {
    none (1),
    inProgress (2),
    success (3),
    failed (4),
	 abort (5)
    }
  ACCESS        read-only
  STATUS        mandatory
  DESCRIPTION
    "This object shows the current status of an application test.
       none        - indicates waiting for test parameters.
       inProgress  - indicates the test is in process.
       success     - indicates the test is completed.
       failed      - indicates the test is failed.
		 abort       - indicates the test was aborted"
::= { applTestStatusEntry 3 }

applTestErrorCode OBJECT-TYPE
  SYNTAX        INTEGER { none (1), timeout (2), icmpError (3), systemError (4) }
  ACCESS        read-only
  STATUS        mandatory
  DESCRIPTION
    "This object shows the reason for a test failure."
::= { applTestStatusEntry 4 }

applTestOwner OBJECT-TYPE
  SYNTAX        DisplayString (SIZE (1..40))
  ACCESS        read-write
  STATUS        mandatory
  DESCRIPTION
    "The network manager who has started the test"
::= { applTestStatusEntry 5 }

applTestRowStatus OBJECT-TYPE
  SYNTAX        RowStatus
  ACCESS        read-write
  STATUS        mandatory
  DESCRIPTION
    "This object is used to create a new row or delete an
     existing row for an application test."
::= { applTestStatusEntry 6 }

-- applPintTestTable: This table is for Ping test

applPingTestTable OBJECT-TYPE
  SYNTAX        SEQUENCE OF ApplPingTestEntry
  ACCESS        not-accessible
  STATUS        mandatory
  DESCRIPTION
    "This table contains objects which allow network manager to
     ping a destination."
::= { diagApplTest 6 }

applPingTestEntry OBJECT-TYPE
  SYNTAX        ApplPingTestEntry
  ACCESS        not-accessible
  STATUS        mandatory
  DESCRIPTION
    "This table contains the input parameters for a ping test
     and the results of the ping test."
  INDEX { applPingTestId }
::= { applPingTestTable 1}

ApplPingTestEntry ::=
  SEQUENCE {
    applPingTestId              INTEGER,
    applPingTestIpAddress       IpAddress,
    applPingTestSourceIpAddr    IpAddress,
    applPingTestPacketSize      INTEGER,
    applPingTestTimeout         INTEGER,
    applPingTestMaxPings        INTEGER,
    applPingTestPktsSent        INTEGER,
    applPingTestPktsRecv        INTEGER,
    applPingTestMinTime         INTEGER,
    applPingTestMaxTime         INTEGER,
    applPingTestAvgTime         INTEGER,
    applPingTestDomain          INTEGER,
    applPingTestIfIndex         INTEGER
}

applPingTestId OBJECT-TYPE
  SYNTAX    INTEGER
  ACCESS    read-only
  STATUS    mandatory
  DESCRIPTION
    "A unique ID to identify each application test."
::= { applPingTestEntry 1 }

applPingTestIpAddress OBJECT-TYPE
  SYNTAX        IpAddress
  ACCESS        read-write
  STATUS        mandatory
  DESCRIPTION
    "The IP address to be pinged."
::= { applPingTestEntry 2 }

applPingTestSourceIpAddr OBJECT-TYPE
  SYNTAX        IpAddress
  ACCESS        read-write
  STATUS        mandatory
  DESCRIPTION
    "The Source IP address where we are pinging from.
     This is an optional object for some devices.
     See operational specification for its use."
::= { applPingTestEntry 3 }

applPingTestPacketSize OBJECT-TYPE
  SYNTAX        INTEGER
  ACCESS        read-write
  STATUS        mandatory
  DESCRIPTION
    "This object corresponds to the size of the packet (in bytes)
     which will be sent during the Ping test.
     The default value for this object is 64 bytes"
::= { applPingTestEntry 4 }

applPingTestTimeout OBJECT-TYPE
  SYNTAX        INTEGER
  ACCESS        read-write
  STATUS        mandatory
  DESCRIPTION
    "This object corresponds to a timeout value (in seconds)
     between Pings.
     The default value for this object is 5 seconds"
::= { applPingTestEntry 5 }

applPingTestMaxPings OBJECT-TYPE
  SYNTAX        INTEGER
  ACCESS        read-write
  STATUS        mandatory
  DESCRIPTION
    "This object corresponds to  the maximum number of times the
     device should Ping for the destination.
     The default value for this object is 10"
::= { applPingTestEntry 6 }

applPingTestPktsSent OBJECT-TYPE
  SYNTAX        INTEGER
  ACCESS        read-only
  STATUS        mandatory
  DESCRIPTION
    "This object corresponds to  the total number of packets sent."
::= { applPingTestEntry 7 }

applPingTestPktsRecv OBJECT-TYPE
  SYNTAX        INTEGER
  ACCESS        read-only
  STATUS        mandatory
  DESCRIPTION
    "This object corresponds to  the total number of packets received
     without error"
::= { applPingTestEntry 8 }

applPingTestMinTime OBJECT-TYPE
  SYNTAX        INTEGER
  ACCESS        read-only
  STATUS        mandatory
  DESCRIPTION
    "The minimum round trip time."
::= { applPingTestEntry 9 }

applPingTestMaxTime OBJECT-TYPE
  SYNTAX        INTEGER
  ACCESS        read-only
  STATUS        mandatory
  DESCRIPTION
    "The maximum round trip time."
::= { applPingTestEntry 10 }

applPingTestAvgTime OBJECT-TYPE
  SYNTAX        INTEGER
  ACCESS        read-only
  STATUS        mandatory
  DESCRIPTION
    "The average round trip time."
::= { applPingTestEntry 11 }

applPingTestDomain    OBJECT-TYPE
  SYNTAX        INTEGER { 
	 noop (1),
    mgmt (2),
    service (3)
    }
  ACCESS        read-write
  STATUS        mandatory
  DESCRIPTION
    "This object specifies the destination ip address's domain.
     The Default is service domain. Not allowed if source ip address is entered.
     This is an optional object for some devices. See operational specification
     its use."
::= { applPingTestEntry 12 }

applPingTestIfIndex  OBJECT-TYPE
  SYNTAX        INTEGER
  ACCESS        read-write
  STATUS        mandatory
  DESCRIPTION
    "This object specifies the interface over which the ping test will
	  take place. "
::= { applPingTestEntry 13 }

-- applTracerouteConfigTable: to enter the parameters for a traceroute test

applTracerouteConfigTable OBJECT-TYPE
  SYNTAX        SEQUENCE OF ApplTracerouteConfigEntry
  ACCESS        not-accessible
  STATUS        mandatory
  DESCRIPTION
    "This table contains objects which allow network manager to
     enter the parameters of a traceroute test."
::= { diagApplTest 7 }

applTracerouteConfigEntry OBJECT-TYPE
  SYNTAX        ApplTracerouteConfigEntry
  ACCESS        not-accessible
  STATUS        mandatory
  DESCRIPTION
    "This table contains the input parameters for a traceroute test."
  INDEX { applTracerouteTestId }
::= { applTracerouteConfigTable 1}

ApplTracerouteConfigEntry ::=
  SEQUENCE {
    applTracerouteTestId        INTEGER,
    applTracerouteIpAddress     IpAddress,
    applTracerouteSourceIpAddr  IpAddress,
    applTraceroutePktsSize      INTEGER,
    applTracerouteTimeout       INTEGER,
    applTracerouteMaxHops       INTEGER,
    applTracerouteDomain        INTEGER,
    applTracerouteIfIndex       INTEGER
}

applTracerouteTestId OBJECT-TYPE
  SYNTAX        INTEGER
  ACCESS        read-only
  STATUS        mandatory
  DESCRIPTION
    "A unique ID to identify each application test."
::= { applTracerouteConfigEntry 1 }

applTracerouteIpAddress OBJECT-TYPE
  SYNTAX        IpAddress
  ACCESS        read-write
  STATUS        mandatory
  DESCRIPTION
    "The destination IP address of a traceroute test."
::= { applTracerouteConfigEntry 2 }

applTracerouteSourceIpAddr OBJECT-TYPE
  SYNTAX        IpAddress
  ACCESS        read-write
  STATUS        mandatory
  DESCRIPTION
    "The source IP address of where the traceroute test started.
     This is an optional object for some devices.
     See operational specification for its use."
::= { applTracerouteConfigEntry 3 }

applTraceroutePktsSize OBJECT-TYPE
  SYNTAX        INTEGER
  ACCESS        read-write
  STATUS        mandatory
  DESCRIPTION
    "This object corresponds to the size of the packet (in bytes)
     which will be sent during the traceroute test. 
     Please refer to product specific documentation for the 
     default values supported"
::= { applTracerouteConfigEntry 4 }

applTracerouteTimeout OBJECT-TYPE
  SYNTAX        INTEGER
  ACCESS        read-write
  STATUS        mandatory
  DESCRIPTION
    "This object corresponds to a timeout value (in seconds)
     of a traceroute test.
     The default value for this object is 5 seconds"
::= { applTracerouteConfigEntry 5 }

applTracerouteMaxHops OBJECT-TYPE
  SYNTAX        INTEGER
  ACCESS        read-write
  STATUS        mandatory
  DESCRIPTION
    "This object corresponds to the maximum number of hops
     to reach the destination.
     The default value for this object is device specific. See
	  Operational Specifications"
::= { applTracerouteConfigEntry 6 }

applTracerouteDomain    OBJECT-TYPE
  SYNTAX        INTEGER {
    noop (1),
    mgmt (2),
    service (3)
    }
  ACCESS        read-write
  STATUS        mandatory
  DESCRIPTION
    "This object specifies the destination ip address's domain.
     The Default is service domain. Not allowed if source ip address is entered.
     This is an optional object for some devices. See operational specification
     its use."
::= { applTracerouteConfigEntry 7 }

applTracerouteIfIndex  OBJECT-TYPE
  SYNTAX        INTEGER
  ACCESS        read-write
  STATUS        mandatory
  DESCRIPTION
    "This object specifies the interface over which the trace-route
	  test will take place. " 
::= { applTracerouteConfigEntry 8 }

-- Traceroute Results Table

applTracerouteResultTable OBJECT-TYPE
  SYNTAX        SEQUENCE OF ApplTracerouteResultEntry
  ACCESS        not-accessible
  STATUS        mandatory
  DESCRIPTION
    "This table contains results of traceroute test."
::= { diagApplTest 8 }

applTracerouteResultEntry OBJECT-TYPE
  SYNTAX        ApplTracerouteResultEntry
  ACCESS        not-accessible
  STATUS        mandatory
  DESCRIPTION
    "An entry contains the objects for the traceroute test."
  INDEX { applTracerouteResultTestId, applTracerouteHopCount }
::= { applTracerouteResultTable 1 }

ApplTracerouteResultEntry ::=
  SEQUENCE {
    applTracerouteResultTestId  INTEGER,
    applTracerouteHopCount      INTEGER,
    applTracerouteIpAddr        IpAddress,
    applTraceroutePktSize       INTEGER,
    applTracerouteProbe1RTT     INTEGER,
    applTracerouteProbe2RTT     INTEGER,
    applTracerouteProbe3RTT     INTEGER
  }

applTracerouteResultTestId OBJECT-TYPE
  SYNTAX        INTEGER
  ACCESS        read-only
  STATUS        mandatory
  DESCRIPTION
    "A unique ID to identify each application test."
::= { applTracerouteResultEntry 1 }

applTracerouteHopCount OBJECT-TYPE
  SYNTAX        INTEGER
  ACCESS        read-only
  STATUS        mandatory
  DESCRIPTION
    "This object contains the number of hops to reach the gateway."
::= { applTracerouteResultEntry 2 }

applTracerouteIpAddr OBJECT-TYPE
  SYNTAX        IpAddress
  ACCESS        read-only
  STATUS        mandatory
  DESCRIPTION
    "This object contains the IP address of the gateway."
::= { applTracerouteResultEntry 3 }

applTraceroutePktSize OBJECT-TYPE
  SYNTAX        INTEGER
  ACCESS        read-only
  STATUS        mandatory
  DESCRIPTION
    "This object corresponds to the size of the packet (in bytes)
     which will be sent during the traceroute test.
     Please refer to product specific documentation for the 
     default values supported"
::= { applTracerouteResultEntry 4 }

applTracerouteProbe1RTT OBJECT-TYPE
  SYNTAX        INTEGER
  ACCESS        read-only
  STATUS        mandatory
  DESCRIPTION
    "This object contains the round trip time (rtt) of the first
     probe sent to the gateway.
     If the probe has a timeout the rtt is set to -1."
::= { applTracerouteResultEntry 5 }

applTracerouteProbe2RTT OBJECT-TYPE
  SYNTAX        INTEGER
  ACCESS        read-only
  STATUS        mandatory
  DESCRIPTION
    "This object contains the round trip time (rtt) of the second
     probe sent to the gateway.
     If the probe has a timeout the rtt is set to -1."
::= { applTracerouteResultEntry 6 }

applTracerouteProbe3RTT OBJECT-TYPE
  SYNTAX        INTEGER
  ACCESS        read-only
  STATUS        mandatory
  DESCRIPTION
    "This object contains the round trip time (rtt) of the third
     probe sent to the gateway.
     If the probe has a timeout the rtt is set to -1."
::= { applTracerouteResultEntry 7 }

diagTestTrapEnable OBJECT-TYPE
  SYNTAX  INTEGER
  ACCESS  read-write
  STATUS  mandatory
  DESCRIPTION
    "This object is used to disable or enable TestOver
     and TestStart trap for all tests. It is bit sum and possible
     bit positions are 1 TestStart trap 2 TestOver trap"
::= { diagTest 1 }

-- Traps

diagApplTestStart TRAP-TYPE
  ENTERPRISE diagTestMIBTraps
  VARIABLES { ifIndex, applTestId, applTestType }
  DESCRIPTION
    "This trap signifies that an application test has been initiated."
::= 1

diagApplTestStop TRAP-TYPE
  ENTERPRISE diagTestMIBTraps
  VARIABLES { ifIndex, applTestId, applTestType, applTestStatus }
  DESCRIPTION
    "This trap signifies that an application test has completed.
     This trap compliments the diagApplTestStart trap."
::= 101 

diagIfTestStart TRAP-TYPE
  ENTERPRISE diagTestMIBTraps
  VARIABLES { ifTestId }
  DESCRIPTION
    "This trap signifies that a diagnostic test has been initiated."
::= 2

diagIfTestOver TRAP-TYPE
  ENTERPRISE diagTestMIBTraps
  VARIABLES { ifTestId }
  DESCRIPTION
    "This trap signifies that a diagnostic test has completed.
     This trap compliments the diagIfTestStart trap"
::= 102
 
END

PDN-TRAPMGR-MIB DEFINITIONS ::= BEGIN

IMPORTS
	IpAddress
		FROM RFC1155-SMI
	OBJECT-TYPE
		FROM RFC-1212
	SwitchState
		FROM PDN-TC
        DisplayString, RowStatus
                FROM SNMPv2-TC
     	pdn-traps
		FROM PDN-HEADER-MIB;

-- ===============================================================
--
-- Device Traps Manager,  01/30/97 
--
-- This MIB will allow an SNMP Manager the ability to edit the Trap Manager
-- table on a Paradyne device. It provides a mechanism to add, delete or edit
-- trap manager entries.
--
-- ===============================================================
--
-- 09/03/2002   Jesus Pinto pinto@paradyne.com
-- Added pdnDevTrapMgrTable
--
-- ===============================================================
--
-- 09/11/2002   Jesus Pinto pinto@paradyne.com
-- Implement changes as per MIBWG review meeting:
--    o Move sysDevConfigTrapsEnable to this mib
--      (renamed as pdnDevConfigTrapsEnable).
--    o Remove devTrapMgrLevel from this mib
--      (not being used, never approved)
--
-- ===============================================================

devTrapMgrMaxNumber OBJECT-TYPE
    SYNTAX  INTEGER
    ACCESS  read-only
    STATUS  mandatory
    DESCRIPTION
        "Maximum number of managers allowed in the devTrapMgrTable. This 
        may vary per device."
    ::= { pdn-traps 1 }

devTrapMgrCurrentNumber OBJECT-TYPE
    SYNTAX  INTEGER
    ACCESS  read-only
    STATUS  mandatory
    DESCRIPTION
        "Current number of managers in devTrapMgrTable."
    ::= { pdn-traps 2 }

devTrapMgrTable OBJECT-TYPE
    SYNTAX  SEQUENCE OF DevTrapMgrEntry
    ACCESS  not-accessible
    STATUS  mandatory
    DESCRIPTION
        "The trap manager table."
    ::= { pdn-traps 3 }

devTrapMgrEntry OBJECT-TYPE
    SYNTAX  DevTrapMgrEntry
    ACCESS  not-accessible
    STATUS  mandatory
    DESCRIPTION
        "An entry in the trap manager table."
    INDEX { devTrapMgrIpAddress }
    ::= { devTrapMgrTable 1 }

--
-- Layout of one entry in the devTrapManagerTable
--

DevTrapMgrEntry ::=
    SEQUENCE {
        devTrapMgrIpAddress
            IpAddress,
        devTrapMgrDestination
            INTEGER,
        devTrapMgrCircuit
            INTEGER,
	devTrapMgrSubCircuit
	    INTEGER
    } 

devTrapMgrIpAddress OBJECT-TYPE
    SYNTAX  IpAddress
    ACCESS  read-write
    STATUS  mandatory
    DESCRIPTION
        "Unique IP address identifying a Trap Manager. An
	 existing Trap Manager may be deleted by setting
	 the devTrapMgrIpAddress object to 0.0.0.0 or by
	 setting the devTrapMgrIpAddress object to a new
	 address.  A new Trap Manager may be added by setting
	 the devTrapMgrIpAddress object of 0.0.0.0 to the new
	 address as long as there is still room for another
	 Trap Manager."
    ::= { devTrapMgrEntry 1 }

devTrapMgrDestination OBJECT-TYPE
    SYNTAX INTEGER 
    ACCESS  read-write
    STATUS  mandatory
    DESCRIPTION
        "The ifIndex to be used with the associated IpAddress
	 when sending traps."
    ::= { devTrapMgrEntry 2 }

devTrapMgrCircuit OBJECT-TYPE
    SYNTAX INTEGER 
    ACCESS  read-write
    STATUS  mandatory
    DESCRIPTION
        "The circuit used for management when multiple circuits
	 are allowed over the specified interface (ifIndex). If
	 the interface allows only one circuit, devTrapMgrCircuit
	 is set to 0."
    ::= { devTrapMgrEntry 3 }

devTrapMgrSubCircuit OBJECT-TYPE
    SYNTAX INTEGER
    ACCESS  read-write
    STATUS  mandatory
    DESCRIPTION
	"The subcircuit used for management when devTrapMgrCircuit
	 can be further subdivided."
    ::= {devTrapMgrEntry 4}

--
-- pdnDevTrapMgrTable.
--
-- This table contains details of the managers configured to 
-- receive TRAPS from the device. This table allows one
-- to modify parameters that are specific to trap managers 
-- e.g., community string, port dest) from their typical
-- default values.
--

pdnDevTrapMgrTable OBJECT-TYPE
    SYNTAX  	SEQUENCE OF PdnDevTrapMgrEntry
    ACCESS  	not-accessible
    STATUS  	mandatory
    DESCRIPTION
        "The paradyne's device trap manager table."
    ::= { pdn-traps 4}

pdnDevTrapMgrEntry OBJECT-TYPE
    SYNTAX  	PdnDevTrapMgrEntry
    ACCESS  	not-accessible
    STATUS  	mandatory
    DESCRIPTION
        "An entry of a trap manager configuration."
    INDEX { pdnDevTrapMgrDestAddress, pdnDevTrapMgrSubnetMask }
    ::= { pdnDevTrapMgrTable 1 }

--
-- Layout of one entry in the pdnDevTrapMgrTable
--

PdnDevTrapMgrEntry ::=
    SEQUENCE {
  	pdnDevTrapMgrDestAddress   IpAddress,
	pdnDevTrapMgrSubnetMask    IpAddress,
	pdnDevTrapMgrDestPort	   INTEGER,
	pdnDevTrapMgrCommunityName DisplayString (SIZE(1..32)),
	pdnDevTrapMgrEnable	   INTEGER,
	pdnDevTrapMgrRowStatus	   RowStatus
    }

pdnDevTrapMgrDestAddress OBJECT-TYPE
   SYNTAX 	IpAddress
   ACCESS 	read-only
   STATUS 	mandatory
   DESCRIPTION
     "The IP Address of the destination to which a trap
      must be sent."
   ::= { pdnDevTrapMgrEntry 1 }

pdnDevTrapMgrSubnetMask OBJECT-TYPE
   SYNTAX 	IpAddress
   ACCESS 	read-only
   STATUS 	mandatory
   DESCRIPTION
     "This object is used to specify the subnet mask"
   ::= { pdnDevTrapMgrEntry 2 }

pdnDevTrapMgrDestPort OBJECT-TYPE
   SYNTAX 	INTEGER
   ACCESS 	read-write
   STATUS 	mandatory
   DESCRIPTION
     "The Port destination used to send the trap."
   DEFVAL { 162 }
   ::= { pdnDevTrapMgrEntry 3 }

pdnDevTrapMgrCommunityName OBJECT-TYPE
   SYNTAX  	DisplayString (SIZE(1..32))
   ACCESS   	read-write
   STATUS 	mandatory
   DESCRIPTION
     "This object corresponds to the name of the SNMP Community
      that will be used when sending the trap out to this
      manager destination."
   DEFVAL { "public" }
   ::= { pdnDevTrapMgrEntry 4 }

pdnDevTrapMgrEnable OBJECT-TYPE
   SYNTAX 	INTEGER {
     		enable (1),
     		disable (2)
   		}
   ACCESS 	read-write
   STATUS 	mandatory
   DESCRIPTION
     "This object corresponds to turning traps 
      on/off for a particular destination.
      enable (1) - traps will be sent to the 
	specified destination.
      disable (2)- traps will not be sent to the 
	specified destination."
   ::= { pdnDevTrapMgrEntry 5 }

pdnDevTrapMgrRowStatus OBJECT-TYPE
   SYNTAX 	RowStatus 
   ACCESS 	read-write
   STATUS 	mandatory
   DESCRIPTION
     "This object is used to add/delete rows
     to/from the table."
   ::= { pdnDevTrapMgrEntry 6 }


pdnDevConfigTrapsEnable OBJECT-TYPE
   SYNTAX  	SwitchState
   ACCESS  	read-write
   STATUS 	mandatory
   DESCRIPTION
	" This objects allows NMS to turn off/on the
	  generation of Traps in the device."
 ::= {  pdn-traps 5 }

END

PDN-SONETEXT-MIB DEFINITIONS ::= BEGIN

IMPORTS
	OBJECT-TYPE
		FROM RFC-1212
	TRAP-TYPE	
		FROM RFC-1215
	TimeTicks
		FROM RFC1155-SMI
	sonetSectionCurrentStatus,
	sonetLineCurrentStatus,
	sonetPathCurrentStatus
		FROM SONET-MIB
	pdnSonetMIB
		FROM PDN-HEADER-MIB;

-- ===============================================================
--
--   Extentions to the SONET-MIB
--
--  Release: 1.0  05/26/99 (Initial Release) J.Strain
--
--  History:
-- 02/07/2000 - added 2 objects to the devSonetConfigTable:
-- 	devSonetStatusLastChange and devSonetStatusChangeTrapEnable.
--	 Added a trap devSonetStatusChange
--
-- This group extends the SONET-MIB.
--

devSonetConfig OBJECT IDENTIFIER ::= { pdnSonetMIB  1 }
devSonetTraps OBJECT IDENTIFIER ::= { pdnSonetMIB  2 }

devSonetConfigTable OBJECT-TYPE
    SYNTAX  SEQUENCE OF DevSonetConfigEntry
    ACCESS  not-accessible
    STATUS  mandatory
    DESCRIPTION
           "The Paradyne Sonet-MIB Table Augment."
    ::= { devSonetConfig  1 }

devSonetConfigEntry OBJECT-TYPE
    SYNTAX  DevSonetConfigEntry
    ACCESS  not-accessible
    STATUS  mandatory
    DESCRIPTION
           "An entry in the Paradyne Sonet-MIB Interface Config Table."
    INDEX   { devSonetIfIndex }
    ::= { devSonetConfigTable  1 }

DevSonetConfigEntry ::=
    SEQUENCE {
    devSonetIfIndex
        INTEGER,
    devSonetXmitClkSrc
        INTEGER,
    devSonetStatusLastChange
	TimeTicks,
    devSonetStatusChangeTrapEnable
	INTEGER

    }

devSonetIfIndex OBJECT-TYPE
    SYNTAX  INTEGER
    ACCESS  read-only
    STATUS  mandatory
    DESCRIPTION
           "The index value which uniquely identifies the
            interface for which this entry contains information
            on interface tests.  The interface identified by a
            particular value of this index is the same interface
            as identified by the same value of ifIndex from the
            Interfaces table of MIB II (RFC 1213)."
    ::= { devSonetConfigEntry 1 }

devSonetXmitClkSrc OBJECT-TYPE
    SYNTAX  INTEGER {
                 loopTiming(1),
                 localTiming(2),
                 throughTiming(3),
                 systemTiming(4)
               }
    ACCESS  read-write
    STATUS  mandatory
    DESCRIPTION
           "This object is used to configure the clock to be used by the transmit
            side of the interface.
              loopTiming -- Timing is Extracted from the Receiving
                            OC-N signal and re-used on the Transmitting
                            OC-N signal. Thats is the timing is
                            supplied by the far-end OC-N interface.
              localTiming -- Timing provided by the internal clock.
              throughTiming -- Timing is Extracted from one OC-N interface
                               and used by the transmitted signal on another
                               OC-N interface.
              systemTiming -- Timing is provided by the source selected for
                               system  timing (devCfgClkSource)"
    ::= { devSonetConfigEntry  2 }

devSonetStatusLastChange OBJECT-TYPE
          SYNTAX  TimeTicks
          ACCESS  read-only
          STATUS mandatory
          DESCRIPTION
                 "The value of MIB II's sysUpTime object at the
                 time this Sonet entered its current line status
                 state.  If the current state was entered prior to
                 the last re-initialization of the proxy-agent,
                 then this object contains a zero value."
          ::= { devSonetConfigEntry 3 }

devSonetStatusChangeTrapEnable  OBJECT-TYPE

          SYNTAX      INTEGER {
                         enabled(1),
                         disabled(2)
                      }
          ACCESS  read-write
          STATUS      mandatory
          DESCRIPTION
                 "Indicates whether devSonetStatusChange traps
                 should be generated for this interface."
--          DEFVAL { disabled }
          ::= { devSonetConfigEntry 4 }

-- ===============================================
--
-- 			Sonet TRAPS
--
-- ===============================================



     devSonetStatusChange TRAP-TYPE

		ENTERPRISE devSonetTraps
         VARIABLES {
			devSonetStatusLastChange,
			sonetSectionCurrentStatus, 
			sonetLineCurrentStatus,
			sonetPathCurrentStatus 
			}
         DESCRIPTION
		"A devSonetStatusChange trap is sent when the
		value of an instance of sonetSectionCurrentStatus
		or sonetLineCurrentStatus or sonetPathCurrentStatus changes.
		It can be utilized by an NMS to trigger polls.  When
		the line status change results in a lower level
		line status change (i.e. sonet), then no traps for
		the lower level are sent."
                    ::= 1 

END

PDN-SECURITY-MIB DEFINITIONS ::= BEGIN

IMPORTS
	IpAddress
		FROM RFC1155-SMI
	OBJECT-TYPE
		FROM RFC-1212
	pdn-security
		FROM PDN-HEADER-MIB
    	RowStatus
		FROM SNMPv2-TC;

-- ===============================================================
--
--  Device Security, 10/04/95
--
--  NOTE: This group is in addition to the community name and 
--        provides an additional level of security not provided
--        by the community name in version 1 of the SNMP standard.
--
-- ===============================================================
-- 
-- 11/18/98 - Rob Steinberger (ras@eng.paradyne.com)
--
-- Reversed Rajesh's change from att-security to pdn-security
-- in that it breaks attDCE.mib.
--
-- 11/09/98 - Rajesh Gowda
-- 1. Added devSecurityTelnetSourceValidation scalar object
-- 2. Added newSecurityMgrSubnetMask objects into newSecurityMgrTable
--    Changed the description of newSecurityMgrIpAddress
-- 3. att-security group name has been changed to pdn-security
-- 4. More enumerations added to object newSecurityMgrAccess.
--
-- ===============================================================
-- 
-- 03/03/2000 - Rajesh Gowda (rgowda@nj.paradyne.com)
--
-- 1. Added devSecurityFtpSourceValidation scalar object
-- 2. Added table object securityMgrTable which deprecates
--    newSecurityMgrTable for the following reasons
--    a. Index for the table is changed
--    b. Manager access object is broken down to 3 objects
--
-- ===============================================================
-- 
-- 01/07/02 - Dragana Gough
--
-- 1. Added devSecurityTrapMgrTable
--
-- 01/11/02 - Dragana Gough
--
-- 2. Removed devSecurityTrapMgrTable and added object in securityMgrTable to
--   signal that traps are to be sent to specified ip address
-- 
-- ===============================================================
-- 
-- 05/21/02 - Jesus Pinto (pinto@paradyne.com)
--
-- 1. Changed STATUS on newSecurityMgrTable to deprecated
-- 2. Changed ACCESS on securityMgrIpAddress and 
--    securityMgrSubnetMask to be read-only. 
-- 
-- ===============================================================
-- 
-- 08/22/02 - Jesus Pinto (pinto@paradyne.com)
--
-- 1.  deprecated securityMgrTrapAccess. Developers should
--     use pdn_TrapMgr.mib for trap mgr configuration.
--

devSecurityMgrValidation OBJECT-TYPE
    SYNTAX INTEGER {
        disable (1),
        enable  (2)
    }
    ACCESS read-write
    STATUS mandatory
    DESCRIPTION
        "This object is used to either enable or disable
        SNMP IP validation. When enabled the first check on any
        incoming PDU is based on the IP address of the datagram.
        If the IP address is configured in the 
        devSecurityMgrTable then the community name is checked.
        If the community name is correct then the lowest access level
        between the the Table and the community name is taken."
    ::= { pdn-security 1 }



devSecurityMgrMaxNumber OBJECT-TYPE
    SYNTAX INTEGER
    ACCESS read-only
    STATUS mandatory
    DESCRIPTION
        "Maximum number of managers allowed in the devSecurityMgrTable."
    ::= { pdn-security 2 }

devSecurityMgrCurrentNumber OBJECT-TYPE
    SYNTAX INTEGER
    ACCESS read-only
    STATUS mandatory
    DESCRIPTION
        "Current number of managers in the devSecurityMgrTable."
    ::= { pdn-security 3 }

--
--  Deprecated:  10/7/96
--        The devSecurityMgrTable has been replaced with the
--        newSecurityMgrTable at the end of this file.
--

devSecurityMgrTable OBJECT-TYPE
    SYNTAX SEQUENCE OF DevSecurityMgrEntry
    ACCESS not-accessible
    STATUS deprecated
    DESCRIPTION
        "A list of the security manager entries.
        In order to add a new Security Manager the devSecurityMgrIpAddress 
        object must be created first by setting it to a valid IP Address."
    ::= { pdn-security 4 }

devSecurityMgrEntry OBJECT-TYPE
    SYNTAX DevSecurityMgrEntry
    ACCESS not-accessible
    STATUS deprecated
    DESCRIPTION
        "The SNMP IP Address configuration items."
    INDEX { devSecurityMgrIpAddress }
    ::= { devSecurityMgrTable 1 }

DevSecurityMgrEntry ::=
    SEQUENCE {
        devSecurityMgrIpAddress
            IpAddress,
        devSecurityMgrAccess
            INTEGER
    }

devSecurityMgrIpAddress OBJECT-TYPE
    SYNTAX IpAddress
    ACCESS read-write
    STATUS deprecated
    DESCRIPTION
        "This is used to specify the IP address that identifies the
        SNMP manager(s) that are authorized to send SNMP messages.

        An existing Security Manager may be deleted by setting the 
        devSecurityMgrIpAddress object to 0.0.0.0 or by setting the 
        devSecurityMgrIpAddress object to a new IP Address.
        A new Security Manager may be added by setting
        the devSecurityMgrIpAddress object of 0.0.0.0 to the new address 
        as long as there is still room for another Security Manager.

        When ever a new Security Manager is added or an existing 
        Security Manager's IP Address is modified, 
        the devSecurityMgrAccess object is set to the default value 
        of read (1)."
    ::= { devSecurityMgrEntry 1 }

devSecurityMgrAccess OBJECT-TYPE
    SYNTAX INTEGER {
        read      (1),
        readWrite (2)
    }
    ACCESS read-write
    STATUS deprecated
    DESCRIPTION
        "This field is used to specify the access allowed for an authorized 
        NMS when Manager Validation is performed. 
        If the IP address for the NMS sending an SNMP message is on the list 
        of allowed managers, this option along with the Community Name access 
        determine the type of access allowed for the that manager. 

        When ever a new Security Manager is added or an existing 
        Security Manager's IP Address is modified, the devSecurityMgrAccess 
        object is set to the default value of read (1).
        If the index for this object is not in the existing table and if there
        is room in the table then the index will be used to create a new 
        Security Manager and will be given the requested access level."
    ::= { devSecurityMgrEntry 2 }

-- ===============================================================
--
--  New Device Security, Version 1.0.0, 8/30/96
--       Updated by Prakash Easwar.
--
-- History :
-- 8/30/96
--      1. The access permission of devSecurityMgrIpAddress has been 
--              changed from read-write to read-only.  Also the Description
--              of this object is modified.
--      2. the devSecurityMgrAccess has been updated to include 
--              noAccess.
--      3. The description of the devSecurityMgrEntry object has been 
--              modified.
--
-- 5/21/02
--      1. This table has been deprecated.
--

newSecurityMgrTable OBJECT-TYPE
    SYNTAX SEQUENCE OF NewSecurityMgrEntry
    ACCESS not-accessible
    STATUS deprecated
    DESCRIPTION
        "A list of the security manager entries. If an entry is not found
         in this table, it is added to the table."
    ::= { pdn-security 5 }

newSecurityMgrEntry OBJECT-TYPE
    SYNTAX NewSecurityMgrEntry
    ACCESS not-accessible
    STATUS deprecated
    DESCRIPTION
        "The SNMP IP Address configuration items."
    INDEX { newSecurityMgrIpAddress }
    ::= { newSecurityMgrTable 1 }

NewSecurityMgrEntry ::=
    SEQUENCE {
        newSecurityMgrIpAddress
            IpAddress,
        newSecurityMgrAccess
            INTEGER,
        newSecurityMgrSubnetMask
            IpAddress
    }

newSecurityMgrIpAddress OBJECT-TYPE
    SYNTAX IpAddress
    ACCESS read-write
    STATUS deprecated
    DESCRIPTION
        "This is used to specify the IP address that identifies the
        SNMP manager(s) that are authorized to send SNMP messages.
        This object is the binary AND of SNMP or telnet source IP
        address and its subnet mask if the subnet mask is available.
        Subnet mask is assumed to be 255.255.255.255 when not available"
    ::= { newSecurityMgrEntry 1 }


newSecurityMgrAccess OBJECT-TYPE
    SYNTAX INTEGER {
        read      (1),
        readWrite (2),
        noAccess  (3),
        telnetNoAccess  (4),
        telnetRead      (5),
        telnetReadWrite (6)
    }
    ACCESS read-write
    STATUS deprecated
    DESCRIPTION
        "This field is used to specify the access allowed for an authorized 
        NMS when Manager Validation is performed. 
        If the IP address for the NMS sending an SNMP message is on the list 
        of allowed managers, this option along with the Community Name access 
        determine the type of access allowed for the that manager. 

        When ever a new Security Manager is added or an existing 
        Security Manager's IP Address is modified, the newSecurityMgrAccess 
        object is set to the default value of read (1).
        If the index for this object is not in the existing table and if there
        is room in the table then the index will be used to create a new 
        Security Manager and will be given the requested access level.
                  In addition changing an existing access permission to noAccess
                  invalidates the corresponding row of this table. It is upto
                  the implementation to decide whether to actually remove this
                  entry from the table or not.

        read (1)            ==&gt; no telnet access and snmp read only access 
        readWrite (2)       ==&gt; no telnet access and snmp read-write access
        noAccess (3)        ==&gt; no telnet access and no snmp read-write access
        telnetNoAccess (4)  ==&gt; telnet access and no snmp access
        telnetRead (5)      ==&gt; telnet access and snmp read only access
        telnetReadWrite (6) ==&gt; telnet access and snmp read-write access."
    ::= { newSecurityMgrEntry 2 }

newSecurityMgrSubnetMask OBJECT-TYPE
    SYNTAX IpAddress
    ACCESS read-write
    STATUS deprecated
    DESCRIPTION
        "This object is used to specify the subnet mask "
    ::= { newSecurityMgrEntry 3 }


devSecurityTelnetSourceValidation OBJECT-TYPE
    SYNTAX INTEGER {
        disable (1),
        enable  (2)
    }
    ACCESS read-write
    STATUS mandatory
    DESCRIPTION
        "This object is used to either enable or disable
        telnet source address screening "
    ::= { pdn-security 6 }

devSecurityFtpSourceValidation OBJECT-TYPE
    SYNTAX INTEGER {
        disable (1),
        enable  (2)
    }
    ACCESS read-write
    STATUS mandatory
    DESCRIPTION
        "This object is used to either enable or disable
        ftp source address screening "
    ::= { pdn-security 7 }

-- ===============================================================
--
--  securityMgrTable
--       Updated by Jesus Pinto 05-21-2002
--
--
-- History :
--	1. Changed securityMgrIpAddress and  
--		securityMgrSubnetMask to be read-only.
--
-- ===============================================================
securityMgrTable OBJECT-TYPE
    SYNTAX SEQUENCE OF SecurityMgrEntry
    ACCESS not-accessible
    STATUS mandatory
    DESCRIPTION
        "A list of the security manager entries. If an entry is not found
        in this table, it is added to the table."
    ::= { pdn-security 8 }

securityMgrEntry OBJECT-TYPE
    SYNTAX SecurityMgrEntry
    ACCESS not-accessible
    STATUS mandatory
    DESCRIPTION
        "The device access security configuration items."
    INDEX { securityMgrIpAddress, securityMgrSubnetMask}
    ::= { securityMgrTable 1 }

SecurityMgrEntry ::=
    SEQUENCE {
        securityMgrIpAddress
            IpAddress,
        securityMgrSubnetMask
            IpAddress,
        securityMgrSnmpAccess
            INTEGER,
        securityMgrTelnetAccess
            INTEGER,
        securityMgrFtpAccess
            INTEGER,
        securityMgrTrapAccess
	    INTEGER,
        securityMgrRowStatus
            RowStatus
    }

securityMgrIpAddress OBJECT-TYPE
    SYNTAX IpAddress
    ACCESS read-only
    STATUS mandatory
    DESCRIPTION
        "This is used to specify the IP address that identifies the
        SNMP manager(s) that are authorized to send SNMP messages."
    ::= { securityMgrEntry 1 }

securityMgrSubnetMask OBJECT-TYPE
    SYNTAX IpAddress
    ACCESS read-only
    STATUS mandatory
    DESCRIPTION
        "This object is used to specify the subnet mask "
    ::= { securityMgrEntry 2 }

securityMgrSnmpAccess OBJECT-TYPE
    SYNTAX INTEGER {
        readOnly  (1),
        readWrite (2),
        noAccess (3)
    }
    ACCESS read-write
    STATUS mandatory
    DESCRIPTION
        "This is used to specify the snmp access to the device."
    ::= { securityMgrEntry 3 }

securityMgrTelnetAccess OBJECT-TYPE
    SYNTAX INTEGER {
        disable (1),
        enable  (2)
    }
    ACCESS read-write
    STATUS mandatory
    DESCRIPTION
        "This is used to specify the telnet access to the device."
    ::= { securityMgrEntry 4 }

securityMgrFtpAccess OBJECT-TYPE
    SYNTAX INTEGER {
        disable (1),
        enable  (2)
    }
    ACCESS read-write
    STATUS mandatory
    DESCRIPTION
        "This is used to specify the ftp access to the device."
    ::= { securityMgrEntry 5 }

securityMgrTrapAccess OBJECT-TYPE
    SYNTAX INTEGER {
        trapAccess  (1),
        noTrapAccess (2)
    }
    ACCESS read-write
    STATUS deprecated
    DESCRIPTION
        "This is used to specify the trap access to the device.
	 NOTE: the pdnDevTrapMgrTable should be used instead."
    ::= { securityMgrEntry 6 }

securityMgrRowStatus OBJECT-TYPE
    SYNTAX RowStatus
    ACCESS read-write
    STATUS mandatory
    DESCRIPTION
        "The status of this table entry."
    ::= { securityMgrEntry 7 }

devSecuritySNMPMgrAccess OBJECT-TYPE
    SYNTAX INTEGER {
        disable (1),
        enable  (2)
    }
    ACCESS read-write
    STATUS mandatory
    DESCRIPTION
        "This object is used to either enable or disable
        SNMP access to the system. When disabled the first check on any
        incoming PDU is based on the UPD type of the datagram.
        If it is an SNMP manager trying to access SNMP agent on the system
	the access will be denied."
    ::= { pdn-security 9 }

END

PDN-HEALTHANDSTATUS-MIB DEFINITIONS ::= BEGIN

IMPORTS
	DisplayString, ifIndex
		FROM RFC1213-MIB
	IpAddress
		FROM RFC1155-SMI
	OBJECT-TYPE
		FROM RFC-1212
     	pdn-devStatus
		FROM PDN-HEADER-MIB
	TRAP-TYPE
		FROM RFC-1215;

-- ===============================================================
--
-- Device Health and Status
--
-- Version 1.7.0
-- Last Updated 05/26/2000

-- History:
-- 1.7.0 - Updated by Rob Stainberger 05/26/00
-- 	 - moved devFailureStatus to devStatus 7
-- 1.6.0 - Updated by Dragana Gough, 03/08/2000
--	 - added deviceFailureStatus Display string
--	 - object 
-- 1.5.0 - Updated by Dragana Gough , 02/23/2000
--	 - Added deviceFailure, devicelfTestFailure and devStatusTrapEnable
-- 1.4.0 - Updated by Rob Steinberger, 11/10/98
--       - Added devLastTrapString for string Variable binding.
-- 1.3.0 - Added devAuthenicationFailureIpAddress for trap processing
-- 1.2.0 - Updated by Soklei Leong, 6/10/98
--       - Added devSNMPSetStatusTable for retrieving the status of a SNMP
--       - SET command when an error occurs.
-- 1.1.0 - Updated by Rocco Sansone, 8/22/97
--       - Added devAbortStatus object for retrieving the last abort code.
-- 1.0.0 - Created 1994.

devStatus       OBJECT IDENTIFIER ::= { pdn-devStatus 1 }

devHealthAndStatus OBJECT-TYPE
    SYNTAX  DisplayString (SIZE (0..255))
    ACCESS  read-only
    STATUS  mandatory
    DESCRIPTION
        "Health and Status of the device. Health &amp; Status is 
        represented as a concatenation of health and status 
        message strings, where each message string is separated
        by a semi-colon. Refer to device-specific user documentation
        for a complete description of the Health and Status codes."
    ::= { devStatus 1 }

devSelfTestResults OBJECT-TYPE
    SYNTAX  DisplayString (SIZE (0..255))
    ACCESS  read-only
    STATUS  mandatory
    DESCRIPTION
        "Self-test results. Self-test (or power-up test) results
        summarizes the test results of each CCA, where each CCA test
        result is separated by a semi-colon. Refer to device-specific 
        user documentation for a complete description of the self test
        codes and messages."
    ::= { devStatus 2 }

devAbortStatus OBJECT-TYPE
    SYNTAX  DisplayString (SIZE (0..255))
    ACCESS  read-only
    STATUS  mandatory
    DESCRIPTION
        "Abort Status.  The devAbortStatus object is used to retrieve the 
	latest abort status that is stored in the agent.  The agent will 
	need to save the latest abort information in non-volatile memory
	so that it will be available immediately after a fatal reset.  
	How long the latest failure information is remembered after this point 
	is an implementation issue.  Refer to device-specific 
        user documentation for a complete description of the abort
        codes and/or messages."
    ::= { devStatus 3 }

devSNMPSetStatusTable OBJECT-TYPE
     SYNTAX   SEQUENCE OF DevSNMPSetStatusEntry
     ACCESS   not-accessible
     STATUS   mandatory
     DESCRIPTION
         "A table containing SNMP Set command Statuses when an error occurs.
          It contains maximum of 5 entries. Oldest entry is pushed out when
          the table is full and a new entry is added."
     ::= { devStatus 4 } 

devSNMPSetStatusEntry OBJECT-TYPE
         SYNTAX   DevSNMPSetStatusEntry
         ACCESS   not-accessible
         STATUS   mandatory
         DESCRIPTION
             "The information regarding each SNMP Set command Status when
              en error occurs. Each entry is index by a request ID generated
              by the client and attached to the UDP when the Set command is
              sent."
         INDEX { devSNMPSetReqId }
     ::= { devSNMPSetStatusTable 1 }  

DevSNMPSetStatusEntry ::=
    SEQUENCE {
        devSNMPSetReqId
            INTEGER,
        devSNMPSetStatus
            DisplayString
    }

devSNMPSetReqId OBJECT-TYPE
    SYNTAX   INTEGER
    ACCESS   read-only                                          
    STATUS   mandatory                                          
    DESCRIPTION                                                 
        "The Request ID which identifies the SNMP Set command in error."                                            
    ::= { devSNMPSetStatusEntry 1 }                                        

devSNMPSetStatus OBJECT-TYPE
    SYNTAX  DisplayString (SIZE (0..255))
    ACCESS  read-only
    STATUS  mandatory                                            
    DESCRIPTION                                                  
        "Indicates the error message string associated with the Set command 
         of this row in the table."
    ::= { devSNMPSetStatusEntry 2 }     

devAuthenticationFailureIpAddress OBJECT-TYPE
    SYNTAX  IpAddress
    ACCESS  read-only
    STATUS  mandatory
    DESCRIPTION
        "Authentication Failure Ip Address is used when a
         authenticationFailure trap is generated.  The single
         varbind represents the ip address causing the error.
         If the ip address is not known, 0.0.0.0 is used."
    ::= { devStatus 5 }

devLastTrapString OBJECT-TYPE
    SYNTAX  DisplayString (SIZE (0..255))
    ACCESS  read-only
    STATUS  mandatory                                            
    DESCRIPTION                                                  
        "This object contains a textual description of the last trap that
         was processed by the device.  The exact text in the description
         is device specific and should be contained user documentation
         outside of this MIB. It is recommended that the important 
         information is contained within the first 100 characters."
    ::= { devStatus 6 }     

devFailureStatus OBJECT-TYPE
    SYNTAX  DisplayString (SIZE (0..255))
    ACCESS  read-only
    STATUS  mandatory
    DESCRIPTION
	 " Device Failure status. Conditions that cause failure
	   are further described in the device documentation."
    ::= { devStatus 7 }

devStatusTrapEnable OBJECT-TYPE
     SYNTAX  INTEGER
     ACCESS  read-write
     STATUS  mandatory
     DESCRIPTION
	    " This object provides ability to enable or disable
	      individual enterprise traps. The object is bit map
	      represented as a sum. The bit positions are:
			1 deviceSelfTestFailure
			2 deviceFailure"
    ::= { devStatus 8 }

devSelfTestFailure TRAP-TYPE
     ENTERPRISE  devStatus  
     VARIABLES { ifIndex, devSelfTestResults }
     DESCRIPTION
       "This trap signifies that the sending protocol's
        device has failed self test.
        The variable binding for this trap would be the selfTest
        devSelfTestResults object of the Health and Status MIB. The
        exact format of this display string will be well-documented
        in the Operational Specifications of the device."
    ::= 1 

deviceFailure TRAP-TYPE
     ENTERPRISE  devStatus  
     VARIABLES { ifIndex, devFailureStatus }
     DESCRIPTION
	" This trap signifies that the sending protocol's
	  device has failed and the failure was not a result
	  of a device test."
     ::= 2 
END

PDN-CONFIG-MIB DEFINITIONS ::= BEGIN

IMPORTS
    ifIndex
        FROM RFC1213-MIB
    Gauge
        FROM RFC1155-SMI
    DateAndTime
        FROM SNMPv2-TC
    TRAP-TYPE
        FROM RFC-1215
    OBJECT-TYPE
        FROM RFC-1212
    pdn-devConfig
        FROM PDN-HEADER-MIB;

-- ===============================================================
--
-- Device Configuration
--
-- Version 1.0.11
--
--
-- Updated 10/11/03 Sue Alfano - Added devCfgClkRate object,
--                               added new enum, external2, to devCfgClkSource.
--
-- Updated 03/07/02 Mohan Mohankumar - changed the description for the object
--				       devConfigTrapEnable to include support
--				       for path Trap and Latency Trap.
--
-- Updated 12/13/01 Dragana Gough - added new objects devConfigTestTimeout,
--				    devConfigTestDuration, devConfigComDiscTime,
--				    devConfigComInactivityTO, devConfigPortNumDisplayFormat,
--				    devConfigDateDisplayFormat, devAcceptRemoteResetFrame
--
-- 
-- Updated 12/04/01 Dragana Gough - updated DESCRIPTION filed for
--				    devConfigTimeOfDay
-- Updated 09/18/2000 Rob Steinberger - Added Usage Comments to 
--                                      devConfigChangeKeysTable
--
-- Updated 09/08/2000 Rob Steinberger - Added devConfigChangeKeysTable
--
-- Updated 05/19/2000 Rob Steinberger - Added dslNam and t3Nam card types
--
-- Updated 03/08/2000 Dragana Gough -updated devConfigTrapEnable documentation
--   to specify cases when the trap configuration is set per interface vs per 
--   entity.  Added Configuration change trap
--
-- Updated 02/10/2000 Dragana Gough -added bit field positions to devConfigTrapEnable
--   to enable disabling/enabling of linkUp and linkDown Traps
--
-- Updated 08/18/99 by J. Colom (jaime@paradyne.com)
--         (Added devConfigNetSyncRole 
--             Added devConfigTimeOfDay )
--
-- Updated 7/14/99 Jaime Colom - Adds dce6APM, sruAPM, ocu4APM, 
--   pktVoiceAPM, dpNAM, stNAM, ddsNAM, dualDsxNniNAM, t3NniNAM card 
--   types as well as acceptingAPM and failedAPM states.
--
-- Updated 7/29/98 Vince Ciletti - Adds 2 and 6 port OCU APM card types.
--
-- ==================================================================

devConfigArea OBJECT IDENTIFIER ::= { pdn-devConfig 1 }

devConfigAreaCopy OBJECT-TYPE
    SYNTAX  INTEGER {
        noOp(1),
        active-to-customer1(2),
        active-to-customer2(3),
        customer1-to-active(4),
        customer1-to-customer2(5),
        customer2-to-active(6),
        customer2-to-customer1(7),
        factory1-to-active(8),
        factory1-to-customer1(9),
        factory1-to-customer2(10),
        factory2-to-active(11),
        factory2-to-customer1(12),
        factory2-to-customer2(13),
        factory3-to-active(14),
        factory3-to-customer1(15),
        factory3-to-customer2(16),
        factory4-to-active(17),
        factory4-to-customer1(18),
        factory4-to-customer2(19),
        factory5-to-active(20),
        factory5-to-customer1(21),
        factory5-to-customer2(22),
        factory6-to-active(23),
        factory6-to-customer1(24),
        factory6-to-customer2(25),
        factory7-to-active(26),
        factory7-to-customer1(27),
        factory7-to-customer2(28),
        factory8-to-active(29),
        factory8-to-customer1(30),
        factory8-to-customer2(31),
        factory9-to-active(32),
        factory9-to-customer1(33),
        factory9-to-customer2(34)
    }
    ACCESS  read-write
    STATUS  mandatory
    DESCRIPTION
       "This object is used to copy the entire contents of one
        configuration area into another configuration area.  The
        supported number of factory configuration areas depends
        on the device model.  The value read from this object is
        always noOp(1)."
    ::= { devConfigArea 1 }

-- General device-wide configuration items

-- The Test Timeout group.  This group is used for configuring
-- timers associated with tests on the device.

devConfigTestTimer    OBJECT IDENTIFIER ::= { pdn-devConfig 2 }

devConfigTestTimeout OBJECT-TYPE
    SYNTAX  INTEGER {
        disable(1),    -- Tests will not be terminated
                       -- based on a timer.
        enable(2)      -- Tests will be terminated after
                       -- the duration specified by
                       -- devConfigTestDuration
    }
    ACCESS  read-write
    STATUS  mandatory
    DESCRIPTION
       "This object specifies whether tests are to be terminated
    after a defined duration.  If the value is enable(2), the
    duration is defined by devConfigTestDuration."
    ::= { devConfigTestTimer 1 }

devConfigTestDuration OBJECT-TYPE
    SYNTAX  INTEGER
    ACCESS  read-write
    STATUS  mandatory
    DESCRIPTION
       "This object specifies the duration that a test will be
    allowed to run before it is automatically terminated.
    Tests will only be terminated if devConfigTestTimeout
    is set to enable."
    ::= { devConfigTestTimer 2 }

-- The Clock Source group.

devConfigClockSrc    OBJECT IDENTIFIER ::= { pdn-devConfig 3 }

devConfigClockSrcTable OBJECT-TYPE
    SYNTAX  SEQUENCE OF DevConfigClockSrcEntry
    ACCESS  not-accessible
    STATUS  mandatory
    DESCRIPTION
        "The clock source table."
    ::= { devConfigClockSrc 1 }
 
devConfigClockSrcEntry OBJECT-TYPE
    SYNTAX  DevConfigClockSrcEntry
    ACCESS  not-accessible
    STATUS  mandatory
    DESCRIPTION
        "An entry in the clock source table."
    INDEX { devCfgClkWhichSrc }
    ::= { devConfigClockSrcTable 1 }
 
--
-- Layout of one entry in the devConfigClockSrcTable
--
 
DevConfigClockSrcEntry ::=
    SEQUENCE {
        devCfgClkWhichSrc    INTEGER,
        devCfgClkSource      INTEGER,
        devCfgClkIfIndex     INTEGER,
        devCfgClkRate        INTEGER
    }

devCfgClkWhichSrc OBJECT-TYPE
    SYNTAX  INTEGER {
        primary(1),     -- The primary master clock source
        secondary(2)    -- The secondary master clock source
    }
    ACCESS  read-only
    STATUS  mandatory
    DESCRIPTION
    "The clock source to which this entry is applicable."
    ::= { devConfigClockSrcEntry 1 }

devCfgClkSource OBJECT-TYPE
    SYNTAX  INTEGER {
        internal(1),    -- Master clock is the internal clock
        external(2),    -- Master clock is external clock source 1
        interface(3),   -- clock source is provided via an interface
        dbm(4),         -- clock source is provided via a backup module
        external2(5)    -- Master clock is external clock source 2
    }
    ACCESS  read-write
    STATUS  mandatory
    DESCRIPTION
       "This object is used to select the source for the master
        clock for the device.  The source selected provides
        synchronization for all the timing within the device,
        and the clocks for all of the external interfaces.

        If this object is interface(3), the specific interface
        used as the master clock source is specified using
        devCfgClkIfIndex.

        If this object is external(2), or external2(5), the clock
        rate can be specified using devCfgClkRate."
    ::= { devConfigClockSrcEntry 2 }

devCfgClkIfIndex OBJECT-TYPE
    SYNTAX  INTEGER
    ACCESS  read-write
    STATUS  mandatory
    DESCRIPTION
       "This object is used to select the interface to be used
        as the source for the master clock for the device, if
        devCfgClkSource is set to interface(3).  The interface
        selected provides synchronization for all the timing
        within the device, and the clocks for all of the
        external interfaces.
        NOTE:  if a synchronous data port is selected and the EDL
               is enabled for that synchronous data port, then the
               external device must provide a clock 8 Kbps less
               than the expected data port rate.  For example, if
               the data port rate is set at 64 Kbps, the external
               clock source needs to supply a 56 Kbps clock signal.

        If devCfgClkSource is not interface(3), the value of this
        object is meaningless."
    ::= { devConfigClockSrcEntry 3 }

devCfgClkRate OBJECT-TYPE
    SYNTAX  INTEGER {
        rate400Hz(1),
        rate8KHz(2),
        rate64KHz(3),
        rate1544KHz(4),
        rate2048KHz(5)
    }
    ACCESS  read-write
    STATUS  mandatory
    DESCRIPTION
       "This object is used to specify the clock signal
        rate associated with the external source selected by
        the devCfgClkSource object."
    ::= { devConfigClockSrcEntry 4 }


-- The Trap Configuration group.

devConfigTrap    OBJECT IDENTIFIER ::= { pdn-devConfig 4 }

devConfigTrapEnable OBJECT-TYPE
    SYNTAX  INTEGER
    ACCESS  read-write
    STATUS  mandatory
    DESCRIPTION
       "Which trap types will be sent by the entity.  This
        object is a bit map represented as a sum, therefore,
        multiple trap types can be enabled simultaneously.
        This objects sets flag (enable/disable) value
        on entity level. If trap enable/disable flags are
        set per interface level by some other object
        this object will read 'enabled' if any one of the 
        interfaces is enabled. If any of the traps
        below are set to enabled by this object 
        it will enable that trap on all interfaces 
        on the entity.
        The various bit positions are:
            1  warmStart traps
            2  authenticationFailure traps
            4  enterpriseSpecific traps
            8  LinkUp trap
            16 LinkDown Trap
            32 path Trap
            64 Latency Trap."
    ::= { devConfigTrap 1 }

cCNTrapEnable OBJECT-TYPE
  SYNTAX  INTEGER
  ACCESS  read-write
  STATUS  mandatory
  DESCRIPTION
    " This object is used to enable or disable
      configuration change trap. It is a bit 
      sequence sum with only accepted values
      1 or 2. Setting the bit sequence to 2 
      would mean enabling the trap and 1 
      would mean disabling it."
  ::= { devConfigTrap 2 }

-- The Paradyne System Alarm group.

devConfigAlarm    OBJECT IDENTIFIER ::= { pdn-devConfig 5 }

devConfigAlarmRelayCutoff OBJECT-TYPE
    SYNTAX  INTEGER {
        noOp(1),
        off(2)
    }
    ACCESS  read-write
    STATUS  mandatory
    DESCRIPTION
       "Writing off(2) to this object will turn off the System
        Alarm Relay.  Reading this object will always return
        noOp(1)."
    ::= { devConfigAlarm 6 }

-- The Paradyne Card Type table.

-- This table is used by multi-slot devices.  It shows what
-- type of card has been configured to occupy each slot in
-- the chassis, and what card type is actually present in the
-- chassis.  If the configured and actual card types do not
-- match, this table allows the actual card type to be accepted,
-- which will change the configuration information for the card.

devConfigCardType    OBJECT IDENTIFIER ::= { pdn-devConfig 6 }

devConfigCardTypeTable OBJECT-TYPE
    SYNTAX  SEQUENCE OF DevConfigCardTypeEntry
    ACCESS  not-accessible
    STATUS  mandatory
    DESCRIPTION
       "The Paradyne Card Type Table."
    ::= { devConfigCardType 7 }

devConfigCardTypeEntry OBJECT-TYPE
    SYNTAX  DevConfigCardTypeEntry
    ACCESS  not-accessible
    STATUS  mandatory
    DESCRIPTION
       "An entry in the Paradyne Card Type Table."
    INDEX  { devCfgCardSlot }
    ::= { devConfigCardTypeTable 1 }

-- Layout of one entry in the devConfigCardTypeTable

DevConfigCardTypeEntry ::=
    SEQUENCE {
    devCfgCardSlot      INTEGER,
    devCfgCardConfig    INTEGER,
    devCfgCardActual    INTEGER,
    devCfgCardAction    INTEGER
    }


devCfgCardSlot OBJECT-TYPE
    SYNTAX  INTEGER
    ACCESS  read-only
    STATUS  mandatory
    DESCRIPTION
       "The slot number which this card occupies in the chassis."
    ::= { devConfigCardTypeEntry 1 }

devCfgCardConfig OBJECT-TYPE
    SYNTAX  INTEGER {
        emptySlot(1),          -- an empty slot
        unsupportedAPM(2),     -- an unrecognized APM
        t1NAM(3),              -- a 1T1/1DSX NAM
        syncDataAPM(4),        -- a synchronous data port APM
        voiceFxsAPM(5),        -- an FXS Voice APM
        voiceEmAPM(6),         -- an E&amp;M Voice APM
        voiceFxoAPM(7),        -- an FXO Voice APM
        dsxAPM(8),             -- an DSX-1 APM
        t1NoDsxNAM(9),         -- a 2T1 with No DSX NAM
        misconfiguredAPM(10),  -- a misconfigured APM
        ocu2APM(11),           -- a 2 port OCU APM
        ocu6APM(12),           -- a 6 port OCU APM
        dce6APM(13),           -- a 6-port DCE APM 
        sruAPM(14),           -- a 5-port SubRate APM
        ocu4APM(15),           -- a 4-port Office Channel Unit APM
        pktVoiceAPM(16),       -- a Packet Voice APM  
        acceptingAPM(17),      -- Accepting State
        failedAPM(18),         -- APM position has failed card
        dpNAM(19),             -- Data Port NAM
        stNAM(20),             -- S/T ISDN NAM
        ddsNAM(21),            -- DDS NAM
        dualDsxNniNAM(22),     -- Dual Dsx-1 NNI NAM
        t3NniNAM(23),          -- T3 NNI NAM
        t3NAM(24),             -- T3 NAM
        dslNAM(25)             -- DSL NAM
    }
    ACCESS  read-only
    STATUS  mandatory
    DESCRIPTION
       "The type of card which has been configured for this slot."
    ::= { devConfigCardTypeEntry 2 }

devCfgCardActual OBJECT-TYPE
    SYNTAX  INTEGER {
        emptySlot(1),         -- an empty slot
        unsupportedAPM(2),    -- an unrecognized APM
        t1NAM(3),             -- a T1 NAM
        syncDataAPM(4),       -- a synchronous data port APM
        voiceFxsAPM(5),       -- an FXS Voice APM
        voiceEmAPM(6),        -- an E&amp;M Voice APM
        voiceFxoAPM(7),       -- an FXO Voice APM
        voiceDsxAPM(8),       -- an DSX-1 APM
        t1NoDsxNAM(9),        -- a 2T1 with No DSX NAM
        misconfigured(10),    -- a misconfigured APM
        ocu2APM(11),          -- a 2 port OCU APM
        ocu6APM(12),          -- a 6 port OCU APM
        dce6APM(13),          -- a 6-port DCE APM 
        sruAPM(14),          -- a 5-port SubRate APM
        ocu4APM(15),          -- a 4-port Office Channel Unit APM
        pktVoiceAPM(16),      -- a Packet Voice APM  
        acceptingAPM(17),     -- Accepting State
        failedAPM(18),        -- APM position has failed card
        dpNAM(19),            -- Data Port NAM
        stNAM(20),            -- S/T ISDN NAM
        ddsNAM(21),           -- DDS NAM
        dualDsxNniNAM(22),    -- Dual Dsx-1 NNI NAM
        t3NniNAM(23),         -- T3 NNI NAM
        t3NAM(24),            -- T3 NAM
        dslNAM(25)            -- DSL NAM
    }
    ACCESS  read-only
    STATUS  mandatory
    DESCRIPTION
       "The type of card which is present in this slot."
    ::= { devConfigCardTypeEntry 3 }

devCfgCardAction OBJECT-TYPE
    SYNTAX  INTEGER {
        noOp(1),
        accept(2)
    }
    ACCESS  read-write
    STATUS  mandatory
    DESCRIPTION
       "Writing accept(2) to this object changes the configured
        card type to match the type of card currently present
        in the slot.  Reading this object always returns noOp(1)."
    ::= { devConfigCardTypeEntry 4 }

-- The Paradyne Device Network Synchronization group.

devConfigNetSync    OBJECT IDENTIFIER ::= { pdn-devConfig 7 }

devConfigNetSyncRole OBJECT-TYPE
    SYNTAX  INTEGER {
        none(1),
        tributary(2),
        controller(3)
    }
    ACCESS  read-write
    STATUS  mandatory
    DESCRIPTION
       "Network Time Synchronization role item for a device in the network.
          none       - Device will ignore network time synchronization messages.
          tributary  - Update the network reference time each time the device  
                       receives an update massage.
          controller - The device will generate the synchronization message and
                       Time of Day clock will be the same as the Network
                       Reference Time."
    DEFVAL  { tributary }
    ::= { devConfigNetSync 1 }

-- The Paradyne Device Configuration Time group.

devConfigTime    OBJECT IDENTIFIER ::= { pdn-devConfig 8 }

devConfigTimeOfDay OBJECT-TYPE
    SYNTAX  DateAndTime
    ACCESS  read-write
    STATUS  mandatory
    DESCRIPTION
    "This is standard definition of Device Time of Day
     (DateAndTime) SYNTAX. The only difference is
     that our group is defining timezone filed (8)
     optional.

     Display format-&gt; 2d-1d-1d,1d:1d:1d.1d,1a1d:1d
	    Fields description
            field  octets  contents                  range
            -----  ------  --------                  -----
              1      1-2   year*                     0..65536
              2       3    month                     1..12
              3       4    day                       1..31
              4       5    hour                      0..23
              5       6    minutes                   0..59
              6       7    seconds                   0..60
                           (use 60 for leap-second)
              7       8    deci-seconds              0..9
              8       9    direction from UTC        '+' / '-'
              9      10    hours from UTC*           0..13
             10      11    minutes from UTC          0..59

            * Notes:
            - the value of year is in network-byte order
            - daylight saving time in New Zealand is +13

            For example, Tuesday May 26, 1992 at 1:30:15 PM EDT would be
            displayed as:

                             1992-5-26,13:30:15.0,-4:0

	    Timezone information (fileds 8-10)
	    is optional.
            Note that if only local time is known, then timezone
            information (fields 8-10) is not present."
    ::= { devConfigTime 1 }

-- The Paradyne Device Configuration Change Key Group

devConfigChangeKeys OBJECT IDENTIFIER ::= { pdn-devConfig 9 }

--
-- Configuration Change Keys Table
--
-- This table contains a set of keys specific to each non-volatile
-- database on the device.  The keys are ensured to change each time
-- there is a change to the database that they represent.
--
-- Example of Use:
--
--   1) Database Discovery
--      This MIB can be used to discover the various non-volatile
--      databases on a device.  Each database has a unique key.
--
--      The discovery process consists of walking devConfigChangeKeysDbKey.
--      Each response corresponds to a different database type.  The NMS
--      only needs to be concerned with the databases that affect them.
--      Each of the "interesting" database keys should be stored for later
--      reference.
--
--   2) Database monitoring
--         After discovery, the NMS can check the database keys of the
--         databases of interest to it either at specific intervals or
--         based on configuration change traps.  When using trap directed,
--         polling, a default polling interval should still apply in case
--         a trap is lost in the transmission process.
--         
--         Checking the keys consists of performing a get operation on
--         devConfigChangeKeysDbKey for the specific database(s) of interest.  
--         If the key has changed from that previously stored, the database
--         has changed.  The new key should be stored for future reference.
--

devConfigChangeKeysTable OBJECT-TYPE
    SYNTAX  SEQUENCE OF DevConfigChangeKeysEntry
    ACCESS  not-accessible
    STATUS  mandatory
    DESCRIPTION
       "The Paradyne Configuration Change Key Table. This table
        is in place to allow a Network Manager to know when the
        configuration on the device changes.  Configuration can
        be found in several databases that may each have a
        unique access method.  For this reason, the keys are
        in the form of a table."
    ::= { devConfigChangeKeys 1 }

devConfigChangeKeysEntry OBJECT-TYPE
    SYNTAX  DevConfigChangeKeysEntry
    ACCESS  not-accessible
    STATUS  mandatory
    DESCRIPTION
       "An entry in the Paradyne Configuration Change Key Table."
    INDEX  { devConfigChangeKeysDbType }
    ::= { devConfigChangeKeysTable 1 }

DevConfigChangeKeysEntry ::=
    SEQUENCE {
    devConfigChangeKeysDbType   INTEGER,
    devConfigChangeKeysDbKey    Gauge
    }

devConfigChangeKeysDbType OBJECT-TYPE
    SYNTAX  INTEGER {
              generalConfig(1),
              rmonAlarm(2),
              rmonUserHistory(3),
              routerConfig(4)
            }
    ACCESS  read-only
    STATUS  mandatory
    DESCRIPTION
       "The type of database that is being keyed.  If a specific
        type is not supported by the device, noSuchName should be
        returned."
    ::= { devConfigChangeKeysEntry 1 }

devConfigChangeKeysDbKey OBJECT-TYPE
    SYNTAX  Gauge
    ACCESS  read-only
    STATUS  mandatory
    DESCRIPTION
       "A unique value that will change each time the database is
        altered.  Effort should be made to increase the number of
        times the database can change without seeing the same
        key."
    ::= { devConfigChangeKeysEntry 2 }

-- The General Configuration group.

devConfiguration    OBJECT IDENTIFIER ::= { pdn-devConfig 10 }

	devConfigComDiscTime OBJECT-TYPE
	     SYNTAX  INTEGER
	     ACCESS  read-write
	     STATUS  mandatory
	     DESCRIPTION
		"This object is used to specify how long
		 to wait before disconnecting. Inactivity
		 is defined as no keyboard activity within
		 a given period of time. The time is kept
		 in seconds. The default is 300 seconds."
	    ::= { devConfiguration 1  }

        devConfigPortNumDisplayFormat OBJECT-TYPE
	    SYNTAX INTEGER {
		       sle(1),
		       unitport(2),
		       name(3)
		}
	    ACCESS read-write 
	    STATUS mandatory
	    DESCRIPTION
	       "This object is used to set display format for the
		port numbers. The default is unit/port number.
		sle(1) - this method is to use Single Logical Entity
			 interface numbers. For example, if sle is  
			 confiugred the sle numbers range from 1 to
			 384 for a stack of 8 units
			 with 48 ports each.
		unitport(2) - this method uses unitnumber/portnumber
			      For previous example the numbers would
			      be from 1/1 to  8/48.
		name(3) - This method allowes user to assign character
			  strings (names) to each interface and to view
			  the interfaces by names."
            ::= { devConfiguration 2 }


	devConfigDateDisplayFormat OBJECT-TYPE
	    SYNTAX INTEGER {
		    ddmmyy(1),
		    mmddyy(2)  
		}
	    ACCESS read-write
	    STATUS mandatory
	    DESCRIPTION
	      "This object is used to specify which format
	       will date be displayed in.The default is 'mmddyy'"
	    ::= { devConfiguration 3 }

       devAcceptRemoteResetFrame OBJECT-TYPE
	   SYNTAX INTEGER {
		    enable(1),
		    disable(2)
		 }
	   ACCESS read-write
	   STATUS mandatory
	   DESCRIPTION
	     "This object is used to enable/disable 
	      acceptance of remote reset frame which
	      would result in hardware reset.
	      The default setting is disabled."
	  ::= { devConfiguration 4 }


--TRAP Group

cCN TRAP-TYPE
  ENTERPRISE devConfigTrap 
  VARIABLES { ifIndex }
  DESCRIPTION
    "This trap signifies a Configuration change  or 
     software upgrade. This trap 
     is of 'warning' class"
 ::= 7

END

PDN-CONTROL-MIB DEFINITIONS ::= BEGIN

IMPORTS
SwitchState 
	FROM PDN-TC
RowStatus, DisplayString 
	FROM SNMPv2-TC
ifIndex 
	FROM IF-MIB
Integer32, Counter32, IpAddress, TimeTicks, NOTIFICATION-TYPE, OBJECT-IDENTITY,
OBJECT-TYPE, MODULE-IDENTITY 
	FROM SNMPv2-SMI
OBJECT-GROUP, NOTIFICATION-GROUP 
	FROM SNMPv2-CONF 
entPhysicalIndex 
	FROM ENTITY-MIB
pdn-common 
	FROM PDN-HEADER-MIB;

-- ====================================================================
--
--  Device Control, Version 4.0, 12/2/97
--
--  Last Updated: 12/23/97 by R. Steinberger (ras@eng.paradyne.com)
--                (Added devControlRMON and devControlLatency groups,
--                 Added global comments,
--                 Added Enum values to devControlTestStatus,
--                 Modified comments on devControlTestCommand)
--                12/31/97 - 1/6/97 by R. Steinberger (ras@eng.paradyne.com)
--                (Completely removed devControlSLA
--                 Changed Enum values for devControlRMON.)
--                03/01/2000 by J. Colom (jaime@paradyne.com)
--                (added new ftp control group)
--                03/02/2000 by Rajesh Gowda (rgowda@nj.paradyne.com)
--                (added devSNSwitchFirmwareTable for old service nodes)
--
--  Device Control, Version 5.0, 11/20/00
--		  Conversion to SMIv2 by Rajesh Raghavan
--		  Addition of Configuration Change Management Objects and Traps
--
--  Device Control, Version 5.1, 05/03/01 by M. Mohankumar (mohanm@eng.paradyne.com)
--		  Added Auto Firmware Download Group
--
--  Device Control, Version 5.2, 06/13/01 by M. Mohankumar (mohanm@eng.paradyne.com)
--		  Changed the description for devAutoFwStatus and devIsAutoFwEnabled of
--                pdnAutoFwGroup
--
--  Device Control, Version 5.3, 11/12/01 by Dragana Gough (dgough@paradyne.com)
--		 Added new Ftp transfer table that is indexed by session ID and contains
--		 three new objects(different from devFileXferConfigTable) -
--	         pdnDevFileXferSessionID, pdnDevFileXferifIndex, pdnDevFileXferUserAccount.
--
--               Added new objects to pdnCCMAutoBackup Group - pdnCCMAutoBackupFilename,
--               pdnCCMAutoBackupAppendTimeStampToFilename, pdnCCMAutoBackupServerIpAddress,
--		 pdnCCMAutoBackupUserName, pdnCCMAutoBackupUserPassword, 
--               pdnCCMAutoBackuUserAccount, and pdnCCMAutoBackupCopyProtocol
--
--		Added new objects to pdnConfigChangeManagement group -
--		pdnCCMOperation.
--
--  Device Control, Version 5.4, 11/14/01 by Dragana Gough (dgough@paradyne.com)
--		 Added group definition, switched RowStatus and XferXferTime positions
--		 in the table. Added pdnDevFileXferSessionIDNext singular object
--  Device Control, Version 5.5, 12/04/01 by Dragana Gough (dgough@paradyne.com)
--		 Added pdnDevFileXferApply.
--
-- ====================================================================
--
pdnControl MODULE-IDENTITY
	LAST-UPDATED 	"0011201800Z"
	ORGANIZATION 	"Paradyne Networks MIB Working Group"
	CONTACT-INFO 	"Paradyne Networks
			331 Newman Springs Road
			Red Bank, NJ 07701
			www.paradyne.com

			General Comments to: mibwg_team@eng.paradyne.com"

	DESCRIPTION	"This MIB Module allow a user to reset a device
			in the DSLAM, as well as perform various operations
			related to the storage and retrieval of firmware
			and configuration files on devices."

	REVISION	"0011201800Z"
	DESCRIPTION	"Initial Conversion to SMIv2"
	::= { pdn-common 10 }
		     
--
-- Device Reset Object
--
-- Used to reset (warm boot) the device.
--
devHWControlReset OBJECT-TYPE
    SYNTAX  INTEGER {
        noOp(1),
        reset(2)
            }
    MAX-ACCESS  read-write
    STATUS current 
    DESCRIPTION
        "Writing the value reset(2) to this object initiates a
         Hardware power-on reset of the device.  
         The value read from this object is noOp(1)."
    ::= { pdnControl 1 }

-- ====================================================================
--
-- Test Table
--
-- This table controls device level tests.
--
devControlTestTable OBJECT-TYPE
    SYNTAX SEQUENCE OF DevControlTestEntry
    MAX-ACCESS  not-accessible
    STATUS current 
    DESCRIPTION
        "A list of Device tests that may be run."
    ::= { pdnControl 2 }

devControlTestEntry OBJECT-TYPE
    SYNTAX  DevControlTestEntry
    MAX-ACCESS  not-accessible
    STATUS current 
    DESCRIPTION
        "The device Test Table."
    INDEX  { devControlTest }
    ::= { devControlTestTable 1 }

DevControlTestEntry ::=
    SEQUENCE {
    devControlTest
        INTEGER,
    devControlTestStatus
        INTEGER,
    devControlTestCmd
        INTEGER
    }

devControlTest OBJECT-TYPE
    SYNTAX INTEGER {
        lampTest (1),
        v35DTELpbkTest (2)
    }
    MAX-ACCESS read-only
    STATUS current
    DESCRIPTION
        "An index into the test table that indicates which test 
         the row involves."
::= { devControlTestEntry 1 }

devControlTestStatus OBJECT-TYPE
    SYNTAX  INTEGER {
        active(1),
        inactive(2)
    }
    MAX-ACCESS  read-only
    STATUS current 
    DESCRIPTION
        "The test status on the device. This object indicates whether
         the indexed test is currently active(1) or inactive(2)."
::= { devControlTestEntry 2 }

devControlTestCmd OBJECT-TYPE
    SYNTAX INTEGER {
        start  (1),
        stop   (2)
    }
    MAX-ACCESS read-create
    STATUS current
    DESCRIPTION
        "Used to start or stop the indexed test.
         When read, the value returned will be the next logical command."
::= { devControlTestEntry 3 }

-- ====================================================================
--
-- Download Control Table
--
-- This table is used to control and provide information concerning
-- downloaded executable images. 
--
devControlDownLoadTable OBJECT-TYPE
    SYNTAX SEQUENCE OF DevControlDownLoadEntry
    MAX-ACCESS  not-accessible
    STATUS current 
    DESCRIPTION
        "A list of the current Download Releases and their associated status.
	 Each Download Release will be indexed by a number from 1 to N.
	 The user will be able to view the Download Release String and 
	 Operational Status of the release (valid or invalid) and 
	 activate a valid Download Release by changing the 
	 Administration Status to active."
    ::= { pdnControl 3 }

devControlDownLoadEntry OBJECT-TYPE
    SYNTAX  DevControlDownLoadEntry
    MAX-ACCESS  not-accessible
    STATUS current 
    DESCRIPTION
        "The Device DownLoad Release entry."
    INDEX  { devControlDownLoadIndex }
    ::= { devControlDownLoadTable 1 }

DevControlDownLoadEntry ::=
    SEQUENCE {
    devControlDownLoadIndex
	Integer32,
    devControlDownLoadRelease
        DisplayString,
    devControlDownLoadOperStatus
        INTEGER,
    devControlDownLoadAdminStatus
        INTEGER
    }

devControlDownLoadIndex OBJECT-TYPE
    SYNTAX Integer32 
    MAX-ACCESS read-only
    STATUS current
    DESCRIPTION
        "This object is used to index the download table (range 1 to N)."
::= { devControlDownLoadEntry 1 }

devControlDownLoadRelease OBJECT-TYPE
    SYNTAX  DisplayString (SIZE (1..16))
    MAX-ACCESS  read-only
    STATUS current 
    DESCRIPTION
  	"This object indicates the Software Release for 
	 this Download. If the Software Download is Operational Status
	 is invalid, the Software Revision Number will be blank."
::= { devControlDownLoadEntry 2 }

devControlDownLoadOperStatus OBJECT-TYPE
    SYNTAX INTEGER {
	valid(1),
	invalid(2)
    }
    MAX-ACCESS read-only
    STATUS current
    DESCRIPTION
        "This object indicates whether or not the indexed 
	 download entry contains a valid(1) or invalid(2) download."
::= { devControlDownLoadEntry 3 }

devControlDownLoadAdminStatus OBJECT-TYPE
    SYNTAX INTEGER {
	active(1),
	inactive(2)
    }
    MAX-ACCESS read-create
    STATUS current
    DESCRIPTION
        "This object indicates whether or not the indexed 
	 download entry is active(1) or inactive(2). 
	 Writing active(1) will activate that software release
	 and cause the unit to reset (response may timeout).
	 Writing active(1) to a download entry whose 
	 devControlDownloadOperStatus is invalid will return BAD VALUE.
	 Writing inactive(2) will always return BAD VALUE."
::= { devControlDownLoadEntry 4 }

-- ====================================================================
--
-- The RMON Group
--
-- This group is a collection of items that control the RMON process.
--
devControlRMON    OBJECT IDENTIFIER ::= { pdnControl 4}

devControlRMONAdminStatus OBJECT-TYPE
    SYNTAX  INTEGER {
        enabled(1),
        disabled(2)
    }
    MAX-ACCESS  read-write
    STATUS current 
    DESCRIPTION
        "The desired state of the RMON process.  If set to enabled(1), the 
         RMON process will perform the collection tasks it is set up to do.  
         If it is disabled(2), RMON will not perform collection."
    ::= { devControlRMON 1 }

-- ====================================================================
--
--  Objects that switch banks in the Service Nodes(ASN).
--  devSNSwitchFirmwareTable is deprecated by devFirmwareControl
--  group in sle_devControl.mib (Atlantis 4.0 onwards)

devSNSwitchFirmwareTable OBJECT-TYPE
    SYNTAX SEQUENCE OF DevSNSwitchFirmwareEntry
    MAX-ACCESS  not-accessible
    STATUS current 
    DESCRIPTION
        "A list of objects needed to switch bank
         and reset the Service Node (ASN)."
    ::= { pdnControl 5 }

devSNSwitchFirmwareEntry OBJECT-TYPE
    SYNTAX  DevSNSwitchFirmwareEntry
    MAX-ACCESS  not-accessible
    STATUS current 
    DESCRIPTION
        "The Service Node Switch Firmware table."
    INDEX  { devSNSwitchFirmwareIndex }
    ::= { devSNSwitchFirmwareTable 1 }

DevSNSwitchFirmwareEntry ::=
    SEQUENCE {
    devSNSwitchFirmwareIndex
        Integer32,
    devSNSwitchFirmwareBank
        INTEGER
    }

devSNSwitchFirmwareIndex OBJECT-TYPE
    SYNTAX Integer32
    MAX-ACCESS read-only
    STATUS current
    DESCRIPTION
        "An index into the Service Node switch firmware table that
         indicates which interface the row involves. This index
         corresponds to the entityPhysicalIndex of the entity MIB "
::= { devSNSwitchFirmwareEntry 1 }

devSNSwitchFirmwareBank OBJECT-TYPE
    SYNTAX  INTEGER {
        noOp(1),
        switch(2)
    }
    MAX-ACCESS  read-create
    STATUS current 
    DESCRIPTION
         "Writing the value switch(2) to this object will
          switch the banks to change the firmware being
          used on the service node. The firmware from the stand
          by (not active) bank will be used as the currently running
          firmware.  The value read from this object is noOp(1)."
::= { devSNSwitchFirmwareEntry 2 }

-- ====================================================================
--
-- The FTP Group
--
-- This group is a collection of items that control the FTP process
--
devControlFTP    OBJECT IDENTIFIER ::= { pdnControl 6}

devControlFTPRate OBJECT-TYPE
    SYNTAX  Integer32
    MAX-ACCESS  read-write
    STATUS current 
    DESCRIPTION
        "FTP max transfer rate in (Kbps)"
    ::= { devControlFTP 1 }


-- =======================================================
--
--  The Paradyne File Transfer Group  (J.Strain)
-- =======================================================
devFileXferMIBObjects OBJECT IDENTIFIER ::= { pdnControl 7}
devFileXferMIBTraps OBJECT IDENTIFIER ::= { pdnControl 8 }

devFileXferConfigTable OBJECT-TYPE
    SYNTAX  SEQUENCE OF DevFileXferConfigEntry
    MAX-ACCESS  not-accessible
    STATUS current 
    DESCRIPTION
           "The Paradyne  FileXfer Client Config Table."
    ::= { devFileXferMIBObjects 1 }

devFileXferConfigEntry OBJECT-TYPE
    SYNTAX  DevFileXferConfigEntry
    MAX-ACCESS  not-accessible
    STATUS current 
    DESCRIPTION

       " Use of the File Tranfer MIB could be used with other MIBS in
              the following manner:
                  a) Use another MIB/means to verify available space /make room
                     for a file to be transfered to this device
                  b) Use this MIB to download the file
                  c) Use another MIB/means to select the file you want to make 
                     active
                                        if your selecting firmware for example.
                  d) Use another MIB/means to reset the device.

        A management station wishing to initiate a file transfer needs to
                         create an entry in this table. To do so, you must
       first identify the ifIndex of the device you intend to
       do the transfer with.  You should
       then create the associated instance of the row status
       It must also, either in the same
       or in successive PDUs, create an instance of
       devFileXferFileName, DevFileXferFileType, 
.      devFileXferServerIpAddress,
       devFileXferOperation.

       It should also modify the default values for the other
       configuration objects if the defaults are not appropriate.

       Once the appropriate instance of all the configuration
       objects have been created, either by an explicit SNMP
       set request or by default, the row status should be set
       to active to initiate the request. Note that this entire
       procedure may be initiated via a single set request which
       specifies a row status of createAndGo as well as specifies
       valid values for the non-defaulted configuration objects.

       Once the DevFileXferConfigEntry request has been created (i.e. the
       devFileXferRowStatus has been made active), the entry
       cannot be modified - the only operation possible
       after this is to delete the row.

       Once the request completes, the management station should
       retrieve the values of the status objects of interest, and
       should then delete the entry.  In order to prevent old
       entries from clogging the table, entries could be aged out,
       but an entry will never be deleted within 5 minutes of
       completing.  "
    INDEX   { ifIndex }
    ::= { devFileXferConfigTable  1 }

DevFileXferConfigEntry ::=
    SEQUENCE {

    devFileXferFileName
        DisplayString,

    devFileXferCopyProtocol
        INTEGER,

    devFileXferFileType
        INTEGER,

    devFileXferServerIpAddress
        IpAddress,

    devFileXferUserName
        DisplayString,

    devFileXferUserPassword
        DisplayString,

    devFileXferOperation
        INTEGER,

    devFileXferPktsSent
        Counter32,

    devFileXferPktsRecv
        Counter32,

    devFileXferOctetsSent
        Counter32,

    devFileXferOctetsRecv
        Counter32,

    devFileXferOwnerString
        OCTET STRING,

    devFileXferStatus
        INTEGER,

    devFileXferErrorStatus
        Integer32,

    devFileXferSendEvent
        INTEGER,

    devFileXferRowStatus
        RowStatus,
		
    devFileXferXferTime
		TimeTicks	
    }

devFileXferFileName OBJECT-TYPE
    SYNTAX  DisplayString
    MAX-ACCESS  read-create
    STATUS current 
    DESCRIPTION
           "This object contains the name of the filetransfer file."
    ::= { devFileXferConfigEntry  1 }

devFileXferCopyProtocol OBJECT-TYPE
    SYNTAX   INTEGER {
                         tftp(1),
                         ftp(2)
                                                }
    MAX-ACCESS  read-create
    STATUS current 
    DESCRIPTION
          "The transfer protocol that should be used to copy the file
           across the network. If the file transfer is to occur locally on the 
           SNMP agent, the method of transfer is left upto the implementation, 
           and is not restricted to the protocols below."

--    DEFVAL  { tftp }
    ::= { devFileXferConfigEntry  2 }

devFileXferFileType OBJECT-TYPE
    SYNTAX  INTEGER {
                                firmware(1),
                                config(2)
                                }

    MAX-ACCESS  read-create
    STATUS current 
    DESCRIPTION
           "Specifies the type of file your want to transfer."
    ::= { devFileXferConfigEntry  3 }

devFileXferServerIpAddress OBJECT-TYPE
    SYNTAX  IpAddress
    MAX-ACCESS  read-create
    STATUS current 
    DESCRIPTION
           "This object contains the file transfer server's IP address. "
    ::= { devFileXferConfigEntry  4 }

devFileXferUserName OBJECT-TYPE
    SYNTAX  DisplayString
    MAX-ACCESS  read-create
    STATUS current 
    DESCRIPTION
           "This object contains the username if a username is needed
        to login to the server."
    ::= { devFileXferConfigEntry  5 }

devFileXferUserPassword OBJECT-TYPE
    SYNTAX  DisplayString
    MAX-ACCESS  read-create
    STATUS current 
    DESCRIPTION
           "This object contains the password if a password is needed
            to login to the server. This object will return null on a read 
            operation."
    ::= { devFileXferConfigEntry  6 }

devFileXferOperation OBJECT-TYPE
    SYNTAX  INTEGER {
                                get(1),
                                put(2)
                                        }
    MAX-ACCESS  read-create
    STATUS current 
    DESCRIPTION
           "This object contains the operation the file transfer wants to 
perform."
    ::= { devFileXferConfigEntry  7 }

devFileXferPktsSent OBJECT-TYPE
    SYNTAX  Counter32
    MAX-ACCESS  read-only
    STATUS current 
    DESCRIPTION
           "This object contains the the number of packets sent to the
        server at the time of interrogation."
    ::= { devFileXferConfigEntry  8 }

devFileXferPktsRecv OBJECT-TYPE
    SYNTAX  Counter32
    MAX-ACCESS  read-only
    STATUS current 
    DESCRIPTION
           "This object contains the the number of packets received from the
        server at the time of interrogation."
    ::= { devFileXferConfigEntry  9 }

devFileXferOctetsSent OBJECT-TYPE
    SYNTAX  Counter32
    MAX-ACCESS  read-only
    STATUS current 
    DESCRIPTION
           "This object contains the the number of octets sent to the
        server at the time of interrogation."
    ::= { devFileXferConfigEntry  10 }

devFileXferOctetsRecv OBJECT-TYPE
    SYNTAX  Counter32
    MAX-ACCESS  read-only
    STATUS current 
    DESCRIPTION
           "This object contains the the number of octets received from the
        server at the time of interrogation."
    ::= { devFileXferConfigEntry  11 }

devFileXferOwnerString OBJECT-TYPE
    SYNTAX   OCTET STRING (SIZE(0..255))
    MAX-ACCESS  read-create
    STATUS current 
    DESCRIPTION
           "The entity which currently has the 'ownership'
        required to invoke the operation on this index."
    ::= { devFileXferConfigEntry  12 }

devFileXferStatus OBJECT-TYPE
    SYNTAX  INTEGER {
                 none(1),
                 success(2),
                 failure(3),
                 inprogress(4)
               }
    MAX-ACCESS  read-only
    STATUS current 
    DESCRIPTION
           "This object contains the status of the file transfer."
    ::= { devFileXferConfigEntry  13 }

devFileXferErrorStatus OBJECT-TYPE
    SYNTAX  Integer32
    MAX-ACCESS  read-only
    STATUS current 
    DESCRIPTION
           "This object contains the reason code of the failure determined in 
devFileXferStatus.
        The reason code are specific to the file transfer protocol.

        Please refer to the file transfer protocols respective RFC for 
clarification
        of the error code value meanings.

        TFTP Error Codes from rfc 1350
        FTP Error Codes from rfc 959"

    ::= { devFileXferConfigEntry  14 }

devFileXferSendEvent OBJECT-TYPE
    SYNTAX INTEGER {
    active(1),
    inactive(2)
    }
    MAX-ACCESS read-create
    STATUS current
    DESCRIPTION
        "This object indicates whether or not to send the 
         devFileXferEvent event trap ."
    ::= { devFileXferConfigEntry  15 }

devFileXferRowStatus OBJECT-TYPE
    SYNTAX  RowStatus
    MAX-ACCESS  read-create
    STATUS current 
    DESCRIPTION
           "This object is used to create
     a new row or delete an
     existing row in this table."
    ::= { devFileXferConfigEntry  16 }

devFileXferXferTime OBJECT-TYPE
    SYNTAX  TimeTicks 
    MAX-ACCESS  read-only
    STATUS current 
    DESCRIPTION
        "This object indicates the elapsed time 
		(in hundredths of a second) of the file transfer."
    ::= { devFileXferConfigEntry 17 }

-- ##########################################
-- Net file transfer table for accessing by 
-- session id 
--###########################################

pdnDevFileXferTable OBJECT-TYPE
    SYNTAX  SEQUENCE OF PdnDevFileXferEntry
    MAX-ACCESS  not-accessible
    STATUS current 
    DESCRIPTION
           "The Paradyne  FileXfer Image Client Config Table accessed by session id."
    ::= { devFileXferMIBObjects 2 }

pdnDevFileXferEntry OBJECT-TYPE
    SYNTAX  PdnDevFileXferEntry
    MAX-ACCESS  not-accessible
    STATUS current 
    DESCRIPTION

       " Use of the File Tranfer MIB could be used with other MIBS in
              the following manner:
                  a) Use another MIB/means to verify available space /make room
                     for a file to be transfered to this device
                  b) Use this MIB to download the file
                  c) Use another MIB object/means to select the file you want to make 
                     active
                                        if your selecting firmware for example.
                  d) Use another MIB/means to reset the device.

        A management station wishing to initiate a file transfer needs to
                         create an entry in this table. To do so, you must
       first identify the session id of the session that   
       the transfer is done with.  This is done by setting SessionID
       to 0 on SET and when session is establish entering that session
       id into this object. You should
       then create the associated instance of the row status
       It must also, either in the same
       or in successive PDUs, create an instance of
       pdnDevFileXferFileName, pdnDevFileXferFileType, 
.      pdnDevFileXferServerIpAddress,
       pdnDevFileXferOperation.

       It should also modify the default values for the other
       configuration objects if the defaults are not appropriate.

       Once the appropriate instance of all the configuration
       objects have been created, either by an explicit SNMP
       set request or by default, the row status should be set
       to active to initiate the request. Note that this entire
       procedure may be initiated via a single set request which
       specifies a row status of createAndGo as well as specifies
       valid values for the non-defaulted configuration objects.

       Once the request completes, the management station should
       retrieve the values of the status objects of interest, and
       should then delete the entry.  In order to prevent old
       entries from clogging the table, entries could be aged out,
       but an entry will never be deleted within 5 minutes of
       completing.  "
    INDEX   { pdnDevFileXferSessionID }
    ::= { pdnDevFileXferTable  1 }

PdnDevFileXferEntry ::=
    SEQUENCE {

    pdnDevFileXferSessionID
        Integer32,

    pdnDevFileXferifIndex
        Integer32,

    pdnDevFileXferFileName
        DisplayString,

    pdnDevFileXferCopyProtocol
        INTEGER,

    pdnDevFileXferFileType
        INTEGER,

    pdnDevFileXferServerIpAddress
        IpAddress,

    pdnDevFileXferUserName
        DisplayString,

    pdnDevFileXferUserPassword
        DisplayString,

    pdnDevFileXferUserAccount
        DisplayString,

    pdnDevFileXferOperation
        INTEGER,

    pdnDevFileXferPktsSent
        Counter32,

    pdnDevFileXferPktsRecv
        Counter32,

    pdnDevFileXferOctetsSent
        Counter32,

    pdnDevFileXferOctetsRecv
        Counter32,

    pdnDevFileXferOwnerString
        OCTET STRING,

    pdnDevFileXferStatus
        INTEGER,

    pdnDevFileXferApply
        INTEGER,

    pdnDevFileXferErrorStatus
        Integer32,

    pdnDevFileXferSendEvent
        INTEGER,

    pdnDevFileXferXferTime
		TimeTicks,	

    pdnDevFileXferRowStatus
        RowStatus
    }

pdnDevFileXferSessionID OBJECT-TYPE
    SYNTAX Integer32 
    MAX-ACCESS not-accessible
    STATUS current
    DESCRIPTION
	   "This object is the session id. This object is used
	    by FileXfer Table to identify the row
	    of this table.  When creating the new row
	    in the table the value of this object may be 
	    obtained by retreiving the value
	    of pdnDevFileXferSessionIDNext."
    ::= { pdnDevFileXferEntry 1 }

pdnDevFileXferifIndex OBJECT-TYPE
    SYNTAX Integer32
    MAX-ACCESS read-create
    STATUS current
    DESCRIPTION
	   "This object specifies the interface
	    number that corresponds to RFC1213.
	    It this object is not used the value
	    of this object should be zero."
    ::= { pdnDevFileXferEntry 2 }

pdnDevFileXferFileName OBJECT-TYPE
    SYNTAX  DisplayString
    MAX-ACCESS  read-create
    STATUS current 
    DESCRIPTION
           "This object contains the name of the filetransfer file."
    ::= { pdnDevFileXferEntry  3 }

pdnDevFileXferCopyProtocol OBJECT-TYPE
    SYNTAX   INTEGER {
                         tftp(1),
                         ftp(2)
                                                }
    MAX-ACCESS  read-create
    STATUS current 
    DESCRIPTION
          "The transfer protocol that should be used to copy the file
           across the network. If the file transfer is to occur locally on the 
           SNMP agent, the method of transfer is left upto the implementation, 
           and is not restricted to the protocols below."

--    DEFVAL  { tftp }
    ::= { pdnDevFileXferEntry  4 }

pdnDevFileXferFileType OBJECT-TYPE
    SYNTAX  INTEGER {
                                firmware(1),
                                config(2)
                                }

    MAX-ACCESS  read-create
    STATUS current 
    DESCRIPTION
           "Specifies the type of file your want to transfer."
    ::= { pdnDevFileXferEntry  5 }

pdnDevFileXferServerIpAddress OBJECT-TYPE
    SYNTAX  IpAddress
    MAX-ACCESS  read-create
    STATUS current 
    DESCRIPTION
           "This object contains the file transfer server's IP address. "
    ::= { pdnDevFileXferEntry  6 }

pdnDevFileXferUserName OBJECT-TYPE
    SYNTAX  DisplayString
    MAX-ACCESS  read-create
    STATUS current 
    DESCRIPTION
           "This object contains the username if a username is needed
        to login to the server."
    ::= { pdnDevFileXferEntry  7 }

pdnDevFileXferUserPassword OBJECT-TYPE
    SYNTAX  DisplayString
    MAX-ACCESS  read-create
    STATUS current 
    DESCRIPTION
           "This object contains the password if a password is needed
            to login to the server. This object will return null on a read 
            operation."
    ::= { pdnDevFileXferEntry  8 }

pdnDevFileXferUserAccount OBJECT-TYPE
    SYNTAX  DisplayString
    MAX-ACCESS  read-create
    STATUS current 
    DESCRIPTION
           "This object contains the name of the the user account information
	    that is stored on ftp server. Server  would contain user name and password
	    under this account name. This object will return null on a read 
            operation. The default value fo this is a null string."
    ::= { pdnDevFileXferEntry  9 }

pdnDevFileXferOperation OBJECT-TYPE
    SYNTAX  INTEGER {
                                get(1),
                                put(2)
                                        }
    MAX-ACCESS  read-create
    STATUS current 
    DESCRIPTION
           "This object contains the operation the file transfer wants to 
            perform."
    ::= { pdnDevFileXferEntry  10 }

pdnDevFileXferPktsSent OBJECT-TYPE
    SYNTAX  Counter32
    MAX-ACCESS  read-only
    STATUS current 
    DESCRIPTION
           "This object contains the the number of packets sent to the
        server at the time of interrogation."
    ::= { pdnDevFileXferEntry  11 }

pdnDevFileXferPktsRecv OBJECT-TYPE
    SYNTAX  Counter32
    MAX-ACCESS  read-only
    STATUS current 
    DESCRIPTION
           "This object contains the the number of packets received from the
        server at the time of interrogation."
    ::= { pdnDevFileXferEntry  12 }

pdnDevFileXferOctetsSent OBJECT-TYPE
    SYNTAX  Counter32
    MAX-ACCESS  read-only
    STATUS current 
    DESCRIPTION
           "This object contains the the number of octets sent to the
        server at the time of interrogation."
    ::= { pdnDevFileXferEntry  13 }

pdnDevFileXferOctetsRecv OBJECT-TYPE
    SYNTAX  Counter32
    MAX-ACCESS  read-only
    STATUS current 
    DESCRIPTION
           "This object contains the the number of octets received from the
        server at the time of interrogation."
    ::= { pdnDevFileXferEntry  14 }

pdnDevFileXferOwnerString OBJECT-TYPE
    SYNTAX   OCTET STRING (SIZE(0..255))
    MAX-ACCESS  read-create
    STATUS current 
    DESCRIPTION
           "The entity which currently has the 'ownership'
        required to invoke the operation on this index."
    ::= { pdnDevFileXferEntry  15 }

pdnDevFileXferStatus OBJECT-TYPE
    SYNTAX  INTEGER {
                 none(1),
                 success(2),
                 failure(3),
                 inprogress(4)
               }
    MAX-ACCESS  read-only
    STATUS current 
    DESCRIPTION
           "This object contains the status of the file transfer."
    ::= { pdnDevFileXferEntry  16 }

pdnDevFileXferApply OBJECT-TYPE
    SYNTAX  INTEGER {
                 yes(1),
                 no(2)
               }
    MAX-ACCESS  read-create
    STATUS current 
    DESCRIPTION
           "This object is configured to specify if the 
	    firmware download will be applied immediatley after 
	    file transfer or not."
    ::= { pdnDevFileXferEntry  17 }

pdnDevFileXferErrorStatus OBJECT-TYPE
    SYNTAX  Integer32
    MAX-ACCESS  read-only
    STATUS current 
    DESCRIPTION
           "This object contains the reason code of the failure determined in 
            devFileXferStatus.
            The reason code are specific to the file transfer protocol.
            Please refer to the file transfer protocols respective RFC for 
            clarification
            of the error code value meanings.
            TFTP Error Codes from rfc 1350
            FTP Error Codes from rfc 959"

    ::= { pdnDevFileXferEntry  18 }

pdnDevFileXferSendEvent OBJECT-TYPE
    SYNTAX INTEGER {
    active(1),
    inactive(2)
    }
    MAX-ACCESS read-create
    STATUS current
    DESCRIPTION
        "This object indicates whether or not to send the 
         pdnDevFileXferEvent event trap ."
    ::= { pdnDevFileXferEntry  19 }

pdnDevFileXferXferTime OBJECT-TYPE
    SYNTAX  TimeTicks 
    MAX-ACCESS  read-only
    STATUS current 
    DESCRIPTION
        "This object indicates the elapsed time 
		(in hundredths of a second) of the file transfer."
    ::= { pdnDevFileXferEntry 20 }

pdnDevFileXferRowStatus OBJECT-TYPE
    SYNTAX  RowStatus
    MAX-ACCESS  read-create
    STATUS current 
    DESCRIPTION
           "This object is used to create
     a new row or delete an
     existing row in this table."
    ::= { pdnDevFileXferEntry  21 }

-- ====================================================================
--
-- Firmware Control Table
--
-- This table is used to control and provide information concerning
-- firmware/executable images.
--
-- ====================================================================
devFirmwareControlMIBObjects OBJECT IDENTIFIER ::= { pdnControl 9 }

devFirmwareControlTable OBJECT-TYPE
    SYNTAX SEQUENCE OF DevFirmwareControlEntry
    MAX-ACCESS  not-accessible
    STATUS  current
    DESCRIPTION
        "A list of the current Firmware Releases and their associated
         status.  Each Firmware Release will be indexed by a number
         from 1 to N.  The user will be able to view the Firmware
         Release String and Operational Status of the release (valid
                 or invalid) and activate a valid Firmware Release by changing
                 the Administration Status to active."
    ::= { devFirmwareControlMIBObjects 1 }

devFirmwareControlEntry OBJECT-TYPE
    SYNTAX  DevFirmwareControlEntry
    MAX-ACCESS  not-accessible
    STATUS  current
    DESCRIPTION
        "The Device Firmware Release entry."
    INDEX  { devFirmwareControlIndex }
    ::= { devFirmwareControlTable 1 }

DevFirmwareControlEntry ::=
    SEQUENCE {
    devFirmwareControlIndex
    	Integer32,
    devFirmwareControlRelease
        DisplayString,
    devFirmwareControlOperStatus
        INTEGER,
    devFirmwareControlAdminStatus
        INTEGER
    }

devFirmwareControlIndex OBJECT-TYPE
    SYNTAX Integer32
    MAX-ACCESS read-only
    STATUS current
    DESCRIPTION
        "This object is used to index the Firmware table (range 1 to N)."
::= { devFirmwareControlEntry 1 }

devFirmwareControlRelease OBJECT-TYPE
    SYNTAX  DisplayString (SIZE (1..16))
    MAX-ACCESS  read-only
    STATUS  current
    DESCRIPTION
    "This object indicates the Software Release for
     this Firmware. If the Software Firmware is Operational Status
     is invalid, the Software Revision Number will be blank."
::= { devFirmwareControlEntry 2 }

devFirmwareControlOperStatus OBJECT-TYPE
    SYNTAX INTEGER {
    valid(1),
    invalid(2),
    unknown(3)
    }
    MAX-ACCESS read-only
    STATUS current
    DESCRIPTION
     "This object indicates whether or not the indexed
     Firmware entry contains a valid(1) or invalid(2) Firmware."
::= { devFirmwareControlEntry 3 }

devFirmwareControlAdminStatus OBJECT-TYPE
    SYNTAX INTEGER {
    active(1),
    inactive(2)
    }
    MAX-ACCESS read-create
    STATUS current
    DESCRIPTION
        "This object indicates whether or not the indexed
     Firmware entry is active(1) or inactive(2).
     Writing active(1) will activate that software release
     and cause the unit to reset (response may timeout).
     Writing active(1) to a Firmware entry whose
     devFirmwareControlOperStatus is invalid will return BAD VALUE.
     Writing inactive(2) will always return BAD VALUE."
::= { devFirmwareControlEntry 4 }

-- ====================================================================
--
-- Configuration Change Management (CCM) Group
-- Modified 10/4/2000 by Rajesh Raghavan
--
-- Objects for controlling automated backup and restore of the 
-- configuration files of devices (cards) in the slots of the 
-- Paradyne DSLAM chassis.
--
-- ====================================================================
pdnConfigChangeMgmt OBJECT IDENTIFIER ::= { pdnControl 10 }

pdnCCMAutoBackup OBJECT IDENTIFIER ::= { pdnConfigChangeMgmt 1 }
  -- CCM Auto Backup Group

pdnCCMAutoBackupType OBJECT-TYPE
    SYNTAX	INTEGER { disabled(0), fixed(1), dynamic(2) }
    MAX-ACCESS  read-write
    STATUS	current
    DESCRIPTION
	"This object indicates whether automatic backup of device
	configuration files to the MCC Flash File System is disabled,
	performed according to a fixed schedule, or whether it occurs
	dynamically at a specified interval after the latest configuration
	change to a device."

  ::= { pdnCCMAutoBackup 1 }

pdnCCMAutoBackupFixedDay OBJECT-TYPE
    SYNTAX	BITS {  sunday(0), 
			monday(1), 
			tuesday(2), 
			wednesday(3), 
			thursday(4), 
			friday(5), 
			saturday(6) }
    MAX-ACCESS	read-write
    STATUS	current
    DESCRIPTION
	"This object indicates the days of the week on which fixed schedule
	automatic backups occur.  If all bits are set, backups occur daily."

  ::= { pdnCCMAutoBackup 2 }

pdnCCMAutoBackupFixedTime OBJECT-TYPE
    SYNTAX	Integer32 (0..1440)
    UNITS	"minutes"
    MAX-ACCESS	read-write
    STATUS	current
    DESCRIPTION
	"This object indicates the time of day, in minutes past midnight,
	 at which automatic backups on a fixed schedule occur."

  ::= { pdnCCMAutoBackup 3 }

pdnCCMAutoBackupDynamicTime OBJECT-TYPE
    SYNTAX	Integer32 (30..1440)
    UNITS	"minutes"
    MAX-ACCESS	read-write
    STATUS	current
    DESCRIPTION
	"This object indicates the interval (in minutes) after the most recent
	configuration change, when a card's configuration will be backed up
	to the MCC Flash File System, when automatic backups are occurring on
	a dynamic schedule.  The minimum interval is 30 minutes.
	The maximum interval is 24 hours (1440 minutes)."

  ::= { pdnCCMAutoBackup 4 }

pdnCCMAutoBackupAppendTimeStampToFilename OBJECT-TYPE
    SYNTAX	INTEGER {
			  enable(1),
			  disable(2)
			}
    MAX-ACCESS  read-create
    STATUS current 
    DESCRIPTION
	"This object indicates that  the time is to be appended to filename of the file 
	 stored to upon automated backup. The defualt value of this
	 object is disabled(2)."
  ::= { pdnCCMAutoBackup 5 }

pdnCCMAutoBackupFilename OBJECT-TYPE
    SYNTAX  DisplayString
    MAX-ACCESS  read-create
    STATUS current 
    DESCRIPTION
	"This is file name that the configuration will be stored to upon automated backup."
  ::= { pdnCCMAutoBackup 6 }

pdnCCMAutoBackupServerIpAddress OBJECT-TYPE
    SYNTAX	IpAddress
    MAX-ACCESS  read-create
    STATUS current 
    DESCRIPTION
	"This object is to configure Ip address of the server used to perform autobackup."
  ::= { pdnCCMAutoBackup 7 }

pdnCCMAutoBackupUserName OBJECT-TYPE
    SYNTAX      DisplayString
    MAX-ACCESS  read-create
    STATUS current 
    DESCRIPTION
	"This object user name used to start ftp session for automatic backup."
  ::= { pdnCCMAutoBackup 8 }

pdnCCMAutoBackupUserPassword OBJECT-TYPE
    SYNTAX      DisplayString
    MAX-ACCESS  read-create
    STATUS current 
    DESCRIPTION
	"This object user password that is paired with user name for ftp server login."
  ::= { pdnCCMAutoBackup 9 }

pdnCCMAutoBackupUserAccount OBJECT-TYPE
    SYNTAX      DisplayString
    MAX-ACCESS  read-create
    STATUS current 
    DESCRIPTION
	"This object is user account name that ftp server contains.
        Under this name ftp server stores UserName and UserPassword info.
	If this object is null(not configured) than the 
	pdnCCMAutoBackupUserName and pdnCCMAutoBackupUserPassword
	are used. The default is null string."
  ::= { pdnCCMAutoBackup 10 }

pdnCCMAutoBackupCopyProtocol OBJECT-TYPE
    SYNTAX   INTEGER {
                         tftp(1),
                         ftp(2)
                                                }
    MAX-ACCESS  read-create
    STATUS current 
    DESCRIPTION
          "The transfer protocol that should be used to copy the file
           across the network. If the file transfer is to occur locally on the 
           SNMP agent, the method of transfer is left upto the implementation, 
           and is not restricted to the protocols below."
--    DEFVAL  { tftp }
    ::= { pdnCCMAutoBackup 11 }

pdnCCMAutoRestore OBJECT-TYPE
    SYNTAX	SwitchState
    MAX-ACCESS	read-write
    STATUS	current
    DESCRIPTION
	"This object specifies whether the MCC Flash File System will restore
	stored configuration files to newly inserted cards in the DSLAM."

  ::= { pdnConfigChangeMgmt 2 }

pdnCCMResyncOperation OBJECT-TYPE
    SYNTAX  INTEGER { noOp(1), get(2), put(3) }
    MAX-ACCESS  read-write
    STATUS  current
    DESCRIPTION
	"This object contains the operation performed when ResyncState is 
	enabled.  The value 'get' retrieves configuration files from the
	MCC FFS to all the devices.  The value 'put' stores all the
	configuration files on the MCC FFS. Querying this object always
	retrieves the value noOp(1)"
    ::= { pdnConfigChangeMgmt 3 }

pdnCCMOperation OBJECT-TYPE
    SYNTAX INTEGER {
		     noOp   (1),
                     apply  (2),
		     save   (3),
		     reset  (4),
		     revert (5),
		     default(6)
		     }
    MAX-ACCESS read-write
    STATUS current
    DESCRIPTION
	" This object contains configuration options for operations performed
          to manage object. SAVE(3) operation is interpreted as copying
	  running configuration to database (nvram). APPLY(2) is operation
	  performed to make configuration paramters take in effect. RESET(4)
	  operation is designed to upload database (nvram),saved, configuration,
	  and make it running configuration. REVERT(5) is configuration option used
	  in a case of error upon set operation (before DD applies configuration
	  parameter(s)). It will effectively make previous applied configuration 
	  parameter set valid, running configuration. In some systems this will be an
	  internal (user transperent) operation in case of error deteced by DD.
	  DEFAULT(6) will upload default parameters to running configuration without
	  changing saved configuration in a database (nvram).
	  Querying this object always retrieves the value noOp(1)."
    ::= { pdnConfigChangeMgmt 4 }
 
-- the following object(s) can be used in conjuction with various tables
-- to create new table entries

pdnDevFileXferSessionIDNext OBJECT-TYPE
    SYNTAX   	Integer32
    MAX-ACCESS  read-only
    STATUS 	current
    DESCRIPTION
	" This object contains an appropriate value to be
	  used for pdnDevFileXferTable.
	  The value of 0 indicates that no unassigned 
	  entries are available.  To obtain 
	  pdnDevFileXferSessionID value for the new entry 
	  the manager issues a management protocol retrieval 
	  operation to obtain a current value of this object.
	  After each retrieval, the agent should modify the value
	  to the next unassigned index.  "
    ::= { devFileXferMIBObjects 3 }

pdnControlMIBTrapsV2	OBJECT-IDENTITY
	STATUS current
	DESCRIPTION	"The traps for the device control MIB."
	::= { pdnControl 0 }
--
--      File Transfer Traps
--

devFileXferEvent NOTIFICATION-TYPE
	OBJECTS {  devFileXferStatus , devFileXferErrorStatus,
                                devFileXferOperation, devFileXferFileType,
                                devFileXferFileName }
   STATUS	current
   DESCRIPTION
     "This trap is to communicate a couple of things about
      the completion of a file transfer.

                devFileXferStatus       - Did it complete successfully or not.
                devFileXferErrorStatus  - If not, what was the error code.
                devFileXferOperation    - What operation was performed?.
                devFileXferFileType     - Was it a firmware xfer or config?
                devFileXferFileName     - The name of the file transfered.
         "

 ::= { pdnControlMIBTrapsV2 1 }

--
--	Configuration Change Management Traps
--	Added 8 Sep 2000 by Rajesh Raghavan
--

devAutoBackupFailEvent NOTIFICATION-TYPE
	OBJECTS { entPhysicalIndex }
	STATUS		current
	DESCRIPTION
	    "This trap indicates a condition exists, which prevents 
	    automated backup of a device's configuration to the 
	    Management Controller Card (MCC) Flash File System at a 
	    scheduled time."
 ::= { pdnControlMIBTrapsV2 2 }


devConfigRestoreFailEvent NOTIFICATION-TYPE
	OBJECTS { entPhysicalIndex }
	STATUS		current
	DESCRIPTION
	    "This trap is sent by a device to indicate that an incorrect
	    or incompatible configuration file is being downloaded to the
	    device from the MCC Flash File System."
 ::= { pdnControlMIBTrapsV2 3 }

pdnDevFileXferEvent NOTIFICATION-TYPE
	OBJECTS {  pdnDevFileXferStatus , pdnDevFileXferErrorStatus,
                                pdnDevFileXferOperation, pdnDevFileXferFileType,
                                pdnDevFileXferFileName }
   STATUS	current
   DESCRIPTION
     "This trap is to communicate a couple of things about
      the completion of a file transfer.

                pdnDevFileXferStatus       - Did it complete successfully or not.
                pdnDevFileXferErrorStatus  - If not, what was the error code.
                pdnDevFileXferOperation    - What operation was performed?.
                pdnDevFileXferFileType     - Was it a firmware xfer or config?
                pdnDevFileXferFileName     - The name of the file transfered.
         "

 ::= { pdnControlMIBTrapsV2 5 }

pdnControlMIBGroups	OBJECT IDENTIFIER ::= { pdnControl 11 }

devResetGroup		OBJECT-GROUP
	OBJECTS		{ devHWControlReset }
	STATUS		current
	DESCRIPTION	"Objects to initiate resets of a device"
  ::= { pdnControlMIBGroups 1 }

devControlTestGroup	OBJECT-GROUP
	OBJECTS		{ devControlTest, devControlTestStatus,
			  devControlTestCmd }
	STATUS		current
	DESCRIPTION	"Objects to control device level tests"
  ::= { pdnControlMIBGroups 2 }

devControlDownloadGroup	OBJECT-GROUP
	OBJECTS		{ devControlDownLoadIndex,
			  devControlDownLoadRelease,
			  devControlDownLoadOperStatus,
			  devControlDownLoadAdminStatus }
	STATUS		current
	DESCRIPTION	"A list of the current Download Releases and
			their associated status."
  ::= { pdnControlMIBGroups 3 }

devControlRMONGroup	OBJECT-GROUP
	OBJECTS		{ devControlRMONAdminStatus }
	STATUS		current
	DESCRIPTION	"The desired state of the RMON process."
  ::= { pdnControlMIBGroups 4 }

devSNSwitchFirmwareGroup	OBJECT-GROUP
	OBJECTS		{ devSNSwitchFirmwareIndex, devSNSwitchFirmwareBank }
	STATUS		current
	DESCRIPTION	"Objects needed to switch bank and reset the
			Service Node."
  ::= { pdnControlMIBGroups 5 }

devControlFTPGroup	OBJECT-GROUP
	OBJECTS		{ devControlFTPRate }
	STATUS		current
	DESCRIPTION	"FTP Max Transfer Rate"
  ::= { pdnControlMIBGroups 6 }

devFileXferMIBGroup	OBJECT-GROUP
	OBJECTS		{ devFileXferFileName, devFileXferCopyProtocol,
			  devFileXferFileType, devFileXferServerIpAddress,
			  devFileXferUserName, devFileXferUserPassword,
			  devFileXferOperation,
			  devFileXferPktsSent, devFileXferPktsRecv,
			  devFileXferOctetsSent, devFileXferOctetsRecv,
			  devFileXferOwnerString,
			  devFileXferStatus, devFileXferErrorStatus,
			  devFileXferSendEvent, devFileXferRowStatus,
			  devFileXferXferTime }
	STATUS		current
	DESCRIPTION	"File Transfer Client Config Objects"
  ::= { pdnControlMIBGroups 7 }

devFirmwareControlGroup	OBJECT-GROUP
	OBJECTS		{ devFirmwareControlIndex, devFirmwareControlRelease,
			  devFirmwareControlOperStatus,
			  devFirmwareControlAdminStatus }
	STATUS		current
	DESCRIPTION 	"Current Firmware Releases and associated status."
  ::= { pdnControlMIBGroups 8 }

devConfigChangeMgmtGroup	OBJECT-GROUP
	OBJECTS		{ pdnCCMAutoBackupType,pdnCCMAutoBackupFixedDay,
	                  pdnCCMAutoBackupFixedTime, pdnCCMAutoBackupDynamicTime,
			  pdnCCMAutoBackupAppendTimeStampToFilename,
			  pdnCCMAutoBackupFilename, pdnCCMAutoBackupServerIpAddress,
			  pdnCCMAutoBackupUserName, pdnCCMAutoBackupUserPassword,
			  pdnCCMAutoBackupUserAccount, pdnCCMAutoBackupCopyProtocol,
			  pdnCCMAutoRestore, pdnCCMResyncOperation,
			  pdnCCMOperation }
	STATUS		current
	DESCRIPTION	"Object group used to manage automatic backup and 
			restore of device configuration files."
  ::= { pdnControlMIBGroups 9 }

devFileXferEventGroup	NOTIFICATION-GROUP
	NOTIFICATIONS	{ devFileXferEvent }
	STATUS		current
	DESCRIPTION	"Notifications associated with 
			devFileXferConfigGroup"
  ::= { pdnControlMIBGroups 10 }

devCCMEventGroup		NOTIFICATION-GROUP
	NOTIFICATIONS	{ devAutoBackupFailEvent, 
			  devConfigRestoreFailEvent }
	STATUS		current
	DESCRIPTION	"Notifications indicating a failure occuring during
			automated backup or restore of device configuration 
			files."
  ::= { pdnControlMIBGroups 11 }

pdnDevFileXferEventGroup	NOTIFICATION-GROUP
	NOTIFICATIONS	{ pdnDevFileXferEvent }
	STATUS		current
	DESCRIPTION	"Notifications associated with 
			pdnDevFileXferConfigGroup"
  ::= { pdnControlMIBGroups 16 }

pdnDevFileXferMIBGroup	OBJECT-GROUP
	OBJECTS		{ pdnDevFileXferifIndex,
			  pdnDevFileXferFileName, pdnDevFileXferCopyProtocol,
			  pdnDevFileXferFileType, pdnDevFileXferServerIpAddress,
			  pdnDevFileXferUserName, pdnDevFileXferUserPassword,
			  pdnDevFileXferUserAccount, pdnDevFileXferOperation,
			  pdnDevFileXferPktsSent, pdnDevFileXferPktsRecv,
			  pdnDevFileXferOctetsSent, pdnDevFileXferOctetsRecv,
			  pdnDevFileXferOwnerString,
			  pdnDevFileXferStatus, pdnDevFileXferApply, pdnDevFileXferErrorStatus,
			  pdnDevFileXferSendEvent, pdnDevFileXferXferTime,
			  pdnDevFileXferRowStatus }
	STATUS		current
	DESCRIPTION	"File Transfer Client Objects"
  ::= { pdnControlMIBGroups 14 }

 devNextTableObjectMIBGroup OBJECT-GROUP
	OBJECTS		 { pdnDevFileXferSessionIDNext }
	STATUS		 current
	DESCRIPTION	 " Group of singular objects that decided next
			   available object for mib tables."
  ::= { pdnControlMIBGroups 15 }

-- ====================================================================
--
-- Auto Firmware Download (AutoFw) Group
-- Added 5/3/2001 by Mohan Mohankumar
--
-- Objects for controlling automated Firmware download by MCC to the
-- other cards in the slots of the Paradyne DSLAM chassis.
--
-- ====================================================================

pdnAutoFw	OBJECT IDENTIFIER ::= { pdnControl 12 }

devIsAutoFwEnabled OBJECT-TYPE
    SYNTAX	SwitchState
    MAX-ACCESS  read-write
    STATUS current
    DESCRIPTION
        "Writing the value enabled(1) or disabled(2) to this object enables 
         or disables the Automatic Firmware download feature."
         
     ::= { pdnAutoFw 1 }

devAutoFwStatus OBJECT-TYPE
    SYNTAX  DisplayString (SIZE (1..255))
    MAX-ACCESS  read-only
    STATUS  current
    DESCRIPTION
    "This indicates the Status of Auto Firmware Download
     where each field is separated by a semi-colon.
     The get function will return the status of the latest 
     card downloaded."
     
     ::= { pdnAutoFw 2 }

pdnAutoFwGroup	OBJECT-GROUP
	OBJECTS		{ devIsAutoFwEnabled, devAutoFwStatus }
	STATUS		current
	DESCRIPTION 	"Auto Firmware Download Feature and associated status."
  ::= { pdnControlMIBGroups 12 }

devAutoFwEvent NOTIFICATION-TYPE
	OBJECTS { devAutoFwStatus }
	STATUS          current
    DESCRIPTION
    "This trap is to communicate the result of the Auto Firmware Download.
     The variable binding for this trap would be the devAutoFwStatus
     of pdnAutoFwGroup. The exact format of this display string will 
     be well-documented."
 ::= { pdnControlMIBTrapsV2 4 }

devAutoFwEventGroup		NOTIFICATION-GROUP
	NOTIFICATIONS	{ devAutoFwEvent }
	STATUS		current
	DESCRIPTION	"Notifications indicating the result of the Auto Firmware Download."
  ::= { pdnControlMIBGroups 13 }

END

-- ===============================================================
-- Copyright (C) 2000-2002 Paradyne Corporation.
--  ATM Extension Group
PDN-ATMEXT-MIB DEFINITIONS ::= BEGIN

    IMPORTS
      MODULE-IDENTITY , OBJECT-IDENTITY,
      OBJECT-TYPE, Integer32,  NOTIFICATION-TYPE,
      Unsigned32
       FROM SNMPv2-SMI
      DisplayString,TruthValue
       FROM SNMPv2-TC
      NOTIFICATION-GROUP, OBJECT-GROUP
       FROM SNMPv2-CONF
      pdnAtm
       FROM PDN-HEADER-MIB
      ifIndex,ifOperStatus
       FROM IF-MIB
      atmInterfaceConfEntry, atmTrafficDescrParamEntry,
      atmVpCrossConnectAdminStatus, atmVcCrossConnectAdminStatus,
      aal5VccEntry
       FROM ATM-MIB;

-- ===============================================================
--
--  Extentions to the ATM MIB (RFC 2515)
--
-- ===============================================================

    pdnAtmExtMIB MODULE-IDENTITY
        LAST-UPDATED "200303310000Z"
        ORGANIZATION "Paradyne Networks
                       MIB Working Group"
        CONTACT-INFO
                       "Paradyne Networks
                       331 Newman Springs Road
                       Red Bank, NJ 07701
                       www.paradyne.com

                       General Comments to: mibwg_team@eng.paradyne.com"

        DESCRIPTION
            "This MIB Module extends the ATM-MIB defined in rfc2515"
        
        REVISION "200305150000Z"
        DESCRIPTION "P. Easwar
            o  Changed object name pdnAtmTrafficRateShape
               to pdnAtmTrafficShaping"
        REVISION "200305110000Z"
        DESCRIPTION "P. Easwar
            o  Added Two New Traffic Descriptor Types
                  o pdnAtmNoClpTaggingNoScrCdvtMdcr
                  o pdnAtmNoClpNoScrCdvtMdcr"
        REVISION "200304310000Z"
        DESCRIPTION "P. Easwar
            o  Added pdnAtmTrafficRateShape."

        REVISION "200303310000Z"
        DESCRIPTION "C. Sikes
            o  Added pdnAal5VccExtTable."

        REVISION "200203270000Z"
        DESCRIPTION "J. Pinto
            o  Added pdnAtmIfConfExtRateShape"
        
        REVISION "200012290000Z"
        DESCRIPTION "P. Easwar
            o  modified the following traps (name/description)
                o pdnAtmIfConfExtLineRateAlarmSet
                o pdnAtmIfConfExtLineRateAlarmClear
                ...to the following 
                o pdnAtmIfConfExtEgressLineRateAlarmSet
                o pdnAtmIfConfExtEgressLineRateAlarmClear
            o  added the following traps
                o pdnAtmIfConfExtIngressLineRateAlarmSet
                o pdnAtmIfConfExtIngressLineRateAlarmClear
            o  deleted the following traps
                o pdnAtmCACGauranteeFailed
                o pdnAtmCACGauranteeRestored"

        REVISION "200012010000Z"
        DESCRIPTION "R. Steinberger
            o Added pdnAtmCACGauranteeFailed and pdnAtmCACGauranteeRestored.
            " 
        
        REVISION "200007060000Z"
        DESCRIPTION "P. Easwar
            o  added the following traps 
                o pdnAtmIfConfExtLineRateAlarmSet
                o pdnAtmIfConfExtLineRateAlarmClear
                o pdnAtmIfConfExtVplNoBandwidthAvail
                o pdnAtmIfConfExtVclNoBandwidthAvail
                o changed the description of the following objects
                o pdnAtmIfConfExtVbrRtBandwidthUtil
                o pdnAtmIfConfExtVbrNrtBandwidthUtil
                o  removed the DEFVAL clause from the following objects
                o pdnAtmIfConfExtVbrRtBandwidthUtil
                o pdnAtmIfConfExtVbrNrtBandwidthUtil"

        REVISION "200004280000Z"
        DESCRIPTION "J. Strain
            o  added the following objects to pdnAtmIfConfExtTable
                o pdnAtmIfConfExtBandwidthUtilCbrReserved
                o pdnAtmIfConfExtBandwidthUtilCbrAssigned
                o pdnAtmIfConfExtBandwidthUtilVbrRtReserved
                o pdnAtmIfConfExtBandwidthUtilVbrRtAssigned
                o pdnAtmIfConfExtBandwidthUtilVbrNrtReserved
                o pdnAtmIfConfExtBandwidthUtilVbrNrtAssigned
                o pdnAtmIfConfExtBandwidthUtilUbrReserved
                o pdnAtmIfConfExtBandwidthUtilUbrAssigned"

        REVISION "200003110000Z"
        DESCRIPTION "P. Easwar
            o  added pdnAtmIfConfExtUnknownCellThreshold
               and pdnAtmIfConfExtOcdEventThreshold"
        REVISION "200002180000Z"
        DESCRIPTION "P. Easwar
            o  Initial Release"

         ::= {  pdnAtm 5 }

    pdnAtmExtMIBObjects    OBJECT IDENTIFIER ::= { pdnAtmExtMIB 1 }
    pdnAtmExtMIBTraps      OBJECT IDENTIFIER ::= { pdnAtmExtMIB 2 }
    pdnAtmExtMIBTrapPrefix OBJECT IDENTIFIER ::= { pdnAtmExtMIBTraps 0 }
    pdnAtmExtMIBConformance OBJECT IDENTIFIER ::= { pdnAtmExtMIB 3 }
    pdnAtmExtMIBTrafficDescriptorTypes   OBJECT IDENTIFIER ::= { pdnAtmExtMIB 4 }

pdnAtmNoClpTaggingNoScrCdvtMdcr   OBJECT-IDENTITY
      STATUS   current
      DESCRIPTION
              "This Traffic Descriptor type is for no CLP with tagging
               and no Sustained Cell Rate. The Use of the Parameter
               Vector for this type:
               Parameter 1: Peak Cell Rate in cells/second
                            CLP=0+1 traffic
               Parameter 2: CDVT in tenths of a microsecond
               Parameter 3: Minimum Desired Cell Rate in cells/second (&lt;= PCR)
               Parameter 4: Tolerance To the MDCR Commitment
                            (&gt;= 1/MDCR) in milliseconds
               Parameter 5: not used

               This Traffic Descriptor type is applicable to connections
               following the UBR.2 conformance definition"
      REFERENCE
               "ATM Forum, ATM User-Network Interface,
                 Version 3.0 (UNI 3.0) Specification, 1994.
                ATM Forum, ATM User-Network Interface,
                 Version 3.1 (UNI 3.1) Specification
                 November 1994.
                ATM Forum, Traffic Management Specification,
                 Version 4.0, af-tm-0056.000, June 1996.
                ATM Forum, Traffic Management Specification,
                 Version 4.1, af-tm-0121.000, March 1999.
                ATM Forum, Addendum to Traffic Management Specification,
                 Version 4.1, for an optional Minimum Desired 
                 Cell Rate (MDCR), af-tm-0150.000, July 2000."
      ::= { pdnAtmExtMIBTrafficDescriptorTypes 1   }

pdnAtmNoClpNoScrCdvtMdcr   OBJECT-IDENTITY
      STATUS   current
      DESCRIPTION
              "This Traffic Descriptor type is for no CLP
               and no Sustained Cell Rate. The Use of the Parameter
               Vector for this type:
               Parameter 1: Peak Cell Rate in cells/second
                            CLP=0+1 traffic
               Parameter 2: CDVT in tenths of a microsecond
               Parameter 3: Minimum Desired Cell Rate in cells/second (&lt;= PCR)
               Parameter 4: Tolerance To the MDCR Commitment
                            (&gt;= 1/MDCR) in milliseconds
               Parameter 5: not used
               This Traffic Descriptor type is applicable to connections
               following the UBR.1 conformance definition"
      REFERENCE
               "ATM Forum, ATM User-Network Interface,
                 Version 3.0 (UNI 3.0) Specification, 1994.
                ATM Forum, ATM User-Network Interface,
                 Version 3.1 (UNI 3.1) Specification
                 November 1994.
                ATM Forum, Traffic Management Specification,
                 Version 4.0, af-tm-0056.000, June 1996.
                ATM Forum, Traffic Management Specification,
                 Version 4.1, af-tm-0121.000, March 1999.
                ATM Forum, Addendum to Traffic Management Specification,
                 Version 4.1, for an optional Minimum Desired 
                 Cell Rate (MDCR), af-tm-0150.000, July 2000."
      ::= { pdnAtmExtMIBTrafficDescriptorTypes 2   }

-- ===============================================================
--
--  Extentions to the ATM Interface Config Table (RFC 2515)
--
--  Release: 1.0  02/18/00 (Initial Release) Prakash Easwar
--
--  This MIB is intended to AUGMENT the atmInterfaceConfTable of the ATM-MIB
--

pdnAtmIfConfExtTable OBJECT-TYPE
    SYNTAX  SEQUENCE OF PdnAtmIfConfExtEntry
    MAX-ACCESS  not-accessible
    STATUS  current
    DESCRIPTION
      "The Paradyne Extension to the atmInterfaceConfTable of the ATM-MIB."
    ::= { pdnAtmExtMIBObjects 1   }

pdnAtmIfConfExtEntry OBJECT-TYPE
    SYNTAX  PdnAtmIfConfExtEntry
    MAX-ACCESS  not-accessible
    STATUS  current
    DESCRIPTION
       "An entry in the Paradyne Extension to the atmInterfaceConfTable of 
       the ATM-MIB."
    AUGMENTS { atmInterfaceConfEntry }
    ::= { pdnAtmIfConfExtTable  1 }

PdnAtmIfConfExtEntry ::=
    SEQUENCE {
    
    pdnAtmIfConfExtVbrRtBandwidthUtil
        Integer32,

    pdnAtmIfConfExtVbrNrtBandwidthUtil
        Integer32,
      
    pdnAtmIfConfExtHecErrorThreshold     
        Integer32,

    pdnAtmIfConfExtUnknownCellThreshold
        Integer32,

    pdnAtmIfConfExtOcdEventThreshold
        Integer32,

    pdnAtmIfConfExtBandwidthUtilCbrReserved
        Integer32,

    pdnAtmIfConfExtBandwidthUtilCbrAssigned
        Integer32,

    pdnAtmIfConfExtBandwidthUtilVbrRtReserved
        Integer32,

    pdnAtmIfConfExtBandwidthUtilVbrRtAssigned
        Integer32,

    pdnAtmIfConfExtBandwidthUtilVbrNrtReserved
        Integer32,

    pdnAtmIfConfExtBandwidthUtilVbrNrtAssigned
        Integer32,

    pdnAtmIfConfExtBandwidthUtilUbrReserved
        Integer32,

    pdnAtmIfConfExtBandwidthUtilUbrAssigned
        Integer32,

    pdnAtmIfConfExtRateShape
        Integer32
    }

pdnAtmIfConfExtVbrRtBandwidthUtil OBJECT-TYPE
    SYNTAX  Integer32 (0..9999)
    MAX-ACCESS  read-write
    STATUS  current
    DESCRIPTION
           "The bandwidth utilization for realtime vbr type traffic
            expressed as a percentage."
    ::= { pdnAtmIfConfExtEntry 1 }

pdnAtmIfConfExtVbrNrtBandwidthUtil OBJECT-TYPE
   SYNTAX  Integer32 (0..9999)
   MAX-ACCESS  read-write
   STATUS  current
   DESCRIPTION
           "The bandwidth utilization for non-realtime VBR type traffic
            expressed as a percentage."
   ::= { pdnAtmIfConfExtEntry 2 }
 
pdnAtmIfConfExtHecErrorThreshold OBJECT-TYPE
   SYNTAX  Integer32
   MAX-ACCESS  read-write
   STATUS  current
   DESCRIPTION
       "The value of this object represents the threshold value for
        the number of uncrorrectable HEC errors in a 15 minutes interval.
        An SNMP link Up/Down trap would be generated if the number of
        uncorrectable HEC errors in a 15 minutes interval exceeds this threshold.
        The valid range of this object is 0 to 1000. A value of 0 will cause
        a trap to be sent on each occurrence of a HEC error. A value of
        -9999 disables the threshold check.
        The default value for this object is 100. "
   DEFVAL  { 100 }
   ::= { pdnAtmIfConfExtEntry 3 }
  
 pdnAtmIfConfExtUnknownCellThreshold OBJECT-TYPE
   SYNTAX  Integer32
   MAX-ACCESS  read-write
   STATUS  current
   DESCRIPTION
       "The value of this object represents the threshold value for
        the number of unknown cells in a 15 minutes interval.
        An SNMP trap would be generated if the number of unknown
        cell in a 15 minutes interval exceeds this threshold.
        The valid range of this object is 0 to 1000. A value of 0 will
        cause a trap to be sent on each occurrence of an unknown cell.
        A value of -9999 disables the threshold check.
        The default value for this object is 10"
   DEFVAL  { 10 }
   ::= { pdnAtmIfConfExtEntry 4 }

 pdnAtmIfConfExtOcdEventThreshold OBJECT-TYPE
   SYNTAX  Integer32
   MAX-ACCESS  read-write
   STATUS  current
   DESCRIPTION
       "The value of this object represents the threshold value for
        the number of Out of Cell Delineation(OCD) events in a 15
        minutes interval. An SNMP trap would be generated if the number
        of OCD events in a 15 minutes interval exceeds this threshold.
        The valid range of this object is 0 to 1000. A value of 0 will
        cause a trap to be sent on each occurrence of a HEC error.
        A value of -9999 disables the threshold check.
        The default value for this object is 0"
   DEFVAL  { 0 }
   ::= { pdnAtmIfConfExtEntry 5 }


pdnAtmIfConfExtBandwidthUtilCbrReserved OBJECT-TYPE
          SYNTAX  Integer32
          MAX-ACCESS     read-write
          STATUS         current
          DESCRIPTION
           "This object specifies the percent of the interface bandwidth to
            be allocated to the CBR traffic class."
          ::= { pdnAtmIfConfExtEntry  6}

pdnAtmIfConfExtBandwidthUtilCbrAssigned OBJECT-TYPE
          SYNTAX  Integer32
          MAX-ACCESS     read-only
          STATUS         current
          DESCRIPTION
           "This object specifies the percent of bandwidth utilization
            (sometimes reffered to as over subscription) the connection
            Addmission Control algorithm has already allowed for the CBR class
            of service."
          ::= { pdnAtmIfConfExtEntry  7}

pdnAtmIfConfExtBandwidthUtilVbrRtReserved OBJECT-TYPE
          SYNTAX  Integer32
          MAX-ACCESS     read-write
          STATUS         current
          DESCRIPTION
           "This object specifies the percent of the interface bandwidth to
            be allocated to the VBR-rt traffic class."
          ::= { pdnAtmIfConfExtEntry  8}

pdnAtmIfConfExtBandwidthUtilVbrRtAssigned OBJECT-TYPE
          SYNTAX  Integer32
          MAX-ACCESS     read-only
          STATUS         current
          DESCRIPTION
           "This object specifies the percent of bandwidth utilization
            (sometimes reffered to as over subscription) the connection
            Addmission Control algorithm has already allowed for the VBR-rt class
            of service."
          ::= { pdnAtmIfConfExtEntry  9}

pdnAtmIfConfExtBandwidthUtilVbrNrtReserved OBJECT-TYPE
          SYNTAX  Integer32
          MAX-ACCESS     read-write
          STATUS         current
          DESCRIPTION
           "This object specifies the percent of the interface bandwidth to
            be allocated to the VBR-nrt traffic class."
          ::= { pdnAtmIfConfExtEntry  10}

pdnAtmIfConfExtBandwidthUtilVbrNrtAssigned OBJECT-TYPE
          SYNTAX  Integer32
          MAX-ACCESS     read-only
          STATUS         current
          DESCRIPTION
           "This object specifies the percent of bandwidth utilization
            (sometimes reffered to as over subscription) the connection
            Addmission Control algorithm has already allowed for the VBR-nrt class
            of service."
          ::= { pdnAtmIfConfExtEntry  11}

pdnAtmIfConfExtBandwidthUtilUbrReserved OBJECT-TYPE
          SYNTAX  Integer32
          MAX-ACCESS     read-write
          STATUS         current
          DESCRIPTION
           "This object specifies the percent of the interface bandwidth to
            be allocated to the UBR traffic class."
          ::= { pdnAtmIfConfExtEntry  12}

pdnAtmIfConfExtBandwidthUtilUbrAssigned OBJECT-TYPE
          SYNTAX  Integer32
          MAX-ACCESS     read-only
          STATUS         current
          DESCRIPTION
           "This object specifies the percent of bandwidth utilization
            (sometimes reffered to as over subscription) the connection
            Addmission Control algorithm has already allowed for the UBR class
            of service."
          ::= { pdnAtmIfConfExtEntry 13}

pdnAtmIfConfExtRateShape OBJECT-TYPE
          SYNTAX  Integer32 (512..46080)
	  UNITS "Kbps"
          MAX-ACCESS     read-write
          STATUS         current
          DESCRIPTION
           "This object is used to specify rate shaping on this interface.
            The valid range of this object is 512 to 46080 [512K..46Mbps] 
	    with increments of 64K. The default value will be set depending
	    on the interface." 
          ::= { pdnAtmIfConfExtEntry 14}

-- ===============================================================
--
--   Extentions to the ATM Interface Config Table (RFC 2515)
--
--  Release: 1.0  02/18/00 (Initial Release) Prakash Easwar
--
-- This MIB is intended to AUGMENT the atmTrafficDescrParamTable of the ATM-MIB
--

pdnAtmTrafficDescrParamExtTable OBJECT-TYPE
    SYNTAX  SEQUENCE OF PdnAtmTrafficDescrParamExtEntry
    MAX-ACCESS  not-accessible
    STATUS  current
    DESCRIPTION
       "The Paradyne Extension to the atmTrafficDescrParamTable of the ATM-MIB."
    ::= { pdnAtmExtMIBObjects 2   }

pdnAtmTrafficDescrParamExtEntry OBJECT-TYPE
    SYNTAX  PdnAtmTrafficDescrParamExtEntry
    MAX-ACCESS  not-accessible
    STATUS  current
    DESCRIPTION
           "An entry in the Paradyne Extension to the atmTrafficDescrParamTable
           of the ATM-MIB."
    AUGMENTS { atmTrafficDescrParamEntry }
    ::= { pdnAtmTrafficDescrParamExtTable  1 }

PdnAtmTrafficDescrParamExtEntry ::=
    SEQUENCE {

    pdnAtmTrafficDescrParamName
        DisplayString (SIZE(1..12)),

    pdnAtmTrafficPolicing
        TruthValue,
    
    pdnAtmTrafficShaping
        TruthValue
    }

pdnAtmTrafficDescrParamName OBJECT-TYPE
          SYNTAX  DisplayString (SIZE(1..12))
          MAX-ACCESS     read-create
          STATUS         current
          DESCRIPTION
           "The value of this Object identifies the traffic descriptor by a
            by a name."
          ::= { pdnAtmTrafficDescrParamExtEntry  1}

pdnAtmTrafficPolicing OBJECT-TYPE
          SYNTAX  TruthValue
          MAX-ACCESS     read-create
          STATUS         current
          DESCRIPTION
           "The value of this Object determines whether or not
            the vcl/vpl to which this traffic descriptor
            is bound will be policed"
          ::= { pdnAtmTrafficDescrParamExtEntry  2}

pdnAtmTrafficShaping OBJECT-TYPE
          SYNTAX  TruthValue
          MAX-ACCESS     read-create
          STATUS         current
          DESCRIPTION
           "The value of this Object determines whether or not
            the vcl/vpl to which this traffic descriptor
            is bound will be rate shaped to the specified
            traffic contract"
          ::= { pdnAtmTrafficDescrParamExtEntry  3}

-- ===============================================================
--
--   Extentions to the ATM AAL5 Virtual Channel Connection 
--   Performance Statistics Table (aal5VccTable) in the ATM-MIB
--   (RFC 2515).
--
--
-- This MIB is intended to AUGMENT the aal5VccTable of the ATM-MIB.
--

pdnAal5VccExtTable OBJECT-TYPE
    SYNTAX  SEQUENCE OF PdnAal5VccExtEntry
    MAX-ACCESS  not-accessible
    STATUS  current
    DESCRIPTION
       "The Paradyne Extension to the aal5VccTable in the ATM-MIB."
    ::= { pdnAtmExtMIBObjects 3  }

pdnAal5VccExtEntry OBJECT-TYPE
    SYNTAX  PdnAal5VccExtEntry
    MAX-ACCESS  not-accessible
    STATUS  current
    DESCRIPTION
           "An entry in the Paradyne Extension to the aal5VccTable.
           in the ATM-MIB."
    AUGMENTS { aal5VccEntry }
    ::= { pdnAal5VccExtTable  1 }

PdnAal5VccExtEntry ::=
    SEQUENCE {
        pdnAal5VccExtOutPDUs        Unsigned32,
        pdnAal5VccExtInPDUs         Unsigned32
    }

pdnAal5VccExtOutPDUs OBJECT-TYPE
          SYNTAX         Unsigned32
          MAX-ACCESS     read-only
          STATUS         current
          DESCRIPTION
           "The total number of AAL5 CPCS PDUs transmitted on the
           interface associated with an AAL5 entry."
          ::= { pdnAal5VccExtEntry  1}

pdnAal5VccExtInPDUs OBJECT-TYPE
          SYNTAX         Unsigned32
          MAX-ACCESS     read-only
          STATUS         current
          DESCRIPTION
           "This total number of AAL5 CPCS PDUs transmitted on the
           interface associated with an AAL5 entry."
          ::= { pdnAal5VccExtEntry  2}


-- ===============================================================
--
-- Trap group
--

pdnAtmIfConfExtExcessInvalidCellsAlarm NOTIFICATION-TYPE
   OBJECTS { ifOperStatus,
             pdnAtmIfConfExtUnknownCellThreshold
           }
   STATUS current
   DESCRIPTION
       "This alarm indicates that the number of cells with
        uncorrectable HEC erros has exceeded the used defined
        the threshold. "
   ::= { pdnAtmExtMIBTrapPrefix 1 }

pdnAtmIfConfExtEgressLineRateAlarmSet NOTIFICATION-TYPE
   OBJECTS { ifIndex }
   STATUS current
   DESCRIPTION
       "This alarm indicates that the line rate of the specified
        interface has dropped below a value which violates the
        traffic contracts of the admitted connections in the egress
        (transmit) direction"
   ::= { pdnAtmExtMIBTrapPrefix 2 }

pdnAtmIfConfExtEgressLineRateAlarmClear NOTIFICATION-TYPE
   OBJECTS { ifIndex }
   STATUS current
   DESCRIPTION
       "This alarm indicates that the line rate of the specified
        interface has risen above a value which would no longer violate the
        traffic contracts of the admitted connections in the egress 
        (transmit) direction"
   ::= { pdnAtmExtMIBTrapPrefix 102 }

pdnAtmIfConfExtVplNoBandwidthAvail NOTIFICATION-TYPE
   OBJECTS { atmVpCrossConnectAdminStatus }
   STATUS current
   DESCRIPTION
       "This alarm indicates that the traffic contract(s)
       associated with the Virtual Path (VP) Cross Connect
       cannot be satisfied by the ATM switch.
       It is left upto the implementation to decide whether or 
       not the VP cross connect will be admitted"
   ::= { pdnAtmExtMIBTrapPrefix 3 }

pdnAtmIfConfExtVclNoBandwidthAvail NOTIFICATION-TYPE
   OBJECTS { atmVcCrossConnectAdminStatus }
   STATUS current
   DESCRIPTION
       "This alarm indicates that the traffic contract(s)
       associated with the Virtual Channel (VC) Cross Connect
       cannot be satisfied by the ATM switch.
       It is left upto the implementation to decide whether or 
       not the VC cross connect will be admitted"
   ::= { pdnAtmExtMIBTrapPrefix 4 }

pdnAtmIfConfExtIngressLineRateAlarmSet NOTIFICATION-TYPE
   OBJECTS { ifIndex }
   STATUS current
   DESCRIPTION
       "This alarm indicates that the line rate of the specified
        interface has dropped below a value which violates the
        traffic contracts of the admitted connections in the ingress
        (receive) direction"
   ::= { pdnAtmExtMIBTrapPrefix 5 }

pdnAtmIfConfExtIngressLineRateAlarmClear NOTIFICATION-TYPE
   OBJECTS { ifIndex }
   STATUS current
   DESCRIPTION
       "This alarm indicates that the line rate of the specified
        interface has risen above a value which would no longer violate the
        traffic contracts of the admitted connections in the ingress
        (receive) direction"
   ::= { pdnAtmExtMIBTrapPrefix 105 }


-- ===============================================================
-- ==
-- == Conformance Information
-- ==
-- ===============================================================

pdnAtmExtMibCompliances   OBJECT IDENTIFIER ::= { pdnAtmExtMIBConformance 1 }
pdnAtmExtMibGroups        OBJECT IDENTIFIER ::= { pdnAtmExtMIBConformance 2 }


--
-- Compliance Statements
--

-- No MANDATORY-GROUPS are specified


--
-- Units of Conformance
--

pdnAtmIfConfExtGroup OBJECT-GROUP
   OBJECTS {
      pdnAtmIfConfExtVbrRtBandwidthUtil,
      pdnAtmIfConfExtVbrNrtBandwidthUtil,
      pdnAtmIfConfExtHecErrorThreshold,
      pdnAtmIfConfExtUnknownCellThreshold,
      pdnAtmIfConfExtOcdEventThreshold,
      pdnAtmIfConfExtBandwidthUtilCbrReserved,
      pdnAtmIfConfExtBandwidthUtilCbrAssigned,
      pdnAtmIfConfExtBandwidthUtilVbrRtReserved,
      pdnAtmIfConfExtBandwidthUtilVbrRtAssigned,
      pdnAtmIfConfExtBandwidthUtilVbrNrtReserved,
      pdnAtmIfConfExtBandwidthUtilVbrNrtAssigned,
      pdnAtmIfConfExtBandwidthUtilUbrReserved,
      pdnAtmIfConfExtBandwidthUtilUbrAssigned,
      pdnAtmIfConfExtRateShape
   }
   STATUS current
   DESCRIPTION
       "Objects grouped for the pdnAtmIfConfExtTable."
   ::= { pdnAtmExtMibGroups 1 }

pdnAtmTrafficDescrParamExtGroup OBJECT-GROUP
   OBJECTS {
      pdnAtmTrafficDescrParamName,
      pdnAtmTrafficPolicing,
      pdnAtmTrafficShaping
   }
   STATUS current
   DESCRIPTION
       "Objects grouped for the pdnAtmTrafficDescrParamExtTable."
   ::= { pdnAtmExtMibGroups 2 }

pdnAal5VccExtGroup OBJECT-GROUP
   OBJECTS {
      pdnAal5VccExtInPDUs,
      pdnAal5VccExtOutPDUs
   }
   STATUS current
   DESCRIPTION
       "Objects grouped for the pdnAal5VccExtTable."
   ::= { pdnAtmExtMibGroups 3 }

pdnAtmExtNotificationGroup NOTIFICATION-GROUP
   NOTIFICATIONS {
      pdnAtmIfConfExtExcessInvalidCellsAlarm,
      pdnAtmIfConfExtEgressLineRateAlarmSet, 
      pdnAtmIfConfExtEgressLineRateAlarmClear, 
      pdnAtmIfConfExtVplNoBandwidthAvail, 
      pdnAtmIfConfExtVclNoBandwidthAvail,
      pdnAtmIfConfExtIngressLineRateAlarmSet,
      pdnAtmIfConfExtIngressLineRateAlarmClear
   }
   STATUS current
   DESCRIPTION
       "Objects grouped for Notification defined in this
        MIB."
   ::= { pdnAtmExtMibGroups 4 }



END

-- ===============================================================
-- Copyright (C) 2000 Paradyne Corporation.
--  ATM M4 Extension Group
PDN-ATMM4EXT-MIB DEFINITIONS ::= BEGIN

    IMPORTS
        MODULE-IDENTITY , OBJECT-TYPE, OBJECT-IDENTITY,
        Gauge32, TimeTicks
            FROM SNMPv2-SMI
        TEXTUAL-CONVENTION
            FROM SNMPv2-TC
        MODULE-COMPLIANCE, OBJECT-GROUP
            FROM SNMPv2-CONF
        pdnAtm
            FROM PDN-HEADER-MIB
        atmfM4VpTestEntry, atmfM4VcTestEntry, atmfM4TcProtoCurrEntry, atmfM4TcProtoHistEntry
            FROM ATM-FORUM-SNMP-M4-MIB
        ifIndex
            FROM IF-MIB;

-- ===============================================================
--
--  Extentions to the ATM Forum M4  Mib
--
-- ===============================================================

    pdnAtmfM4ExtMIB MODULE-IDENTITY
        LAST-UPDATED "200103080000Z"
        ORGANIZATION "Paradyne Corporation
                      MIB Working Group"
        CONTACT-INFO
                  "Paradyne Corporation
                   8545 126th Avenue North
                   Largo, FL 33773
                   www.paradyne.com

                   General Comments to: mibwg_team@eng.paradyne.com"

        DESCRIPTION
            "This MIB Module extends the ATM-FORUM-SNMP-M4-MI defined
             in the Atm Forums M4 Mib
            "
        REVISION "200208150000Z"
        DESCRIPTION "P. Easwar
            o  Added New Table pdnAtmfM4VpLoopbackTestTable.
		"

        REVISION "200103080000Z"
        DESCRIPTION "R.A.Bowhall
            o  Added error code of adminStatusDisabled(8).
	    "

        REVISION "200009260000Z"
        DESCRIPTION "R. Steinberger
            o  Added size to pdnAtmfM4Vc1CellLoopReportedLocation.
            "
        REVISION "200009220000Z"
        DESCRIPTION "R. Steinberger
            o  Added error code of testTimeOut(7).
            o  Added description of use of pdnAtmfM4Vc1CellLoopTable
            o  Changed pdnAtmfM4Vc1CellLoopReportedLocation type to 
               meet actual M4 definition of OCTET STRING(SIZE(16))
            o  Added the pdnAtmfM4LoopbackLocationTable
            "
        REVISION "200009210000Z"
        DESCRIPTION "J.Strain
            o  Added E2E and SEG as Multiple OAM Cell Tests
            o  documented mapping of atmfM4VcTestType to the corresponding
                                 atmfM4VcTestCode results table
            "
        REVISION "200009080000Z"
        DESCRIPTION "R. Steinberger
            o  Cleaned tabs throughout document.
            o  Fixed naming convention.
            o  Added pdnAtmfM4Vc1CellLoopTable for ATM OAM loopbacks 
               that send only single test cell.
            o  Added conformance section.
            "
        REVISION "200006290000Z"
        DESCRIPTION "Z. Pan
            o  added augmented atmfM4VcTestTable for ATM OAM loopback test.
            "
        ::= {  pdnAtm 6 }

    pdnAtmfM4ExtObjects     OBJECT IDENTIFIER  ::= { pdnAtmfM4ExtMIB 1 }
    pdnAtmfM4ExtTraps       OBJECT IDENTIFIER  ::= { pdnAtmfM4ExtMIB 2 }
    pdnAtmfM4ExtConformance OBJECT IDENTIFIER  ::= { pdnAtmfM4ExtMIB 3 }
    pdnAtmfM4ExtTrapPrefix  OBJECT IDENTIFIER  ::= { pdnAtmfM4ExtTraps 0 }
--
-- Textual Conventions Specific to this MIB Module
--
PdnAtmfM4TestErrorCode ::= TEXTUAL-CONVENTION
    STATUS  current
    DESCRIPTION
        "The specific error codes related to attempting to run a test. The
         codes have the following meanings:

           noError(0)             -- No Error Occurred
           badIfIndex(1)          -- Specified interface does not exist
           noVccFound(2)          -- The Vcc does not exist on the interface
           notOwner(3)            -- Not the current owner of the test
           noResourceAvailable(4) -- Device memory allocation failure
           noLoopbackAllocated(5) -- Could not start the test
           testCompleted(6)       -- Test completed or stopped normally
           testTimeOut(7)         -- Test unsuccessfully due to timeout
           adminStatusDisabled(8) -- ifAdminStatus is Disabled 
        "
    SYNTAX  INTEGER {
                noError(0),
                badIfIndex(1),
                noVccFound(2),
                notOwner(3),
                noResourceAvailable(4),
                noLoopbackAllocated(5),
                testCompleted(6),
                testTimeOut(7),
                adminStatusDisabled(8)
            }

--
-- ATM TC layer current and historical fifteen-minute interval statistics 
-- pdnAtmfM4TcProtoCurrExtTable and pdnAtmfM4TcProtoHistExtTable
--

-- ATM TC layer current fifteen-minute interval data statistics 

pdnAtmfM4TcProtoCurrExtTable OBJECT-TYPE
    SYNTAX  SEQUENCE OF PdnAtmfM4TcProtoCurrExtEntry
    MAX-ACCESS  not-accessible
    STATUS  current
    DESCRIPTION
       "The Paradyne Extension to the atmfM4TcProtoCurrTable of the
        ATM-FORUM-SNMP-M4-MIB."
    ::= { pdnAtmfM4ExtObjects 1   }

pdnAtmfM4TcProtoCurrExtEntry OBJECT-TYPE
    SYNTAX  PdnAtmfM4TcProtoCurrExtEntry
    MAX-ACCESS  not-accessible
    STATUS  current
    DESCRIPTION
       "The Paradyne Extension to the atmfM4TcProtoCurrTable of the
        ATM-FORUM-SNMP-M4-MIB."
    AUGMENTS { atmfM4TcProtoCurrEntry }
    ::= { pdnAtmfM4TcProtoCurrExtTable  1 }

PdnAtmfM4TcProtoCurrExtEntry ::= SEQUENCE {
    pdnAtmfM4TcProtoCurrCellIns         Gauge32,
    pdnAtmfM4TcProtoCurrCellOuts        Gauge32,
    pdnAtmfM4TcProtoCurrInDiscards      Gauge32,
    pdnAtmfM4TcProtoCurrOutDiscards     Gauge32,
    pdnAtmfM4TcProtoCurrLCDEvents       Gauge32,
    pdnAtmfM4TcProtoCurrUnknownCells    Gauge32,
    pdnAtmfM4TcProtoCurrCorrectedHEC    Gauge32
    }

pdnAtmfM4TcProtoCurrCellIns OBJECT-TYPE
    SYNTAX Gauge32
    MAX-ACCESS read-only
    STATUS current
    DESCRIPTION
    "The number of ATM cells received on this interface since the
     start of this interval"
    ::= { pdnAtmfM4TcProtoCurrExtEntry 1 } 

pdnAtmfM4TcProtoCurrCellOuts OBJECT-TYPE
    SYNTAX Gauge32
    MAX-ACCESS read-only
    STATUS current
    DESCRIPTION
    "The number of ATM cells sent on this interface since the
     start of this interval"
    ::= { pdnAtmfM4TcProtoCurrExtEntry 2 } 

pdnAtmfM4TcProtoCurrInDiscards OBJECT-TYPE
    SYNTAX Gauge32
    MAX-ACCESS read-only
    STATUS current
    DESCRIPTION
    "The number of RX ATM cells dropped on this interface since the
     start of this interval"
    ::= { pdnAtmfM4TcProtoCurrExtEntry 3 } 

pdnAtmfM4TcProtoCurrOutDiscards OBJECT-TYPE
    SYNTAX Gauge32
    MAX-ACCESS read-only
    STATUS current
    DESCRIPTION
    "The number of TX ATM cells dropped on this interface since the
     start of this interval"
    ::= { pdnAtmfM4TcProtoCurrExtEntry 4 } 

pdnAtmfM4TcProtoCurrLCDEvents OBJECT-TYPE
    SYNTAX Gauge32
    MAX-ACCESS read-only
    STATUS current
    DESCRIPTION
    "The number of Loss of Cell Delineation (LCD) event occurred 
     on this interface since the start of this interval"
    ::= { pdnAtmfM4TcProtoCurrExtEntry 5 } 

pdnAtmfM4TcProtoCurrUnknownCells OBJECT-TYPE
    SYNTAX Gauge32
    MAX-ACCESS read-only
    STATUS current
    DESCRIPTION
    "The number of unknown Cells received on this interface since
     the start of this interval"
    ::= { pdnAtmfM4TcProtoCurrExtEntry 6 } 

pdnAtmfM4TcProtoCurrCorrectedHEC OBJECT-TYPE
    SYNTAX Gauge32
    MAX-ACCESS read-only
    STATUS current
    DESCRIPTION
    "The number of Cell with corrected HEC received on this interface
     since the start of this interval"
    ::= { pdnAtmfM4TcProtoCurrExtEntry 7 } 

--
-- ATM TC layer historical fifteen-minute interval statistics 
-- (per interface and time interval)
--

pdnAtmfM4TcProtoHistExtTable OBJECT-TYPE
    SYNTAX  SEQUENCE OF PdnAtmfM4TcProtoHistExtEntry
    MAX-ACCESS  not-accessible
    STATUS  current
    DESCRIPTION
       "The Paradyne Extension to the atmfM4TcProtoHistTable of the
        ATM-FORUM-SNMP-M4-MIB."
    ::= { pdnAtmfM4ExtObjects 2   }

pdnAtmfM4TcProtoHistExtEntry OBJECT-TYPE
    SYNTAX  PdnAtmfM4TcProtoHistExtEntry
    MAX-ACCESS  not-accessible
    STATUS  current
    DESCRIPTION
       "The Paradyne Extension to the atmfM4TcProtoHistTable of the
        ATM-FORUM-SNMP-M4-MIB."
    AUGMENTS { atmfM4TcProtoHistEntry }
    ::= { pdnAtmfM4TcProtoHistExtTable  1 }

PdnAtmfM4TcProtoHistExtEntry ::= SEQUENCE {
    pdnAtmfM4TcProtoHistCellIns         Gauge32,
    pdnAtmfM4TcProtoHistCellOuts        Gauge32,
    pdnAtmfM4TcProtoHistInDiscards      Gauge32,
    pdnAtmfM4TcProtoHistOutDiscards     Gauge32,
    pdnAtmfM4TcProtoHistLCDEvents       Gauge32,
    pdnAtmfM4TcProtoHistUnknownCells    Gauge32,
    pdnAtmfM4TcProtoHistCorrectedHEC    Gauge32
    }

pdnAtmfM4TcProtoHistCellIns OBJECT-TYPE
    SYNTAX Gauge32
    MAX-ACCESS read-only
    STATUS current
    DESCRIPTION
    "The number of ATM cells received on this interface
     during this interval"
    ::= { pdnAtmfM4TcProtoHistExtEntry 1 } 

pdnAtmfM4TcProtoHistCellOuts OBJECT-TYPE
    SYNTAX Gauge32
    MAX-ACCESS read-only
    STATUS current
    DESCRIPTION
    "The number of ATM cells sent on this interface during
     this interval"
    ::= { pdnAtmfM4TcProtoHistExtEntry 2 } 

pdnAtmfM4TcProtoHistInDiscards OBJECT-TYPE
    SYNTAX Gauge32
    MAX-ACCESS read-only
    STATUS current
    DESCRIPTION
    "The number of RX ATM cells dropped on this interface
     during this interval"
    ::= { pdnAtmfM4TcProtoHistExtEntry 3 } 

pdnAtmfM4TcProtoHistOutDiscards OBJECT-TYPE
    SYNTAX Gauge32
    MAX-ACCESS read-only
    STATUS current
    DESCRIPTION
    "The number of TX ATM cells dropped on this interface
     during this interval"
    ::= { pdnAtmfM4TcProtoHistExtEntry 4 } 

pdnAtmfM4TcProtoHistLCDEvents OBJECT-TYPE
    SYNTAX Gauge32
    MAX-ACCESS read-only
    STATUS current
    DESCRIPTION
    "The number of Loss of Cell Delineation (LCD) event occurred 
     on this interface during this interval"
    ::= { pdnAtmfM4TcProtoHistExtEntry 5 } 

pdnAtmfM4TcProtoHistUnknownCells OBJECT-TYPE
    SYNTAX Gauge32
    MAX-ACCESS read-only
    STATUS current
    DESCRIPTION
    "The number of unknown Cells received on this interface since
     the start of this interval"
    ::= { pdnAtmfM4TcProtoHistExtEntry 6 } 

pdnAtmfM4TcProtoHistCorrectedHEC OBJECT-TYPE
    SYNTAX Gauge32
    MAX-ACCESS read-only
    STATUS current
    DESCRIPTION
    "The number of Cell with corrected HEC received on this interface
     during this interval"
    ::= { pdnAtmfM4TcProtoHistExtEntry 7 } 


--
--  The following object defines a group of OAM test types.
--  This group is to contain any Paradyne Specific OAM test
--

pdnAtmfM4TestTypes OBJECT IDENTIFIER ::= { pdnAtmfM4ExtObjects 3 }

--
--  The following OID is defined to initiate continuous Segment OAM Cells
--  

pdnAtmfM4TestOAMLoopbackSegMultiCell OBJECT-IDENTITY
     STATUS    current
     DESCRIPTION
          "This identifies an OAM Loopback Test on a VPL, VPC,
          VCL, or VCC termination point, using a segment OAM
          cell.

          The test type must have appended to it a code that uniquely
          identifies an intermediate point responsible for looping
          back the cell.  If this is absent, the loopback is performed
          at the end of the segment or connection.

          E.g., the OID { pdnAtmfM4TestOAMLoopbackSegMultiCell 5 } identifies
          that the loopback should be performed at the intermediate
          point labeled 5."
     ::= { pdnAtmfM4TestTypes 1 }

--
--  The following OID is defined to initiate continuous End to End OAM cells
--  

pdnAtmfM4TestOAMLoopbackE2EMultiCell OBJECT-IDENTITY
     STATUS    current
     DESCRIPTION
          "This identifies an OAM Loopback Test on a VPL, VPC,
          VCL, or VCC termination point, using an end-to-end OAM
          cell."
     ::= { pdnAtmfM4TestTypes 2 }

--
--      Test Code to Test Results Matrix
--      
--      atmfM4VcTestType                atmfM4VcTestCode Result Table
--      ________________                _____________________________
--
--      atmfM4TestOAMLoopbackSeg(standard is a single cell test)
--                                      pdnAtmfM4Vc1CellLoopTable
--      atmfM4TestOAMLoopbackE2E(standard is a single cell test)
--                                      pdnAtmfM4Vc1CellLoopTable
--
--      pdnAtmfM4TestOAMLoopbackSegMultiCell
--                                      pdnAtmfM4VcLoopbackTestTable
--      pdnAtmfM4TestOAMLoopbackE2EMultiCell
--                                      pdnAtmfM4VcLoopbackTestTable
--

--
-- OAM Loopback test (multiple cell) detailed results table
--

pdnAtmfM4VcLoopbackTestTable   OBJECT-TYPE 
    SYNTAX       SEQUENCE OF PdnAtmfM4VcLoopbackTestEntry 
    MAX-ACCESS   not-accessible 
    STATUS       current 
    DESCRIPTION 
      "This table contains input and results for OAM loopback 
       tests. There can be only one test running per ATM VCC 
       This table should be used in conjunction with atmfM4VcTestTable
       with all the semantics of atmfM4VcTestTable." 
::= { pdnAtmfM4ExtObjects 4 } 

pdnAtmfM4VcLoopbackTestEntry OBJECT-TYPE 
    SYNTAX       PdnAtmfM4VcLoopbackTestEntry 
    MAX-ACCESS   not-accessible 
    STATUS       current 
    DESCRIPTION 
      "An entry containing objects for test results
       for ATM OAM loopback test" 
    AUGMENTS { atmfM4VcTestEntry } 
::= { pdnAtmfM4VcLoopbackTestTable 1 } 

PdnAtmfM4VcLoopbackTestEntry ::= 
    SEQUENCE { 
      pdnAtmfM4VcLoopbackTestElpsTime         TimeTicks,
      pdnAtmfM4VcLoopbackTestCellsSent        Gauge32,
      pdnAtmfM4VcLoopbackTestCellsRcvd        Gauge32,
      pdnAtmfM4VcLoopbackTestMinRTDelay       Gauge32,
      pdnAtmfM4VcLoopbackTestMaxRTDelay       Gauge32,
      pdnAtmfM4VcLoopbackTestAvgRTDelay       Gauge32,
      pdnAtmfM4VcLoopbackTestErrorCode        PdnAtmfM4TestErrorCode
    } 

pdnAtmfM4VcLoopbackTestElpsTime OBJECT-TYPE 
    SYNTAX       TimeTicks
    MAX-ACCESS   read-only 
    STATUS       current 
    DESCRIPTION 
      "This object contains the time that has elapsed since the test started."
::= { pdnAtmfM4VcLoopbackTestEntry 1 } 

pdnAtmfM4VcLoopbackTestCellsSent OBJECT-TYPE 
    SYNTAX       Gauge32
    MAX-ACCESS   read-only 
    STATUS       current 
    DESCRIPTION 
      "This object specifies a count of the number of test cells that
       have been sent. The value of this object stops increasing
       when it reaches its maximum value."
::= { pdnAtmfM4VcLoopbackTestEntry 2 } 

pdnAtmfM4VcLoopbackTestCellsRcvd OBJECT-TYPE 
    SYNTAX       Gauge32
    MAX-ACCESS   read-only 
    STATUS       current 
    DESCRIPTION 
      "This object specifies a count of the number of test cells that
       have been received.  The value of this object stops increasing
       when it reaches its maximum value."
::= { pdnAtmfM4VcLoopbackTestEntry 3 } 

pdnAtmfM4VcLoopbackTestMinRTDelay OBJECT-TYPE 
    SYNTAX       Gauge32
    UNITS        "milliseconds"
    MAX-ACCESS   read-only 
    STATUS       current 
    DESCRIPTION 
      "This object contains the value of the shortest round trip delay 
       since the test has been started. It is calculated only on the cells
       that have been received. Cells that were dropped are not counted."
::= { pdnAtmfM4VcLoopbackTestEntry 4 } 

pdnAtmfM4VcLoopbackTestMaxRTDelay OBJECT-TYPE 
    SYNTAX       Gauge32
    UNITS        "milliseconds"
    MAX-ACCESS   read-only 
    STATUS       current 
    DESCRIPTION 
      "This object contains the value of the longest round trip delay 
       since the test has been started. It is calculated only on the cells
       that have been received. Cells that were dropped are not counted."
::= { pdnAtmfM4VcLoopbackTestEntry 5 } 

pdnAtmfM4VcLoopbackTestAvgRTDelay OBJECT-TYPE 
    SYNTAX       Gauge32
    UNITS        "milliseconds"
    MAX-ACCESS   read-only 
    STATUS       current 
    DESCRIPTION 
      "This object contains the value of the average round trip delay 
       since the test has been started. It is calculated only on the cells
       that have been received. Cells that were dropped are not counted."
::= { pdnAtmfM4VcLoopbackTestEntry 6 } 

pdnAtmfM4VcLoopbackTestErrorCode OBJECT-TYPE 
    SYNTAX       PdnAtmfM4TestErrorCode
    MAX-ACCESS   read-only 
    STATUS       current 
    DESCRIPTION 
      "This object contains the specific error code on the test result."
::= { pdnAtmfM4VcLoopbackTestEntry 7 } 

--
-- Single Cell OAM Loopback test detailed results
--
-- This table contains results for single cell OAM tests that are not
-- of a broadcast variety.
--
-- Recommended Use:
--
-- 1) The NMS will start a test using the M4 MIB's atmfM4VcTestTable.
-- 2) Upon starting the test, the agent will put the corresponding OID
--    of a row in this table into the atmfM4VcTestCode object.
-- 3) When the value of atmfM4VcTestResult is not equal to inProgress(3),
--    the values contained in this table should be read.
--
pdnAtmfM4Vc1CellLoopTable   OBJECT-TYPE 
    SYNTAX       SEQUENCE OF PdnAtmfM4Vc1CellLoopEntry 
    MAX-ACCESS   not-accessible 
    STATUS       current 
    DESCRIPTION 
      "This table contains input and results for single cell OAM
       loopback tests. There can be only one test running per ATM VCC 
       This table should be used in conjunction with atmfM4VcTestTable
       with all the semantics of atmfM4VcTestTable." 
::= { pdnAtmfM4ExtObjects 5 } 

pdnAtmfM4Vc1CellLoopEntry OBJECT-TYPE 
    SYNTAX       PdnAtmfM4Vc1CellLoopEntry 
    MAX-ACCESS   not-accessible 
    STATUS       current 
    DESCRIPTION 
      "An entry containing objects for test results 
       for a single cell ATM OAM loopback test" 
    AUGMENTS { atmfM4VcTestEntry } 
::= { pdnAtmfM4Vc1CellLoopTable 1 } 

PdnAtmfM4Vc1CellLoopEntry ::= 
    SEQUENCE { 
      pdnAtmfM4Vc1CellLoopRTDelay             Gauge32,
      pdnAtmfM4Vc1CellLoopReportedLocation    OCTET STRING,
      pdnAtmfM4Vc1CellLoopErrorCode           PdnAtmfM4TestErrorCode
    } 

pdnAtmfM4Vc1CellLoopRTDelay OBJECT-TYPE 
    SYNTAX       Gauge32
    UNITS        "milliseconds"
    MAX-ACCESS   read-only 
    STATUS       current 
    DESCRIPTION 
      "This object contains the value of the round trip delay of the
       the test cell. A value of zero indicates that no cell has been
       received."
::= { pdnAtmfM4Vc1CellLoopEntry 1 } 

pdnAtmfM4Vc1CellLoopReportedLocation OBJECT-TYPE 
    SYNTAX       OCTET STRING(SIZE(16))
    MAX-ACCESS   read-only 
    STATUS       current 
    DESCRIPTION 
      "This object contains the value of the location identifier
       reported by the received cell."
::= { pdnAtmfM4Vc1CellLoopEntry 2 } 

pdnAtmfM4Vc1CellLoopErrorCode OBJECT-TYPE 
    SYNTAX       PdnAtmfM4TestErrorCode
    MAX-ACCESS   read-only 
    STATUS       current 
    DESCRIPTION 
      "This object contains the specific error code on the test result."
::= { pdnAtmfM4Vc1CellLoopEntry 3 }

--
-- OAM Segment Loopback Location Code
--
pdnAtmfM4LoopbackLocationTable   OBJECT-TYPE
    SYNTAX       SEQUENCE OF PdnAtmfM4LoopbackLocationEntry
    MAX-ACCESS   not-accessible
    STATUS       current
    DESCRIPTION
          "This table contains the ATM OAM loopback location codes
           for ATM cell layer interfaces."
    ::= { pdnAtmfM4ExtObjects 6 }

pdnAtmfM4LoopbackLocationEntry OBJECT-TYPE
    SYNTAX       PdnAtmfM4LoopbackLocationEntry
    MAX-ACCESS   not-accessible
    STATUS       current
    DESCRIPTION
          "An entry containing objects for ATM OAM loopback locations."
    INDEX { ifIndex }
    ::= { pdnAtmfM4LoopbackLocationTable 1 }

PdnAtmfM4LoopbackLocationEntry ::=
    SEQUENCE {
      pdnAtmfM4LoopbackLocationCode        OCTET STRING
    }

pdnAtmfM4LoopbackLocationCode OBJECT-TYPE
    SYNTAX       OCTET STRING(SIZE(16))
    MAX-ACCESS   read-write
    STATUS       current
    DESCRIPTION
          "This object contains the value of ATM OAM Loopback Location Code"
    ::= { pdnAtmfM4LoopbackLocationEntry 1 }

pdnAtmfM4VpLoopbackTestTable   OBJECT-TYPE 
    SYNTAX       SEQUENCE OF PdnAtmfM4VpLoopbackTestEntry 
    MAX-ACCESS   not-accessible 
    STATUS       current 
    DESCRIPTION 
      "This table contains input and results for OAM loopback 
       tests. There can be only one test running per ATM VPC
       This table should be used in conjunction with atmfM4VpTestTable
       with all the semantics of atmfM4VpTestTable." 
::= { pdnAtmfM4ExtObjects 7 }

pdnAtmfM4VpLoopbackTestEntry OBJECT-TYPE 
    SYNTAX       PdnAtmfM4VpLoopbackTestEntry 
    MAX-ACCESS   not-accessible 
    STATUS       current 
    DESCRIPTION 
      "An entry containing objects for test results
       for ATM OAM loopback test" 
    AUGMENTS { atmfM4VpTestEntry } 
::= { pdnAtmfM4VpLoopbackTestTable 1 } 

PdnAtmfM4VpLoopbackTestEntry ::= 
    SEQUENCE { 
      pdnAtmfM4VpLoopbackTestElpsTime         TimeTicks,
      pdnAtmfM4VpLoopbackTestCellsSent        Gauge32,
      pdnAtmfM4VpLoopbackTestCellsRcvd        Gauge32,
      pdnAtmfM4VpLoopbackTestMinRTDelay       Gauge32,
      pdnAtmfM4VpLoopbackTestMaxRTDelay       Gauge32,
      pdnAtmfM4VpLoopbackTestAvgRTDelay       Gauge32,
      pdnAtmfM4VpLoopbackTestErrorCode        PdnAtmfM4TestErrorCode
    } 

pdnAtmfM4VpLoopbackTestElpsTime OBJECT-TYPE 
    SYNTAX       TimeTicks
    MAX-ACCESS   read-only 
    STATUS       current 
    DESCRIPTION 
      "This object contains the time that has elapsed since the test started."
::= { pdnAtmfM4VpLoopbackTestEntry 1 } 

pdnAtmfM4VpLoopbackTestCellsSent OBJECT-TYPE 
    SYNTAX       Gauge32
    MAX-ACCESS   read-only 
    STATUS       current 
    DESCRIPTION 
      "This object specifies a count of the number of test cells that
       have been sent. The value of this object stops increasing
       when it reaches its maximum value."
::= { pdnAtmfM4VpLoopbackTestEntry 2 } 

pdnAtmfM4VpLoopbackTestCellsRcvd OBJECT-TYPE 
    SYNTAX       Gauge32
    MAX-ACCESS   read-only 
    STATUS       current 
    DESCRIPTION 
      "This object specifies a count of the number of test cells that
       have been received.  The value of this object stops increasing
       when it reaches its maximum value."
::= { pdnAtmfM4VpLoopbackTestEntry 3 } 

pdnAtmfM4VpLoopbackTestMinRTDelay OBJECT-TYPE 
    SYNTAX       Gauge32
    UNITS        "milliseconds"
    MAX-ACCESS   read-only 
    STATUS       current 
    DESCRIPTION 
      "This object contains the value of the shortest round trip delay 
       since the test has been started. It is calculated only on the cells
       that have been received. Cells that were dropped are not counted."
::= { pdnAtmfM4VpLoopbackTestEntry 4 } 

pdnAtmfM4VpLoopbackTestMaxRTDelay OBJECT-TYPE 
    SYNTAX       Gauge32
    UNITS        "milliseconds"
    MAX-ACCESS   read-only 
    STATUS       current 
    DESCRIPTION 
      "This object contains the value of the longest round trip delay 
       since the test has been started. It is calculated only on the cells
       that have been received. Cells that were dropped are not counted."
::= { pdnAtmfM4VpLoopbackTestEntry 5 } 

pdnAtmfM4VpLoopbackTestAvgRTDelay OBJECT-TYPE 
    SYNTAX       Gauge32
    UNITS        "milliseconds"
    MAX-ACCESS   read-only 
    STATUS       current 
    DESCRIPTION 
      "This object contains the value of the average round trip delay 
       since the test has been started. It is calculated only on the cells
       that have been received. Cells that were dropped are not counted."
::= { pdnAtmfM4VpLoopbackTestEntry 6 } 

pdnAtmfM4VpLoopbackTestErrorCode OBJECT-TYPE 
    SYNTAX       PdnAtmfM4TestErrorCode
    MAX-ACCESS   read-only 
    STATUS       current 
    DESCRIPTION 
      "This object contains the specific error code on the test result."
::= { pdnAtmfM4VpLoopbackTestEntry 7 } 

-- Conformance Information

pdnAtmfM4Groups       OBJECT IDENTIFIER ::= { pdnAtmfM4ExtConformance 1 }
pdnAtmfM4Compliances  OBJECT IDENTIFIER ::= { pdnAtmfM4ExtConformance 2 }

pdnAtmfM4Compliance MODULE-COMPLIANCE
    STATUS  current
    DESCRIPTION
        "The compliance statement for SNMP entities which support
         the ATM M4 extensions."
    MODULE
         GROUP pdnAtmfM4LoopbackLocationGroup
         DESCRIPTION
             "The conditional objects in the Loopback Location Group."
             OBJECT  pdnAtmfM4LoopbackLocationCode
             MIN-ACCESS  read-only
             DESCRIPTION
                "Write access is not required"
    ::= { pdnAtmfM4Compliances 1 }

--
-- Units of Conformance
--
 
pdnAtmfM4TcCurrGroup OBJECT-GROUP
    OBJECTS {
        pdnAtmfM4TcProtoCurrCellIns,
        pdnAtmfM4TcProtoCurrCellOuts,
        pdnAtmfM4TcProtoCurrInDiscards,
        pdnAtmfM4TcProtoCurrOutDiscards,
        pdnAtmfM4TcProtoCurrLCDEvents,
        pdnAtmfM4TcProtoCurrUnknownCells,
        pdnAtmfM4TcProtoCurrCorrectedHEC
    }
    STATUS  current
    DESCRIPTION
        "The objects in the ATM TC layer current table."
    ::= { pdnAtmfM4Groups 1 }

pdnAtmfM4TcHistGroup OBJECT-GROUP
    OBJECTS {
        pdnAtmfM4TcProtoHistCellIns,
        pdnAtmfM4TcProtoHistCellOuts,
        pdnAtmfM4TcProtoHistInDiscards,
        pdnAtmfM4TcProtoHistOutDiscards,
        pdnAtmfM4TcProtoHistLCDEvents,
        pdnAtmfM4TcProtoHistUnknownCells,
        pdnAtmfM4TcProtoHistCorrectedHEC
    }
    STATUS  current
    DESCRIPTION
        "The objects in the ATM TC layer history table."
    ::= { pdnAtmfM4Groups 2 }

pdnAtmfM4VcLoopbackTestGroup OBJECT-GROUP
    OBJECTS {
        pdnAtmfM4VcLoopbackTestElpsTime,
        pdnAtmfM4VcLoopbackTestCellsSent,
        pdnAtmfM4VcLoopbackTestCellsRcvd,
        pdnAtmfM4VcLoopbackTestMinRTDelay,
        pdnAtmfM4VcLoopbackTestMaxRTDelay,
        pdnAtmfM4VcLoopbackTestAvgRTDelay,
        pdnAtmfM4VcLoopbackTestErrorCode
    }
    STATUS  current
    DESCRIPTION
        "The objects in the ATM OAM Loopback Test (multiple cell) table for ATM VCC."
    ::= { pdnAtmfM4Groups 3 }

pdnAtmfM4Vc1CellLoopGroup OBJECT-GROUP
    OBJECTS {
        pdnAtmfM4Vc1CellLoopRTDelay,
        pdnAtmfM4Vc1CellLoopReportedLocation,
        pdnAtmfM4Vc1CellLoopErrorCode
    }
    STATUS  current
    DESCRIPTION
        "The objects in the ATM Single Cell OAM Loopback Test table."
    ::= { pdnAtmfM4Groups 4 }

pdnAtmfM4LoopbackLocationGroup OBJECT-GROUP
    OBJECTS {
        pdnAtmfM4LoopbackLocationCode
    }
    STATUS  current
    DESCRIPTION
        "The objects in the ATM Loopback Location table."
    ::= { pdnAtmfM4Groups 5 }

pdnAtmfM4VpLoopbackTestGroup OBJECT-GROUP
    OBJECTS {
        pdnAtmfM4VpLoopbackTestElpsTime,
        pdnAtmfM4VpLoopbackTestCellsSent,
        pdnAtmfM4VpLoopbackTestCellsRcvd,
        pdnAtmfM4VpLoopbackTestMinRTDelay,
        pdnAtmfM4VpLoopbackTestMaxRTDelay,
        pdnAtmfM4VpLoopbackTestAvgRTDelay,
        pdnAtmfM4VpLoopbackTestErrorCode
    }
    STATUS  current
    DESCRIPTION
        "The objects in the ATM OAM Loopback Test (multiple cell) table for ATM VPC."
    ::= { pdnAtmfM4Groups 6 }
END

PDN-ATMSTATS-MIB DEFINITIONS ::= BEGIN

IMPORTS
	MODULE-IDENTITY , OBJECT-TYPE, Integer32, Gauge32, Counter32
		FROM SNMPv2-SMI
	TimeInterval,RowStatus
		FROM SNMPv2-TC
	ifIndex
		FROM IF-MIB
   pdnAtm
		FROM PDN-HEADER-MIB
	atmVclVpi, atmVclVci
		FROM ATM-MIB;


-- ===============================================================
--
--   ATM Stats Group
--
--  Release: 1.0  05/26/99 (Initial Release)
--
--  Last Updated: 03/28/2002
--
--
    pdnAtmStatsMIB MODULE-IDENTITY
		LAST-UPDATED "0002281200Z"
		ORGANIZATION "Paradyne Networks
					  MIB Working Group"
		CONTACT-INFO
				      "Paradyne Networks
					   331 Newman Springs Road
		               Red Bank, NJ 07701
					   www.paradyne.com

					   General Comments to: mibwg_team@eng.paradyne.com"

		DESCRIPTION
		"This MIB Module supports ATM Statistics "

        REVISION "0203280000Z"
	         DESCRIPTION " D.GOUGH Added pdnAtmStatTable to count HEC and OCD errors 
		 per interface."

        REVISION "0004130000Z"
		DESCRIPTION "Z. Pan
			o	added pdnAtmVclCurrTable - a current 15 minute cells stats
			 	 and  pdnAtmVclHistTable - 96 -  15 minute history cells stats"

        REVISION "9905260000Z"
		DESCRIPTION "J. Strain
			o  Initial - VPL and VCL Stats Table"
	::= {  pdnAtm 3 }

pdnAtmVplStat OBJECT IDENTIFIER ::= { pdnAtmStatsMIB  1 }
pdnAtmVclStat OBJECT IDENTIFIER ::= { pdnAtmStatsMIB  2 }
pdnAtmStat OBJECT IDENTIFIER ::= { pdnAtmStatsMIB  3 }

-- ===============================================================
--
-- The following 2 tables were taken from draft-ietf-atommib-atm2-12.txt.
--			1) Atm VPL Statistics Table
--			2) Atm VCL Statistics Table
--
-- The following changes  were made to the VCL table:
--	  1)  This additional object 'pdnAtmVclStatRowStatus' is used to allow the
--		user to dynamically select the VCL's
--		the user would like to collect statistics on.
--				
-- The following changes were made by D. Gough
-- 	1)Added pdnAtmStatTable to count HEC and OCD errors per interface
-- ===============================================================
--
--                   Definitions of Supplemental Managed Objects
--                               for ATM Management
--
--                                  March 13, 1998
-- 
-- 						Original Authors
-- 
--                               Faye Ly  (editor)
--                               3Com Corporation
--                                 fayely@3com.com
-- 
-- 
--                              Michael Noto  (editor)
--                          Network Equipment Technologies
--                                mike_noto@net.com
-- 
-- 
--                              Andrew Smith  (editor)
--                                 Extreme Networks
--                           ansmith@extremenetworks.com
-- 
-- 
--                          Ethan Mickey Spiegel  (editor)
--                                  Cisco Systems
--                                mspiegel@cisco.com
-- 
-- 
--                               Kaj Tesink  (editor)
--                           Bell Communications Research
--                               kaj@cc.bellcore.com
-- 
-- 
-- ===============================================================

-- ===============================================================
--	
--			Atm VPL Statistics Table
--
-- ===============================================================

              pdnAtmVplStatTable   OBJECT-TYPE
                  SYNTAX       SEQUENCE OF PdnAtmVplStatEntry
                  MAX-ACCESS   not-accessible
                  STATUS       current
                  DESCRIPTION
                      "This table contains all statistic counters per
                      VPL.  It is used to monitor the usage of the VPL
                      in terms of incoming cells and outgoing cells."
                  ::= { pdnAtmVplStat 1 }
 
              pdnAtmVplStatEntry    OBJECT-TYPE
                  SYNTAX       PdnAtmVplStatEntry
                  MAX-ACCESS   not-accessible
                  STATUS       current
                  DESCRIPTION
                      "Each entry in this table represents a VPL."
                  INDEX { pdnAtmVplStatIfIndex, pdnAtmVplStatVpi }
                  ::= { pdnAtmVplStatTable 1 }
 
              PdnAtmVplStatEntry ::=
                  SEQUENCE {
                      pdnAtmVplStatIfIndex           Integer32,
                      pdnAtmVplStatVpi               Integer32,
                      pdnAtmVplStatTotalCellIns      Counter32,
                      pdnAtmVplStatClp0CellIns       Counter32,
                      pdnAtmVplStatTotalDiscards     Counter32,
                      pdnAtmVplStatClp0Discards      Counter32,
                      pdnAtmVplStatTotalCellOuts     Counter32,
                      pdnAtmVplStatClp0CellOuts      Counter32,
                      pdnAtmVplStatTaggedOuts        Counter32
              }

              pdnAtmVplStatIfIndex OBJECT-TYPE
                  SYNTAX  Integer32
                  MAX-ACCESS  read-only
                  STATUS current
                  DESCRIPTION
                      "A unique value for each interface.  Its value
                      ranges between 1 and the value of ifNumber.  The
                      value for each interface must remain constant at
                      least from one re-initialization of the entity's
                      network management system to the next re-
                      initialization."
                  ::= { pdnAtmVplStatEntry 1 }

              pdnAtmVplStatVpi OBJECT-TYPE
                  SYNTAX   Integer32
                  MAX-ACCESS   read-only
	              STATUS   current
                  DESCRIPTION
                      "The VPI value of the VPL."
                  ::= { pdnAtmVplStatEntry 2 }
 
              pdnAtmVplStatTotalCellIns OBJECT-TYPE
                  SYNTAX   Counter32
                  MAX-ACCESS   read-only
                  STATUS   current
                  DESCRIPTION
                      "The total number of valid ATM cells received by
 
                      this VPL including both CLP=0 and CLP=1 cells.
                      The cells are counted prior to the application of
                      the traffic policing."
                  ::= { pdnAtmVplStatEntry 3 }
 
              pdnAtmVplStatClp0CellIns OBJECT-TYPE
                  SYNTAX   Counter32
                  MAX-ACCESS   read-only
                  STATUS   current
                  DESCRIPTION
                      "The number of valid ATM cells received by this
                      VPL with CLP=0.  The cells are counted prior to
                      the application of the traffic policing."
                  ::= { pdnAtmVplStatEntry 4 }
 
              pdnAtmVplStatTotalDiscards OBJECT-TYPE
                  SYNTAX   Counter32
                  MAX-ACCESS   read-only
                  STATUS   current
                  DESCRIPTION
                      "The total number of valid ATM cells discarded by
                      the traffic policing entity.  This includes cells
                      originally received with CLP=0 and CLP=1."
                  ::= { pdnAtmVplStatEntry 5 }
 
              pdnAtmVplStatClp0Discards OBJECT-TYPE
                  SYNTAX   Counter32
                  MAX-ACCESS   read-only
                  STATUS   current
                  DESCRIPTION
                      "The total number of valid ATM cells received with
                      CLP=0 an  discarded by the traffic policing
                      entity."
                  ::= { pdnAtmVplStatEntry 6 }
 
              pdnAtmVplStatTotalCellOuts OBJECT-TYPE
                  SYNTAX   Counter32
                  MAX-ACCESS   read-only
                  STATUS   current
                  DESCRIPTION
                      "The total number of valid ATM cells transmitted
                      by this VPL.  This includes both CLP=0 and CLP=1
                      cells."
                  ::= { pdnAtmVplStatEntry 7 }
 
 
              pdnAtmVplStatClp0CellOuts OBJECT-TYPE
                  SYNTAX   Counter32
                  MAX-ACCESS   read-only
                  STATUS   current
                  DESCRIPTION
                      "The total number of valid ATM cells transmitted
                      with CLP=0 by this VPL."
                  ::= { pdnAtmVplStatEntry 8 }
 
              pdnAtmVplStatTaggedOuts OBJECT-TYPE
                  SYNTAX   Counter32
                  MAX-ACCESS   read-only
                  STATUS   current
                  DESCRIPTION
                      "The total number of valid ATM cells tagged by the
                      traffic policing entity from CLP=0 to CLP=1 and
                      transmitted by this VPL."
                  ::= { pdnAtmVplStatEntry 9 }

-- ===============================================================
--	
--			Atm VCL Statistics Table
--
-- ===============================================================
 
              pdnAtmVclStatTable   OBJECT-TYPE
                  SYNTAX   SEQUENCE OF PdnAtmVclStatEntry
                  MAX-ACCESS   not-accessible
                  STATUS   current
                  DESCRIPTION
                      "This table contains all statistic counters per
                      VCL.  It is used to monitor the usage of the VCL
                      in terms of incoming cells and outgoing cells."
                  ::= { pdnAtmVclStat 2 }
 
              pdnAtmVclStatEntry    OBJECT-TYPE
                  SYNTAX   PdnAtmVclStatEntry
                  MAX-ACCESS   not-accessible
                  STATUS   current
                  DESCRIPTION
                      "Each entry in this table represents a VCL."
                  INDEX {  pdnAtmVclStatIfIndex, pdnAtmVclStatVpi, pdnAtmVclStatVci }
                  ::= { pdnAtmVclStatTable 1 }
 
              PdnAtmVclStatEntry ::=
                  SEQUENCE {
                      pdnAtmVclStatIfIndex           Integer32,
                      pdnAtmVclStatVpi               Integer32,
                      pdnAtmVclStatVci               Integer32,
                      pdnAtmVclStatTotalCellIns      Counter32,
                      pdnAtmVclStatClp0CellIns       Counter32,
                      pdnAtmVclStatTotalDiscards     Counter32,
                      pdnAtmVclStatClp0Discards      Counter32,
                      pdnAtmVclStatTotalCellOuts     Counter32,
                      pdnAtmVclStatClp0CellOuts      Counter32,
                      pdnAtmVclStatTaggedOuts        Counter32,
                      pdnAtmVclStatRowStatus       	 RowStatus
                  }
 
              pdnAtmVclStatIfIndex OBJECT-TYPE
                  SYNTAX  Integer32
                  MAX-ACCESS  read-only
                  STATUS current
                  DESCRIPTION
                      "A unique value for each interface.  Its value
                      ranges between 1 and the value of ifNumber.  The
                      value for each interface must remain constant at
                      least from one re-initialization of the entity's
                      network management system to the next re-
                      initialization."
                  ::= { pdnAtmVclStatEntry 1 }
 
              pdnAtmVclStatVpi OBJECT-TYPE
                  SYNTAX     Integer32
                  MAX-ACCESS     read-only
                  STATUS     current
                  DESCRIPTION
                      "The VPI value of the VCL."
                  ::= { pdnAtmVclStatEntry 2 }

              pdnAtmVclStatVci OBJECT-TYPE
                  SYNTAX     Integer32
                  MAX-ACCESS     read-only
                  STATUS     current
                  DESCRIPTION
                      "The VCI value of the VCL."
                  ::= { pdnAtmVclStatEntry 3 }
 
              pdnAtmVclStatTotalCellIns OBJECT-TYPE
                  SYNTAX   Counter32
                  MAX-ACCESS   read-only
                  STATUS   current
                  DESCRIPTION
                      "The total number of valid ATM cells received by
                      this VCL including both CLP=0 and CLP=1 cells.
                      The cells are counted prior to the application of
                      the traffic policing."
                  ::= { pdnAtmVclStatEntry 4 }
 
              pdnAtmVclStatClp0CellIns OBJECT-TYPE
			      SYNTAX   Counter32
                  MAX-ACCESS   read-only
                  STATUS   current
                  DESCRIPTION
                      "The number of valid ATM cells received by this
                      VCL with CLP=0.  The cells are counted prior to
                      the application of the traffic policing."
                  ::= { pdnAtmVclStatEntry 5 }
 
              pdnAtmVclStatTotalDiscards OBJECT-TYPE
                  SYNTAX   Counter32
                  MAX-ACCESS   read-only
                  STATUS   current
                  DESCRIPTION
                      "The total number of valid ATM cells discarded by
                      the traffic policing entity.  This includes cells
                      originally received with CLP=0 and CLP=1."
                  ::= { pdnAtmVclStatEntry 6 }
 
              pdnAtmVclStatClp0Discards OBJECT-TYPE
                  SYNTAX   Counter32
                  MAX-ACCESS   read-only
                  STATUS   current
                  DESCRIPTION
                      "The total number of valid ATM cells received with
                      CLP=0 an  discarded by the traffic policing
                      entity."
                  ::= { pdnAtmVclStatEntry 7 }
 
              pdnAtmVclStatTotalCellOuts OBJECT-TYPE
                  SYNTAX   Counter32
                  MAX-ACCESS   read-only
                  STATUS   current
                  DESCRIPTION
                      "The total number of valid ATM cells transmitted
                      by this VCL.  This includes both CLP=0 and CLP=1
                      cells."
                  ::= { pdnAtmVclStatEntry 8 }
 
              pdnAtmVclStatClp0CellOuts OBJECT-TYPE
                  SYNTAX   Counter32
                  MAX-ACCESS   read-only
                  STATUS   current
                  DESCRIPTION
                      "The total number of valid ATM cells transmitted
                      with CLP=0 by this VCL."
                  ::= { pdnAtmVclStatEntry 9 }
 
              pdnAtmVclStatTaggedOuts OBJECT-TYPE
                  SYNTAX   Counter32
                  MAX-ACCESS   read-only
                  STATUS   current
                  DESCRIPTION
                      "The total number of valid ATM cells tagged by the
                      traffic policing entity from CLP=0 to CLP=1 and
                      transmitted by this VCL."
                  ::= { pdnAtmVclStatEntry 10 }


			pdnAtmVclStatRowStatus OBJECT-TYPE
				    SYNTAX  RowStatus
				    MAX-ACCESS  read-write
				    STATUS current
				    DESCRIPTION
			           "This object is used to create a new row
						 or delete an existing row in this table. When a new
						row is added, statistics are collected for the
						VCL. Statistics collection is terminated by deletion of the
						row."
				    ::= { pdnAtmVclStatEntry  11 }

-- ===============================================================
--
-- ATM VCL current and historical fifteen-minute interval statistics 
-- pdnAtmfVclCurrTable and pdnAtmVclHistTable
--  ZPan.

-- Current fifteen-minute interval statistics per VCL

pdnAtmVclCurrTable OBJECT-TYPE
     SYNTAX    SEQUENCE OF    PdnAtmVclCurrEntry
     MAX-ACCESS     not-accessible
     STATUS    current
     DESCRIPTION
          "This table maintains per-TP statistics for the
          fifteen-minute interval currently being collected."
     ::= { pdnAtmVclStat 3 }

pdnAtmVclCurrEntry OBJECT-TYPE
     SYNTAX    PdnAtmVclCurrEntry
     MAX-ACCESS     not-accessible
     STATUS    current
     DESCRIPTION
          "An entry in this table for VCL termination points.
          Each VCL Termination Point automatically has
          an entry in this table associated with it."
     INDEX     { ifIndex, 
		 atmVclVpi,
		 atmVclVci }
     ::= { pdnAtmVclCurrTable 1 }

PdnAtmVclCurrEntry ::= SEQUENCE {
     pdnAtmVclCurrElapsedTime 	     TimeInterval,
     pdnAtmVclCurrTotalCellIns       Gauge32,
     pdnAtmVclCurrTotalInDiscards    Gauge32,
     pdnAtmVclCurrTotalCellOuts      Gauge32,
     pdnAtmVclCurrTotalOutDiscards   Gauge32
          }

pdnAtmVclCurrElapsedTime OBJECT-TYPE
     SYNTAX TimeInterval
     MAX-ACCESS read-only
     STATUS current
     DESCRIPTION
          "Amount of time, measured in seconds, that statistics
          for this entry (the current interval) have been counted."
     ::= { pdnAtmVclCurrEntry 1 }

pdnAtmVclCurrTotalCellIns OBJECT-TYPE
     SYNTAX    Gauge32
     MAX-ACCESS     read-only
     STATUS    current
     DESCRIPTION
          "The total number of valid ATM cells received by this VCL.
	       This number corresponds to that of toal cells recieved
           from CPE if this interface is a DSL ATM interface" 
     ::= { pdnAtmVclCurrEntry 2 }

pdnAtmVclCurrTotalInDiscards OBJECT-TYPE
     SYNTAX    Gauge32
     MAX-ACCESS     read-only
     STATUS    current
     DESCRIPTION
          "The number of discarded received cells."
     ::= { pdnAtmVclCurrEntry 3 }

pdnAtmVclCurrTotalCellOuts OBJECT-TYPE
     SYNTAX    Gauge32
     MAX-ACCESS     read-only
     STATUS    current
     DESCRIPTION
          "The number of cells that have been successfully sent.
	       This number corresponds to that of toal cells transmitted
           to CPE if this interface is a DSL ATM interface" 
     ::= { pdnAtmVclCurrEntry 4 }

pdnAtmVclCurrTotalOutDiscards OBJECT-TYPE
     SYNTAX    Gauge32
     MAX-ACCESS     read-only
     STATUS    current
     DESCRIPTION
          "The number of discarded transmitted cells since this interval."
     ::= { pdnAtmVclCurrEntry 5 }


-- History fifteen-minute interval statistics per VCL and time interval
-- These data are only recorded for permanent connections.

pdnAtmVclHistTable OBJECT-TYPE
     SYNTAX    SEQUENCE OF    PdnAtmVclHistEntry
     MAX-ACCESS     not-accessible
     STATUS    current
     DESCRIPTION
          "This table maintains per-interface statistics for previous
          fifteen-minute intervals."
     ::= { pdnAtmVclStat 4 }

pdnAtmVclHistEntry OBJECT-TYPE
     SYNTAX    PdnAtmVclHistEntry
     MAX-ACCESS     not-accessible
     STATUS    current
     DESCRIPTION
          "An entry in History Data table for VCL termination points.
          Each VCL Termination Point automatically has
          an entry in this table associated with it."
     INDEX     { ifIndex,
		     atmVclVpi,
		     atmVclVci,
	         pdnAtmVclHistIndex }
     ::= { pdnAtmVclHistTable 1 }

PdnAtmVclHistEntry ::= SEQUENCE {
     pdnAtmVclHistIndex            Integer32,
     pdnAtmVclHistElapsedTime      TimeInterval,
     pdnAtmVclHistTotalCellIns     Gauge32,
     pdnAtmVclHistTotalInDiscards  Gauge32,
     pdnAtmVclHistTotalCellOuts    Gauge32,
     pdnAtmVclHistTotalOutDiscards Gauge32
          }

pdnAtmVclHistIndex OBJECT-TYPE
     SYNTAX    Integer32 (1..96)
     MAX-ACCESS     not-accessible
     STATUS    current
     DESCRIPTION
          "A number between 1 and 96, which identifies the interval
          for which the set of statistics in this entry was
          collected.
          The interval identified by 1 is the most recently completed
          15 minute interval, and the interval identified by N is the
          interval immediately preceding the one identified by N-1."
     ::= { pdnAtmVclHistEntry 1 }

pdnAtmVclHistElapsedTime OBJECT-TYPE
     SYNTAX    TimeInterval
     MAX-ACCESS     read-only
     STATUS    current
     DESCRIPTION
          "Amount of Time, measured in units of 0.01 second, that
 	   statistics for this entry(the current interval) have been
	   counted."
     ::= { pdnAtmVclHistEntry 2 }

pdnAtmVclHistTotalCellIns OBJECT-TYPE
     SYNTAX    Gauge32
     MAX-ACCESS     read-only
     STATUS    current
     DESCRIPTION
          "The total number of valid ATM cells received by this VCL
	   during this interval.
	   This number corresponds to that of toal cells recieved
           from CPE if this interface is a DSL ATM interface" 
     ::= { pdnAtmVclHistEntry 3 }

pdnAtmVclHistTotalInDiscards OBJECT-TYPE
     SYNTAX    Gauge32
     MAX-ACCESS     read-only
     STATUS    current
     DESCRIPTION
          "The number of discarded received cells during this interval."
     ::= { pdnAtmVclHistEntry 4 }

pdnAtmVclHistTotalCellOuts OBJECT-TYPE
     SYNTAX    Gauge32
     MAX-ACCESS     read-only
     STATUS    current
     DESCRIPTION
          "The number of cells that have been successfully sent during
	       this interval.
	       This number corresponds to that of toal cells transmitted
           to CPE if this interface is a DSL ATM interface" 
     ::= { pdnAtmVclHistEntry 5 }

pdnAtmVclHistTotalOutDiscards OBJECT-TYPE
     SYNTAX    Gauge32
     MAX-ACCESS     read-only
     STATUS    current
     DESCRIPTION
          "The number of discarded transmitted cells during this interval."
     ::= { pdnAtmVclHistEntry 6 }

-- ===============================================================

-- ===============================================================
--	
--			Atm Statistics Table
--
-- ===============================================================

              pdnAtmStatTable   OBJECT-TYPE
                  SYNTAX       SEQUENCE OF PdnAtmStatEntry
                  MAX-ACCESS   not-accessible
                  STATUS       current
                  DESCRIPTION
                      "This table contains all statistic counters per
                      interface.  It is used to monitor the errors 
                      in terms of incoming cells."
                  ::= { pdnAtmStat 1 }
 
              pdnAtmStatEntry    OBJECT-TYPE
                  SYNTAX       PdnAtmStatEntry
                  MAX-ACCESS   not-accessible
                  STATUS       current
                  DESCRIPTION
                      "Each entry in this table represents a error count
		       per interface."
                  INDEX { ifIndex }
                  ::= { pdnAtmStatTable 1 }
 
              PdnAtmStatEntry ::=
                  SEQUENCE {
                      pdnAtmStatHECErrors         Counter32,
                      pdnAtmStatLCDErrors         Counter32	
              }

              pdnAtmStatHECErrors OBJECT-TYPE
                  SYNTAX   Counter32
                  MAX-ACCESS   read-only
                  STATUS   current
                  DESCRIPTION
                      "The total number of ATM cells discarded on 
		      this interface due to a HEC violation."
                  ::= { pdnAtmStatEntry 1 }

              pdnAtmStatLCDErrors OBJECT-TYPE
                  SYNTAX   Counter32
                  MAX-ACCESS   read-only
                  STATUS   current
                  DESCRIPTION
                      "The total number of Loss of Cell Delineataion
		      events (LCD) that occured on this interface."
                  ::= { pdnAtmStatEntry 2 }

END

-- ===============================================================
-- Copyright (C) 2003 Paradyne Corporation.
-- ===============================================================

PDN-MPE-DSLAM-SYSTEM-MIB DEFINITIONS ::= BEGIN

IMPORTS
   NOTIFICATION-TYPE,
   OBJECT-TYPE,
   MODULE-IDENTITY,
   Integer32,
   TimeTicks
	FROM SNMPv2-SMI
   OBJECT-GROUP, NOTIFICATION-GROUP,
   MODULE-COMPLIANCE
	FROM SNMPv2-CONF
   TruthValue, TEXTUAL-CONVENTION
	FROM SNMPv2-TC
   SnmpAdminString
        FROM SNMP-FRAMEWORK-MIB
   ContactState
	FROM PDN-TC
   entPhysicalIndex,
   entPhysicalEntry
	FROM ENTITY-MIB
   pdn-mpe
	FROM PDN-HEADER-MIB
   mpeSysObjectID
        FROM PDN-MPE-MIB2-MIB

;

mpe-dslam	 MODULE-IDENTITY
   LAST-UPDATED    "200306060000Z"  -- June 6, 2003
   ORGANIZATION    "Paradyne Corporation
		    MIB Working Group"

   CONTACT-INFO    "Paradyne Corporation
		    8545 126th Avenue North
		    Largo, FL 33733
		    www.paradyne.com

		    General Comments to: mibwg_team@paradyne.com

		    Editors
                    Prakash Easwar
                    Jesus Pinto
		    Dragana Gough
                    Clay Sikes"

  DESCRIPTION
   "The mpe dslam MIB. This MIB is written specifically to
   extend entPhysicalTable." 

   REVISION "200306060000Z"  -- June 6, 2003
   DESCRIPTION "Jesus Pinto and Clay Sikes
               Removed the entPhysicalIndex as an object in the
               mpeAlarmRelayInputStateChanged notification. This
               object was redundant in that it's the instance
               part of the mpeAlarmRelayState object."

   REVISION "200304250000Z"  -- April 25, 2003
   DESCRIPTION "Jesus Pinto and Clay Sikes
               Change mpeAlarmRelayInputState to mpeAlarmRelayState
               and changed it from a read-only object to a read-
               write object. This should give ultimate flexibility."

   REVISION "200304180000Z"  -- April 18, 2003
   DESCRIPTION "Jesus Pinto and Clay Sikes
               Needed objects to read Alarm Relay Input State. The
               addition of mpeEntPhysicalExtAlarmRelayInputContactState
               below was not a good idea as it implied a dense augments.
               mpeEntPhysicalExtAlarmRelayInputContactState was deprecated.

               Added a new table, mpeAlarmRelayTable to hold alarm
               relay objects where the table implies a sparse augments.
               Deprecated mpeAlarmRrelayEquipmentIndex, 
               mpeAlarmRelayInputContactState, and the
               mpeAlarmRelayInputcontactStateChanged trap they were
               designed for to discourage use in new projects. Added a new 
               trap, mpeAlarmRelayInputStateChanged, as a replacement that
               uses objects defined in or related to the mpeAlarmRelayTable.

               The mpeAlarmRelayTable allows Alarm Relay Input state to be
               read and has a direct relationship with the objects defined
               for the mpeAlarmRelayInputStateChanged trap. Since this table
               is indexed the entPhysicalIndex, it is extremely flexible in 
               that it can apply to a Single Management Entity / Single 
               Logical Entity, a chassis, or what ever level of granularity 
               is desired in the implementation."

   REVISION "200303201500Z"  -- March 20, 2003
   DESCRIPTION "Added new notifications to complement the
		entConfigChange notification defined in RFC2737."

   REVISION "200303070000Z"  -- March 7, 2003
   DESCRIPTION "Added mpeEntPhysicalExtAlarmRelayInputContactState."

   REVISION "200210250000Z"  -- October 25, 2002
   DESCRIPTION "Added mpeEntPhysicalExtTable and cleaned up some
                MIB compiler warnings."

   REVISION "0208150000Z"
   DESCRIPTION "Added mpeAlarmRelayEquipIndex, 
                Added mpeAlarmRelayInputContactState,
		Added mpeAlarmRelayInputContactStateChanged trap."

   REVISION "0202210000Z"
   DESCRIPTION "Added mpeDeviceFailureCleared Trap."

   REVISION "0201280000Z"
   DESCRIPTION "Added table to extend entityPhysicalTable by
		one object that would specify state of the alarm." 

   REVISION "0001220000Z"
   DESCRIPTION "Initial Release" 

   ::= { pdn-mpe 24 }

mpeSysDevDslamMIBObjects OBJECT IDENTIFIER ::= { mpe-dslam 1 }
mpeSysDevDslamMIBTraps   OBJECT IDENTIFIER ::= { mpe-dslam 2 }
mpeEntExtAlarms          OBJECT IDENTIFIER ::= { mpeSysDevDslamMIBObjects 1}
mpeAlarmRelay            OBJECT IDENTIFIER ::= { mpeSysDevDslamMIBObjects 2}
mpeEntExtMibObjects      OBJECT IDENTIFIER ::= { mpeSysDevDslamMIBObjects 3}
mpeSysDevDslamMIBNotifications   OBJECT IDENTIFIER ::= { mpeSysDevDslamMIBTraps 0 }



-- =========================================================================
-- Textual Conventions
-- =========================================================================


MpeEntExtAdminStatus ::= TEXTUAL-CONVENTION
    STATUS      current
    DESCRIPTION "Values to support the desired state of the entity.
                These values were selected to correspond to the syntax of
                the ifAdminStatus in the IF-MIB."
    SYNTAX INTEGER {
        up(1),       -- The Administrator considers the entity to be in
                     -- the 'up' or 'operational' state.
        down(2),     -- The Administrator considers the entity to be in 
                     -- the 'down' or non-operational' state. Generally
                     -- in this state, alarms or traps should not be reported.
        testing(3)   -- The Administrator considers the entity to be in
                     -- a state where the entity is under going some sort
                     -- of tests.
    }

MpeEntExtOperStatus ::= TEXTUAL-CONVENTION
    STATUS      current
    DESCRIPTION "Values to support the current operational state of the 
                entity. These values were selected to correspond to the
                syntax of the ifOperStatus in the IF-MIB."
    SYNTAX INTEGER {
        up(1),            -- The entity is operational.
        down(2),          -- The entity is non-operational.
        testing(3),       -- The entity is in some test mode.
        unknown(4),       -- The entity is in an 'unknown' state.
        dormant(5),       -- The entity is in a 'dormant' state.
        notPresent(6),    -- The entity was present, but is currently
                          -- not present.
        reserved1(7)      -- Not used, but reserved.
    }


-- =========================================================================
-- MIB Objects
-- =========================================================================

--
--ALARM objects
--

mpeEntExtAlarmTable OBJECT-TYPE
    SYNTAX SEQUENCE OF MpeEntExtAlarmEntry
    MAX-ACCESS not-accessible
    STATUS current
    DESCRIPTION
        "This table lists the alarm states of the objects
	listed in the entity-MIB entPhysicalTable."
    ::= { mpeEntExtAlarms 1 }

mpeEntExtAlarmEntry OBJECT-TYPE
    SYNTAX MpeEntExtAlarmEntry
    MAX-ACCESS not-accessible
    STATUS current
    DESCRIPTION
        "An mpeEntExtAlarmTable entry indicates the 
        alarm state of the physical entity."
    AUGMENTS { entPhysicalEntry }
    ::= { mpeEntExtAlarmTable 1 }

MpeEntExtAlarmEntry ::= SEQUENCE {
    mpeEntExtAlarm TruthValue
    }

mpeEntExtAlarm OBJECT-TYPE
    SYNTAX TruthValue
    MAX-ACCESS read-only
    STATUS current
    DESCRIPTION
        "This variable indicates the alarm state of the
	 physical entity."
    ::= { mpeEntExtAlarmEntry 1 }

-- 
-- AlarmRelay objects. For the purpose of being used
-- as VarBinds for the AlarmRelayInputContact trap.
--
mpeAlarmRelayEquipIndex OBJECT-TYPE
    SYNTAX Integer32
    MAX-ACCESS accessible-for-notify
    STATUS deprecated
    DESCRIPTION
        "This variable is the index of the equipment whose
	alarms are being relayed. It is a integer number
	starting from 1 until the max number of physical
	connectors the DSLAM device has to support relay.

        NOTE: This object has been deprecated. Please consider using
              the mpeAlarmRelayTable and mpeAlarmRelayInputStateChanged
              objects."
    ::= { mpeAlarmRelay 1 }

mpeAlarmRelayInputContactState OBJECT-TYPE
    SYNTAX ContactState
    MAX-ACCESS accessible-for-notify
    STATUS deprecated
    DESCRIPTION
        "This variable indicates the alarm state of the
	 Input Contact (open/closed).

        NOTE: This object has been deprecated. Please consider using
              the mpeAlarmRelayTable and mpeAlarmRelayInputStateChanged
              objects."
    ::= { mpeAlarmRelay 2 }


-- =========================================================================
-- Alarm Relay Table
-- =========================================================================

mpeAlarmRelayTable OBJECT-TYPE
    SYNTAX      SEQUENCE OF MpeAlarmRelayEntry
    MAX-ACCESS  not-accessible
    STATUS      current
    DESCRIPTION "This table holds objects that relate to Alarm Relay
                input or output."
    ::= { mpeAlarmRelay 3 }

mpeAlarmRelayEntry OBJECT-TYPE
    SYNTAX      MpeAlarmRelayEntry
    MAX-ACCESS  not-accessible
    STATUS      current
    DESCRIPTION "An entry in this table is a sparse augmentation of the
                entPhysicalEntry. As such, it is indexed by the 
                entPhysicalIndex and not an augmentation of the
                entPhysicalTable."
    INDEX       { entPhysicalIndex }
    ::= { mpeAlarmRelayTable 1 }

MpeAlarmRelayEntry ::=
    SEQUENCE {
        mpeAlarmRelayState   ContactState
}

mpeAlarmRelayState OBJECT-TYPE
    SYNTAX      ContactState
    MAX-ACCESS  read-write
    STATUS      current
    DESCRIPTION "This object is used to read or write the state an alarm 
                relay input or output."
    ::= { mpeAlarmRelayEntry 1 }



-- =========================================================================
-- Augmentation of entPhysicalTable
-- =========================================================================

mpeEntPhysicalExtTable OBJECT-TYPE
    SYNTAX      SEQUENCE OF MpeEntPhysicalExtEntry
    MAX-ACCESS  not-accessible
    STATUS      current
    DESCRIPTION "This table contains entity information that is not defined 
                in the standard ENTITY-MIB."
    ::= { mpeEntExtMibObjects 1 }


mpeEntPhysicalExtEntry OBJECT-TYPE
    SYNTAX      MpeEntPhysicalExtEntry
    MAX-ACCESS  not-accessible
    STATUS      current
    DESCRIPTION "An entry extends the entPhysicalEntry defined in the 
                ENTITY-MIB."
    AUGMENTS    { entPhysicalEntry }
    ::= { mpeEntPhysicalExtTable 1 }

MpeEntPhysicalExtEntry ::=
    SEQUENCE {
        mpeEntPhysicalExtUpTime      TimeTicks,
        mpeEntPhysicalExtLocation    SnmpAdminString,
        mpeEntPhysicalExtAdminStatus MpeEntExtAdminStatus,
        mpeEntPhysicalExtOperStatus  MpeEntExtOperStatus
    }

mpeEntPhysicalExtUpTime OBJECT-TYPE
    SYNTAX      TimeTicks
    MAX-ACCESS   read-only
    STATUS      current
    DESCRIPTION "The time (in hundredths of a second --just like the
                sysUpTime) since the entity was last re-initialized."
    ::= { mpeEntPhysicalExtEntry 1 }

mpeEntPhysicalExtLocation OBJECT-TYPE
    SYNTAX      SnmpAdminString
    MAX-ACCESS  read-write
    STATUS      current
    DESCRIPTION "This object allows the manager to enter the location of 
                the physical entity where applicable. For example, in a 
                stack, chassis or units may be in different locations. In 
                this case, it would be logical for the manager to set this 
                object to the location of the associated chassis. 

                Where the location doesn't make sense, it is recommended 
                that the object return a zero-length string."
    ::= { mpeEntPhysicalExtEntry 2 }

mpeEntPhysicalExtAdminStatus OBJECT-TYPE
    SYNTAX      MpeEntExtAdminStatus
    MAX-ACCESS  read-write
    STATUS      current
    DESCRIPTION "The desired state of the entity."
    ::= { mpeEntPhysicalExtEntry 3 }

mpeEntPhysicalExtOperStatus OBJECT-TYPE
    SYNTAX      MpeEntExtOperStatus
    MAX-ACCESS  read-only
    STATUS      current
    DESCRIPTION "The current operational state of the entity."
    ::= { mpeEntPhysicalExtEntry 4 }



-- =========================================================================
--Traps
-- =========================================================================

mpeCcn NOTIFICATION-TYPE
  OBJECTS { entPhysicalIndex }
  STATUS current
  DESCRIPTION
    "This trap signifies a Configuration change  or 
     software upgrade in the xDSL card. This trap 
     is of 'warning' class"
::= { mpeSysDevDslamMIBTraps 7 }

mpeDeviceFailure NOTIFICATION-TYPE
  OBJECTS { entPhysicalIndex }
  STATUS current
  DESCRIPTION
    "This trap signifies that the sending protocol's
     device has failed and the failure was not a result
     of a device test. 
     Note there are no variable bindings for this trap"
::= { mpeSysDevDslamMIBTraps 15 }
 
mpeDeviceFailureCleared NOTIFICATION-TYPE
  OBJECTS { entPhysicalIndex }
  STATUS current
  DESCRIPTION
    "This trap signifies that the sending protocol's
     device has failed but now it is operational.
     Failure was not a result
     of a device test." 
::= { mpeSysDevDslamMIBTraps 16 }
 
mpeNonSupportedMCC NOTIFICATION-TYPE
  OBJECTS { mpeSysObjectID }
  STATUS current
  DESCRIPTION
    "AN has detected MCC firmware release too low to support
     this device"
::= { mpeSysDevDslamMIBTraps 20 }

mpeNonSupportedChassis NOTIFICATION-TYPE
  OBJECTS { mpeSysObjectID }
  STATUS current
  DESCRIPTION
    "AN in slot xx has been installed in a chassis that cannot
     support one or more of its features. "
::= { mpeSysDevDslamMIBTraps 21 }


mpeAlarmRelayInputContactStateChanged NOTIFICATION-TYPE
  OBJECTS { mpeAlarmRelayEquipIndex, mpeAlarmRelayInputContactState }
  STATUS deprecated
  DESCRIPTION
    "This trap signifies that the state of the InputContact Alarm
     has changed since last time.
     NOTE: This object has been deprecated. Please consider using
           the mpeAlarmRelayInputStateChanged notification."
::= { mpeSysDevDslamMIBTraps 22 }

mpeEntPhysicalExtEntityCreated NOTIFICATION-TYPE
  OBJECTS { entPhysicalIndex }
  STATUS current
  DESCRIPTION " This trap signifies that an instance of this entity has
		been created in the entPhysicalTable.

		This trap is generated in addition to the entConfigChange 
		notification defined in RFC2737."

::= { mpeSysDevDslamMIBTraps 23 }

mpeEntPhysicalExtEntityDeleted NOTIFICATION-TYPE
  OBJECTS { entPhysicalIndex }
  STATUS current
  DESCRIPTION " This trap signifies that an instance of this entity has
		been deleted from the entPhysicalTable.

		This trap is generated in addition to the entConfigChange
		notification defined in RFC2737."	

::= { mpeSysDevDslamMIBTraps 24 }

mpeEntPhysicalExtEntityChanged NOTIFICATION-TYPE
  OBJECTS { entPhysicalIndex }
  STATUS current
  DESCRIPTION " This trap signifies that an instance of this entity has
		been modified in the entPhysicalTable as a result of a
		change in any of the objects in that table.

		This trap is generated in addition to the entConfigChange 
		notification defined in RFC2737."

::= { mpeSysDevDslamMIBTraps 25 }

mpeAlarmRelayInputStateChanged NOTIFICATION-TYPE
  OBJECTS { mpeAlarmRelayState }
  STATUS current
  DESCRIPTION
    "This trap signifies that the state of the Alarm Relay Input
     has changed."
::= { mpeSysDevDslamMIBNotifications 26 }


-- =========================================================================
--CONFORMANCE
-- =========================================================================

mpeSysDevDslamConformance  OBJECT IDENTIFIER ::= { mpe-dslam 3 }

mpeSysDevDslamGroups OBJECT IDENTIFIER
    ::= { mpeSysDevDslamConformance 1 }

mpeSysDevDslamCompliances OBJECT IDENTIFIER
    ::= { mpeSysDevDslamConformance 2 }

mpeSysDevDslamDeprecatedGroup OBJECT IDENTIFIER
    ::= { mpeSysDevDslamConformance 3 }

-- =========================================================================
-- COMPLIANCE statements
-- =========================================================================

mpeSysDevDslamAlarmCompliances MODULE-COMPLIANCE
  STATUS current
  DESCRIPTION
    "The compliance statement for entities and their
    alarms states."
  MODULE -- this module
  GROUP mpeSysDevDslamAlarmStateGroup
	DESCRIPTION "The conditional objects in the group"
        OBJECT mpeEntExtAlarm
        DESCRIPTION
           "Write access is not required."

  ::= { mpeSysDevDslamCompliances 1 }

mpeSysDevDslamAlarmStateGroup OBJECT-GROUP
  OBJECTS {
     mpeEntExtAlarm
  }
  STATUS current
  DESCRIPTION
    "The collection of objects which are used
    to describe alarm states for equipments
    physically connected to a DSLAM device."
::= { mpeSysDevDslamGroups 1 }

mpeEntityExtNotificationGroup NOTIFICATION-GROUP
  NOTIFICATIONS {
      mpeCcn,
      mpeDeviceFailure,
      mpeDeviceFailureCleared,
      mpeNonSupportedMCC,
      mpeNonSupportedChassis,
      mpeEntPhysicalExtEntityCreated,
      mpeEntPhysicalExtEntityDeleted,
      mpeEntPhysicalExtEntityChanged,
      mpeAlarmRelayInputStateChanged
  }
  STATUS current
  DESCRIPTION
    "The collection of objects which are used
    to notify that trap conditions are met."
::= { mpeSysDevDslamGroups 2 }

mpeSysDevDslamAlarmRelayGroup OBJECT-GROUP
  OBJECTS {
     mpeAlarmRelayState
  }
  STATUS current
  DESCRIPTION
    "The collection of objects which are used
    for Alarm Relay objects."
::= { mpeSysDevDslamGroups 3 }

mpeEntPhysicalExtGroup OBJECT-GROUP
  OBJECTS {
    mpeEntPhysicalExtUpTime,
    mpeEntPhysicalExtLocation,
    mpeEntPhysicalExtAdminStatus,
    mpeEntPhysicalExtOperStatus
  }
  STATUS current
  DESCRIPTION
    "The collection of objects which are used
    in extending the entPhysicalTable."
::= { mpeSysDevDslamGroups 4 }


------------------------
-- Deprecated Objects --
------------------------
mpeDslamDeprecatedObjectsGroup OBJECT-GROUP
  OBJECTS {
    mpeAlarmRelayEquipIndex,
    mpeAlarmRelayInputContactState
  }
  STATUS deprecated
  DESCRIPTION
    "The collection of objects that have been deprecated."
::= { mpeSysDevDslamDeprecatedGroup 1 }

mpeDslamDeprecatedNotificationsGroup NOTIFICATION-GROUP
  NOTIFICATIONS {
    mpeAlarmRelayInputContactStateChanged
  }
  STATUS deprecated
  DESCRIPTION
    "The collection of traps/notifications that have been deprecated."
::= { mpeSysDevDslamDeprecatedGroup 2 }



END

-- ===============================================================
-- Copyright (C) 2002 Paradyne Corporation.
-- Enterprise device control mib (mpe support)
-- This MIB contains objects that is used to perform
-- various operations on a device.
PDN-MPE-DEVICE-CONTROL-MIB DEFINITIONS ::= BEGIN



IMPORTS
ResetStates 
FROM PDN-TC
IpAddress, Integer32, Counter32, TimeTicks, 
NOTIFICATION-TYPE,
OBJECT-IDENTITY, OBJECT-TYPE,
MODULE-IDENTITY
FROM SNMPv2-SMI
OBJECT-GROUP, NOTIFICATION-GROUP
FROM SNMPv2-CONF
entPhysicalIndex
FROM ENTITY-MIB
pdn-mpe
FROM PDN-HEADER-MIB
RowStatus,
DisplayString
FROM SNMPv2-TC
;

mpeDevControl MODULE-IDENTITY
	LAST-UPDATED  	"0204290000Z"
   	ORGANIZATION    "Paradyne Corporation
		         MIB Working Group"

   	CONTACT-INFO    "Paradyne Corporation
		         8545 126th Avenue North
		         Largo, FL 33733
		         www.paradyne.com

		         General Comments to: mibwg_team@paradyne.com

		         Editors
                         Prakash Easwar
		         Rajesh Raghaven
		         Kathy Wilson
			 Aamir Shaikh"

	DESCRIPTION	"This MIB Module allows a user to reset a device
			in the DSLAM, as well as perform various operations
			related to the storage and retrieval of firmware
			and configuration files on devices."

	REVISION	"0204290000Z"
	DESCRIPTION	"Aamir Shaikh
	o  Adding mpeDevControlExtendedSelfTest object"

 	REVISION	"0204090905Z"
	DESCRIPTION	"Kathy Wilson
	o  Add mpeDevFileXferFileFormat object"

	REVISION	"0011211800Z"
	DESCRIPTION	"Delete CCM objects and traps"

	REVISION	"0010261400Z"
	DESCRIPTION	"Combine the mpeCCMResync objects"

	REVISION	"0010181830Z"
	DESCRIPTION	"Addition of mpeCCMAutoBackupType object"

	REVISION	"0010061800Z"
	DESCRIPTION	"Initial conversion to SMIv2"


	::= { pdn-mpe 10 }

mpeDevControlMIBObjects     OBJECT IDENTIFIER ::= { mpeDevControl 1 }
mpeDevControlMIBTraps       OBJECT IDENTIFIER ::= { mpeDevControl 2 }
mpeDevControlMIBGroups	    OBJECT IDENTIFIER ::= { mpeDevControl 3 }
mpeDevHwControl             OBJECT IDENTIFIER ::= { mpeDevControlMIBObjects 1 }
mpeDevFileXferConfig        OBJECT IDENTIFIER ::= { mpeDevControlMIBObjects 2 }
mpeDevFirmwareControl       OBJECT IDENTIFIER ::= { mpeDevControlMIBObjects 3 }
mpeDevTestControl	    OBJECT IDENTIFIER ::= { mpeDevControlMIBObjects 4 }

mpeDevControlMIBTrapsV2		OBJECT-IDENTITY
	STATUS 	current
	DESCRIPTION	"The traps for the device control MIB."
	::= { mpeDevControlMIBTraps 0 }

-- Device Reset Object
-- Used to reset (warm boot) the device.

mpeDevControlTable OBJECT-TYPE
   SYNTAX  SEQUENCE OF DevControlEntry
   MAX-ACCESS  not-accessible
   STATUS  current
    DESCRIPTION
         "A table that contains generic information about
           Card Control."
    ::= { mpeDevHwControl  1 }

mpeDevControlEntry OBJECT-TYPE
   SYNTAX  DevControlEntry
   MAX-ACCESS  not-accessible
   STATUS  current
   DESCRIPTION
         "A list of information for device Control."
   INDEX  { entPhysicalIndex }
    ::= { mpeDevControlTable 1 }

DevControlEntry ::=
    SEQUENCE {
              mpeDevControlReset                    ResetStates
             }

mpeDevControlReset OBJECT-TYPE
    SYNTAX  ResetStates
    MAX-ACCESS  read-create
    STATUS  current
    DESCRIPTION
        "Writing the value reset (2) to this object 
         initiates a Hardware power-on reset of the device. 
         Writing the value resetToFactoryDefaults (3) causes the device to re-configure 
         itself with factory defaults. Writing the value (4) causes the device
	 to re-configure itself with a previously loaded active configuration. 
	 The value read from this object is noOp(1)."
     ::= { mpeDevControlEntry 1 }

--
-- Device reset and put it in extended selftest mode 
--

mpeDevControlSelfTestTable OBJECT-TYPE
   SYNTAX  SEQUENCE OF DevControlSelfTestEntry
   MAX-ACCESS  not-accessible
   STATUS  current
    DESCRIPTION
         "A table containing information to control device specific Self-Test
	  operations."
    ::= { mpeDevHwControl  2 }

mpeDevControlSelfTestEntry OBJECT-TYPE
   SYNTAX  DevControlSelfTestEntry
   MAX-ACCESS  not-accessible
   STATUS  current
   DESCRIPTION
         "A list of objects for performing Self-Test operations."
   INDEX  { entPhysicalIndex }
    ::= { mpeDevControlSelfTestTable 1 }

DevControlSelfTestEntry ::=
    SEQUENCE {
              	mpeDevControlExtendedSelfTest	    INTEGER
             }

mpeDevControlExtendedSelfTest OBJECT-TYPE
    SYNTAX  INTEGER {
                     noOp(1),
                     enableExtendSelfTestAndReset(2)
                    }
    MAX-ACCESS  read-write
    STATUS  current
    DESCRIPTION
        "This object is used to start the extended Power-On Self-Test
	 test.  Writing the value enableExtendSelfTestAndReset(2) to this
	 object resets the device and puts it into extended Power-On 
	 Self-Test mode.  During device initialization, the extended
	 Self-Test would be carried out first and then the device would
	 carry out its normal boot operation. The value read from this
	 object is noOp(1). Writing back the same value, noOp(1) will not
	 start the test. Note that if extended Self-Test fails for some
	 reason, after re-initialization, the value of this object will 
	 default to enableExtendSelfTestAndReset(2) again unless the 
	 manager explicitly chooses not to do so."

     ::= { mpeDevControlSelfTestEntry 1 }

--
-- Perform Device specific tests
--

mpeDevControlTestTable OBJECT-TYPE
   SYNTAX  SEQUENCE OF MpeDevControlTestEntry
   MAX-ACCESS  not-accessible
   STATUS  current
    DESCRIPTION
         "A table that contains configuration information to perform
	  device specific tests."
    ::= { mpeDevTestControl  3 }

mpeDevControlTestEntry OBJECT-TYPE
   SYNTAX  MpeDevControlTestEntry
   MAX-ACCESS  not-accessible
   STATUS  current
   DESCRIPTION
         "A list of configuration information for device specific tests."
   INDEX  { entPhysicalIndex }
    ::= { mpeDevControlTestTable 1 }

MpeDevControlTestEntry ::=
    SEQUENCE {
              	mpeDevControlTestType 	    INTEGER,
		mpeDevControlTestStatus     INTEGER,
		mpeDevControlTestCmd 	    INTEGER
             }

mpeDevControlTestType OBJECT-TYPE
    SYNTAX  INTEGER {
                     lampTest(1)
                    }
    MAX-ACCESS  read-write
    STATUS  current
    DESCRIPTION
        "This object is used to specify the type of the test to start."

     ::= { mpeDevControlTestEntry 1 }

mpeDevControlTestStatus OBJECT-TYPE
    SYNTAX  INTEGER {
                      active(1),
	              inactive(2)
                    }
    MAX-ACCESS  read-only
    STATUS  current
    DESCRIPTION
        "The test status on the device. This object indicates whether
         the indexed test is currently active(1) or inactive(2)."

     ::= { mpeDevControlTestEntry 2 }

mpeDevControlTestCmd OBJECT-TYPE
    SYNTAX  INTEGER {
                    start  (1),
	            stop   (2)
                    }
    MAX-ACCESS  read-write
    STATUS  current
    DESCRIPTION
        "Used to start or stop the indexed test.
         When read, the value returned will be the next logical command."

     ::= { mpeDevControlTestEntry 3 }

-- =======================================================
--
--  The Paradyne File Transfer Group  (J.Strain)
-- =======================================================

mpeDevFileXferConfigTable OBJECT-TYPE
    SYNTAX  SEQUENCE OF MpeDevFileXferConfigEntry
    MAX-ACCESS  not-accessible
    STATUS  current
    DESCRIPTION
           "The Paradyne  FileXfer Client Config Table."
    ::= { mpeDevFileXferConfig  1 }

mpeDevFileXferConfigEntry OBJECT-TYPE
    SYNTAX  MpeDevFileXferConfigEntry
    MAX-ACCESS  not-accessible
    STATUS  current
    DESCRIPTION

       " Use of the File Tranfer MIB could be used with other MIBS in
              the following manner:
                  a) Use another MIB/means to verify available space /make room
                     for a file to be transfered to this device
                  b) Use this MIB to download the file
                  c) Use another MIB/means to select the file you want to make 
                     active
                                        if your selecting firmware for example.
                  d) Use another MIB/means to reset the device.

        A management station wishing to initiate a file transfer needs to
                         create an entry in this table. To do so, you must
       first identify the entPhysicalIndex of the device you intend to
       do the transfer with.  You should
       then create the associated instance of the row status
       It must also, either in the same
       or in successive PDUs, create an instance of
       mpeDevFileXferFileName, mpeDevFileXferFileType, 
.      mpeDevFileXferServerIpAddress,
       mpeDevFileXferOperation.

       It should also modify the default values for the other
       configuration objects if the defaults are not appropriate.

       Once the appropriate instance of all the configuration
       objects have been created, either by an explicit SNMP
       set request or by default, the row status should be set
       to active to initiate the request. Note that this entire
       procedure may be initiated via a single set request which
       specifies a row status of createAndGo as well as specifies
       valid values for the non-defaulted configuration objects.

       Once the MpeDevFileXferConfigEntry request has been created (i.e. the
       mpeDevFileXferRowStatus has been made active), the entry
       cannot be modified - the only operation possible
       after this is to delete the row.

       Once the request completes, the management station should
       retrieve the values of the status objects of interest, and
       should then delete the entry.  In order to prevent old
       entries from clogging the table, entries could be aged out,
       but an entry will never be deleted within 5 minutes of
       completing.  "
    INDEX   { entPhysicalIndex }
    ::= { mpeDevFileXferConfigTable  1 }

MpeDevFileXferConfigEntry ::=
    SEQUENCE {

    mpeDevFileXferFileName
        DisplayString,

    mpeDevFileXferCopyProtocol
        INTEGER,

    mpeDevFileXferFileType
        INTEGER,

    mpeDevFileXferServerIpAddress
        IpAddress,

    mpeDevFileXferUserName
        DisplayString,

    mpeDevFileXferUserPassword
        DisplayString,

    mpeDevFileXferOperation
        INTEGER,

    mpeDevFileXferPktsSent
        Counter32,

    mpeDevFileXferPktsRecv
        Counter32,

    mpeDevFileXferOctetsSent
        Counter32,

    mpeDevFileXferOctetsRecv
        Counter32,

    mpeDevFileXferOwnerString
        OCTET STRING,

    mpeDevFileXferStatus
        INTEGER,

    mpeDevFileXferErrorStatus
        Integer32,

    mpeDevFileXferSendEvent
        INTEGER,

    mpeDevFileXferRowStatus
        RowStatus,
		
    mpeDevFileXferXferTime
	TimeTicks,	
		
    mpeDevFileXferFileFormat
	INTEGER	
    }

mpeDevFileXferFileName OBJECT-TYPE
    SYNTAX  DisplayString
    MAX-ACCESS  read-create
    STATUS  current
    DESCRIPTION
           "This object contains the name of the filetransfer file."
    ::= { mpeDevFileXferConfigEntry  1 }

mpeDevFileXferCopyProtocol OBJECT-TYPE
    SYNTAX   INTEGER {
                         tftp(1),
                         ftp(2)
                                                }
    MAX-ACCESS  read-create
    STATUS  current
        DESCRIPTION
          "The transfer protocol that should be used to copy the file
           across the network. If the file transfer is to occur locally on the 
           SNMP agent, the method of transfer is left upto the implementation, 
           and is not restricted to the protocols below."

--    DEFVAL  { tftp }
    ::= { mpeDevFileXferConfigEntry  2 }

mpeDevFileXferFileType OBJECT-TYPE
    SYNTAX  INTEGER {
                                firmware(1),
                                config(2)
                                }

    MAX-ACCESS  read-create
    STATUS  current
    DESCRIPTION
           "Specifies the type of file your want to transfer."
    ::= { mpeDevFileXferConfigEntry  3 }

mpeDevFileXferServerIpAddress OBJECT-TYPE
    SYNTAX  IpAddress
    MAX-ACCESS  read-create
    STATUS  current
    DESCRIPTION
           "This object contains the file transfer server's IP address. "
    ::= { mpeDevFileXferConfigEntry  4 }

mpeDevFileXferUserName OBJECT-TYPE
    SYNTAX  DisplayString
    MAX-ACCESS  read-create
    STATUS  current
    DESCRIPTION
           "This object contains the username if a username is needed
        to login to the server."
    ::= { mpeDevFileXferConfigEntry  5 }

mpeDevFileXferUserPassword OBJECT-TYPE
    SYNTAX  DisplayString
    MAX-ACCESS  read-create
    STATUS  current
    DESCRIPTION
           "This object contains the password if a password is needed
            to login to the server. This object will return null on a read 
            operation."
    ::= { mpeDevFileXferConfigEntry  6 }

mpeDevFileXferOperation OBJECT-TYPE
    SYNTAX  INTEGER {
                                get(1),
                                put(2)
                                        }
    MAX-ACCESS  read-create
    STATUS  current
    DESCRIPTION
           "This object contains the operation the file transfer wants to 
perform."
    ::= { mpeDevFileXferConfigEntry  7 }

mpeDevFileXferPktsSent OBJECT-TYPE
    SYNTAX  Counter32
    MAX-ACCESS  read-only
    STATUS  current
    DESCRIPTION
           "This object contains the the number of packets sent to the
        server at the time of interrogation."
    ::= { mpeDevFileXferConfigEntry  8 }

mpeDevFileXferPktsRecv OBJECT-TYPE
    SYNTAX  Counter32
    MAX-ACCESS  read-only
    STATUS  current
    DESCRIPTION
           "This object contains the the number of packets received from the
        server at the time of interrogation."
    ::= { mpeDevFileXferConfigEntry  9 }

mpeDevFileXferOctetsSent OBJECT-TYPE
    SYNTAX  Counter32
    MAX-ACCESS  read-only
    STATUS  current
    DESCRIPTION
           "This object contains the the number of octets sent to the
        server at the time of interrogation."
    ::= { mpeDevFileXferConfigEntry  10 }

mpeDevFileXferOctetsRecv OBJECT-TYPE
    SYNTAX  Counter32
    MAX-ACCESS  read-only
    STATUS  current
    DESCRIPTION
           "This object contains the the number of octets received from the
        server at the time of interrogation."
    ::= { mpeDevFileXferConfigEntry  11 }

mpeDevFileXferOwnerString OBJECT-TYPE
    SYNTAX   OCTET STRING (SIZE(0..255))
    MAX-ACCESS  read-create
    STATUS  current
    DESCRIPTION
           "The entity which currently has the 'ownership'
        required to invoke the operation on this index."
    ::= { mpeDevFileXferConfigEntry  12 }

mpeDevFileXferStatus OBJECT-TYPE
    SYNTAX  INTEGER {
                 none(1),
                 success(2),
                 failure(3),
                 inprogress(4)
               }
    MAX-ACCESS  read-only
    STATUS  current
    DESCRIPTION
           "This object contains the status of the file transfer."
    ::= { mpeDevFileXferConfigEntry  13 }

mpeDevFileXferErrorStatus OBJECT-TYPE
    SYNTAX  Integer32
    MAX-ACCESS  read-only
    STATUS  current
    DESCRIPTION
           "This object contains the reason code of the failure determined in 
mpeDevFileXferStatus.
        The reason code are specific to the file transfer protocol.

        Please refer to the file transfer protocols respective RFC for 
clarification
        of the error code value meanings.

        TFTP Error Codes from rfc 1350
        FTP Error Codes from rfc 959"

    ::= { mpeDevFileXferConfigEntry  14 }

mpeDevFileXferSendEvent OBJECT-TYPE
    SYNTAX INTEGER {
    active(1),
    inactive(2)
    }
    MAX-ACCESS read-create
    STATUS current
    DESCRIPTION
        "This object indicates whether or not to send the 
         mpeDevFileXferEvent event trap ."
    ::= { mpeDevFileXferConfigEntry  15 }

mpeDevFileXferRowStatus OBJECT-TYPE
    SYNTAX  RowStatus
    MAX-ACCESS  read-create
    STATUS  current
    DESCRIPTION
           "This object is used to create
     a new row or delete an
     existing row in this table."
    ::= { mpeDevFileXferConfigEntry  16 }

mpeDevFileXferXferTime OBJECT-TYPE
    SYNTAX  TimeTicks 
    MAX-ACCESS  read-only
    STATUS  current
    DESCRIPTION
        "This object indicates the elapsed time 
		(in hundredths of a second) of the file transfer."
    ::= { mpeDevFileXferConfigEntry 17 }

mpeDevFileXferFileFormat OBJECT-TYPE
    SYNTAX  INTEGER {
                      ascii(1),
                      binary(2)
                    }
    MAX-ACCESS  read-create
    STATUS  current
    DESCRIPTION
           "This object contains the file representation type. A
	   file representation type of ascii implies an ASCII,
	   non-print text file. A file representation type of 
	   binary implies an binary image file. The default file
	   representation type is binary(2)."

--    DEFVAL  { binary }
    ::= { mpeDevFileXferConfigEntry  18 }


-- ====================================================================
--
-- Firmware Control Table
--
-- This table is used to control and provide information concerning
-- firmware/executable images.
--
-- ====================================================================

mpeDevFirmwareControlTable OBJECT-TYPE
    SYNTAX SEQUENCE OF DevFirmwareControlEntry
    MAX-ACCESS  not-accessible
    STATUS  current
    DESCRIPTION
        "A list of the current Firmware Releases and their associated
         status.  Each Firmware Release will be indexed by a number
         from 1 to N.  The user will be able to view the Firmware
         Release String and Operational Status of the release (valid
                 or invalid) and activate a valid Firmware Release by changing
                 the Administration Status to active."
    ::= { mpeDevFirmwareControl 1 }

mpeDevFirmwareControlEntry OBJECT-TYPE
    SYNTAX  DevFirmwareControlEntry
    MAX-ACCESS  not-accessible
    STATUS  current
    DESCRIPTION
        "The Device Firmware Release entry."
    INDEX  { entPhysicalIndex, mpeDevFirmwareControlIndex }
    ::= { mpeDevFirmwareControlTable 1 }

DevFirmwareControlEntry ::=
    SEQUENCE {
    mpeDevFirmwareControlIndex
    Integer32,
    mpeDevFirmwareControlRelease
        DisplayString,
    mpeDevFirmwareControlOperStatus
        INTEGER,
    mpeDevFirmwareControlAdminStatus
        INTEGER
    }

mpeDevFirmwareControlIndex OBJECT-TYPE
    SYNTAX Integer32
    MAX-ACCESS read-only
    STATUS current
    DESCRIPTION
        "This object is used to index the Firmware table (range 1 to N)."
::= { mpeDevFirmwareControlEntry 1 }

mpeDevFirmwareControlRelease OBJECT-TYPE
    SYNTAX  DisplayString (SIZE (1..16))
    MAX-ACCESS  read-only
    STATUS  current
    DESCRIPTION
    "This object indicates the Software Release for
     this Firmware. If the Software Firmware is Operational Status
     is invalid, the Software Revision Number will be blank."
::= { mpeDevFirmwareControlEntry 2 }

mpeDevFirmwareControlOperStatus OBJECT-TYPE
    SYNTAX INTEGER {
    valid(1),
    invalid(2),
    unknown(3)
    }
    MAX-ACCESS read-only
    STATUS current
    DESCRIPTION
     "This object indicates whether or not the indexed
     Firmware entry contains a valid(1) or invalid(2) Firmware."
::= { mpeDevFirmwareControlEntry 3 }

mpeDevFirmwareControlAdminStatus OBJECT-TYPE
    SYNTAX INTEGER {
    active(1),
    inactive(2)
    }
    MAX-ACCESS read-create
    STATUS current
    DESCRIPTION
        "This object indicates whether or not the indexed
     Firmware entry is active(1) or inactive(2).
     Writing active(1) will activate that software release
     and cause the unit to reset (response may timeout).
     Writing active(1) to a Firmware entry whose
     mpeDevFirmwareControlOperStatus is invalid will return BAD VALUE.
     Writing inactive(2) will always return BAD VALUE."
::= { mpeDevFirmwareControlEntry 4 }

--
--      File Transfer Traps
--

mpeDevFileXferEvent NOTIFICATION-TYPE
	OBJECTS {  mpeDevFileXferStatus , mpeDevFileXferErrorStatus,
                                mpeDevFileXferOperation, mpeDevFileXferFileType,
                                mpeDevFileXferFileName }
	STATUS		current
   	DESCRIPTION
     		"This trap is to communicate a couple of things about
      		the completion of a file transfer.

                mpeDevFileXferStatus       - Did it complete successfully or not.
                mpeDevFileXferErrorStatus  - If not, what was the error code.
                mpeDevFileXferOperation    - What operation was performed?.
                mpeDevFileXferFileType     - Was it a firmware xfer or config?
                mpeDevFileXferFileName     - The name of the file transfered.
         	"

 ::= { mpeDevControlMIBTrapsV2 1 }

mpeDevHwControlGroup	OBJECT-GROUP
	OBJECTS		{ mpeDevControlReset,
		  	  mpeDevControlExtendedSelfTest  }
	STATUS		current
	DESCRIPTION	"Objects necessary to implement minimal hardware 
			control"
 ::= { mpeDevControlMIBGroups 1 }

mpeDevFileXferConfigGroup	OBJECT-GROUP
	OBJECTS		{ mpeDevFileXferFileName,
			  mpeDevFileXferCopyProtocol,
			  mpeDevFileXferFileType,
			  mpeDevFileXferServerIpAddress,
			  mpeDevFileXferUserName,
			  mpeDevFileXferUserPassword,
			  mpeDevFileXferOperation,
			  mpeDevFileXferPktsSent,
			  mpeDevFileXferPktsRecv,
			  mpeDevFileXferOctetsSent,
			  mpeDevFileXferOctetsRecv,
			  mpeDevFileXferOwnerString,
			  mpeDevFileXferStatus,
			  mpeDevFileXferErrorStatus,
			  mpeDevFileXferSendEvent,
			  mpeDevFileXferRowStatus,
			  mpeDevFileXferXferTime, 
			  mpeDevFileXferFileFormat }
	STATUS		current
	DESCRIPTION	"Object group used to implement file transfer 
			functionality"
  ::= { mpeDevControlMIBGroups 2 }

mpeDevFirmwareControlGroup	OBJECT-GROUP
	OBJECTS		{ mpeDevFirmwareControlIndex,
		 	  mpeDevFirmwareControlRelease,
			  mpeDevFirmwareControlOperStatus,
			  mpeDevFirmwareControlAdminStatus }
	STATUS		current
	DESCRIPTION	"Object group used to manage firmware releases on 
			devices"
  ::= { mpeDevControlMIBGroups 3 }

mpeDevTestControlGroup		OBJECT-GROUP
	OBJECTS       { mpeDevControlTestType,
			mpeDevControlTestStatus,
			mpeDevControlTestCmd
             	      }
	STATUS       current
	DESCRIPTION  "Objects necessary to implement device specific tests"
  ::= { mpeDevControlMIBGroups 4 }

mpeDevFileXferEventGroup	NOTIFICATION-GROUP
	NOTIFICATIONS	{ mpeDevFileXferEvent }
	STATUS		current
	DESCRIPTION	"Notifications associated with 
			mpeDevFileXferConfigGroup"
  ::= { mpeDevControlMIBGroups 5 }

END

PDN-MPE-HEALTH-AND-STATUS-MIB DEFINITIONS ::= BEGIN

-- Last-Updated: 6/16/00

-- Enterprise Health and Status  MIB (mpe support)
-- Copyright (C) 2000 Paradyne Corporation.
--
-- Created by : Wayne Jadoo / Prakash Easwar

IMPORTS
DisplayString
  FROM SNMPv2-TC
OBJECT-TYPE
  FROM RFC-1212
entPhysicalIndex
  FROM ENTITY-MIB  
mpe-devHealth
  FROM PDN-HEADER-MIB
TRAP-TYPE
  FROM RFC-1215
;

mpeDevHealthAndStatusMIBObjects  OBJECT IDENTIFIER ::= { mpe-devHealth  1 }
mpeDevHealthAndStatusMIBTraps    OBJECT IDENTIFIER ::= { mpe-devHealth  2 }

 -- groups for Paradyne  health and Status MIB

mpeDevHealthAndStatusTable OBJECT-TYPE
  SYNTAX  SEQUENCE OF MpeDevHealthAndStatusEntry
  ACCESS  not-accessible
  STATUS  mandatory
  DESCRIPTION
    "A table that contains information about an Entity's health."
::= { mpeDevHealthAndStatusMIBObjects 1 }

mpeDevHealthAndStatusEntry OBJECT-TYPE
  SYNTAX  MpeDevHealthAndStatusEntry
  ACCESS  not-accessible
  STATUS  mandatory
  DESCRIPTION
    "A list of information for an entity's health."
  INDEX  { entPhysicalIndex }
::= { mpeDevHealthAndStatusTable 1 }

MpeDevHealthAndStatusEntry ::=
  SEQUENCE 
  {
     mpeDevSelfTestResults DisplayString
  }

mpeDevSelfTestResults OBJECT-TYPE
  SYNTAX  DisplayString (SIZE (0..255))
  ACCESS  read-only
  STATUS  mandatory
  DESCRIPTION
    "Self-test results. Self-test (or power-up test) results
     summarizes the test results of each CCA, where each CCA test
     result is separated by a semi-colon. Refer to device-specific 
     user documentation for a complete description of the self test
     codes and messages."
::= { mpeDevHealthAndStatusEntry  1 }

-- Traps for Device failure 

mpeSelfTestFailure TRAP-TYPE
  ENTERPRISE  mpeDevHealthAndStatusMIBTraps
  VARIABLES { mpeDevSelfTestResults }
  DESCRIPTION
    "This trap signifies that the sending protocol's
     device has failed self test.
     The variable binding for this trap would be the selfTest
     devSelfTestResults object of the Health and Status MIB. The
     exact format of this display string will be well-documented
     in the Operational Specifications of the device."
::= 1

END

PDN-REACHDSL-MIB DEFINITIONS ::= BEGIN

--
-- Copyright (C) 2002, Paradyne. All rights reserved.
--

IMPORTS
    MODULE-IDENTITY, OBJECT-TYPE, Unsigned32
        FROM SNMPv2-SMI
    ifIndex
        FROM IF-MIB
    MODULE-COMPLIANCE, OBJECT-GROUP
        FROM SNMPv2-CONF
    DisplayString  
        FROM SNMPv2-TC
    pdn-interfaces
        FROM PDN-HEADER-MIB;
 
pdnReachDSL  MODULE-IDENTITY
        LAST-UPDATED "200210151700Z"
        ORGANIZATION "Paradyne Corp MIB Working Group"
        CONTACT-INFO "Paradyne Networks, Inc.
              8545, 126th Ave. N.,
              Largo, FL 33779
              www.paradyne.com

           General Comments to:
              mibwg_team@eng.paradyne.com

           Editors: A.Z.Shaikh
                    Daniel Varagunasingh
		    Jesus Pinto"

        DESCRIPTION 
           "The Paradyne enterprise ReachDSL MIB.
            This MIB is written specifically to facilitate 
            in the management of ReachDSL devices as well as
            help in configuration of Spectrum Management 
            specific objects for ReachDSL products."

        REVISION "200301151200Z"
        DESCRIPTION
           "1. This mib SHOULD only be used for reachDSL
	       specific technology and not for spectrum
	       management."

        REVISION "200301121200Z"
        DESCRIPTION
           "1. The pdn_spectrummgmt.mib is a new common
	       mib that should be used for all DSL interfaces
	       that require configuration spectrum management
	       parameters."

        REVISION "200210151700Z"
        DESCRIPTION
           "1. Deprecated the reach DSL Circuit Identifier Object.
            2. Added 'Quad Mode' as a loop measurement method.
            3. Added Configuration object for Quad Mode.
            4. Deprecated the old conformance statement &amp; units
               of conformance.
            5. Added new conformance statement &amp; units of
               conformance to clearly reflect the objects' roles."

        REVISION "200207120315Z"
        DESCRIPTION
           "1. Deprecated the Spectrum Management Zone Object.
            2. Added Loop Measurement Method object.
            3. Added EWL Units object.
            4. Added Spectrum Management Mode object.
            5. Added objects for Min &amp; Max EWL values.
            These changes are required for dynamic updation of
            spectrum management configuration."

        ::= { pdn-interfaces 20 }

pdnReachDSLObjects  OBJECT IDENTIFIER ::= { pdnReachDSL 1 }

--
-- START OF PdnReachDSL mib definitions
--

reachDSLSpectrumMgmtSelection OBJECT-TYPE
    SYNTAX      INTEGER {
                    enabled(1),
                    disabled(2)
                }
    MAX-ACCESS  read-write
    STATUS      current
    DESCRIPTION
       "This object has been deprecated. The corresponding
        object in the new pdn_spectrumMgmt.mib should be used
	instead.
	
	This object is used to Enable or Disable 
        Spectrum Management on this device. Enabling
        this object limits the DSL speeds and the maximum
        transmit power on each port based on line length in order
        to meet local Spectrum Management guidelines.

        The values that this object can accept are controlled
        by the 'Mode' object."

    ::= { pdnReachDSLObjects 1 }

reachDSLSpectrumMgmtZone OBJECT-TYPE
    SYNTAX      INTEGER {
                    usa1(1),
                    uk1(2),
                    canada1(3),
                    japan1(4),
                    emea1(5)
                }
    MAX-ACCESS  read-only
    STATUS      deprecated
    DESCRIPTION
       "This object shows the geographic location or the spectrum
        zone used for spectrum management.  It also represents
        which Spectrum Management standard will be used on this
        device to calculate the effective maximum 'Tx Rates' and
        the maximum allowed 'Tx Power' to comply with Spectrum
        Management regulations for that specific region.

        Note: Spectrum Management must be Enabled for
              'SpectrumMgmtZone' to take effect."

    DEFVAL { usa1 }

    ::= { pdnReachDSLObjects 2 }

reachDSLSpectrumMgmtConfTable OBJECT-TYPE
    SYNTAX      SEQUENCE OF ReachDSLSpectrumMgmtConfEntry
    MAX-ACCESS  not-accessible
    STATUS      current
    DESCRIPTION
	"The ReachDSL Spectrum Management Configuration Table
        This table is used for configuring spectrum management
        objects." 

    ::= { pdnReachDSLObjects 3 }

reachDSLSpectrumMgmtConfEntry OBJECT-TYPE
    SYNTAX      ReachDSLSpectrumMgmtConfEntry
    MAX-ACCESS  not-accessible
    STATUS      current
    DESCRIPTION
       	"An entry in the ReachDSL Spectrum Management 
        Configuration table.

        Note: This entry can be accessed only for ifIndex 
              values that belong to a physical interface. 
              e.g. for ifType = 'adsl'."

    INDEX   { ifIndex }

    ::= { reachDSLSpectrumMgmtConfTable 1 }

ReachDSLSpectrumMgmtConfEntry ::= 
    SEQUENCE {
        reachDSLSpectrumMgmtConfEWL            Unsigned32,
        reachDSLSpectrumMgmtConfLoopLength     INTEGER,
        reachDSLSpectrumMgmtConfAtucMaxTxPower INTEGER,
        reachDSLSpectrumMgmtConfAturMaxTxPower INTEGER,
        reachDSLSpectrumMgmtConfQuadMode       INTEGER
    }

reachDSLSpectrumMgmtConfEWL OBJECT-TYPE
    SYNTAX      Unsigned32
    MAX-ACCESS  read-write
    STATUS      current
    DESCRIPTION
       "This object has been deprecated. The corresponding
        object in the new pdn_spectrumMgmt.mib should be used
	instead.

        The Equivalent Working Length (EWL).  The value selected
        corresponds to the estimated length of the line in

            feet   - if 'EWLUnits' object is 'feet'.
            meters - if 'EWLUnits' object is 'meters'. 

        This value is usually specified by the carrier and MUST
        be in integral multiples of 

            500 feet, if 'EWLUnits' is 'feet'.
            200 meters, if 'EWLUnits' is 'meters'.

        The range of values that this object can take is determined
        by the 'MinEWL' and 'MaxEWL' objects.
        Changing this object may limit the maximum transmit power
        and the effective DSL speeds at which the ports train up.

        Note: This object will be used only if Spectrum Management
              is enabled and 'LoopMeasurementMethod' is 'ewl'.
              This object shares a mutual exclusion relationship
              with 'ConfLoopLength' &amp; 'ConfQuadMode' objects, as
              only one of the three will be used for configuration
              at any given instant of time."

    ::= { reachDSLSpectrumMgmtConfEntry 1 }

reachDSLSpectrumMgmtConfLoopLength OBJECT-TYPE
    SYNTAX      INTEGER {
                    short(1),
                    medium(2),
                    long(3)
                }
    MAX-ACCESS  read-write
    STATUS      current
    DESCRIPTION
       "This object has been deprecated. The corresponding
        object in the new pdn_spectrumMgmt.mib should be used
	instead.


        This entry specifies the loop length for the line. The
        configurable values are short(1), medium(2) and long(3).
        The 'Loop Length' feature can be used only if the 
        'reachDSLSpectrumMgmtSelection' object is Enabled and
        the 'LoopMeasurementMethod' is 'loopLength'. Changing this
        object may limit the maximum transmit power and the
        effective DSL speeds at which ports train up.

        Note: This object shares a mutual exclusion relationship 
              with the 'ConfEWL' &amp; 'ConfQuadMode' objects.
              i.e. only one of the three can be used for
              configuration at one time."

    ::= { reachDSLSpectrumMgmtConfEntry 2 }

reachDSLSpectrumMgmtConfAtucMaxTxPower OBJECT-TYPE
    SYNTAX      INTEGER (-140..120)
    UNITS       "tenth dB"
    MAX-ACCESS  read-write
    STATUS      current
    DESCRIPTION
        "The maximum transmit power at the ATUC (in tenth dB).  
        This value will be based on the spectrum management 
        selection.  It ranges from -140 to 120 in increments
        of 10."

    ::= { reachDSLSpectrumMgmtConfEntry 3 }

reachDSLSpectrumMgmtConfAturMaxTxPower OBJECT-TYPE
    SYNTAX      INTEGER (-140..120)
    UNITS       "tenth dB"
    MAX-ACCESS  read-write
    STATUS      current
    DESCRIPTION
        "The maximum transmit power at the ATUR (in tenth dB).
        This value will be based on the spectrum management
        selection. It ranges from -140 to 120 in increments
        of 10."

    ::= { reachDSLSpectrumMgmtConfEntry 4 }

reachDSLSpectrumMgmtConfQuadMode OBJECT-TYPE
    SYNTAX      INTEGER {
                    sameQuad(1),
                    segregatedQuadUpto3km(2),
                    segregatedQuadAbove3km(3)
                }
    MAX-ACCESS  read-write
    STATUS      current
    DESCRIPTION
       "This object has been deprecated. The corresponding
        object in the new pdn_spectrumMgmt.mib should be used
	instead.

        This entry specifies the quad cable configuration &amp;
        length for the line. The configurable values are
        sameQuad(1), segregatedQuadUpto3km(2) and
        segregatedQuadAbove3km(3). The 'Quad Mode' feature can be
        used only if the 'reachDSLSpectrumMgmtSelection' object
        is Enabled and the 'LoopMeasurementMethod' is 'quadMode'.
        Changing this object may limit the maximum transmit power
        and the effective DSL speeds at which ports train up.

        Note: This object shares a mutual exclusion relationship 
              with the 'ConfEWL' &amp; 'ConfLoopLength' objects.
              i.e. only one of the three can be used for
              configuration at one time."

    ::= { reachDSLSpectrumMgmtConfEntry 5 }

reachDSLSpectrumMgmtLineInfoTable OBJECT-TYPE
    SYNTAX      SEQUENCE OF ReachDSLSpectrumMgmtLineInfoEntry
    MAX-ACCESS  not-accessible
    STATUS      current
    DESCRIPTION
       "This object has been deprecated. The corresponding
        object in the new pdn_spectrumMgmt.mib should be used
	instead.

        The ReachDSL Spectrum Management Line Info Table.
        This table gives information about the spectrum 
        management ranges that are applicable for each port,
        based on the spectral requirements for the device."

    ::= { pdnReachDSLObjects 4 }

reachDSLSpectrumMgmtLineInfoEntry OBJECT-TYPE
    SYNTAX      ReachDSLSpectrumMgmtLineInfoEntry
    MAX-ACCESS  not-accessible
    STATUS      current
    DESCRIPTION
       "This object has been deprecated. The corresponding
        object in the new pdn_spectrumMgmt.mib should be used
	instead.


        An entry in the reachDSLSpectrumMgmtLineInfoTable table.

        Note: This entry can be accessed only for ifIndex values
              that belong to a physical interface. 
              e.g. for ifType = 'adsl'."

    INDEX   { ifIndex }

    ::= { reachDSLSpectrumMgmtLineInfoTable 1 }

ReachDSLSpectrumMgmtLineInfoEntry ::= 
    SEQUENCE {
        reachDSLSpectrumMgmtAtucMaxTxRate  Unsigned32,
        reachDSLSpectrumMgmtAtucMinTxRate  Unsigned32,
        reachDSLSpectrumMgmtAtucMaxTxPower INTEGER, 
        reachDSLSpectrumMgmtAturMaxTxRate  Unsigned32,
        reachDSLSpectrumMgmtAturMinTxRate  Unsigned32,
        reachDSLSpectrumMgmtAturMaxTxPower INTEGER,
        reachDSLSpectrumMgmtMinEWL         Unsigned32,
        reachDSLSpectrumMgmtMaxEWL         Unsigned32
    }

reachDSLSpectrumMgmtAtucMaxTxRate OBJECT-TYPE
    SYNTAX      Unsigned32
    UNITS       "bps"
    MAX-ACCESS  read-only
    STATUS      current
    DESCRIPTION
       "This object has been deprecated. The corresponding
        object in the new pdn_spectrumMgmt.mib should be used
	instead.


        This rate will be the max allowed Tx Rate(in bps) for 
        the port based on the Spectrum Management requirements for
        ATUC in a particular spectral compliance configuration."
 
    ::= { reachDSLSpectrumMgmtLineInfoEntry 1 }

reachDSLSpectrumMgmtAtucMinTxRate OBJECT-TYPE
    SYNTAX      Unsigned32
    UNITS       "bps"
    MAX-ACCESS  read-only
    STATUS      current
    DESCRIPTION
       "This object has been deprecated. The corresponding
        object in the new pdn_spectrumMgmt.mib should be used
	instead.


        This rate will be the min allowed Tx Rate based on the
        spectrum management requirements for the ATUC. The
        MinTxRate will be upper bounded by
        'reachDSLSpectrumMgmtAtucMaxTxRate' object."

    ::= { reachDSLSpectrumMgmtLineInfoEntry 2 }

reachDSLSpectrumMgmtAtucMaxTxPower OBJECT-TYPE
    SYNTAX      INTEGER(-140..120)
    UNITS       "tenth dB"
    MAX-ACCESS  read-only
    STATUS      current
    DESCRIPTION
       "This object has been deprecated. The corresponding
        object in the new pdn_spectrumMgmt.mib should be used
	instead.


        The maximum transmit power at the ATUC (in tenth dB).  
        This value will be based on the spectrum management
        selection."

    ::= { reachDSLSpectrumMgmtLineInfoEntry 3 }

reachDSLSpectrumMgmtAturMaxTxRate OBJECT-TYPE
    SYNTAX      Unsigned32
    UNITS       "bps"
    MAX-ACCESS  read-only
    STATUS      current
    DESCRIPTION
       "This object has been deprecated. The corresponding
        object in the new pdn_spectrumMgmt.mib should be used
	instead.


        This rate will be the max allowed Tx Rate(in bps) for 
        the port based on the Spectrum Management requirements for
        ATUC in a particular spectral compliance configuration."

    ::= { reachDSLSpectrumMgmtLineInfoEntry 4 }

reachDSLSpectrumMgmtAturMinTxRate OBJECT-TYPE
    SYNTAX      Unsigned32
    UNITS       "bps"
    MAX-ACCESS  read-only
    STATUS      current
    DESCRIPTION
       "This object has been deprecated. The corresponding
        object in the new pdn_spectrumMgmt.mib should be used
	instead.


        This rate will be the min allowed Tx Rate based on the
        spectrum management requirements for the ATUR. The 
        MinTxRate will be upper bounded by
        'reachDSLSpectrumMgmtAturMaxTxRate' object."

    ::= { reachDSLSpectrumMgmtLineInfoEntry 5 }

reachDSLSpectrumMgmtAturMaxTxPower OBJECT-TYPE
    SYNTAX      INTEGER(-140..120)
    UNITS       "tenth dB"
    MAX-ACCESS  read-only
    STATUS      current
    DESCRIPTION
       "This object has been deprecated. The corresponding
        object in the new pdn_spectrumMgmt.mib should be used
	instead.


        The maximum transmit power at the ATUR (in tenth dB).  This
        value will be based on the spectrum management selection."

    ::= { reachDSLSpectrumMgmtLineInfoEntry 6 }

reachDSLSpectrumMgmtMinEWL OBJECT-TYPE
    SYNTAX      Unsigned32
    MAX-ACCESS  read-only
    STATUS      current
    DESCRIPTION
       "This object has been deprecated. The corresponding
        object in the new pdn_spectrumMgmt.mib should be used
	instead.

	
        The minimum value (in feet, if 'EWLUnits' is 'feet, or in
        meters, if 'EWLUnits' is 'meters') that the 'ConfEWL'
        object can accept. Together with the 'MaxEWL' object,
        this object indicates the range of EWL when 'EWLUnits' is
        either 'feet' or 'meters'.

        Note : This object is valid only if the
               'LoopMeasurementMethod' object is 'ewl'."

    ::= { reachDSLSpectrumMgmtLineInfoEntry 7 }

reachDSLSpectrumMgmtMaxEWL OBJECT-TYPE
    SYNTAX      Unsigned32
    MAX-ACCESS  read-only
    STATUS      current
    DESCRIPTION
       "This object has been deprecated. The corresponding
        object in the new pdn_spectrumMgmt.mib should be used
	instead.

	
        The maximum value (in feet, if 'EWLUnits' is 'feet, or in
        meters, if 'EWLUnits' is 'meters') that the 'ConfEWL'
        object can accept. Together with the 'MinEWL' object,
        this object indicates the range of EWL when 'EWLUnits' is
        either 'feet' or 'meters'.

        Note : This object is valid only if the
               'LoopMeasurementMethod' object is 'ewl'."

    ::= { reachDSLSpectrumMgmtLineInfoEntry 8 }

reachDSLLineTable OBJECT-TYPE
    SYNTAX      SEQUENCE OF ReachDSLLineEntry
    MAX-ACCESS  not-accessible
    STATUS      current
    DESCRIPTION
       "The ReachDSL Line Table."

    ::= { pdnReachDSLObjects 5 }

reachDSLLineEntry OBJECT-TYPE
    SYNTAX      ReachDSLLineEntry
    MAX-ACCESS  not-accessible
    STATUS      current
    DESCRIPTION
       "An entry in the reachDSLLineTable.

        Note: This entry can be accessed only for ifIndex values
              that belong to a physical interface. 
              e.g. for ifType = 'adsl'."

    INDEX   { ifIndex }

    ::= { reachDSLLineTable 1 }

ReachDSLLineEntry ::= 
    SEQUENCE {
        reachDSLPotsDetectionVoltage  INTEGER,
        reachDSLCircuitIdentifier     DisplayString
    }

reachDSLPotsDetectionVoltage OBJECT-TYPE
    SYNTAX      INTEGER (0..74)
    UNITS       "volts"
    MAX-ACCESS  read-write
    STATUS      current
    DESCRIPTION
        "This object defines the configurable voltage used to 
        detect the presence of POTS on the DSL line. The range
        is 0-74 volts. The default value is 3 volts.

        Note: This object can be accessed only for ifIndex  
              values that belong to a physical interface.
              i.e. ifType = adsl/reachDSL."

    DEFVAL { 3 }

    ::= { reachDSLLineEntry 1 }

reachDSLCircuitIdentifier OBJECT-TYPE
    SYNTAX      DisplayString (SIZE(1..32))
    MAX-ACCESS  read-write
    STATUS      deprecated
    DESCRIPTION
       "The value of this object reflects the transmission
        vendor's circuit identifier to facilitate troubleshooting.

        Note: This object can be accessed only for ifIndex  
              values that belong to a physical interface.
              e.g. for ifType = 'adsl'.

        This object is deprecated in favor of ifAlias. It is
        highly recommended that future implementations use
        ifAlias to store the Circuit Identifier associated with
        reach DSL interfaces." 

    ::= { reachDSLLineEntry 2 }

reachDSLSpectrumMgmtLoopMeasurementMethod OBJECT-TYPE
    SYNTAX      INTEGER {
                    none(1),
                    loopLength(2),
                    ewl(3),
                    quadMode(4)
                }
    MAX-ACCESS  read-only
    STATUS      current
    DESCRIPTION
       "This object has been deprecated. The corresponding
        object in the new pdn_spectrumMgmt.mib should be used
	instead.


        This object indicates the measurement method used in
        describing the Loop Length of a circuit. Following are the
        details of each of the options:

            none(1)       - Indicates that the Spectral Compliance
                            is NOT dependant on any Loop Length
                            measurements or configurations.
            loopLength(2) - The 'ConfLoopLength' object is used to
                            determine spectral compliance. The
                            'ConfEWL' &amp; 'ConfQuadMode' objects are
                            not used in this mode.
            ewl(3)        - The 'ConfEWL' object is used to
                            configure the estimated loop length,
                            which is used to determine spectral
                            compliance. In this mode the
                            'ConfLoopLength' &amp; 'ConfQuadMode'
                            objects are not used. 
            quadMode(4)   - The 'ConfQuadMode' object is used to
                            determine spectral compliance. The
                            'ConfEWL' &amp; 'ConfLoopLength' objects
                            are not used in this mode.

        This object determines which of the three objects :
        'ConfEWL', 'ConfLoopLength' or 'ConfQuadMode' is used
        (if any) to enforce spectrally compliant maximum
        'Tx Rates' and the maximum allowed 'Tx Power' on a given
        circuit."

    ::= { pdnReachDSLObjects 6 }

reachDSLSpectrumMgmtEWLUnits OBJECT-TYPE
    SYNTAX      INTEGER {
                    none(1),
                    feet(2),
                    meters(3)
                }
    MAX-ACCESS  read-only
    STATUS      current
    DESCRIPTION
       "This object has been deprecated. The corresponding
        object in the new pdn_spectrumMgmt.mib should be used
	instead.


        This object indicates the units of measurement used in
        describing the Estimated Working Length of a circuit.
        Following are the details of each of the units:

            none(1)     - Indicates that the Spectral Compliance is
                          NOT dependant on the 'ConfEWL' object.
            feet(2)     - The 'ConfEWL' is measured and configured
                          in feet.
            meters(3)   - The 'ConfEWL' is measured and configured
                          in meters."

    ::= { pdnReachDSLObjects 7 }

reachDSLSpectrumMgmtMode OBJECT-TYPE
    SYNTAX      INTEGER {
                    enableOnly(1),
                    disableOnly(2),
                    both(3)
                }
    MAX-ACCESS  read-only
    STATUS      current
    DESCRIPTION
       "This object has been deprecated. The corresponding
        object in the new pdn_spectrumMgmt.mib should be used
	instead.


        This object restricts the MAX-ACCESS of the 'Selection'
        object.
        Following are the details of each of the values:

            enableOnly(1)  - Indicates that the 'Selection' object
                             IS always 'enabled' and cannot be set
                             to 'disabled'.
            disableOnly(2) - Indicates that the 'Selection' object
                             IS always 'disabled' and cannot be set
                             to 'enabled'.
            both(3)        - Indicates that the 'Selection' object
                             will accept both the 'enabled' and
                             'disabled' values."

    ::= { pdnReachDSLObjects 8 }

--
-- Conformance information
--

pdnReachDSLConformance  OBJECT IDENTIFIER
    ::= { pdnReachDSL 2 }

pdnReachDSLGroups       OBJECT IDENTIFIER
    ::= { pdnReachDSLConformance 1 }

pdnReachDSLCompliances  OBJECT IDENTIFIER
    ::= { pdnReachDSLConformance 2 }

-- Compliance statements

pdnReachDSLCompliance1 MODULE-COMPLIANCE 
    STATUS      current
    DESCRIPTION
       "The compliance statement for SNMP entities which manage
        ReachDSL interfaces."

    MODULE   -- this module
        MANDATORY-GROUPS { 
            pdnReachDSLGeneralConfigGroup,
            pdnReachDSLGeneralInformationGroup
        }

-- The groups :
--      pdnReachDSLEWLModeGroup
--      pdnReachDSLLoopLengthModeGroup
--      pdnReachDSLQuadModeGroup
-- are mutually exclusive; at most one of these groups is
-- implemented for a particular reachDSL interface. If the
-- Loop Measurement Method is 'none', then none of these
-- groups should be implemented.

    GROUP   pdnReachDSLEWLModeGroup
    DESCRIPTION
       "This group is mandatory for reachDSL interfaces whose
        loop/line length measurement method is EWL.
        i.e.the reachDSLSpectrumMgmtLoopMeasurementMethod object
        is 'ewl'."

    GROUP   pdnReachDSLLoopLengthModeGroup
    DESCRIPTION
       "This group is mandatory for reachDSL interfaces whose
        loop/line length measurement method is LoopLength (short
        /medium/long).
        i.e.the reachDSLSpectrumMgmtLoopMeasurementMethod object
        is 'loopLength'."

    GROUP   pdnReachDSLQuadModeGroup
    DESCRIPTION
       "This group is mandatory for reachDSL interfaces whose
        loop/line length measurement method is based on Quads.
        i.e.the reachDSLSpectrumMgmtLoopMeasurementMethod object
        is 'quadMode'."

    OBJECT      reachDSLSpectrumMgmtSelection
    MIN-ACCESS  read-only
    DESCRIPTION 
       "Write access is not required."

    OBJECT      reachDSLSpectrumMgmtConfAtucMaxTxPower
    MIN-ACCESS  read-only
    DESCRIPTION 
       "Write access is not required."

    OBJECT      reachDSLSpectrumMgmtConfAturMaxTxPower
    MIN-ACCESS  read-only
    DESCRIPTION 
       "Write access is not required."

    OBJECT      reachDSLPotsDetectionVoltage
    MIN-ACCESS  read-only
    DESCRIPTION 
       "Write access is not required."

    ::= { pdnReachDSLCompliances 2 }

-- Units of conformance

pdnReachDSLGeneralConfigGroup OBJECT-GROUP
    OBJECTS {
        reachDSLSpectrumMgmtSelection,
        reachDSLSpectrumMgmtConfAtucMaxTxPower,
        reachDSLSpectrumMgmtConfAturMaxTxPower,
        reachDSLPotsDetectionVoltage
    }
    STATUS      current
    DESCRIPTION 
       "A collection of configuration objects required for
        providing access to configure all reachDSL interfaces."

    ::= { pdnReachDSLGroups 4 }

pdnReachDSLGeneralInformationGroup OBJECT-GROUP
    OBJECTS {
        reachDSLSpectrumMgmtAtucMaxTxRate,
        reachDSLSpectrumMgmtAtucMinTxRate,
        reachDSLSpectrumMgmtAtucMaxTxPower,
        reachDSLSpectrumMgmtAturMaxTxRate,
        reachDSLSpectrumMgmtAturMinTxRate,
        reachDSLSpectrumMgmtAturMaxTxPower,
        reachDSLSpectrumMgmtLoopMeasurementMethod,
        reachDSLSpectrumMgmtEWLUnits,
        reachDSLSpectrumMgmtMode
    }
    STATUS      current
    DESCRIPTION 
       "A collection of objects providing information applicable
        to all reachDSL interfaces."

    ::= { pdnReachDSLGroups 5 }

-- The following three groups are mutually exclusive; at most one
-- of these groups is implemented for any interface

pdnReachDSLEWLModeGroup OBJECT-GROUP
    OBJECTS {
        reachDSLSpectrumMgmtConfEWL,
        reachDSLSpectrumMgmtMinEWL,
        reachDSLSpectrumMgmtMaxEWL
    }
    STATUS      current
    DESCRIPTION 
       "A collection of objects providing configuration
        access and information specific to reachDSL interfaces
        whose loop/line length measurement method is EWL.
        i.e.the reachDSLSpectrumMgmtLoopMeasurementMethod object
        is 'ewl'."

    ::= { pdnReachDSLGroups 6 }

pdnReachDSLLoopLengthModeGroup OBJECT-GROUP
    OBJECTS {
        reachDSLSpectrumMgmtConfLoopLength
    }
    STATUS      current
    DESCRIPTION 
       "A collection of object(s) providing configuration
        access and information specific to reachDSL interfaces
        whose loop/line length measurement method is Loop Length
        (short/medium/long).
        i.e.the reachDSLSpectrumMgmtLoopMeasurementMethod object
        is 'loopLength'."

    ::= { pdnReachDSLGroups 7 }

pdnReachDSLQuadModeGroup OBJECT-GROUP
    OBJECTS {
        reachDSLSpectrumMgmtConfQuadMode
    }
    STATUS      current
    DESCRIPTION 
       "A collection of object(s) providing configuration
        access and information specific to reachDSL interfaces
        whose loop/line length measurement method is based on the
        Quad configuration.
        i.e.the reachDSLSpectrumMgmtLoopMeasurementMethod object
        is 'quadMode'."

    ::= { pdnReachDSLGroups 8 }

--
-- Deprecated definitions - Compliance
--

pdnReachDSLCompliance MODULE-COMPLIANCE 
    STATUS      deprecated
    DESCRIPTION
       "The compliance statement for SNMP entities which manage
        ReachDSL interfaces."

MODULE   -- this module
    MANDATORY-GROUPS { 
       pdnReachDSLConfigurationGroup, pdnReachDSLInformationGroup
    }
 
    OBJECT      reachDSLSpectrumMgmtSelection
    MIN-ACCESS  read-only
    DESCRIPTION 
       "Write access is not required."

    OBJECT      reachDSLSpectrumMgmtConfEWL
    MIN-ACCESS  read-only
    DESCRIPTION 
       "Write access is not required."

    OBJECT      reachDSLSpectrumMgmtConfLoopLength
    MIN-ACCESS  read-only
    DESCRIPTION 
       "Write access is not required."

    OBJECT      reachDSLSpectrumMgmtConfAtucMaxTxPower
    MIN-ACCESS  read-only
    DESCRIPTION 
       "Write access is not required."

    OBJECT      reachDSLSpectrumMgmtConfAturMaxTxPower
    MIN-ACCESS  read-only
    DESCRIPTION 
       "Write access is not required."

    OBJECT      reachDSLPotsDetectionVoltage
    MIN-ACCESS  read-only
    DESCRIPTION 
       "Write access is not required."

    OBJECT      reachDSLCircuitIdentifier
    MIN-ACCESS  read-only
    DESCRIPTION 
       "Write access is not required."

    ::= { pdnReachDSLCompliances 1 }

--
-- Deprecated definitions - Groups
--

pdnReachDSLConfigurationGroup OBJECT-GROUP
    OBJECTS {
        reachDSLSpectrumMgmtSelection,
        reachDSLSpectrumMgmtConfEWL,
        reachDSLSpectrumMgmtConfLoopLength,
        reachDSLSpectrumMgmtConfAtucMaxTxPower,
        reachDSLSpectrumMgmtConfAturMaxTxPower,
        reachDSLPotsDetectionVoltage,
        reachDSLCircuitIdentifier
    }
    STATUS      deprecated -- Set as required for the group
    DESCRIPTION 
       "A collection of configuration objects required 
        for providing access to configuration as well 
        as status information for reachDSL products."

    ::= { pdnReachDSLGroups 1 }

pdnReachDSLInformationGroup OBJECT-GROUP
    OBJECTS {
        reachDSLSpectrumMgmtAtucMaxTxRate,
        reachDSLSpectrumMgmtAtucMinTxRate,
        reachDSLSpectrumMgmtAtucMaxTxPower,
        reachDSLSpectrumMgmtAturMaxTxRate,
        reachDSLSpectrumMgmtAturMinTxRate,
        reachDSLSpectrumMgmtAturMaxTxPower,
        reachDSLSpectrumMgmtMinEWL,
        reachDSLSpectrumMgmtMaxEWL,
        reachDSLSpectrumMgmtLoopMeasurementMethod,
        reachDSLSpectrumMgmtEWLUnits,
        reachDSLSpectrumMgmtMode
    }
    STATUS      deprecated -- Set as required for the group
    DESCRIPTION 
        "A collection of objects providing access meant
         specifically for accessing information for 
         for reachDSL products."

    ::= { pdnReachDSLGroups 2 }

pdnReachDSLDeprecatedGroup OBJECT-GROUP
    OBJECTS {
        reachDSLSpectrumMgmtZone,
        reachDSLCircuitIdentifier
    }
    STATUS      deprecated -- Set as required for the group
    DESCRIPTION 
        "A collection of objects that have been deprecated."

    ::= { pdnReachDSLGroups 3 }

END

PDN-SPECTRUMMGMT-MIB DEFINITIONS ::= BEGIN
----------------------------------------------------------------
-- Copyright (C) 2003, Paradyne. All rights reserved.
----------------------------------------------------------------
IMPORTS
	Integer32, Unsigned32,
	OBJECT-TYPE, MODULE-IDENTITY 
	    FROM SNMPv2-SMI
	MODULE-COMPLIANCE, OBJECT-GROUP
            FROM SNMPv2-CONF
	entPhysicalIndex
            FROM ENTITY-MIB
	ifIndex, ifType
	    FROM IF-MIB
	pdn-interfaces
	    FROM PDN-HEADER-MIB;
	
pdnSpectrumMgmt	MODULE-IDENTITY
	    LAST-UPDATED "200212091500Z"
	    ORGANIZATION "Paradyne Corp MIB Working Group"
	    CONTACT-INFO "Paradyne Networks, Inc.
			  8545 126th Ave North
			  Largo, FL 33733
			  www.paradyne.com

			  General Comments to:
			    mibwg_team@eng.paradyne.com

			  Editors: R.A.Bowhall,
				   Jesus Pinto"

	    DESCRIPTION "R.A.Bowhall
	    	The Paradyne enterprise SPECTRUM MIB.
	    	This MIB is written to facilitate spectrum
		management of any xDSL interfaces. This mib
	 	replaces older versions of the spectrum 
		management including the reachDSL.mib."

	    REVISION "200301151300Z"
	    DESCRIPTION "Jesus Pinto
		1. Changed indexes on GeneralConfigTable.
		2. Removed DSL Line Table.
		3. Renamed newSpectrumMgmtAturMaxTxRate
		4. Renamed newSpectrumMgmtAturMinTxRate
		5. Renamed newSpectrumMgmtAturTxPower
		6. Renamed newSpectrumMgmtAtucMinTxRate
		7. Renamed newSpectrumMgmtAtucMaxTxRate
		8. Renamed newSpectrumMgmtAtucTxPower
		9. Added   newSpectrumMgmtXturMax2TxRate
		10.Added   newSpectrumMgmtXturMin2TxRate
		11.Added   newSpectrumMgmtXtucMax2TxRate
		12.Added   newSpectrumMgmtXtucMax2TxRate"

	    REVISION "200301091500Z"
	    DESCRIPTION "Jesus Pinto
		1. Deprecated spectrumMgmtTable and all its objects.
		2. Added newSpectrumMgmtTable.
		3. Added newSpectrumMgmtMode.
		4. Added newSpectrumMgmtEWLUnits.
		5. Added newSpectrumMgmtLoopMeasurementMethod.
		6. Added newSpectrumMgmtLineInfoTable.
		7. Added newSpectrumMgmtGeneralConfigTable."

	    REVISION "0105161530Z"
	    DESCRIPTION "R.A.Bowhall
	    	Added DEFVAL caluse,  Added the pdnSpecMgmtTraps,
	    	and pdnSpecMgmtMIBConformance info.
		Added an Informational Note at the Beginning of
		this MIB."

	    REVISION "0105080550Z"
	    DESCRIPTION "R.A.Bowhall
	    	Added the EWL Deployment Guidelines Table
	    	and Changed spectrumMgmtAllowedSpeeds to
		spectrumMgmtAllowedSpeedsMin1, spectrumMgmtAllowedSpeedsMax1,
		spectrumMgmtAllowedSpeedsMin2, spectrumMgmtAllowedSpeedsMax2"

	    ::= { pdn-interfaces 19 }

pdnSpecMgmtObjects		OBJECT IDENTIFIER ::= { pdnSpectrumMgmt 1 }
pdnNewSpecMgmtObjects		OBJECT IDENTIFIER ::= { pdnSpectrumMgmt 2 }

--
-- START OF Spectrum Management definitions
--

--
-- General options for spectrum management
--
newSpectrumMgmtGeneralConfigTable OBJECT-TYPE
     SYNTAX  SEQUENCE OF NewSpectrumMgmtGeneralConfigEntry
     MAX-ACCESS  not-accessible
     STATUS  current
     DESCRIPTION
	"General Configuration of the spectrum management.
	This table contains an entry for each technology
	managed by this device."
     ::= { pdnNewSpecMgmtObjects 1 }

newSpectrumMgmtGeneralConfigEntry OBJECT-TYPE
     SYNTAX  NewSpectrumMgmtGeneralConfigEntry
     MAX-ACCESS  not-accessible
     STATUS  current
     DESCRIPTION
	"An entry with the general spectrum mgmt configuration
	 parameters for a specific DSL technology."
    INDEX   { entPhysicalIndex, ifType }
    ::= { newSpectrumMgmtGeneralConfigTable 1 }

NewSpectrumMgmtGeneralConfigEntry ::= SEQUENCE {
     newSpectrumMgmtSelection		  INTEGER,
     newSpectrumMgmtMode		  INTEGER,
     newSpectrumMgmtLoopMeasurementMethod INTEGER,
     newSpectrumMgmtEWLUnits		  INTEGER
}

newSpectrumMgmtSelection OBJECT-TYPE
     SYNTAX  INTEGER {
		enabled(1),
		disabled(2)
	 }
     MAX-ACCESS read-write
     STATUS  	current
     DESCRIPTION
	"This object is used to Enable or Disable 
	 Spectrum Management on DSL interfaces 
	 managed by this device. Enabling this object
	 limits the DSL speeds on each port based on
	 line length in order to meet ANSI T1.417
	 Spectrum Management requirements or BT Access
	 Network Spectrum requirements.

	The values that this object can accept are
        controlled by the -Mode- object."

     ::= { newSpectrumMgmtGeneralConfigEntry 1 }

newSpectrumMgmtMode OBJECT-TYPE
    SYNTAX      INTEGER {
                    enableOnly(1),
                    disableOnly(2),
                    both(3)
                }
    MAX-ACCESS  read-only
    STATUS      current
    DESCRIPTION
       "This object restricts the MAX-ACCESS of the 'Selection'
        object.
        Following are the details of each of the values:

            enableOnly(1)  - Indicates that the 'Selection' object
                             IS always 'enabled' and cannot be set
                             to 'disabled'.
            disableOnly(2) - Indicates that the 'Selection' object
                             IS always 'disabled' and cannot be set
                             to 'enabled'.
            both(3)        - Indicates that the 'Selection' object
                             will accept both the 'enabled' and
                             'disabled' values."

    ::= { newSpectrumMgmtGeneralConfigEntry 2 }

newSpectrumMgmtLoopMeasurementMethod OBJECT-TYPE
    SYNTAX      INTEGER {
                    none(1),
                    loopLength(2),
                    ewl(3),
                    quadMode(4)
                }
    MAX-ACCESS  read-only
    STATUS      current
    DESCRIPTION
       "This object indicates the measurement method used in
        describing the Loop Length of a circuit. Following are the
        details of each of the options:

            none(1)       - Indicates that the Spectral Compliance
                            is NOT dependant on any Loop Length
                            measurements or configurations.
            loopLength(2) - The 'ConfLoopLength' object is used to
                            determine spectral compliance. The
                            'ConfEWL' &amp; 'ConfQuadMode' objects are
                            not used in this mode.
            ewl(3)        - The 'ConfEWL' object is used to
                            configure the estimated loop length,
                            which is used to determine spectral
                            compliance. In this mode the
                            'ConfLoopLength' &amp; 'ConfQuadMode'
                            objects are not used.
            quadMode(4)   - The 'ConfQuadMode' object is used to
                            determine spectral compliance. The
                            'ConfEWL' &amp; 'ConfLoopLength' objects
                            are not used in this mode.

        This object determines which of the three objects :
        'ConfEWL', 'ConfLoopLength' or 'ConfQuadMode' is used
        (if any) to enforce spectrally compliant maximum
        'Tx Rates' and the maximum allowed 'Tx Power' on a given
        circuit."

    ::= { newSpectrumMgmtGeneralConfigEntry 3 }

newSpectrumMgmtEWLUnits OBJECT-TYPE
    SYNTAX      INTEGER {
                    none(1),
                    feet(2),
                    meters(3)
                }
    MAX-ACCESS  read-only
    STATUS      current
    DESCRIPTION
       "This object indicates the units of measurement used in
        describing the Estimated Working Length of a circuit.
        Following are the details of each of the units:

            none(1)     - Indicates that the Spectral Compliance is
                          NOT dependant on the 'ConfEWL' object.
            feet(2)     - The 'ConfEWL' is measured and configured
                          in feet.
            meters(3)   - The 'ConfEWL' is measured and configured
                          in meters."

    ::= { newSpectrumMgmtGeneralConfigEntry 4 }

--
-- Spectrum Mgmt Configuration Table
--
newSpectrumMgmtConfTable OBJECT-TYPE
    SYNTAX      SEQUENCE OF NewSpectrumMgmtConfEntry
    MAX-ACCESS  not-accessible
    STATUS      current
    DESCRIPTION
       "The new Spectrum Management Configuration Table
        This table is used for configuring spectrum management
        objects on any DSL interface." 

    ::= { pdnNewSpecMgmtObjects 2 }

newSpectrumMgmtConfEntry OBJECT-TYPE
    SYNTAX      NewSpectrumMgmtConfEntry
    MAX-ACCESS  not-accessible
    STATUS      current
    DESCRIPTION
       "An entry in the xDSL Spectrum Management 
        Configuration table.

        Note: This entry can be accessed only for ifIndex 
              values that belong to a physical interface. 
              e.g. for ifType = 'shdsl' (IANAifType=169)."

    INDEX   { ifIndex }

    ::= { newSpectrumMgmtConfTable 1 }

NewSpectrumMgmtConfEntry ::= 
    SEQUENCE {
        newSpectrumMgmtConfEWL            	Unsigned32,
        newSpectrumMgmtConfLoopLength     	INTEGER,
        newSpectrumMgmtConfQuadMode       	INTEGER
    }

newSpectrumMgmtConfEWL OBJECT-TYPE
    SYNTAX      Unsigned32
    MAX-ACCESS  read-write
    STATUS      current
    DESCRIPTION
       "The Equivalent Working Length (EWL).  The value selected
        corresponds to the estimated length of the line in

            feet   - if 'EWLUnits' object is 'feet'.
            meters - if 'EWLUnits' object is 'meters'. 

        This value is usually specified by the carrier and MUST
        be in integral multiples of 

            500 feet, if 'EWLUnits' is 'feet'.
            200 meters, if 'EWLUnits' is 'meters'.

        The range of values that this object can take is determined
        by the 'MinEWL' and 'MaxEWL' objects.
        Changing this object may limit the maximum transmit power
        and the effective DSL speeds at which the ports train up.

        Note: This object will be used only if Spectrum Management
              is enabled and 'LoopMeasurementMethod' is 'ewl'.
              This object shares a mutual exclusion relationship
              with the 'ConfLoopLength' &amp; 'ConfQuadMode' objects, 
	      as only one of the two will be used for configuration
	      at any time."

    ::= { newSpectrumMgmtConfEntry 1 }

newSpectrumMgmtConfLoopLength OBJECT-TYPE
    SYNTAX      INTEGER {
                    short(1),
                    medium(2),
                    long(3)
                }
    MAX-ACCESS  read-write
    STATUS      current
    DESCRIPTION
       "This entry specifies the loop length for the line. The
        configurable values are short(1), medium(2) and long(3).
        The 'Loop Length' feature can be used only if the 
        'shdslSpectrumMgmtSelection' object is Enabled and
        the 'LoopMeasurementMethod' is 'loopLength'. Changing this
        object may limit the maximum transmit power and the
        effective DSL speeds at which ports train up.

        Note: This object shares a mutual exclusion relationship 
              with the 'ConfEWL'  objects. i.e. only one of the
	      three can be used for configuration at one time."

    ::= { newSpectrumMgmtConfEntry 2 }

newSpectrumMgmtConfQuadMode OBJECT-TYPE
    SYNTAX      INTEGER {
                    sameQuad(1),
                    segregatedQuadUpto3km(2),
                    segregatedQuadAbove3km(3)
                }
    MAX-ACCESS  read-write
    STATUS      current
    DESCRIPTION
       "This entry specifies the quad cable configuration &amp;
        length for the line. The configurable values are
        sameQuad(1), segregatedQuadUpto3km(2) and
        segregatedQuadAbove3km(3). The 'Quad Mode' feature can be
        used only if the 'reachDSLSpectrumMgmtSelection' object
        is Enabled and the 'LoopMeasurementMethod' is 'quadMode'.
        Changing this object may limit the maximum transmit power
        and the effective DSL speeds at which ports train up.

        Note: This object shares a mutual exclusion relationship 
              with the 'ConfEWL' &amp; 'ConfLoopLength' objects.
              i.e. only one of the three can be used for
              configuration at one time."

    ::= { newSpectrumMgmtConfEntry 3 }

--
-- Spectrum Management Line Info Table
--
newSpectrumMgmtLineInfoTable OBJECT-TYPE
    SYNTAX      SEQUENCE OF NewSpectrumMgmtLineInfoEntry
    MAX-ACCESS  not-accessible
    STATUS      current
    DESCRIPTION
       "The Spectrum Management Line Info Table.
        This table gives information about the spectrum 
        management ranges that are applicable for each port,
        based on the spectral requirements for the device."

    ::= { pdnNewSpecMgmtObjects 3 }

newSpectrumMgmtLineInfoEntry OBJECT-TYPE
    SYNTAX      NewSpectrumMgmtLineInfoEntry
    MAX-ACCESS  not-accessible
    STATUS      current
    DESCRIPTION
       "An entry in the newSpectrumMgmtLineInfoTable table.

        Note: This entry can be accessed only for ifIndex values
              that belong to a physical interface. 
              e.g. for ifType = 'adsl'."

    INDEX   { ifIndex }

    ::= { newSpectrumMgmtLineInfoTable 1 }

NewSpectrumMgmtLineInfoEntry ::= 
    SEQUENCE {
        newSpectrumMgmtXtucMax1TxRate  Unsigned32,
        newSpectrumMgmtXtucMin1TxRate  Unsigned32,
        newSpectrumMgmtXtucMax2TxRate  Unsigned32,
        newSpectrumMgmtXtucMin2TxRate  Unsigned32,
        newSpectrumMgmtXtucMaxTxPower  INTEGER,
        newSpectrumMgmtXturMax1TxRate  Unsigned32,
        newSpectrumMgmtXturMin1TxRate  Unsigned32,
        newSpectrumMgmtXturMax2TxRate  Unsigned32,
        newSpectrumMgmtXturMin2TxRate  Unsigned32,
        newSpectrumMgmtXturMaxTxPower  INTEGER,
        newSpectrumMgmtMinEWL          Unsigned32,
        newSpectrumMgmtMaxEWL          Unsigned32
    }

newSpectrumMgmtXtucMax1TxRate OBJECT-TYPE
    SYNTAX      Unsigned32
    UNITS       "bps"
    MAX-ACCESS  read-only
    STATUS      current
    DESCRIPTION
       "This rate will be the max allowed Tx Rate(in bps) for 
        the port based on the Spectrum Management requirements for
        XTUC in a particular spectral compliance configuration.
	
	Some measurement methods may have more than one range for
	the TxRate. Min1TxRate and Max1TxRate will always have
	the first range of values and the Min2TxRate and Max2TxRate
	will have the second range if the method demands it."
 
    ::= { newSpectrumMgmtLineInfoEntry 1 }

newSpectrumMgmtXtucMin1TxRate OBJECT-TYPE
    SYNTAX      Unsigned32
    UNITS       "bps"
    MAX-ACCESS  read-only
    STATUS      current
    DESCRIPTION
       "This rate will be the min allowed Tx Rate based on the
        spectrum management requirements for the XTUC. The
        MinTxRate will be upper bounded by 
	'newSpectrumMgmtXtucMax1TxRate' object.

	Some measurement methods may have more than one range for
	the TxRate. Min1TxRate and Max1TxRate will always have
	the first range of values and the Min2TxRate and Max2TxRate
	will have the second range if the method demands it."

    ::= { newSpectrumMgmtLineInfoEntry 2 }


newSpectrumMgmtXtucMax2TxRate OBJECT-TYPE
    SYNTAX      Unsigned32
    UNITS       "bps"
    MAX-ACCESS  read-only
    STATUS      current
    DESCRIPTION
       "This rate will be the max allowed Tx Rate(in bps) for 
        the port based on the Spectrum Management requirements for
        XTUC in a particular spectral compliance configuration.
	This object is the 
	
	Some measurement methods may have more than one range for
	the TxRate. Min1TxRate and Max1TxRate will always have
	the first range of values and the Min2TxRate and Max2TxRate
	will have the second range if the method demands it."
 
    ::= { newSpectrumMgmtLineInfoEntry 3 }

newSpectrumMgmtXtucMin2TxRate OBJECT-TYPE
    SYNTAX      Unsigned32
    UNITS       "bps"
    MAX-ACCESS  read-only
    STATUS      current
    DESCRIPTION
       "This rate will be the min allowed Tx Rate based on the
        spectrum management requirements for the XTUC. The
        MinTxRate will be upper bounded by 
	'newSpectrumMgmtXtucMax1TxRate' object.

	Some measurement methods may have more than one range for
	the TxRate. Min1TxRate and Max1TxRate will always have
	the first range of values and the Min2TxRate and Max2TxRate
	will have the second range if the method demands it."

    ::= { newSpectrumMgmtLineInfoEntry 4 }


newSpectrumMgmtXtucMaxTxPower OBJECT-TYPE
    SYNTAX      INTEGER(-140..120)
    UNITS       "tenth dB"
    MAX-ACCESS  read-only
    STATUS      current
    DESCRIPTION
       "The maximum transmit power at the ATUC (in tenth dB).  
        This value will be based on the spectrum management
        selection."

    ::= { newSpectrumMgmtLineInfoEntry 5 }


newSpectrumMgmtXturMax1TxRate OBJECT-TYPE
    SYNTAX      Unsigned32
    UNITS       "bps"
    MAX-ACCESS  read-only
    STATUS      current
    DESCRIPTION
       "This rate will be the max allowed Tx Rate(in bps) for 
        the port based on the Spectrum Management requirements for
        XTUR in a particular spectral compliance configuration.
	This object is the 
	
	Some measurement methods may have more than one range for
	the TxRate. Min1TxRate and Max1TxRate will always have
	the first range of values and the Min2TxRate and Max2TxRate
	will have the second range if the method demands it."
 
    ::= { newSpectrumMgmtLineInfoEntry 6 }

newSpectrumMgmtXturMin1TxRate OBJECT-TYPE
    SYNTAX      Unsigned32
    UNITS       "bps"
    MAX-ACCESS  read-only
    STATUS      current
    DESCRIPTION
       "This rate will be the min allowed Tx Rate based on the
        spectrum management requirements for the XTUR. The
        MinTxRate will be upper bounded by 
	'newSpectrumMgmtXturMax1TxRate' object.

	Some measurement methods may have more than one range for
	the TxRate. Min1TxRate and Max1TxRate will always have
	the first range of values and the Min2TxRate and Max2TxRate
	will have the second range if the method demands it."

    ::= { newSpectrumMgmtLineInfoEntry 7 }


newSpectrumMgmtXturMax2TxRate OBJECT-TYPE
    SYNTAX      Unsigned32
    UNITS       "bps"
    MAX-ACCESS  read-only
    STATUS      current
    DESCRIPTION
       "This rate will be the max allowed Tx Rate(in bps) for 
        the port based on the Spectrum Management requirements for
        XTUR in a particular spectral compliance configuration.
	
	Some measurement methods may have more than one range for
	the TxRate. Min1TxRate and Max1TxRate will always have
	the first range of values and the Min2TxRate and Max2TxRate
	will have the second range if the method demands it."
 
    ::= { newSpectrumMgmtLineInfoEntry 8 }

newSpectrumMgmtXturMin2TxRate OBJECT-TYPE
    SYNTAX      Unsigned32
    UNITS       "bps"
    MAX-ACCESS  read-only
    STATUS      current
    DESCRIPTION
       "This rate will be the min allowed Tx Rate based on the
        spectrum management requirements for the XTUR. The
        MinTxRate will be upper bounded by 
	'newSpectrumMgmtXtucMax1TxRate' object.

	Some measurement methods may have more than one range for
	the TxRate. Min1TxRate and Max1TxRate will always have
	the first range of values and the Min2TxRate and Max2TxRate
	will have the second range if the method demands it."

    ::= { newSpectrumMgmtLineInfoEntry 9 }

newSpectrumMgmtXturMaxTxPower OBJECT-TYPE
    SYNTAX      INTEGER(-140..120)
    UNITS       "tenth dB"
    MAX-ACCESS  read-only
    STATUS      current
    DESCRIPTION
       "The maximum transmit power at the ATUR (in tenth dB).  This
        value will be based on the spectrum management selection."

    ::= { newSpectrumMgmtLineInfoEntry 10 }

newSpectrumMgmtMinEWL OBJECT-TYPE
    SYNTAX      Unsigned32
    MAX-ACCESS  read-only
    STATUS      current
    DESCRIPTION
       "The minimum value (in feet, if 'EWLUnits' is 'feet, or in
        meters, if 'EWLUnits' is 'meters') that the 'ConfEWL'
        object can accept. Together with the 'MaxEWL' object,
        this object indicates the range of EWL when 'EWLUnits' is
        either 'feet' or 'meters'.

        Note : This object is valid only if the
               'LoopMeasurementMethod' object is 'ewl'."

    ::= { newSpectrumMgmtLineInfoEntry 11 }

newSpectrumMgmtMaxEWL OBJECT-TYPE
    SYNTAX      Unsigned32
    MAX-ACCESS  read-only
    STATUS      current
    DESCRIPTION
       "The maximum value (in feet, if 'EWLUnits' is 'feet, or in
        meters, if 'EWLUnits' is 'meters') that the 'ConfEWL'
        object can accept. Together with the 'MinEWL' object,
        this object indicates the range of EWL when 'EWLUnits' is
        either 'feet' or 'meters'.

        Note : This object is valid only if the
               'LoopMeasurementMethod' object is 'ewl'."

    ::= { newSpectrumMgmtLineInfoEntry 12 }

-- 
--		D E P R E C A T E D
--  
-- The following objects are supported for the first version
-- of the shdsl cards. They are now deprecated and should not
-- be used for future products.
--
spectrumMgmtCountryCode OBJECT-TYPE
     SYNTAX  INTEGER {
		usa(1),
		uk(2)
	 }
     MAX-ACCESS  read-write
     STATUS  deprecated
     DESCRIPTION
	"This object selects which Spectrum Management 
	 standard will be used on this device to calculate the 
	 'allowed speeds' to comply with Spectrum Management.

	 Note:Spectrum Management must be Enabled for 'Country
	 Code' to take effect. 

	 'USA' is the only valid selection for Region Setting
	 'Annex A', 'UK' will not be selectable.

	 'UK' for is the only valid selecton for Region Setting
	 'Annex B', 'USA' will not be selectable."

       DEFVAL { usa }
     ::= { pdnSpecMgmtObjects 2 }


spectrumMgmtTable OBJECT-TYPE
     SYNTAX  SEQUENCE OF SpectrumMgmtEntry
     MAX-ACCESS  not-accessible
     STATUS  deprecated
     DESCRIPTION
	"The Spectrum Management Table."
	::= { pdnSpecMgmtObjects 3 }

spectrumMgmtEntry OBJECT-TYPE
     SYNTAX  SpectrumMgmtEntry
     MAX-ACCESS  not-accessible
     STATUS  deprecated
     DESCRIPTION
	"An entry in the Spectrum Management table."
    INDEX   { ifIndex }
    ::= { spectrumMgmtTable 1 }

SpectrumMgmtEntry ::= SEQUENCE {
     spectrumMgmtEWL			Integer32,
     spectrumMgmtLineLength		INTEGER,
     spectrumMgmtAllowedSpeedsMin1	Integer32,
     spectrumMgmtAllowedSpeedsMax1	Integer32,
     spectrumMgmtAllowedSpeedsMin2	Integer32,
     spectrumMgmtAllowedSpeedsMax2	Integer32
 }

spectrumMgmtEWL OBJECT-TYPE
     SYNTAX Integer32
     MAX-ACCESS read-write
     STATUS deprecated
     DESCRIPTION
	"The Estimated Working Length [EWL(ft)].  The value
	selected is the estimated length of the line in ft.
	See the Deployment guideline Table below.
	This value is usually specified by the carrier.  This 
	value is only required if spectrumMgmt is Enabled and
	the spectrumMgmtCountryCode selected is 'USA'."
     ::= { spectrumMgmtEntry 1 }

--  Estimated Working Length Deployment guidelines for G.shdsl
--  --------------------------------------------------------- 
-- | Line Bit Rate(kbps)  | Deployment guideline,EWL (ft)    |
--  --------------------------------------------------------- 
-- |     LBR &lt;= 592       |          15500                   |
--  --------------------------------------------------------- 
-- |  600 &lt;= LBR &lt;= 616   |          15000                   |
-- |  624 &lt;= LBR &lt;= 648   |          14500                   |
-- |---------------------------------------------------------|
-- |  656 &lt;= LBR &lt;= 688   |          14000                   |
-- |  696 &lt;= LBR &lt;= 800   |          13500                   |
-- |---------------------------------------------------------|
-- |  808 &lt;= LBR &lt;= 832   |          12500                   |
-- |  840 &lt;= LBR &lt;= 896   |          12000                   |
-- |---------------------------------------------------------|
-- |  904 &lt;= LBR &lt;= 952   |          13000                   |
-- |  960 &lt;= LBR &lt;= 1000  |          12500                   |
-- |---------------------------------------------------------|
-- | 1008 &lt;= LBR &lt;= 1088  |          12000                   |
-- | 1096 &lt;= LBR &lt;= 1160  |          11500                   |
-- |---------------------------------------------------------|
-- | 1168 &lt;= LBR &lt;= 1320  |          11000                   |
-- | 1328 &lt;= LBR &lt;= 1472  |          10500                   |
-- |---------------------------------------------------------|
-- | 1480 &lt;= LBR &lt;= 1536  |          10000                   |
-- | 1544 &lt;= LBR &lt;= 1552  |          10500                   |
-- |---------------------------------------------------------|
-- | 1560 &lt;= LBR &lt;= 1664  |          10000                   |
-- | 1672 &lt;= LBR &lt;= 1880  |           9500                   |
-- |---------------------------------------------------------|
-- | 1888 &lt;= LBR &lt;= 2008  |           9000                   |
-- | 2016 &lt;= LBR &lt;= 2320  |           8500                   |
--  --------------------------------------------------------- 
-- Where LBR = Line Bit Rate
--
-- Note:Equivalent Working Length(EWL):EWL=L26+3(L24)/4,
--      where L26 is the total length of 26-gauge cable
--      in the loop excluding any bridged tap and L24 is
--      the total length of 19,22 or 24-gauge cable in
--      the loop excluding any bridged tap.   All lengths
--      are in kilofeet (ft). This formula is suitable for
--      use with systems operating below 1.1MHz.  
--
--      Note: Some EWL may have more then one range i.e., EWL
--      =12.5 Kft - ranges 192 Kbit/s to 832Kbits and 960 kbits
--      to 1000 kbits
--

spectrumMgmtAllowedSpeedsMin1 OBJECT-TYPE
     SYNTAX  Integer32
     MAX-ACCESS  read-only
     STATUS  deprecated
     DESCRIPTION
	"This rate will be the Minimum Line Bit Rate based
	 on the Line Length selected. 
	 See the Deployment guideline Table above.
	 Example: EWL=12.5 this value may be 808kbps"
     ::= { spectrumMgmtEntry 2 }

spectrumMgmtAllowedSpeedsMax1 OBJECT-TYPE
     SYNTAX  Integer32
     MAX-ACCESS  read-only
     STATUS  deprecated
     DESCRIPTION
	"This rate will be the Maximum Line Bit Rate based
	 on the Line Length selected
	 See the Deployment guideline Table above.
	 Example: EWL=12.5 this value may be 832kbps"
     ::= { spectrumMgmtEntry 3 }

spectrumMgmtAllowedSpeedsMin2 OBJECT-TYPE
     SYNTAX  Integer32
     MAX-ACCESS  read-only
     STATUS  deprecated
     DESCRIPTION
	"This rate will be the Minimum Line Bit Rate based
	 on the Line Length selected.
	 See the Deployment guideline Table above.
	 Example: EWL=12.5 this value may be 960kbps"
     ::= { spectrumMgmtEntry 4 }

spectrumMgmtAllowedSpeedsMax2 OBJECT-TYPE
     SYNTAX  Integer32
     MAX-ACCESS  read-only
     STATUS  deprecated
     DESCRIPTION
	"This rate will be the Maximum Line Bit Rate based
	 on the Line Length selected.
	 See the Deployment guideline Table above.
	 Example: EWL=12.5 this value may be 1000kbps"
     ::= { spectrumMgmtEntry 5 }

spectrumMgmtLineLength OBJECT-TYPE
     SYNTAX INTEGER {
		short(1),
		medium(2),
		long(3)
	 }
     MAX-ACCESS read-write
     STATUS deprecated
     DESCRIPTION
	"This 'Line Length' feature is only required if the
	 SpectrumMgmt is Enabled and the spectrumMgmtCountryCode
	 selected is 'UK'.
	 'Short' Line Length from the exchange can support speeds
	 up to 2056 Kbps.
	 'Medium' Line Length can support speeds up to 1496 Kbps.
	 'Long' Line Length can suppport speeds up to 872 Kbps."

       DEFVAL { short }
     ::= { spectrumMgmtEntry 6 }



--
--	C O N F O R M A N C E       S T A T E M E N T S
--

   pdnSpecMgmtConformance	OBJECT IDENTIFIER 
		::= { pdnSpectrumMgmt 3 }

   pdnSpecMgmtGroups		OBJECT IDENTIFIER
		::= { pdnSpecMgmtConformance 1 }

   pdnSpecMgmtCompliances	OBJECT IDENTIFIER
		::= { pdnSpecMgmtConformance 2 }


-- 
-- 	C O M P L I A N C E       S T A T E M E N T S
--

pdnSpecMgmtCompliance 	MODULE-COMPLIANCE
    STATUS      current
    DESCRIPTION
       "The compliance statement for SNMP entities that control
        spectrum management on interfaces."

    MODULE   -- this module
        MANDATORY-GROUPS { 
            pdnGeneralConfigGroup,
            pdnLineInfoGroup
        }

--
-- Groups
--
-- pdnEWLModeGroup,
-- pdnLoopLengthModeGroup,
-- pdnQuadModeGroup
--
-- are mutually exclusive; that is, at most one of these groups
-- is implemented for a particular DSL interface. If the
-- Loop Measurement Method is 'none', then none of these groups
-- should be implemented.
--
    GROUP   pdnEWLModeGroup
    DESCRIPTION
       "This group is mandatory for DSL interfaces whose
        loop/line length measurement method is EWL.
        i.e.the newSpectrumMgmtLoopMeasurementMethod object
        is 'ewl'."

    GROUP   pdnLoopLengthModeGroup
    DESCRIPTION
       "This group is mandatory for DSL interfaces whose
        loop/line length measurement method is LoopLength.
        i.e.the newSpectrumMgmtLoopMeasurementMethod object
        is 'loopLength'."

    GROUP   pdnQuadModeGroup
    DESCRIPTION
       "This group is mandatory for DSL interfaces whose
        loop/line length measurement method is based on Quads.
        i.e.the newSpectrumMgmtLoopMeasurementMethod object
        is 'quadMode'."

    OBJECT  	newSpectrumMgmtSelection
    MIN-ACCESS  read-only
    DESCRIPTION 
       "Write access is not required."

    ::= { pdnSpecMgmtCompliances 1 }

	
--
-- 	U N I T S    O F    C O N F O R M A N C E
--

-- Mandatory group
pdnGeneralConfigGroup	OBJECT-GROUP
	OBJECTS {
		newSpectrumMgmtSelection,
		newSpectrumMgmtMode,
		newSpectrumMgmtLoopMeasurementMethod,
		newSpectrumMgmtEWLUnits
	}
	STATUS	current
	DESCRIPTION
		"A collection of general configuration objects
		required for the spectrum management of
		interfaces."

	::= { pdnSpecMgmtGroups 1 }

-- Mandatory group
pdnLineInfoGroup	OBJECT-GROUP
	OBJECTS {
	        newSpectrumMgmtXtucMax1TxRate,
        	newSpectrumMgmtXtucMin1TxRate,
	        newSpectrumMgmtXtucMax2TxRate,
        	newSpectrumMgmtXtucMin2TxRate,
         	newSpectrumMgmtXtucMaxTxPower,
        	newSpectrumMgmtXturMax1TxRate,
        	newSpectrumMgmtXturMin1TxRate,
        	newSpectrumMgmtXturMax2TxRate,
        	newSpectrumMgmtXturMin2TxRate,
        	newSpectrumMgmtXturMaxTxPower,
        	newSpectrumMgmtMinEWL,
        	newSpectrumMgmtMaxEWL
	}
	STATUS	current
	DESCRIPTION
		"A collection of objects providing information
		regarding spectrum management of interfaces."

	::= { pdnSpecMgmtGroups 2 }

--
-- Optional group
-- (pdnEWLModeGroup, pdnLineLoopModeGroup or pdnQuadModeGroup
--  should be implemented)
--
pdnEWLModeGroup	OBJECT-GROUP
	OBJECTS {
		newSpectrumMgmtConfEWL,
		newSpectrumMgmtMinEWL,
		newSpectrumMgmtMaxEWL
	}
	STATUS	current
	DESCRIPTION
		" A collection of configuration objects used to
		  control spectrum management of DSL intfs when
		  the measurement method is 'EWL'."

	::= { pdnSpecMgmtGroups 3 }

--
-- Optional group
-- (pdnEWLModeGroup, pdnLineLoopModeGroup or pdnQuadModeGroup
--  should be implemented)
--
pdnLoopLengthModeGroup	OBJECT-GROUP
	OBJECTS {
		newSpectrumMgmtConfLoopLength
	}
	STATUS	current
	DESCRIPTION
		" A collection of configuration objects used to
		  control spectrum management of DSL intfs when
		  the measurement method is 'LoopLength' "

	::= { pdnSpecMgmtGroups 4 }

--
-- Optional group
-- (pdnEWLModeGroup, pdnLineLoopModeGroup or pdnQuadModeGroup
--  should be implemented)
--
pdnQuadModeGroup OBJECT-GROUP
    	OBJECTS {
        	newSpectrumMgmtConfQuadMode
    	}
	STATUS      current
    	DESCRIPTION 
       		"A collection of object(s) providing configuration
        	access and information specific to DSL interfaces
        	whose loop/line length measurement method is based on the
        	Quad configuration.
        	i.e.the newSpectrumMgmtLoopMeasurementMethod object
        	is 'quadMode'."

    	::= { pdnSpecMgmtGroups 5 }

--
--		D E P R E C A T E D       G R O U P S
--
pdnSpectrumMgmtDeprecatedGroup	OBJECT-GROUP
	OBJECTS {
		spectrumMgmtCountryCode,
		spectrumMgmtEWL,
		spectrumMgmtLineLength,
		spectrumMgmtAllowedSpeedsMin1,
		spectrumMgmtAllowedSpeedsMax1,
		spectrumMgmtAllowedSpeedsMin2,
		spectrumMgmtAllowedSpeedsMax2
	}
	STATUS	deprecated
	DESCRIPTION
		" Deprecated objects "

	::= { pdnSpecMgmtGroups 7 }

END

PDN-MGMT-IP-MIB DEFINITIONS ::= BEGIN
-- 
-- 
--                    SNMPv2 Management Information Base
--                  for Managing Classical IP and ARP over
--                     ATM PVCs for management purposes
-- 
-- Note:
-- 
--    The IP, UDP, and TCP MIB modules currently support only IPv4. These
--    three modules use the IpAddress type defined as an OCTET STRING of
--    length 4 to represent the IPv4 32-bit internet addresses.  (See RFC
--    2578, SMI for SNMPv2.)  They do not support the new 128-bit IPv6
--    internet addresses.
-- 
-- Table of Contents
-- 
--    1. Introduction
--    2. The Management IP Model
--    3. Structure of the MIB
--    4. Definitions
-- 
-- 1.  Introduction
-- 
--    The primary purpose of this document is to define MIBs for
--    configuration and management of Classical IP ports (also called
--    IP interfaces) that are used for managing a DSLAM device. Currently
--    the issues addressed are only those pertaining to managing a DSLAM
--    through IP over Ethernet and ATM PVCs only. Use and interpretation
--    of the MIBs defined in this document for managing IP over other
--    transports (eg. Frame Relay, ATM SVCs, etc) is beyond the current
--    scope of this document.
-- 
-- 2.  The Management IP Model
-- 
--    A DSLAM is considered to have one or more 'IP Ports'. These IP
--    Ports could either be standard Ethernet based IP Ports or those
--    operating over ATM PVCs (with RFC 2684 encapsulation).
-- 
--    Each IP Port is associated with an interface index (ifIndex of
--    RFC 2863), an IP address (Ipv4, IpAddress of RFC 2578), and an
--    IP Network Mask among other things. The ipAddrTable (defined in
--    RFC 2011) comes close to handling most of these parameters, but is
--    indexed on the IP address itself. Since it is our requirement that
--    the IP port exist whether an IP address has been assigned to it or
--    not (eg. a port configured to obtain the IP address through DHCP
--    or BOOTP), a new table has been defined in this document, which is
--    indexed on the interface index of the IP port itself.
-- 
--    In case of IP ports that are associated with ATM PVCs, each IP port
--    consists of one or more point-to-point PVC links. RFC 2320 has a
--    set of MIB tables defined for managing IP and ARP over ATM, but
--    they are better suited for systems that do InATMARP (RFC 2225)
--    and over SVCs. Unlike ARP in ethernet based IP systems, ATM ARP is
--    not very common and is not implemented in most networks. Hence a
--    MIB table is defined in this document to manually add, delete or
--    manage these PVCs for the sole purpose of carrying IP based
--    management traffic.
-- 
--    The management IP model used in this document could be depicted
--    in a couple of diagrams as shown below
-- 
-- 
--    Case #1 : Ethernet based IP
-- 
--           _________________________________ 
--          /                                 \
--          | IP Port ifIndex : 1001802       |    IP Port (covered by
--          | IP Address      : 135.26.25.1   |          this document)
--          | Subnet Mask     : 255.255.255.0 |
--          | Physical Address: 00-E0-39-87-  |
--          |                         BC-40   |
--          \_________________________________/
--                           |
--                           |
--                           | Ethernet
--                           | Media
--                           |
--          _________________________________________________
--         |                |               |                |
--         |                |               |                |
--     ___________    ____________     ___________      ____________
--    /           \  /            \   /           \    /            \
--    |  Host #1  |  |   Host #2  |   |  Host #3  |    |   Host #4  |
--    |135.26.25.2|  |IP Gateway 1|   |135.26.25.4|    |IP Gateway 2|
--    |           |  | 135.26.25.3|   |           |    | 135.26.25.5|
--    |00-E0-39-  |  |00-E0-49-   |   |00-12-3A-  |    |00-5D-65-   |
--    |   11-11-11|  |   22-22-22 |   |   33-33-33|    |   44-44-44 |
--    \___________/  \____________/   \___________/    \____________/
--                          |                                |
--                          |                                |
--                To other nets/subnets            To other nets/subnets
-- 
--    The Ethernet ARP Table for this IP Port would look like
--               ________________________________
--              /                                \
--              | &lt;Next Hop IP,  mac Address&gt;    |
--              | 135.26.25.2, 00-E0-39-11-11-11 |
--              | 135.26.25.3, 00-E0-49-22-22-22 |
--              | 135.26.25.4, 00-12-3A-33-33-33 |
--              | 135.26.25.5, 00-5D-65-44-44-44 |
--              \________________________________/
--    Note : The Ethernet ARP Table is not covered by this document.
-- 
-- 
--    Case #2 : ATM PVC based IP
-- 
--           ___________________________________
--          /                                   \
--          | IP Port ifIndex : 1005101         | IP Port  (covered by
--          | IP Address      : 135.26.26.1     |        this document)
--          | Subnet Mask     : 255.255.255.255 |
--          | Physical Address: 11-11-11-11-11- |
--          |  (8 octets)              11-11-11 |
--          \___________________________________/
--         ATM  |             |A           |  ATM
--        PVC#1 |             |T           | PVC#3
--          ____/             |M           \_______________
--         |ifIndex:1003901   |            ifIndex:1003902 |
--         |VPI:0, VCI:32     |P           VPI:46, VCI:124 |
--     __________________     |V                  ___________________
--    /                  \    |C                 /                   \
--    |     Host #1      |    |#                 |      Host #3      |
--    |   135.26.26.2    |    |2                 |    135.26.26.4    |
--    | 22-22-22-22-22-22|    |                  | 44-44-44-44-44-44 |
--    |            -22-22|    |                  |            -44-44 |
--    \__________________/    |ifIndex:1003901   \___________________/
--                            |VPI:10, VCI:54
--                   ___________________
--                  /                   \
--                  |      Host #2      |
--                  |    135.26.26.3    |
--                  | 33-33-33-33-33-33 |
--                  |            -33-33 |
--                  \___________________/
-- 
--    The ATM ARP Table for this IP Port would look like
--               _______________________________________________________
--              /                                                       \
--              | &lt;Next Hop IP, IP Port ifIndex, atm ifIndex, vpi, vci&gt; |
--              | 135.26.26.2,      1005101,      1003901,     0,   32  |
--              | 135.26.26.3,      1005101,      1003901,    10,   54  |
--              | 135.26.26.4,      1005101,      1003902,    46,  124  |
--              \_______________________________________________________/
--    Note : The ATM ARP Table is covered by this document in the form of
--           an Inverse ARP Table. ie. the table is indexed on the
--           &lt;atmIfIndex, atmVpi, atmVci&gt; combination.
-- 
-- 3.  Structure of the MIB
-- 
--    The MIB consists of two tables and other common object(s).
-- 
--    The first table is the IP Port Table. There is one entry per IP
--    port/interface in the system. This table contains the configuration
--    details of the port. This table is indexed on the interface index
--    of the IP port. The interface index of the IP Port may or may not
--    be represented in the ifTable of RFC2863.
-- 
--    The syntax and meaning of pdnMgmtIpPhysAddress is identical to
--    that of ifPhysAddress (defined in ifTable - RFC 2863), with the
--    following properties
--        1. pdnMgmtIpPhysAddress is writeable, in case of non-ethernet
--           type of media.
--        2. In case of ethernet type of media, pdnMgmtIpPhysAddress is
--           read-only and has the ethernet MAC address of the underlying
--           ethernet data link.
-- 
--    The second table is the ATM Inverse ARP Table. This table contains
--    one entry per ATM PVC that has been designated to carry IP
--    management traffic. This table is indexed on the user side
--    ATM ifIndex (usually one of the Uplinks), VPI &amp; VCI of the PVC.
--    Entries in this table can be dynamically created modified or
--    destroyed as required. An SNMP agent operating on this table
--    utilizes the standard ATM MIBs (RFC 2515) to create and manage
--    the PVCs. Creation of a new entry in this table could fail,
--    if the PVC is either already in use or the PVC is a data PVC.
-- 
--    Apart from the these two tables, this MIB also defines a "Default
--    Router" for the system. All management IP packets with unknown
--    routes to their destinations will be forwarded to this router for
--    further routing.
-- 
-- 4.  Definitions
 

IMPORTS
    MODULE-IDENTITY, OBJECT-TYPE, IpAddress
        FROM SNMPv2-SMI
    MODULE-COMPLIANCE, OBJECT-GROUP
        FROM SNMPv2-CONF
    PhysAddress, RowStatus
        FROM SNMPv2-TC
    AtmVpIdentifier, AtmVcIdentifier
        FROM ATM-TC-MIB
    InterfaceIndex
        FROM IF-MIB
    pdn-interfaces
        FROM PDN-HEADER-MIB;

pdnMgmtIpMIB MODULE-IDENTITY
    LAST-UPDATED "200206051500Z"
    ORGANIZATION "Paradyne Corporation MIB Working Group"
    CONTACT-INFO
            "         Paradyne Networks Inc.

             Postal:  8545, 126th Ave. N.
                      Largo, FL 33779
                      US
             Editors: Daniel M.V.
                      Jesus Pinto
             Email:   mibwg_team@eng.paradyne.com"

    DESCRIPTION
            "The MIB module for configuration and management of IP
             interfaces/ports used for managing a DSLAM."
    ::= { pdn-interfaces 21 }

pdnMgmtIpConfObjects OBJECT IDENTIFIER ::= { pdnMgmtIpMIB 1 }

pdnMgmtIpPortTable OBJECT-TYPE
    SYNTAX      SEQUENCE OF PdnMgmtIpPortEntry
    MAX-ACCESS  not-accessible
    STATUS      current
    DESCRIPTION
            "This table contains one row per IP port in the system."
    ::= { pdnMgmtIpConfObjects 1 }

pdnMgmtIpPortEntry OBJECT-TYPE
    SYNTAX      PdnMgmtIpPortEntry
    MAX-ACCESS  not-accessible
    STATUS      current
    DESCRIPTION
            "Configuration information about a particular IP port
             in the system."
    INDEX   { pdnMgmtIpPortIndex }
    ::= { pdnMgmtIpPortTable 1 }

PdnMgmtIpPortEntry ::=
    SEQUENCE {
        pdnMgmtIpPortIndex    InterfaceIndex,
        pdnMgmtIpAddress      IpAddress,
        pdnMgmtIpNetMask      IpAddress,
        pdnMgmtIpEthGateway   IpAddress,
        pdnMgmtIpPhysAddress  PhysAddress,
        pdnMgmtIpConfigMode   INTEGER,
        pdnMgmtBootIfIndex    InterfaceIndex,
        pdnMgmtBootVpi        AtmVpIdentifier,
        pdnMgmtBootVci        AtmVcIdentifier,
        pdnMgmtIpAdminStatus  INTEGER
}

pdnMgmtIpPortIndex OBJECT-TYPE
    SYNTAX      InterfaceIndex
    MAX-ACCESS  not-accessible
    STATUS      current
    DESCRIPTION
            "The index for this entry."
    ::= { pdnMgmtIpPortEntry 1 }

pdnMgmtIpAddress OBJECT-TYPE
    SYNTAX      IpAddress
    MAX-ACCESS  read-write
    STATUS      current
    DESCRIPTION
            "The IP address assigned to this port.

             If the pdnMgmtIpConfigMode is set to modes other than
             'manual', then the MAX-ACCESS for this object is
             read-only and the value of the object represents the
             actual IP address assigned to the port by the DHCP
             or BOOTP client (or 0.0.0.0, if none assigned).

             A 0.0.0.0 for this object indicates that no IP
             address is assigned to the port.

             Changes to this object could disrupt data flow
             through the port as the IP port tears down the
             IP stack first before instantiating the stack
             again with the new IP address."
    ::= { pdnMgmtIpPortEntry 2 }

pdnMgmtIpNetMask OBJECT-TYPE
    SYNTAX      IpAddress
    MAX-ACCESS  read-write
    STATUS      current
    DESCRIPTION
            "The IP subnet mask assigned to this port.

             If the pdnMgmtIpConfigMode is set to modes other than
             'manual', then the MAX-ACCESS for this object is
             read-only and the value of the object represents the
             actual IP subnet mask assigned to the port by the DHCP
             or BOOTP client (or 0.0.0.0, if none assigned).

             A 0.0.0.0 for the this object indicates that no IP
             subnet mask is assigned to the port.

             Changes to this object could disrupt data flow
             through the port as the IP port tears down the
             IP stack first before instantiating the stack
             again with the new IP subnet mask."
    ::= { pdnMgmtIpPortEntry 3 }

pdnMgmtIpEthGateway OBJECT-TYPE
    SYNTAX      IpAddress
    MAX-ACCESS  read-write
    STATUS      current
    DESCRIPTION
            "The IP Gateway for an ethernet based IP port.

             This object is supported only on IP ports that are
             configured to run over ethernet type of media.
             This object would be set to 0.0.0.0 for other types of
             interfaces and is not valid.

             Furthermore, if the pdnMgmtIpConfigMode is set to
             modes other than 'manual', then the MAX-ACCESS for this
             object is read-only and the value of the object represents
             the actual IP Gateway mask assigned to the port by the
             DHCP or BOOTP client (or 0.0.0.0, if none assigned).

             A 0.0.0.0 for this object indicates that no IP
             Gateway is assigned to the port."
    ::= { pdnMgmtIpPortEntry 4 }

pdnMgmtIpPhysAddress OBJECT-TYPE
    SYNTAX      PhysAddress
    MAX-ACCESS  read-write
    STATUS      current
    DESCRIPTION
            "The physical address associated with the media.

             For IP Ports with Ethernet type of media, the
             MAX-ACCESS for this object is restricted to read-only.
             In such cases, this object would reflect the MAC address
             of the underlying ethernet data link.

             For IP Ports that run over ATM PVCs, this object is
             writable."
    ::= { pdnMgmtIpPortEntry 5 }

pdnMgmtIpConfigMode OBJECT-TYPE
    SYNTAX      INTEGER {
                    manual(1),  -- IP configuration is manual
                    dhcp(2),    -- IP config by DHCP protocol
                    bootp(3)    -- IP config by BOOTP protocol
                }
    MAX-ACCESS  read-write
    STATUS      current
    DESCRIPTION
            "The IP configuration mode for the port.

             In 'manual' mode, it is upto the user to provide
             the IP address &amp; IP subnet mask of the port.

             In 'dhcp' or 'bootp' modes, the respective
             protocols are resposible to obtain and populate
             the IP address &amp; IP subnet mask for the port.

             Whenever the config mode is changed from 'manual'
             mode, the IP address and the IP subnet mask for
             the port would automatically be reset to 0.0.0.0.

             The external agent (SNMP or others) SHOULD NOT
             attempt to write the IP address or the IP subnet
             mask of the port when this object is not in
             'manual' mode."
    ::= { pdnMgmtIpPortEntry 6 }

pdnMgmtBootIfIndex OBJECT-TYPE
    SYNTAX      InterfaceIndex
    MAX-ACCESS  read-write
    STATUS      current
    DESCRIPTION
            "The interface index of the ATM interface to be used
             by BOOTP or DHCP client, if the pdnMgmtIpConfigMode
             is set to 'bootp' or 'dhcp' respectively.

             Even if the IP port (interface) is configured for
             'manual' configuration, the value of this object can
             be modified to indicate the default ATM ifIndex for
             BOOTP or DHCP to operate on.

             This object is valid only if the IP Port has ATM PVC(s)
             as the underlying data link media. For IP Ports over
             ethernet type of media, the MAX-ACCESS for this object
             is read-only, and the object is set to 0 always."
    ::= { pdnMgmtIpPortEntry 7 }

pdnMgmtBootVpi OBJECT-TYPE
    SYNTAX      AtmVpIdentifier
    MAX-ACCESS  read-write
    STATUS      current
    DESCRIPTION
            "The VPI of the ATM PVC to be used by BOOTP or DHCP
             client, if the pdnMgmtIpConfigMode is set to 'bootp'
             or 'dhcp' respectively.

             Even if the IP port (interface) is configured for
             'manual' configuration, the value of this object can
             be modified to indicate the default ATM PVC's VPI for
             BOOTP or DHCP to operate on.

             This object is valid only if the IP Port has ATM PVC(s)
             as the underlying data link media. For IP Ports over
             ethernet type of media, the MAX-ACCESS for this object
             is read-only, and the object is set to 0 always."
    ::= { pdnMgmtIpPortEntry 8 }

pdnMgmtBootVci OBJECT-TYPE
    SYNTAX      AtmVcIdentifier
    MAX-ACCESS  read-write
    STATUS      current
    DESCRIPTION
            "The VCI of the ATM PVC to be used by BOOTP or DHCP
             client, if the pdnMgmtIpConfigMode is set to 'bootp' or
             'dhcp' respectively.

             Even if the IP port (interface) is configured for
             'manual' configuration, the value of this object can
             be modified to indicate the default ATM PVC's VCI for
             BOOTP or DHCP to operate on.

             This object is valid only if the IP Port has ATM PVC(s)
             as the underlying data link media. For IP Ports over
             ethernet type of media, the MAX-ACCESS for this object
             is read-only, and the object is set to 0 always."
    ::= { pdnMgmtIpPortEntry 9 }

pdnMgmtIpAdminStatus OBJECT-TYPE
    SYNTAX      INTEGER {
                    up(1),
                    down(2)
                }
    MAX-ACCESS  read-write
    STATUS      current
    DESCRIPTION
            "The status of the IP Port (interface).

             Data flow through the IP Port is possible only if this
             object is set to 'up'.

             When this object is set to 'down', the interface SHALL
             be torn down and all routes (associated with this port)
             be purged automatically, until the port is set to 'up'
             state again."
    ::= { pdnMgmtIpPortEntry 10 }

pdnMgmtAtmInvArpTable OBJECT-TYPE
    SYNTAX      SEQUENCE OF PdnMgmtAtmInvArpEntry
    MAX-ACCESS  not-accessible
    STATUS      current
    DESCRIPTION
            "This table contains one row per Inverse ATM ARP entry
             in the system. This table maps the &lt;ifIndex, vpi, vci&gt;
             index to corresponding &lt;ipPortIndex, remoteIp&gt;."
    ::= { pdnMgmtIpConfObjects 2 }

pdnMgmtAtmInvArpEntry OBJECT-TYPE
    SYNTAX      PdnMgmtAtmInvArpEntry
    MAX-ACCESS  not-accessible
    STATUS      current
    DESCRIPTION
            "ATM Inverse ARP entry corresponding to a particular
             ATM PVC that is being used by management IP traffic."
    INDEX   { pdnMgmtAtmIfIndex, pdnMgmtAtmVpi, pdnMgmtAtmVci }
    ::= { pdnMgmtAtmInvArpTable 1 }

PdnMgmtAtmInvArpEntry ::=
    SEQUENCE {
        pdnMgmtAtmIfIndex         InterfaceIndex,
        pdnMgmtAtmVpi             AtmVpIdentifier,
        pdnMgmtAtmVci             AtmVcIdentifier,
        pdnMgmtIpPortIfIndex      InterfaceIndex,
        pdnMgmtNextHopIp          IpAddress,
        pdnMgmtAtmInvArpRowStatus RowStatus
}

pdnMgmtAtmIfIndex OBJECT-TYPE
    SYNTAX      InterfaceIndex
    MAX-ACCESS  not-accessible
    STATUS      current
    DESCRIPTION
            "The interface index associated with the ATM PVC."
    ::= { pdnMgmtAtmInvArpEntry 1 }

pdnMgmtAtmVpi OBJECT-TYPE
    SYNTAX      AtmVpIdentifier
    MAX-ACCESS  not-accessible
    STATUS      current
    DESCRIPTION
            "The VPI associated with the ATM PVC."
    ::= { pdnMgmtAtmInvArpEntry 2 }

pdnMgmtAtmVci OBJECT-TYPE
    SYNTAX      AtmVcIdentifier
    MAX-ACCESS  not-accessible
    STATUS      current
    DESCRIPTION
            "The VCI associated with the ATM PVC."
    ::= { pdnMgmtAtmInvArpEntry 3 }

pdnMgmtIpPortIfIndex OBJECT-TYPE
    SYNTAX      InterfaceIndex
    MAX-ACCESS  read-create
    STATUS      current
    DESCRIPTION
            "The Interface Index of the IP port to which
             this inverse ARP entry is associated with."
    ::= { pdnMgmtAtmInvArpEntry 4 }

pdnMgmtNextHopIp OBJECT-TYPE
    SYNTAX      IpAddress
    MAX-ACCESS  read-create
    STATUS      current
    DESCRIPTION
            "The IP address of the unit at the other end of
             this ATM PVC. This represents the IP Gateway
             equivalent for IP traffic on this specific ATM PVC."
    ::= { pdnMgmtAtmInvArpEntry 5 }

pdnMgmtAtmInvArpRowStatus OBJECT-TYPE
    SYNTAX      RowStatus
    MAX-ACCESS  read-create
    STATUS      current
    DESCRIPTION
            "This object is used to create/delete the ATM inverse
             ARP entry in this table. "
    ::= { pdnMgmtAtmInvArpEntry 6 }

pdnMgmtIpDefaultRouter OBJECT-TYPE
    SYNTAX      IpAddress
    MAX-ACCESS  read-write
    STATUS      current
    DESCRIPTION
            "This object identifies the default IP router to use for
             IP packets with no other known route.

             An IP address of 0.0.0.0 would disable and delete the
             default route from the system."
    ::= { pdnMgmtIpConfObjects 3 }

-- Conformance Information

pdnMgmtIpConformance OBJECT IDENTIFIER ::= { pdnMgmtIpMIB 2 }

pdnMgmtIpGroups OBJECT IDENTIFIER
    ::= { pdnMgmtIpConformance 1 }
pdnMgmtIpCompliances OBJECT IDENTIFIER
    ::= { pdnMgmtIpConformance 2 }

-- Compliance Statements

pdnMgmtIpConfigCompliance MODULE-COMPLIANCE
    STATUS current
    DESCRIPTION
            "The compliance statement for SNMP entities which
             manage the configuration parameters on a Management
             IP port/interface."
    MODULE   -- this module
    MANDATORY-GROUPS {
        pdnMgmtIpConfigGroup
    }

    OBJECT  pdnMgmtIpAddress
    MIN-ACCESS read-only
    DESCRIPTION
            " Write access is not required."

    OBJECT pdnMgmtIpNetMask
    MIN-ACCESS read-only
    DESCRIPTION
            "Write access is not required."

    OBJECT pdnMgmtIpEthGateway
    MIN-ACCESS read-only
    DESCRIPTION
            "Write access is not required."

    OBJECT pdnMgmtIpPhysAddress
    MIN-ACCESS read-only
    DESCRIPTION
            "Write access is not required."

    OBJECT pdnMgmtIpConfigMode
    MIN-ACCESS read-only
    DESCRIPTION
            "Write access is not required."

    OBJECT pdnMgmtBootIfIndex
    MIN-ACCESS read-only
    DESCRIPTION
            "Write access is not required."

    OBJECT pdnMgmtBootVpi
    MIN-ACCESS read-only
    DESCRIPTION
            "Write access is not required."

    OBJECT pdnMgmtBootVci
    MIN-ACCESS read-only
    DESCRIPTION
            "Write access is not required."

    OBJECT pdnMgmtIpAdminStatus
    MIN-ACCESS read-only
    DESCRIPTION
            "Write access is not required."

    OBJECT pdnMgmtIpPortIfIndex
    MIN-ACCESS read-only
    DESCRIPTION
            "Write access is not required."

    OBJECT pdnMgmtNextHopIp
    MIN-ACCESS read-only
    DESCRIPTION
            "Write access is not required."

    OBJECT pdnMgmtAtmInvArpRowStatus
    MIN-ACCESS read-only
    DESCRIPTION
            "Write access is not required."

    OBJECT pdnMgmtIpDefaultRouter
    MIN-ACCESS read-only
    DESCRIPTION
            "Write access is not required."

    ::= { pdnMgmtIpCompliances 1 }

-- Units of Conformance

pdnMgmtIpConfigGroup OBJECT-GROUP
    OBJECTS {
        pdnMgmtIpAddress,
        pdnMgmtIpNetMask,
        pdnMgmtIpEthGateway,
        pdnMgmtIpPhysAddress,
        pdnMgmtIpConfigMode,
        pdnMgmtBootIfIndex,
        pdnMgmtBootVpi,
        pdnMgmtBootVci,
        pdnMgmtIpAdminStatus,
        pdnMgmtIpPortIfIndex,
        pdnMgmtNextHopIp,
        pdnMgmtAtmInvArpRowStatus,
        pdnMgmtIpDefaultRouter
    }
    STATUS current
    DESCRIPTION
            "A collection of Management IP configuration objects
             that are required to configure the device."
    ::= { pdnMgmtIpGroups 1 }

END


PDN-SFP-MIB DEFINITIONS ::= BEGIN

-------------------------------------------------------------------
--  Copyright (C) 2003, Paradyne. All rights reserved.
--
--  This MIB Enables an NMS to extract and Display information associated
--  with the SFP modules. 
-------------------------------------------------------------------

IMPORTS
    Integer32,
    MODULE-IDENTITY, OBJECT-TYPE, NOTIFICATION-TYPE
        FROM SNMPv2-SMI
    MODULE-COMPLIANCE, OBJECT-GROUP, NOTIFICATION-GROUP
        FROM SNMPv2-CONF
    DisplayString, DateAndTime
        FROM SNMPv2-TC
    ifIndex
       FROM IF-MIB
     pdn-ietf-drafts
       FROM PDN-HEADER-MIB;


pdnSfp  MODULE-IDENTITY
        LAST-UPDATED "200304230000Z"
        ORGANIZATION "Paradyne Corp MIB Working Group"
        CONTACT-INFO "Paradyne Networks, Inc.
              8545, 126th Ave. N.,
              Largo, FL 33779
              www.paradyne.com

             General Comments to:
                mibwg_team@paradyne.com

             Editors: Prakash Easwar"

        DESCRIPTION 
              "SFP is short for Small Form-Factor Pluggable (SFP) Transceiver. 
              They  plug into an SFP Compaitble Port and allow for compact
              Hardware design
              SFP modules contain an EEPROM containing information about the
              part. This MIB defines objects which will allow an NMS to extract
              the information from the SFP modules in a MIB format.
              The MIB objects defined in this MIB are based on the 
              **Small Form Factor Pluggable (SFP) Transceiver MultiSource Agreement(MSA)**
              Since SFP MODULES are an extension of the port itself, the ifIndex for a
              sfp Compatible Port will be used to access information from these modules.
              The Entity MIB (RFC 2737) Should Contain Entries for Each SFP Module.
              SFP to Port to PortIfIndex can be acheived via the Entity MIB (RFC2737)"
       REVISION "200304230000Z"
            DESCRIPTION "Added new enum to sfpEncoding MIB Object"
       REVISION "200302010000Z"
            DESCRIPTION "Initial MIB Creation"
   
         ::= { pdn-ietf-drafts 3 }

sfpMIBObjects   OBJECT IDENTIFIER ::= { pdnSfp 1 }
sfpMIBNotifications OBJECT IDENTIFIER ::= { pdnSfp 2 }
sfpMIBConformance  OBJECT IDENTIFIER ::= { pdnSfp 3 }

--
-- START OF sfp mib definitions
--

sfpCompatibleInterfaceCount OBJECT-TYPE
     SYNTAX	Integer32
     MAX-ACCESS read-only
     STATUS	current
     DESCRIPTION
       "The number of physical ports in the system which are sfp compatible"
     ::= { sfpMIBObjects 1 }

sfpInfoTable OBJECT-TYPE
       SYNTAX SEQUENCE OF SfpInfoEntry
       MAX-ACCESS not-accessible
       STATUS current
       DESCRIPTION
         "The sfp information table."
       ::= { sfpMIBObjects 2 }

sfpInfoEntry OBJECT-TYPE
     SYNTAX	SfpInfoEntry
     MAX-ACCESS not-accessible
     STATUS current
     DESCRIPTION
       "An entry in the SFP Information Table"
     INDEX { ifIndex }
     ::= { sfpInfoTable 1 }

SfpInfoEntry ::= SEQUENCE {
       sfpIdentifier INTEGER,
       sfpVendorSpecificIdentifier OCTET STRING,
       sfpExtIdentifier INTEGER,
       sfpConnector INTEGER, 
       sfpVendorSpecificConnector OCTET STRING,
       sfpTransceiverComplianceCodes BITS,
       sfpFibreChannelLinkLength BITS,
       sfpFibreChannelTransmitterTechnology BITS,
       sfpFibreChannelTransmissionMedia BITS,
       sfpFibreChannelTransmissionSpeed BITS,
       sfpEncoding INTEGER,
       sfpBRNominal100Mbps Integer32,
       sfpLength9MiKm Integer32,
       sfpLength9Mi100M Integer32,
       sfpLength50Mi10M Integer32,
       sfpLength62Pt5Mi10M Integer32,
       sfpLengthCopperM Integer32,
       sfpVendorName DisplayString,
       sfpVendorOUI  OCTET STRING,
       sfpVendorPN DisplayString,
       sfpVendorSN DisplayString,
       sfpVendorRev DisplayString,
       sfpLaserWavelength Integer32,
       sfpOptions BITS,
       sfpBRMin Integer32,
       sfpBRMax Integer32,
       sfpVendorDate DateAndTime,
       sfpVendorSpecificLotCode OCTET STRING,
       sfpVendorSpecificData OCTET STRING,
       sfpStatusCurrent  BITS
     }

sfpIdentifier OBJECT-TYPE
     SYNTAX	INTEGER {
              unknown(1),
              gbic(2),
              fixed(3),
              sfp(4),
              other(5)
            }
     MAX-ACCESS read-only
     STATUS	current
     DESCRIPTION
       "The type of serial transceiver
                 unknown -- Unknown or unspecified
                 gbic -- GBIC
                 fixed -- Module/connector soldered to motherboard
                 sfp -- SFP transceiver
                 other -- Vendor specific"
     ::= { sfpInfoEntry 1 }

sfpVendorSpecificIdentifier OBJECT-TYPE
     SYNTAX	 OCTET STRING (SIZE(1))
     MAX-ACCESS read-only
     STATUS	current
     DESCRIPTION
       "The vendor specific identifier. This Object will be set to
        value other than {0,0} only if sfpIdentifier returns a value of
        other"
     ::= { sfpInfoEntry 2 }

sfpExtIdentifier OBJECT-TYPE
     SYNTAX	INTEGER {
              unknown(1),
              simd(2)
            }
     MAX-ACCESS read-only
     STATUS	current
     DESCRIPTION
       "The type of serial transceiver
                 unknown -- Unknown or unspecified
                 simd -- Serial ID module Definition"
     ::= { sfpInfoEntry 3 }

sfpConnector OBJECT-TYPE
     SYNTAX	INTEGER {
              unknown(1),
              sc(2),
              fcscc1(3),
              fcscc2(4),
              bnctnc(5),
              fcch(6),
              fiberJack(7),
              lc(8),
              mtrj(9),
              mu(10),
              sg(11),
              opticalPigtail(12),
              hssdcii(13),
              copperPigtail(14),
              other(15)
            }
     MAX-ACCESS read-only
     STATUS	current
     DESCRIPTION
       "The type of external connector provided
                 unknown -- Unknown or unspecified
                 sc -- SC
                 fcscc1 -- Fibre Channel Style 1 copper connector
                 fcscc2 -- Fibre Channel Style 2 copper connector
                 bnctnc -- BNC-TNC
                 fcch -- Fibre Channel coaxial headers
                 fiberJack -- Fiber Jack
                 lc -- LC
                 mtrj -- MT-RJ
                 mu -- MU
                 sg -- SG
                 opticalPigtail -- Optical Pigtail
                 hssdcii -- HSSDC II
                 copperPigtail -- Copper Pigtail
                 other -- Vendor specific"
     ::= { sfpInfoEntry 4 }

sfpVendorSpecificConnector OBJECT-TYPE
     SYNTAX	 OCTET STRING (SIZE(1))
     MAX-ACCESS read-only
     STATUS	current
     DESCRIPTION
       "The type of vendor specific Connector. This Object will be set to
        value other than {0,0} only if sfpConnector returns a value of
        other"
     ::= { sfpInfoEntry 5 }

sfpTransceiverComplianceCodes OBJECT-TYPE
     SYNTAX	BITS {
              unknown(0),
              oc48LongReach1(1),
              oc48LongReach2(2),
              oc48LongReach3(3),
              oc48IntermediateReach1(4),
              oc48IntermediateReach2(5),
              oc48ShortReach(6),
              oc12SMLongReach1(7),
              oc12SMLongReach2(8),
              oc12SMLongReach3(9),
              oc12SMIntermediateReach1(10),
              oc12SMIntermediateReach2(11),
              oc12MMShortReach(12),
              oc3SMLongReach1(13),
              oc3SMLongReach2(14),
              oc3SMLongReach3(15),
              oc3SMIntermediateReach1(16),
              oc3SMIntermediateReach2(17),
              oc3MMShortReach(18),
              base1000T(19),
              base1000CX(20),
              base1000LX(21),
              base1000SX(22),
              sx1x(23),
              lx1x(24),
              copperActive1x(25),
              copperPassive1x(26)
            }
     MAX-ACCESS read-only
     STATUS	current
     DESCRIPTION
       "The sfp transceiver codes for sonet
                 unknown -- Unknown

                 -- SONET Compliance Codes --

                 oc48LongReach1  -- OC-48, long reach, SONET LR-1 Compliant
                 oc48LongReach2  -- OC-48, long reach, SONET LR-2 Compliant
                 oc48LongReach3  -- OC-48, long reach, SONET LR-3 Compliant
                 oc48IntermediateReach1 -- OC-48, intermediate reach, SONET IR-1  Compliant
                 oc48IntermediateReach2 -- OC-48, intermediate reach, SONET IR-2 Compliant
                 oc48ShortReach -- OC-48 short reach, SONET SR Compliant
                 oc12SMLongReach1  -- OC-12, single mode long reach, SONET LR-1 Compliant
                 oc12SMLongReach2  -- OC-12, single mode long reach, SONET LR-2 Compliant
                 oc12SMLongReach3  -- OC-12, single mode long reach, SONET LR-3 Compliant
                 oc12SMIntermediateReach1 -- OC-12, songle mode intermediate reach, SONET IR-1  Compliant
                 oc12SMIntermediateReach2 -- OC-12, songle mode intermediate reach, SONET IR-2 Compliant
                 oc12MMShortReach -- OC-12 multi-mode short reach, SONET SR Compliant
                 oc3SMLongReach1 -- OC-3, single mode long reach, SONET LR-1 Compliant
                 oc3SMLongReach2 -- OC-3, single mode long reach, SONET LR-2 Compliant
                 oc3SMLongReach3 -- OC-3, single mode long reach, SONET LR-3 Compliant
                 oc3SMIntermediateReach1 -- OC-3, songle mode intermediate reach, SONET IR-1  Compliant
                 oc3SMIntermediateReach2 -- OC-3, songle mode intermediate reach, SONET IR-2 Compliant
                 oc3MMShortReach -- OC-3 multi-mode short reach, SONET SR Compliant

                 -- Gigabit Ethernet Compliance Codes --

                 base1000T -- 1000BASE-T 
                 base1000CX -- 1000BASE-CX
                 base1000LX -- 1000BASE-LX
                 base1000SX -- 1000BASE-SX

                 -- Infiniband Compliance Codes --
                 
                 lx1x -- 1X LX
                 sx1x -- 1X SX
                 copperActive1x -- 1X Copper Active
                 copperPassive1x -- 1X Copper Passive"
     ::= { sfpInfoEntry 6 }

sfpFibreChannelLinkLength OBJECT-TYPE
     SYNTAX	BITS {
			  unknown(0),
              veryLong(1),
              short(2),
              intermediate(3),
              long(4)
            }
     MAX-ACCESS read-only
     STATUS	current
     DESCRIPTION
       "The link length for fibre
                 unknown -- Unknown
                 veryLong -- very long distance
                 short -- short distance
                 intermediate -- intermediate distance
                 long -- long distance
                 notFibre -- The transmission is media is not Fibre"
     ::= { sfpInfoEntry 7 }

sfpFibreChannelTransmitterTechnology OBJECT-TYPE
     SYNTAX	BITS {
			  unknown(0),
              lc(1),
              el1(2),
              el2(3),
              sn(4),
              sl(5),
              ll(6)
            }
     MAX-ACCESS read-only
     STATUS	current
     DESCRIPTION
       "The fibre channel transmitter technology
                 unknown -- Unknown
                 lc -- Longwave Laser
                 el1 -- Electrical inter-enclosure
                 el2 -- Electrical intra-enclosure
                 sn -- Shortwave laser w/o OFC
                 sl -- Shortwave laser w/ OFC
                 ll -- Longwave Laser"
     ::= { sfpInfoEntry 8 }

sfpFibreChannelTransmissionMedia OBJECT-TYPE
     SYNTAX	BITS {
              unknown(0),
              tw(1),
              tp(2),
              mi(3),
              tv(4),
              m6(5),
              m5(6),
              sm(7)
            }
     MAX-ACCESS read-only
     STATUS	current
     DESCRIPTION
       "The fibre channel transmitter technology
                 unknown -- Unknown
                 tw -- Twin Axial Pair
                 tp -- Shielded Twisted Pair
                 mi -- Miniature Coax
                 tv -- Video Coax
                 m6 -- Multi-mode, 62.5mi
                 m5 -- Multi-mode, 50mi
                 sm -- Single Mode"
     ::= { sfpInfoEntry 9 }

sfpFibreChannelTransmissionSpeed OBJECT-TYPE
     SYNTAX	BITS {
			  unknown(0),
              mbps400(1),
              mbps200(2),
              mbps100(3)
            }
     MAX-ACCESS read-only
     STATUS	current
     DESCRIPTION
       "The fibre channel transmission speed
                 unknown -- Unknown
                 mbps400 -- Twin Axial Pair
                 mbps200 -- Shielded Twisted Pair
                 mbps100 -- Miniature Coax"
     ::= { sfpInfoEntry 10 }

sfpEncoding OBJECT-TYPE
     SYNTAX	INTEGER {
              unknown(1),
              b8b10(2),
              b4b5(3),
              nrz(4),
              manchester(5),
              sonetScrambled(6)
            }
     MAX-ACCESS read-only
     STATUS	current
     DESCRIPTION
       "The type of serial encoding that is the nominal
        design target of the particular SFP transceiver
                 unknown -- Unknown or unspecified
                 b8b10 -- 8B10B
                 b4b5 -- 4B5B
                 nrz -- NRZ
                 manchester -- Manchester,
                 sonetScrambled -- SONET Scrambled"
     ::= { sfpInfoEntry 11 }

sfpBRNominal100Mbps OBJECT-TYPE
     SYNTAX	Integer32
	 UNITS  "100 Megabits per second (Mbps)"
     MAX-ACCESS read-only
     STATUS	current
     DESCRIPTION
       "The nominal bit rate(BR, nominal) which is specified in unitd of 100mbps, 
        rounded off to the nearest 100 Mbps. The bit rate includes those bits necessary 
        to encode and delimit the signal as well as those bits carrying data information. 
        A value of 0 indicates that the bit rate is not specified and must be determined 
        from the tranceiver technology. The actual information transfer rate will depend 
        on the encoding of the data, as defined by the encoding value."
     ::= { sfpInfoEntry 12 }

sfpLength9MiKm OBJECT-TYPE
     SYNTAX	Integer32
	 UNITS  "Kilometer(Km)"
     MAX-ACCESS read-only
     STATUS	current
     DESCRIPTION
       "The link length that is supported by the sfp transceiver while operating 
        in compliance with applicable standards using single mode fibre (9 micron).
        The value is in units of kilometers. A value of 255 means that the sfp 
        transceiver supports a link length greater than 254 Km.  A value of 0 
        means that the transceiver does not support single mode fibre (9 micron) 
        or that the length information must be determined from the transceiver technology"
     ::= { sfpInfoEntry 13 }

sfpLength9Mi100M  OBJECT-TYPE
     SYNTAX	Integer32
	 UNITS  "100 Meters(M)"
     MAX-ACCESS read-only
     STATUS	current
     DESCRIPTION
       "The link length that is supported by the sfp transceiver while operating in 
        compliance with applicable standards using single mode fibre (9 micron).The 
        value is in units of 100 meters. A value of 255 means that the sfp transceiver 
        supports a link length greater than 25.4 Km.  A value of 0 means that the 
        transceiver does not support single mode fibre (9 micron) or that the length 
        information must be determined from the transceiver technology"
     ::= { sfpInfoEntry 14 }

sfpLength50Mi10M  OBJECT-TYPE
     SYNTAX	Integer32
	 UNITS  "10 Meters(M)"
     MAX-ACCESS read-only
     STATUS	current
     DESCRIPTION
       "The link length that is supported by the sfp transceiver while operating in 
        compliance with applicable standards using multi-mode fibre (50 micron).
        The value is in units of 10 meters. A value of 255 means that the sfp transceiver 
        supports a link length greater than 2.54 Km.  A value of 0 means that the 
        transceiver does not support multi-mode fibre (50 micron) or that the length 
        information must be determined from the transceiver technology"
     ::= { sfpInfoEntry 15 }

sfpLength62Pt5Mi10M  OBJECT-TYPE
     SYNTAX	Integer32
	 UNITS  "10 Meters(M)"
     MAX-ACCESS read-only
     STATUS	current
     DESCRIPTION
       "The link length that is supported by the sfp transceiver while operating in 
        compliance with applicable standards using multi-mode fibre (62.5 micron).
        The value is in units of 10 meters. A value of 255 means that the sfp transceiver 
        supports a link length greater than 2.54 Km.  A value of 0 means that the 
        transceiver does not support multi-mode fibre (62.5 micron) or that the length 
        information must be determined from the transceiver technology"
     ::= { sfpInfoEntry 16 }

sfpLengthCopperM OBJECT-TYPE
     SYNTAX	Integer32
	 UNITS  "1 Meter(M)"
     MAX-ACCESS read-only
     STATUS	current
     DESCRIPTION
       "The link length that is supported by the sfp transceiver while operating 
        in compliance with applicable standards using copper cable. The value is in 
        units of 1 meters. A value of 255 means that the sfp transceiver supports a 
        link length greater than 254 meters. A value of 0 means that the transceiver 
        does not support copper cables or that the length information must be 
        determined from the transceiver technology"
     ::= { sfpInfoEntry 17 }

sfpVendorName OBJECT-TYPE
     SYNTAX	DisplayString (SIZE(0..16))
     MAX-ACCESS read-only
     STATUS	current
     DESCRIPTION
       "The sfp vendor name which is essentially the full name of the corporation, 
        a commonly accepted abbreviation of the name of the corporation, the SCSI 
        company code for the corporation, or the stock exchange code for the corporation."
     ::= { sfpInfoEntry 18 }

sfpVendorOUI OBJECT-TYPE
     SYNTAX	 OCTET STRING (SIZE(3))
     MAX-ACCESS read-only
     STATUS	current
     DESCRIPTION
       "The sfp vendor organizationally unique identifier field (vendor OUI) that 
        contains the IEEE company identifier for the vendor. A value of all zero in 
        the 3 octet field indicates that the vendor OUI is unspecified"
     ::= { sfpInfoEntry 19 }

sfpVendorPN OBJECT-TYPE
     SYNTAX	DisplayString (SIZE(0..16))
     MAX-ACCESS read-only
     STATUS	current
     DESCRIPTION
       "The sfp vendor part number (Vendor PN) or product name if the Vendor PN is 
        unspecified, the null string {0, 0} will be returned"
     ::= { sfpInfoEntry 20 }

sfpVendorSN OBJECT-TYPE
     SYNTAX	DisplayString (SIZE(0..16))
     MAX-ACCESS read-only
     STATUS	current
     DESCRIPTION
       "The sfp vendor serial number (Vendor SN) if the Vendor SN is unspecified, 
        the null string {0, 0} will be returned"
     ::= { sfpInfoEntry 21 }

sfpVendorRev OBJECT-TYPE
     SYNTAX	DisplayString (SIZE(0..4))
     MAX-ACCESS read-only
     STATUS	current
     DESCRIPTION
       "The sfp vendor product revision number (Vendor Rev) 
        if the Vendor Rev is unspecified, the null string {0, 0} will be 
        returned"
     ::= { sfpInfoEntry 22 }

sfpLaserWavelength OBJECT-TYPE
     SYNTAX	Integer32
     UNITS  "Nano Meter(NM)"
     MAX-ACCESS read-only
     STATUS	current
     DESCRIPTION
       "Nominal Transmitter output wavelength at room temperature."
     ::= { sfpInfoEntry 23 }

sfpOptions OBJECT-TYPE
     SYNTAX	BITS {
              unknown(0),
              rateSelect(1),
              txDisable(2),
              txFault(3),
              losNormal(5),
              losInverted(4)
            }
     MAX-ACCESS read-only
     STATUS	current
     DESCRIPTION
       "The options implemented in the SFP transceiver
                 unknown -- Unknown
                 rateSelect -- RATE_SELECT is implemented. 
                               If this bit is not set, no control of pin is required.
                               If this bit is set, then active control if the rate
                               select pin is required.
                               In Both cases, compliance with mlutiple rate standards
                               should be determined by the following objects 
                                    sfpTransceiverComplianceCodes
                                    sfpFibreChannelTransmissionSpeed
                 txDisable -- TX_DISABLE is impelmented and disables the serial output
                 txFault -- TX_FAULT is implemented.
                 losNormal -- loss of signal implemented
                                los high indicates the received optical power is below the 
                                worst case receiver sensitivity (as defined by the standard
                                in use.
                                los low indicates normal operation
                 losInverted -- loss of signal implemented
                                los low indicates the received optical power is below the 
                                worst case receiver sensitivity (as defined by the standard
                                in use.
                                los high indicates normal operation"
     ::= { sfpInfoEntry 24 }
       
sfpBRMin OBJECT-TYPE
     SYNTAX	Integer32
	 UNITS  "percent below sfpBRNominal"
     MAX-ACCESS read-only
     STATUS	current
     DESCRIPTION
       "The lower bit rate limit at which the SFP transceiver will meet its
        specifications (BR, min) is specified in units of 1% below the nominal
        bit rate. A value of zero indicates that this field is not specified."
     ::= { sfpInfoEntry 25 }

sfpBRMax OBJECT-TYPE
     SYNTAX	Integer32
	 UNITS  "percent above sfpBRNominal"
     MAX-ACCESS read-only
     STATUS	current
     DESCRIPTION
       "The upper bit rate limit at which the SFP transceiver will meet its
        specifications (BR, max) is specified in units of 1% above the nominal
        bit rate. A value of zero indicates that this field is not specified."
     ::= { sfpInfoEntry 26 }

sfpVendorDate OBJECT-TYPE
     SYNTAX	DateAndTime
     MAX-ACCESS read-only
     STATUS	current
     DESCRIPTION
       "The Vendors date"
     ::= { sfpInfoEntry 27 }

sfpVendorSpecificLotCode OBJECT-TYPE
     SYNTAX	OCTET STRING (SIZE(2))
     MAX-ACCESS read-only
     STATUS	current
     DESCRIPTION
       "The Vendor Specific Lot code. A value of {0, 0} indicates that
        the lot code is unspecified"
     ::= { sfpInfoEntry 28 }

sfpVendorSpecificData OBJECT-TYPE
     SYNTAX	OCTET STRING (SIZE(0..32))
     MAX-ACCESS read-only
     STATUS	current
     DESCRIPTION
       "Vendor Specific Information which can be read from the SFP transceiver"
     ::= { sfpInfoEntry 29 }

sfpStatusCurrent OBJECT-TYPE
     SYNTAX	BITS {
			  unknown(0),
              notInstalled(1),
              installed(2),
              faulty(3),
              operational(4),
              enabled(5),
              disabled(6),
              inValidCCBase(7),
              inValidCCExt(8)
            }
     MAX-ACCESS read-only
     STATUS	current
     DESCRIPTION
       "The current state of the sfp transceiver
                 unknown -- Unknown
                 notInstalled -- the SFP transceiver is not installed
                 installed -- the sfp transceiver has been installed
                 faulty -- the sfp transceiver is faulty
                 operational -- the sfp transceiver is working properly
                 enabled -- the sfp transceiver has been enabled
                 disabled -- the sfp transceiver has been diabled,
                 invalidCCBase -- indicates that the first 64 bytes
                                  of serial information in the SFP 
                                  transceiver is invalid. The check is done by
                                  comparing the 64-th byte with the sum of the contents
                                  of the first 63 bytes (bytes 0 to 62, inclusive).
                 invalidCCExt -- indicates that the first 32 bytes of the extended
                                  serial information in the SFP tranceiver is invalid.
                                  The check is done by comparing theu 95-th byte with the
                                  sum of the contents of the first 32 bytes 
                                  (bytes 64 to 94, inclusive)."
     ::= { sfpInfoEntry 30 }

sfpCommandTable OBJECT-TYPE
       SYNTAX SEQUENCE OF SfpCommandEntry
       MAX-ACCESS not-accessible
       STATUS current
       DESCRIPTION
         "The sfp command table."
       ::= { sfpMIBObjects 3 }

sfpCommandEntry OBJECT-TYPE
     SYNTAX	SfpCommandEntry
     MAX-ACCESS not-accessible
     STATUS current
     DESCRIPTION
       "An entry in the SFP Command Table"
     INDEX { ifIndex }
     ::= { sfpCommandTable 1 }

SfpCommandEntry ::= SEQUENCE {
       sfpCommand INTEGER
    }

sfpCommand OBJECT-TYPE
     SYNTAX INTEGER {
                 noCmd(1),
                 enable(2),
                 disable(3),
                 reset(4)
     }
     MAX-ACCESS read-write
     STATUS	current
     DESCRIPTION
       "This Object specifies the command to be applied to the sfp transceiver
        associated with a physical interface
                 noCmd -- no command has been issued to this sfp device
                 enable -- enables the sfp device 
                 disable -- disables the sfp device 
                 reset -- resets the sfp device
        when read the last command issued to the sfp device will be returned or
        noCmd will be returned if a command has not been issued yet"
     ::= { sfpCommandEntry 1 }

sfpNotificationEnable OBJECT-TYPE
     SYNTAX	BITS {
             faulty(0),
             operational(1),
             inserted(2),
             removed(3)
     }
     MAX-ACCESS read-write
     STATUS	current
     DESCRIPTION
       "Provides the ability to enable and disable notifications defined
        in this mib
             faulty
                 indicates sfpEventFaulty notifications should be generated 
                 when the sfp is detected as being faulty
             operational
                 indicates sfpEventOperational notifications should be generated 
                 when the sfp is detected as being working properly
             inserted
                 indicates sfpEventInserted notifications should be generated when 
                 the sfp is insreted into a physical port
             removed
                 indicates sfpEventRemoved notifications should be generated when the 
                 sfp is removed from a physical port"
     DEFVAL { { } }
     ::= { sfpMIBObjects 4 }

------------------------------------------
-- SFP Notifications
------------------------------------------

sfpNotificationsPrefix OBJECT IDENTIFIER
     ::= { sfpMIBNotifications 0 }


sfpEventFaulty NOTIFICATION-TYPE
     OBJECTS { sfpStatusCurrent }
     STATUS current
     DESCRIPTION
     "The sfpEventFaulty notification is sent when the sfp 
      associated with a physical port is detected as being faulty"
     ::= { sfpNotificationsPrefix  1 }

sfpEventOperational NOTIFICATION-TYPE
     OBJECTS { sfpStatusCurrent }
     STATUS current
     DESCRIPTION
     "The sfpEventOperational notification is sent when the sfp 
      associated with a physical port is detected as being working 
      normally"
     ::= { sfpNotificationsPrefix  2 }

sfpEventInserted NOTIFICATION-TYPE
     OBJECTS { sfpStatusCurrent }
     STATUS current
     DESCRIPTION
     "The sfpEventInserted notification is sent when the sfp is inserted 
      into a physical port"
     ::= { sfpNotificationsPrefix  3 }

sfpEventRemoved NOTIFICATION-TYPE
     OBJECTS { sfpStatusCurrent }
     STATUS current
     DESCRIPTION
     "The sfpEventRemoved notification is sent when the sfp is removed 
      from a physical port"
     ::= { sfpNotificationsPrefix  4 }

------------------------------------------
-- Conformance information
------------------------------------------

sfpGroups OBJECT IDENTIFIER ::= { sfpMIBConformance 1 }
sfpCompliances OBJECT IDENTIFIER ::= { sfpMIBConformance 2 }

sfpReadWriteCompliance MODULE-COMPLIANCE
     STATUS  current
     DESCRIPTION
         "Compliance statement configuring the sfp device."
     MODULE

     GROUP sfpCommandGroup
     DESCRIPTION
       "Implementation of this group is optional for all
        sfp implmentations"
     
     GROUP sfpNotificationsGroup
     DESCRIPTION
       "Implementation of this group is optional for all
        sfp implmentations"
 ::= { sfpCompliances 1 }

sfpReadOnlyCompliance MODULE-COMPLIANCE
     STATUS  current
     DESCRIPTION
         "Compliance statement reading the SFP information."
     MODULE
     MANDATORY-GROUPS { sfpMIBObjectsGroup, sfpInformationGroup }
 ::= { sfpCompliances 2 }

sfpNotificationCompliance MODULE-COMPLIANCE
     STATUS  current
     DESCRIPTION
         "Compliance statement sfp device notifications."
     MODULE

     GROUP sfpEventGroup
     DESCRIPTION
       "Implementation of this group is optional for all
        sfp implmentations"
 ::= { sfpCompliances 3 }

--
-- Units of Conformance
--

sfpMIBObjectsGroup OBJECT-GROUP
    OBJECTS {
       sfpCompatibleInterfaceCount
    }
    STATUS  current
    DESCRIPTION
      "A collection of scalar objects in section sfpMIBObjects 
       providing information about sfp compatible intefaces"
    ::= { sfpGroups 1 }

sfpInformationGroup OBJECT-GROUP
   OBJECTS {
       sfpIdentifier,
       sfpVendorSpecificIdentifier,
       sfpExtIdentifier,
       sfpConnector, 
       sfpVendorSpecificConnector,
       sfpTransceiverComplianceCodes,
       sfpFibreChannelLinkLength,
       sfpFibreChannelTransmitterTechnology,
       sfpFibreChannelTransmissionMedia,
       sfpFibreChannelTransmissionSpeed,
       sfpEncoding,
       sfpBRNominal100Mbps,
       sfpLength9MiKm,
       sfpLength9Mi100M,
       sfpLength50Mi10M,
       sfpLength62Pt5Mi10M,
       sfpLengthCopperM,
       sfpVendorName,
       sfpVendorOUI,
       sfpVendorPN,
       sfpVendorSN,
       sfpVendorRev,
       sfpLaserWavelength,
       sfpOptions,
       sfpBRMin,
       sfpBRMax,
       sfpVendorDate,
       sfpVendorSpecificLotCode,
       sfpVendorSpecificData,
       sfpStatusCurrent
    }
    STATUS  current
    DESCRIPTION
      "A collection of sfpInfoTable objects providing
       information applicable to sfp transceivers."
    ::= { sfpGroups 2 }

sfpCommandGroup OBJECT-GROUP
    OBJECTS {
      sfpCommand
    }
    STATUS  current
    DESCRIPTION
       "A collection of sfpCommandTable objects providing
        a way to issue commands to an sfp transceiver."
    ::= { sfpGroups 3 }

sfpNotificationsGroup OBJECT-GROUP
    OBJECTS {
        sfpNotificationEnable
    }
    STATUS  current
    DESCRIPTION
      "A collection of scalar objects in section sfpMIBObjects 
       to enable/disable notifications sent by the agent"
    ::= { sfpGroups 4 }


sfpEventGroup NOTIFICATION-GROUP
    NOTIFICATIONS {
        sfpEventFaulty,
        sfpEventOperational,
        sfpEventInserted,
        sfpEventRemoved 
    }
    STATUS  current
    DESCRIPTION
      "A collection of sfp notifications"
    ::= { sfpGroups 5 }

END

PDN-DS1EXT-MIB DEFINITIONS ::= BEGIN

-------------------------------------------------------------------
--	Copyright (C) 2002, Paradyne. All rights reserved.
--
--	This MIB is an extension to the standard DS1 MIB (rfc2495).
-------------------------------------------------------------------

IMPORTS
	MODULE-IDENTITY, OBJECT-TYPE
	    FROM SNMPv2-SMI
	ifIndex
	    FROM IF-MIB
	MODULE-COMPLIANCE, OBJECT-GROUP
	    FROM SNMPv2-CONF
	ent-ds1
	    FROM PDN-HEADER-MIB;
	
pdnDs1Ext  MODULE-IDENTITY
	    LAST-UPDATED "200204050000Z"
	    ORGANIZATION "Paradyne Corp MIB Working Group"
	    CONTACT-INFO "Paradyne Networks, Inc.
			  8545, 126th Ave. N.,
			  Largo, FL 33779
			  www.paradyne.com

			  General Comments to:
			    mibwg_team@paradyne.com

			  Editors: Vic Sperry" 

	    DESCRIPTION 
               "The Paradyne enterprise DS1/G.703 extension MIB.
                This MIB provides additional DS1 and G.703 (E1) configuration
                objects not provided by rfc2495."

	    ::= { ent-ds1 5 }

pdnDs1ExtObjects  OBJECT IDENTIFIER ::= { pdnDs1Ext 1 }

--
-- START OF pdnDs1Ext mib definitions
--

pdnDs1ExtConfTable OBJECT-TYPE
     SYNTAX	 SEQUENCE OF PdnDs1ExtConfEntry
     MAX-ACCESS  not-accessible
     STATUS  	 current
     DESCRIPTION
	"The Paradyne DS1/G.703 extension configuration table.
	 This table is used for configuring extensions to DS1
         and G.703 interfaces."
	::= { pdnDs1ExtObjects 1 }

pdnDs1ExtConfEntry OBJECT-TYPE
     SYNTAX	 PdnDs1ExtConfEntry
     MAX-ACCESS  not-accessible
     STATUS  	 current
     DESCRIPTION
	"An entry in the Paradyne DS1/G.703 extension configuration table.
         Note: The objects used depend on the type of interface.

         For DS1: use pdnDs1ExtConfLineLengthType and one of
                      (pdnDs1ExtConfLineLength or pdnDs1ExtConfLineBuildOut)

         For G.703: use pdnDs1ExtConfLineLengthType and pdnDs1ExtConfConnector
        "
    INDEX   { ifIndex }
    ::= { pdnDs1ExtConfTable 1 }

PdnDs1ExtConfEntry ::=
     SEQUENCE {
     pdnDs1ExtConfLineLengthType   INTEGER,
     pdnDs1ExtConfLineLength       INTEGER,
     pdnDs1ExtConfLineBuildOut     INTEGER,
     pdnDs1ExtConfConnector        INTEGER
     }

pdnDs1ExtConfLineLengthType OBJECT-TYPE
     SYNTAX  	INTEGER {
		  shortHaul(1),
		  longHaul(2)
     }
     MAX-ACCESS read-write
     STATUS	current
     DESCRIPTION
	"This entry specifies the type of loop length for the interface.
         short-haul is intended for intra-building use.
         long-haul is intended for inter-building use."

     DEFVAL { longHaul }
     ::= { pdnDs1ExtConfEntry 1 }

pdnDs1ExtConfLineLength OBJECT-TYPE
     SYNTAX  	INTEGER {
		  feet000To133(1),
		  feet134To266(2),
		  feet267To399(3),
		  feet400To533(4),
		  feet534To655(5)
     }
     MAX-ACCESS read-write
     STATUS	current
     DESCRIPTION
	"This entry specifies the loop length, in feet, for a short-haul
         DS1 line. This object only applies to DS1 interfaces.
	 Note: This object shares a mutually exclusive relationship 
	 with the pdnDs1ExtConfLineBuildOut object i.e. only one of the
         two can be used for configuration at one time, based on the
         pdnDs1ExtConfLineLengthType object."
     DEFVAL { feet000To133 }
     ::= { pdnDs1ExtConfEntry 2 }

pdnDs1ExtConfLineBuildOut OBJECT-TYPE
     SYNTAX  	INTEGER {
		  dB0Pnt0(1),
		  dB7Pnt5(2),
		  dB15Pnt0(3),
		  dB22Pnt5(4)
     }
     MAX-ACCESS read-write
     STATUS	current
     DESCRIPTION
	"This entry specifies the line build out, in decibels, for a
         long-haul DS1 line.
         dB0Pnt0  = 0.0 dB         
         dB7Pnt5  = -7.5 dB         
         dB15Pnt0 = -15.0 dB         
         dB22Pnt5 = -22.5 dB         
         This object only applies to DS1 interfaces.
	 Note: This object shares a mutually exclusive relationship 
	 with the pdnDs1ExtConfLineLength object i.e. only one of the
         two can be used for configuration at one time, based on the
         pdnDs1ExtConfLineLengthType object."
     DEFVAL { dB0Pnt0 }
     ::= { pdnDs1ExtConfEntry 3 }

pdnDs1ExtConfConnector OBJECT-TYPE
     SYNTAX  	INTEGER {
		  bnc(1),
		  rj48(2)
     }
     MAX-ACCESS read-write
     STATUS	current
     DESCRIPTION
	"This entry specifies the type of connector to be used.
         This object only applies to G.703 interfaces.

         bnc: 75-Ohm connector supporting only short-haul.
         rj48: 120-Ohm connector supporting both short-haul and long-haul."

     DEFVAL { rj48 }
     ::= { pdnDs1ExtConfEntry 4 }

------------------------------------------
-- Conformance information
------------------------------------------

pdnDs1ExtConformance OBJECT IDENTIFIER ::= { pdnDs1Ext 2 }
pdnDs1ExtGroups      OBJECT IDENTIFIER ::= { pdnDs1ExtConformance 1 }
pdnDs1ExtCompliances OBJECT IDENTIFIER ::= { pdnDs1ExtConformance 2 }

pdnDs1ExtCompliance MODULE-COMPLIANCE
     STATUS  current
     DESCRIPTION
         "Compliance statement for using this MIB for configuring
          DS1 interfaces."
     MODULE  -- this module

         GROUP       pdnDs1ExtT1ConfigGroup
         DESCRIPTION
             "Implementation of this group is required for systems
              wishing to conform to this MIB for the purposes of
              configuring a DS1 interface."

         OBJECT     pdnDs1ExtConfLineLengthType
         MIN-ACCESS read-only
         DESCRIPTION
             "The ability to set pdnDs1ExtConfLineLengthType is not required."

         OBJECT     pdnDs1ExtConfLineLength
         MIN-ACCESS read-only
         DESCRIPTION
             "The ability to set pdnDs1ExtConfLineLength is not required."

         OBJECT     pdnDs1ExtConfLineBuildOut
         MIN-ACCESS read-only
         DESCRIPTION
             "The ability to set pdnDs1ExtConfLineBuildOut is not required."

 ::= { pdnDs1ExtCompliances 1 }


pdnDs1ExtG703Compliance MODULE-COMPLIANCE
     STATUS  current
     DESCRIPTION
         "Compliance statement for using this MIB for configuring
          G.703 interfaces."
     MODULE  -- this module

         GROUP       pdnDs1ExtE1ConfigGroup
         DESCRIPTION
             "Implementation of this group is required for systems
              wishing to conform to this MIB for the purposes of
              configuring a G.703 interface."

         OBJECT     pdnDs1ExtConfLineLengthType
         MIN-ACCESS read-only
         DESCRIPTION
             "The ability to set pdnDs1ExtConfLineLengthType is not required."

         OBJECT     pdnDs1ExtConfConnector
         MIN-ACCESS read-only
         DESCRIPTION
             "The ability to set pdnDs1ExtConfConnector is not required."

 ::= { pdnDs1ExtCompliances 2 }


--
-- Units of Conformance
--

pdnDs1ExtT1ConfigGroup OBJECT-GROUP
	OBJECTS {
           pdnDs1ExtConfLineLengthType,
           pdnDs1ExtConfLineLength,
           pdnDs1ExtConfLineBuildOut
        }
	STATUS  current -- Set as required for the group
	DESCRIPTION 
	   "A collection of configuration objects required 
	    for configuring a T1 interface."

	::= { pdnDs1ExtGroups 1 }

pdnDs1ExtE1ConfigGroup OBJECT-GROUP
	OBJECTS {
           pdnDs1ExtConfLineLengthType,
           pdnDs1ExtConfConnector
        }
	STATUS  current -- Set as required for the group
	DESCRIPTION 
	   "A collection of configuration objects required 
	    for configuring a G.703 (E1) interface."

	::= { pdnDs1ExtGroups 2 }
END

PDN-MPD-EXT-MIB DEFINITIONS ::= BEGIN

IMPORTS
    MODULE-IDENTITY, OBJECT-TYPE
        FROM SNMPv2-SMI
    TEXTUAL-CONVENTION
        FROM SNMPv2-TC
    pdnMpdExt
        FROM PDN-HEADER-MIB
    MODULE-COMPLIANCE, OBJECT-GROUP
        FROM SNMPv2-CONF;

pdnMpdExtMIB MODULE-IDENTITY
    LAST-UPDATED "200304081900Z"
    ORGANIZATION "Paradyne Corporation MIB Working Group"
    CONTACT-INFO
            "         Paradyne Networks Inc.

             Postal:  8545, 126th Ave. N.
                      Largo, FL 33779
                      US
             Editor:  Jesus Pinto
             Email:   mibwg_team@eng.paradyne.com"

    DESCRIPTION
            "This management information module supports the objects
             that extend the Message Processing Dispatcher mib as
	     described in rfc3412_std62_a.mib."

    ::= { pdnMpdExt 1 }

pdnMpdExtMIBObjects OBJECT IDENTIFIER ::= 
	{ pdnMpdExtMIB 1 }

pdnMpdExtMIBConformance OBJECT IDENTIFIER ::= 
	{ pdnMpdExtMIB 2 }

PdnMpdExtSecurityMode ::= TEXTUAL-CONVENTION
             STATUS       current
             DESCRIPTION
                  "A set of combinations of Model and SecurityLevel
		   that can be supported by an agent. An agent can
		   support more than a single combination at once.

                     Bit 0 : None.
				- SNMP access is not allowed.

                     Bit 1 : SNMPv1, noAuthNoPriv.
				- SNMPv1 access is allowed with
				- no auth and no privacy.

				- Only Security checking based on
				  community names is performed.

                     Bit 2 : SNMPv2c, no AuthNoPriv.
				- SNMPv2c access is allowed with
				- no auth and no privacy.

				- Only Security checking based on
				  community names is performed.

                     Bit 3 : SNMPv3, noAuthNoPriv.
				- SNMPv3 access is allowed with
				- no auth and no privacy.

                     Bit 4 : SNMPv3, AuthNoPriv.
				- SNMPv3 access is allowed with
				- authentication and no privacy.

                     Bit 5 : SNMPv3, AuthPriv.
				- SNMPv3 access is allowed with
				- authentication and privacy.
                  "
              SYNTAX      BITS {
                  none(0),
                  snmpv1NoAuthNoPriv(1),
                  snmpv2cNoAuthNoPriv(2),
                  snmpv3NoAuthNoPriv(3),
		  snmpv3AuthNoPriv(4),
		  snmpv3AuthPriv(5)
              }

pdnMpdExtSecurityModeConfig OBJECT-TYPE
    SYNTAX      PdnMpdExtSecurityMode
    MAX-ACCESS  read-write
    STATUS      current
    DESCRIPTION
            "This object is used to configure the level of SNMP
	     access that the agent supports. That is, which
	     combinations of Model Processing can be dispatched
	     and what security levels are supported for those models.

	     An agent can choose to support more than a single 
	     combination of modes, (e.g., SNMPv1 and SNMPv2 with
	     noAuthNoPriv) or choose to support a single option
	     (e.g., a very secured agent with only SNMPv3 with
             authentication and privacy enabled.). Even some of
	     these combinations may not be supported at all.

	     Setting this object to a valid value will cause 
	     the entries associated with those Models and
	     SecurityLevels being changed to become active/inactive
	     in tables processed by the SNMPv3 Framework.
	    "

    ::= { pdnMpdExtMIBObjects 1 }

--
-- Conformance Information
--

pdnMpdExtCompliances OBJECT IDENTIFIER
     ::= { pdnMpdExtMIBConformance 1 }

pdnMpdExtGroups OBJECT IDENTIFIER
     ::= { pdnMpdExtMIBConformance 2 }

pdnMpdExtCompliance MODULE-COMPLIANCE
     STATUS  current
     DESCRIPTION
             "The compliance statement for MPD extension mib."
     MODULE -- this module
     MANDATORY-GROUPS
	{
	pdnMpdExtGroup
	}

     OBJECT pdnMpdExtSecurityModeConfig
     MIN-ACCESS read-only
     DESCRIPTION
	     "Write access is not required."


     ::= { pdnMpdExtCompliances 1 }

-- units of conformance

pdnMpdExtGroup	OBJECT-GROUP
     OBJECTS
     {
	pdnMpdExtSecurityModeConfig
     }
     STATUS current
     DESCRIPTION
             "A collection of configuration objects applicable
              to MPD extention."
     ::= { pdnMpdExtGroups 1 }

END

PDN-LINK-FAULT-MGMT-MIB DEFINITIONS ::= BEGIN

IMPORTS
    MODULE-IDENTITY, OBJECT-TYPE,
    Integer32
        FROM SNMPv2-SMI
    ifIndex
        FROM RFC1213-MIB
    pdnLinkFaultMgmt
        FROM PDN-HEADER-MIB
    MODULE-COMPLIANCE, OBJECT-GROUP
        FROM SNMPv2-CONF;

pdnLinkFaultMgmtMIB MODULE-IDENTITY
    LAST-UPDATED "200304031900Z"
    ORGANIZATION "Paradyne Corporation MIB Working Group"
    CONTACT-INFO
            "         Paradyne Networks Inc.

             Postal:  8545, 126th Ave. N.
                      Largo, FL 33779
                      US
             Editor:  Jesus Pinto
             Email:   mibwg_team@eng.paradyne.com"

    DESCRIPTION
            "This management information module supports the objects
             to be used for fault management configuration on primary
	     and secondary links."

   REVISION "200304231800Z"  -- April 23, 2003
   DESCRIPTION "- Added pdnLinkFailureSfPeriodBeforeSwitching object,
		- Added pdnLinkFailureSfBerThreshold object."

    ::= { pdnLinkFaultMgmt 1 }

pdnLinkFaultMgmtMIBObjects OBJECT IDENTIFIER ::= 
	{ pdnLinkFaultMgmtMIB 1 }

pdnLinkFaultMgmtMIBConformance OBJECT IDENTIFIER ::= 
	{ pdnLinkFaultMgmtMIB 2 }

pdnLinkFaultMgmtApsSelection OBJECT-TYPE
    SYNTAX      INTEGER { enabled(1), disabled(2) }
    MAX-ACCESS  read-write
    STATUS      current
    DESCRIPTION
            "This object is used to enable or disable the
	     Automatic Protection Switching (Aps) feature
	     on this device. This object can not be enabled
	     if the -Switchover due to link failures- is enabled."
    ::= { pdnLinkFaultMgmtMIBObjects 1 }

pdnLinkFaultMgmtSwitchoverSelection OBJECT-TYPE
    SYNTAX      INTEGER { enabled(1), disabled(2) }
    MAX-ACCESS  read-write
    STATUS      current
    DESCRIPTION
            "This object is used to enable or disable the
	     Switchover Due to link failures feature on 
	     on this device. This object can not be enabled
	     if the APS feature is enabled."
    ::= { pdnLinkFaultMgmtMIBObjects 2 }

pdnDualLinkSelection OBJECT-TYPE
    SYNTAX      INTEGER { enabled(1), disabled(2) }
    MAX-ACCESS  read-write
    STATUS      current
    DESCRIPTION
            "This object is used to enable or disable the
	     ability to split traffic among dual links."
    ::= { pdnLinkFaultMgmtMIBObjects 4 }


--
-- Switchover due to Link Failure
--
-- This set of objects are used to configure the
-- conditions and thresholds in the primary link
-- before initiating a switchover to the alternate link.
-- 
--

pdnLinkFailureConfigTable OBJECT-TYPE
    SYNTAX	SEQUENCE OF PdnLinkFailureConfigEntry
    MAX-ACCESS  not-accessible
    STATUS	current
    DESCRIPTION 
	    "This table contains one row per link
	     being monitored for link failures."
    ::= { pdnLinkFaultMgmtMIBObjects 3 }

pdnLinkFailureConfigEntry OBJECT-TYPE
    SYNTAX      PdnLinkFailureConfigEntry
    MAX-ACCESS  not-accessible
    STATUS      current
    DESCRIPTION
            "Configuration information about a particular
             interface being monitored for link failured."
    INDEX   { ifIndex }
    ::= { pdnLinkFailureConfigTable 1 }

PdnLinkFailureConfigEntry ::=
    SEQUENCE {
	pdnLinkFailureLOSPeriodBeforeSwitching	Integer32,
        pdnLinkFailureLOFPeriodBeforeSwitching	Integer32,
	pdnLinkFailureAISLPeriodBeforeSwitching	Integer32,
	pdnLinkFailureSdPeriodBeforeSwitching	Integer32,
	pdnLinkFailureSfPeriodBeforeSwitching	Integer32,
	pdnLinkFailureSdBerThreshold		Integer32,
	pdnLinkFailureSfBerThreshold		Integer32
    }

pdnLinkFailureLOSPeriodBeforeSwitching OBJECT-TYPE
    SYNTAX      Integer32 (0..300)
    UNITS	"seconds"
    MAX-ACCESS  read-write
    STATUS      current
    DESCRIPTION
            "This object allows users to configure the amount of
             time a LOS condition shall exist on this uplink before
             initiating a switchover.

	     Switchover due to LOS condition on this uplink will
             not be valid if any of the APS (Automatic Protection
             Switching) is enabled."
    ::= { pdnLinkFailureConfigEntry 1 }


pdnLinkFailureLOFPeriodBeforeSwitching OBJECT-TYPE
    SYNTAX      Integer32 (0..300)
    UNITS	"seconds"
    MAX-ACCESS  read-write
    STATUS      current
    DESCRIPTION
            "This object allows users to configure the amount of
             time a LOF condition shall exist on this uplink before
             initiating a switchover.

	     Switchover due to LOF condition on this uplink will
             not be valid if any of the APS (Automatic Protection
             Switching) is enabled."
    ::= { pdnLinkFailureConfigEntry 2 }

pdnLinkFailureAISLPeriodBeforeSwitching OBJECT-TYPE
    SYNTAX      Integer32 (0..300)
    UNITS	"seconds"
    MAX-ACCESS  read-write
    STATUS      current
    DESCRIPTION
            "This object allows users to configure the amount of
             time a AIS-L condition shall exist on this uplink before
             initiating a switchover.

	     Switchover due to AIS-L condition on this uplink will
             not be valid if any of the APS (Automatic Protection
             Switching) is enabled."
    ::= { pdnLinkFailureConfigEntry 3 }

pdnLinkFailureSdPeriodBeforeSwitching OBJECT-TYPE
    SYNTAX      Integer32 (0..300)
    UNITS	"seconds"
    MAX-ACCESS  read-write
    STATUS      current
    DESCRIPTION
            "This object allows users to configure the amount of
             time a Signal Degraded (Sd) condition shall exist on
	     this uplink before initiating a switchover.

	     Switchover due to Sd condition on this uplink will
             not be valid if any of the APS (Automatic Protection
             Switching) is enabled."
    ::= { pdnLinkFailureConfigEntry 4 }

pdnLinkFailureSfPeriodBeforeSwitching OBJECT-TYPE
    SYNTAX      Integer32 (0..300)
    UNITS	"seconds"
    MAX-ACCESS  read-write
    STATUS      current
    DESCRIPTION
            "This object allows users to configure the amount of
             time a Signal Failure Bit (Sf) condition shall exist on
	     this uplink before initiating a switchover.

	     Switchover due to Sf condition on this uplink will
             not be valid if any of the APS (Automatic Protection
             Switching) is enabled."
    ::= { pdnLinkFailureConfigEntry 5 }


pdnLinkFailureSdBerThreshold OBJECT-TYPE
    SYNTAX      Integer32 (5..9)
    MAX-ACCESS  read-write
    STATUS      current
    DESCRIPTION
            "This object allows users to configure the threshold
             for the Signal Degrade Bit Error Rate (Sd).

	     The negated value of this number is used as the exponent
	     of 10 for computing the threshold value for the Bit Error
	     Rate (BER). For example, a value of 5 indicates a BER
	     threshold of 10^-5."
    ::= { pdnLinkFailureConfigEntry 6 }

pdnLinkFailureSfBerThreshold OBJECT-TYPE
    SYNTAX      Integer32 (3..5)
    MAX-ACCESS  read-write
    STATUS      current
    DESCRIPTION
            "This object allows users to configure the threshold
             for the Signal Failure Bit Error Rate (Sf).

	     The negated value of this number is used as the exponent
	     of 10 for computing the threshold value for the Bit Error
	     Rate (BER). For example, a value of 5 indicates a BER
	     threshold of 10^-5."
    ::= { pdnLinkFailureConfigEntry 7 }


--
-- Conformance Information
--

pdnLinkFaultMgmtCompliances OBJECT IDENTIFIER
     ::= { pdnLinkFaultMgmtMIBConformance 1 }

pdnLinkFaultMgmtGroups OBJECT IDENTIFIER
     ::= { pdnLinkFaultMgmtMIBConformance 2 }

pdnLinkFaultMgmtCompliance MODULE-COMPLIANCE
     STATUS  current
     DESCRIPTION
             "The compliance statement for SNMP entities capable
	      of configuring link fault conditions."
     MODULE
     MANDATORY-GROUPS {	pdnLinkFaultMgmtGeneralGroup }

     OBJECT pdnLinkFaultMgmtApsSelection
     MIN-ACCESS read-only
     DESCRIPTION
	     "Write access is not required."

     OBJECT pdnLinkFaultMgmtSwitchoverSelection
     MIN-ACCESS read-only
     DESCRIPTION
	     "Write access is not required."

     OBJECT pdnDualLinkSelection
     MIN-ACCESS read-only
     DESCRIPTION
	     "Write access is not required."

     OBJECT pdnLinkFailureLOSPeriodBeforeSwitching
     MIN-ACCESS read-only
     DESCRIPTION
	     "Write access is not required."

     OBJECT pdnLinkFailureLOFPeriodBeforeSwitching
     MIN-ACCESS read-only
     DESCRIPTION
	     "Write access is not required."

     OBJECT pdnLinkFailureAISLPeriodBeforeSwitching
     MIN-ACCESS read-only
     DESCRIPTION
	     "Write access is not required."

     OBJECT pdnLinkFailureSdPeriodBeforeSwitching
     MIN-ACCESS read-only
     DESCRIPTION
	     "Write access is not required."

     OBJECT pdnLinkFailureSdBerThreshold
     MIN-ACCESS read-only
     DESCRIPTION
	     "Write access is not required."

     OBJECT pdnLinkFailureSfPeriodBeforeSwitching
     MIN-ACCESS read-only
     DESCRIPTION
	     "Write access is not required."

     OBJECT pdnLinkFailureSfBerThreshold
     MIN-ACCESS read-only
     DESCRIPTION
	     "Write access is not required."

-- Optional groups

     GROUP pdnLinkSwitchoverGroup
     DESCRIPTION
	     "Implementation of this group is optional for the
	      link fault management implementation."

     ::= { pdnLinkFaultMgmtCompliances 1 }

-- units of conformance

pdnLinkFaultMgmtGeneralGroup	OBJECT-GROUP
     OBJECTS
     {
	pdnLinkFaultMgmtApsSelection,
	pdnLinkFaultMgmtSwitchoverSelection,
	pdnDualLinkSelection
     }
     STATUS current
     DESCRIPTION
             "A collection of configuration objects applicable
              to link fault mgmt implementation."
     ::= { pdnLinkFaultMgmtGroups 1 }

pdnLinkSwitchoverGroup OBJECT-GROUP
     OBJECTS
     {
	pdnLinkFailureLOSPeriodBeforeSwitching,
	pdnLinkFailureLOFPeriodBeforeSwitching,
	pdnLinkFailureAISLPeriodBeforeSwitching,
	pdnLinkFailureSdPeriodBeforeSwitching,
	pdnLinkFailureSfPeriodBeforeSwitching,
	pdnLinkFailureSdBerThreshold,
	pdnLinkFailureSfBerThreshold
     }
     STATUS current
     DESCRIPTION
             "A collection of configuration objects applicable to
              all redundancy implementations."
     ::= { pdnLinkFaultMgmtGroups 2 }

END


PDN-ENTITY-REDUNDANCY-MIB DEFINITIONS ::= BEGIN

IMPORTS
    MODULE-IDENTITY, NOTIFICATION-TYPE, OBJECT-TYPE
        FROM SNMPv2-SMI
    TEXTUAL-CONVENTION
        FROM SNMPv2-TC
    entPhysicalIndex
        FROM ENTITY-MIB
    pdnEntityRedundancy
        FROM PDN-HEADER-MIB
    MODULE-COMPLIANCE, OBJECT-GROUP, NOTIFICATION-GROUP
        FROM SNMPv2-CONF;

pdnEntRedunMIB MODULE-IDENTITY
    LAST-UPDATED "200301121100Z"
    ORGANIZATION "Paradyne Corporation MIB Working Group"
    CONTACT-INFO
            "         Paradyne Networks Inc.

             Postal:  8545, 126th Ave. N.
                      Largo, FL 33779
                      US
             Editor:  Jesus Pinto
             Email:   mibwg_team@eng.paradyne.com"

    DESCRIPTION
            "This management information module supports the
             objects to be used for redundancy of entities."

    REVISION "200307251300Z"
    DESCRIPTION "J. Pinto
    		- Added pdnRedunGeneralNotificationEnable.
		- Modified DESCRIPTION for pdnRedunNotificationEnable.
		"

    REVISION "200305221000Z"
    DESCRIPTION "J. Pinto
    		- Fixed spelling name of this mib in line#1
		"

    REVISION "200305041700Z"
    DESCRIPTION "J. Pinto
    		- Removed the word non-critical from the PdnRedunStates.
		- Added pdnYCableSelection scalar object.
		- Added pdnRedunGeneralStatusAlarm scalar object.
	 	- Modified PdnRedunAlarmStatus TEXTUAL-CONVENTION.
		- Added traps for new alarm conditions.
		"

    REVISION "200303031500Z"
    DESCRIPTION "J. Pinto
    		- Modified PdnRedunCmd Textual Convention to add
      		a new forceswitch command."

    ::= { pdnEntityRedundancy 1 }

PdnRedunStates ::= TEXTUAL-CONVENTION
    STATUS 	current
    DESCRIPTION 
        "This textual Convention describes the valid states
         relevant to the redundancy feature that an entity
         module can be.

	 The possibles states are:

	 activeState
         -----------
	 the module is currently performing its main functions
	 in the system, including communicating with other
         modules, monitoring the operation of itself and 
         other standby modules.

	 activeAlarmState
         ----------------
	 the same as an activeState except an Alarm condition 
	 has been detected on the module.

	 standbyState
         ------------
	 the module is primarily in a dormant state until an 
         event is triggered that requires its activation. While
         in this state, the module only performs background tests
	 to verify that its hardware is operating properly and 
         monitor the active module for proper operation.


	 standbyAlarmState
         ----------------
	 the same as an standbyState except a Alarm condition 
	 has been detected on the module."

    SYNTAX	INTEGER {
	           activeState(1),
		   activeAlarmState(2),
		   standbyState(3),
	           standbyAlarmState(4)
		}
	        

PdnRedunCmd ::= TEXTUAL-CONVENTION
    STATUS	current
    DESCRIPTION
	"This list of commands allows an user to perform
         actions on the redundancy entities.

	 The commands are:

	 noCmd
         -----
	 This value should be returned by a read request when no
         previous command has been issue. This value may not be 
	 used in a write operation. A wrongValue error shall be 
	 returned in this case.

	 switch
         ------

	 This is the *Normal* switch.

	 shall be directed to an entity in the Active, 	
         Active/Alarm, Standby or Standby/Alarm state. Will cause an
	 entity and its redundant mate to switch roles unless the 
	 Standby entity is in a failed state or redundancy is disabled.
	 A switch  shall result in the Active or Active/Alarm entity 
	 going into a Standby or Standby/Alarm state and the Standby 
	 or Standby/Alarm entity going into the Active or Active/Alarm 
	 state.

	 forceswitch 
         -----------

	 This is the *Forced* switch.

         shall be directed to an entity in the Active, 
         Active/Alarm, Standby or Standby/Alarm state. Will cause an 
	 entity and its redundant mate to switch roles regardless of 
	 the state of the entities or if redundancy is enabled. A switch
	 shall result in the Active or Active/Alarm entity going into a 
	 Standby or Standby/Alarm state and the Standby or Standby/Alarm
	 entity going into the Active or Active/Alarm state." 

    SYNTAX	INTEGER {
		   noCmd(1),
		   switch(2),
	           forcedswitch(3) 
		}
		

PdnRedunAlarmStatus ::= TEXTUAL-CONVENTION
    STATUS	current
    DESCRIPTION
	"This textual convention lists the possibles alarm status.

	 The status are:

	     noAlarm
	     ---------------------------
	     This is the normal status when there is 
	     no alarm condition.

	     linkDefect
	     ----------------------------
	     This alarm is detected when there is an
	     abnormal condition in the link (e.g., 
	     LOS, LOF, etc.) of this redundant unit.

	     hwFailure
	     ----------------------------
	     This alarm is detected when there is a
	     hardware failure on this redundant unit.

	     hwMissing
	     ----------------------------
	     This alarm is detected when there is
	     an expected piece of hw that is missing
	     on this redundant unit.

	     hwIncompatible
             ----------------------------
	     This alarm is detected when the modules in a
	     redundancy configuration present hardware 
	     incompatibilities.


	     fwIncompatible
             ----------------------------
	     This alarm is detected when the modules in a 
	     redundancy configuration present firmware 
	     incompatibilities.

	     cfgIncompatible
             -----------------------------
	     This alarm is detected when the modules in a 
	     redundancy configuration present configuration
	     incompatibilities."

    SYNTAX      BITS {
		noAlarm(0),
		linkDefect(1),
		hwFailure(2),
		hwMissing(3),
		hwIncompatible(4), 
		fwIncompatible(5),
		cfgIncompatible(6)
		}

PdnRedunGeneralAlarmStatus ::= TEXTUAL-CONVENTION
    STATUS	current
    DESCRIPTION
	"This textual convention lists the possibles alarm status
	 that are general to the redundancy feature; which are not
         associated to a particular redundant module.

	 The status are:

	     noAlarm
             ---------------------------
	     This is the Normal status with no General alarm condition.

	     noActiveModule
	     ---------------------------
	     This alarm is detected when no module is 
	     in the Active State.

	     standbyAlarmOrReset
	     ----------------------------
	     This alarm is detected when on of the modules
	     configured for redundancy is either in the 
	     Standby-Alarm or Reset Test state.
         "

    SYNTAX      BITS {
		noAlarm(0),
		noActiveModule(1),
		standbyAlarmOrReset(2)
		}


pdnEntityRedundancyMIBObjects OBJECT IDENTIFIER ::= 
	{ pdnEntRedunMIB 1 }

pdnEntityRedundancyNotifications OBJECT IDENTIFIER ::= 
	{ pdnEntRedunMIB 2 }

pdnEntityRedundancyConformance OBJECT IDENTIFIER ::= 
	{ pdnEntRedunMIB 3 }


pdnEntityRedundancySelection OBJECT-TYPE
    SYNTAX      INTEGER { enabled(1), disabled(2) }
    MAX-ACCESS  read-write
    STATUS      current
    DESCRIPTION
            "This object is used to enable or disable
	     the redundancy feature on this device."
    ::= { pdnEntityRedundancyMIBObjects 1 }


pdnYCableSelection OBJECT-TYPE
    SYNTAX      INTEGER { enabled(1), disabled(2) }
    MAX-ACCESS  read-write
    STATUS      current
    DESCRIPTION
            "This object is used to configure the
	     Y-cable presence used for tx and rx
	     of data between the redundant units.

	     When the selection is enabled (1), it
	     indicates that the tx and rx signals
	     of each redundant unit are sharing
	     a single common pair to tx and rx 
	     data to the network.

	     When the selection is disable (2), it
	     indicates that the tx and rx signals
	     of each redundant unit has a separate
	     (independant) pair to tx and rx data 
	     to the network.
	    "
    ::= { pdnEntityRedundancyMIBObjects 2 }

pdnRedunGeneralAlarmStatus OBJECT-TYPE
    SYNTAX      PdnRedunGeneralAlarmStatus
    MAX-ACCESS  read-only
    STATUS      current
    DESCRIPTION
            "This object provides status of any General 
	     Alarm detected by the redundancy feature.
	    "
    ::= { pdnEntityRedundancyMIBObjects 3 }

pdnRedunGeneralNotificationEnable OBJECT-TYPE
    SYNTAX      PdnRedunGeneralAlarmStatus
    MAX-ACCESS  read-write
    STATUS      current
    DESCRIPTION
            "This object provides the ability to enable and
	     disable the following general notifications:

		o pdnRedunEventNoActiveModule
		o pdnRedunEventStandbyAlarmOrReset

	    "
    ::= { pdnEntityRedundancyMIBObjects 6 }

--
-- Command Table
--

pdnRedunCmdTable OBJECT-TYPE
    SYNTAX	SEQUENCE OF PdnRedunCmdEntry
    MAX-ACCESS  not-accessible
    STATUS	current
    DESCRIPTION 
	    "This table contains one row per entity
             module being used for redundancy."
    ::= { pdnEntityRedundancyMIBObjects 4 }

pdnRedunCmdEntry OBJECT-TYPE
    SYNTAX      PdnRedunCmdEntry
    MAX-ACCESS  not-accessible
    STATUS      current
    DESCRIPTION
            "Commands that can be performed on a particular
             entity module used for redundancy."
    INDEX   { entPhysicalIndex }
    ::= { pdnRedunCmdTable 1 }

PdnRedunCmdEntry ::=
    SEQUENCE {
	pdnRedunCommand	PdnRedunCmd
    }

pdnRedunCommand  OBJECT-TYPE
    SYNTAX      PdnRedunCmd
    MAX-ACCESS  read-write
    STATUS      current
    DESCRIPTION
            "This object allows users to command an entity module,
             configured for redundancy to perform an action such as
             switch (2).

	     Reading this object should return the last command
             issued on this interface or noCmd (1) if no command
             has been issued since last reset."
    ::= { pdnRedunCmdEntry 1 }


--
-- Alarm/Status table
--

pdnRedunStatusTable OBJECT-TYPE
    SYNTAX	SEQUENCE OF PdnRedunStatusEntry
    MAX-ACCESS  not-accessible
    STATUS	current
    DESCRIPTION 
	    "This table contains configuration and status
	     information related to events in entity modules
  	     used for redundancy."
    ::= { pdnEntityRedundancyMIBObjects 5 }

pdnRedunStatusEntry OBJECT-TYPE
    SYNTAX      PdnRedunStatusEntry
    MAX-ACCESS  not-accessible
    STATUS      current
    DESCRIPTION
            "Configuration and Status information for a 
	     particular entity module used for redundancy."
    INDEX   { entPhysicalIndex }
    ::= { pdnRedunStatusTable 1 }

PdnRedunStatusEntry ::=
    SEQUENCE {
	pdnRedunEntityState		PdnRedunStates,
	pdnRedunAlarmStatus		PdnRedunAlarmStatus,
	pdnRedunNotificationEnable 	PdnRedunAlarmStatus
    }

pdnRedunEntityState  OBJECT-TYPE
    SYNTAX      PdnRedunStates
    MAX-ACCESS  read-only
    STATUS      current
    DESCRIPTION
            "This object is used to display the current state
	     on an entity that is used for redundancy."
    ::= { pdnRedunStatusEntry 1 }

pdnRedunAlarmStatus  OBJECT-TYPE
    SYNTAX      PdnRedunAlarmStatus
    MAX-ACCESS  read-only
    STATUS      current
    DESCRIPTION
            "This object provides status of any Alarm
	     detected in a redundant entity."

    ::= { pdnRedunStatusEntry 2 }

pdnRedunNotificationEnable  OBJECT-TYPE
    SYNTAX      PdnRedunAlarmStatus
    MAX-ACCESS  read-write
    STATUS      current
    DESCRIPTION
            "This object provides the ability to enable and
	     disable the following notifications:

		o pdnRedunEventHwIncompatible
		o pdnRedunEventFwIncompatible
		o pdnRedunEventCfgIncompatible
		o pdnRedunEventLinkDefect
		o pdnRedunEventHwFailure
		o pdnRedunEventHwMissingHwFailure
	    "
    ::= { pdnRedunStatusEntry 3 }

--
-- Redundancy Notifications
--

pdnRedunNotificationsPrefix OBJECT IDENTIFIER
		::= { pdnEntityRedundancyNotifications 0 }

pdnRedunEventNoActiveModule NOTIFICATION-TYPE
     OBJECTS { pdnRedunGeneralAlarmStatus }
     STATUS  current
     DESCRIPTION
	     "This notification will be issued when no module
	     is in the Active State."
     ::= { pdnRedunNotificationsPrefix 1 }

pdnRedunEventHwIncompatible NOTIFICATION-TYPE
     OBJECTS { pdnRedunAlarmStatus }
     STATUS  current
     DESCRIPTION
	     "This notification will be issued when the modules
	     in a redundancy configuration present hardware 
	     incompatibilities."
     ::= { pdnRedunNotificationsPrefix 2 }

pdnRedunEventStandbyAlarmOrReset NOTIFICATION-TYPE
     OBJECTS { pdnRedunGeneralAlarmStatus }
     STATUS  current
     DESCRIPTION
	     "This notification will be issued when one of the
	     modules configured for redundancy is either in the
	     Standby/Alarm or Reset Test state."
     ::= { pdnRedunNotificationsPrefix 3 }

pdnRedunEventFwIncompatible NOTIFICATION-TYPE
     OBJECTS { pdnRedunAlarmStatus }
     STATUS  current
     DESCRIPTION
	     "This notification will be issued when the modules
	     in a redundancy configuration present firmware
	     incompatibilities."
     ::= { pdnRedunNotificationsPrefix 4 }

pdnRedunEventCfgIncompatible NOTIFICATION-TYPE
     OBJECTS { pdnRedunAlarmStatus }
     STATUS  current
     DESCRIPTION
	     "This notification will be issued when the modules 
	     in a redundancy configuration present configuration
	     incompatibilities."
     ::= { pdnRedunNotificationsPrefix 5 }

pdnRedunEventLinkDefect NOTIFICATION-TYPE
     OBJECTS { pdnRedunAlarmStatus }
     STATUS  current
     DESCRIPTION
	     "This notification will be issued when a module
	     in a redundancy configuration has a link condition."
     ::= { pdnRedunNotificationsPrefix 6 }

pdnRedunEventHwFailure NOTIFICATION-TYPE
     OBJECTS { pdnRedunAlarmStatus }
     STATUS  current
     DESCRIPTION
	     "This notification will be issued when a module
	     in a redundancy configuration has a hardware
	     failure condition."
     ::= { pdnRedunNotificationsPrefix 7 }

pdnRedunEventHwMissingHwFailure NOTIFICATION-TYPE
     OBJECTS { pdnRedunAlarmStatus }
     STATUS  current
     DESCRIPTION
	     "This notification will be issued when a module
	     in a redundancy configuration is expecting a
	     piece of hw to be used for redundancy which can
	     not be found or is not operational.
	     "
     ::= { pdnRedunNotificationsPrefix 8 }

--
-- Conformance Information
--

pdnEntityRedundancyCompliances OBJECT IDENTIFIER
     ::= { pdnEntityRedundancyConformance 1 }

pdnEntityRedundancyGroups OBJECT IDENTIFIER
     ::= { pdnEntityRedundancyConformance 2 }

pdnEntityRedundancyCompliance MODULE-COMPLIANCE
     STATUS  current
     DESCRIPTION
             "The compliance statement for SNMP entities which
	      manage the configuration parameters on entities
	      used for redundancy."
     MODULE
     MANDATORY-GROUPS {	pdnRedundancyGeneralGroup }

     OBJECT pdnEntityRedundancySelection
     MIN-ACCESS read-only
     DESCRIPTION
	     "Write access is not required."

     OBJECT pdnRedunCommand
     MIN-ACCESS read-only
     DESCRIPTION
	     "Write access is not required."

     OBJECT pdnRedunNotificationEnable
     MIN-ACCESS read-only
     DESCRIPTION
	     "Write access is not required."

-- Optional groups

     GROUP pdnEntityRedundancyOptGroup
     DESCRIPTION
	     "Implementation of this group is optional for the
	      redundancy management implementation."

     GROUP pdnEntityRedundancyEventGroup
     DESCRIPTION
	     "Implementation of this group is optional for the
	      notification implementation."

     ::= { pdnEntityRedundancyCompliances 1 }

-- units of conformance

pdnRedundancyGeneralGroup	OBJECT-GROUP
     OBJECTS
     {
	pdnEntityRedundancySelection,
	pdnYCableSelection,
	pdnRedunGeneralAlarmStatus,
	pdnRedunGeneralNotificationEnable
     }
     STATUS current
     DESCRIPTION
             "A collection of general configuration objects
              for the entity redundancy implementation."
     ::= { pdnEntityRedundancyGroups 1 }

pdnEntityRedundancyOptGroup	OBJECT-GROUP
     OBJECTS
     {
	pdnRedunCommand,
	pdnRedunNotificationEnable,
	pdnRedunEntityState,
	pdnRedunAlarmStatus
     }
     STATUS current
     DESCRIPTION
             " A collection of configuration objects 
	      applicable to redundancy implementations."
     ::= { pdnEntityRedundancyGroups 2 }

pdnEntityRedundancyEventGroup	NOTIFICATION-GROUP
     NOTIFICATIONS
     {
	pdnRedunEventNoActiveModule,
	pdnRedunEventHwIncompatible,
	pdnRedunEventStandbyAlarmOrReset,
	pdnRedunEventFwIncompatible,
	pdnRedunEventCfgIncompatible,
	pdnRedunEventLinkDefect,
	pdnRedunEventHwFailure,
	pdnRedunEventHwMissingHwFailure

     }
     STATUS current
     DESCRIPTION
             "A collection of redundancy notifications."
     ::= { pdnEntityRedundancyGroups 3 }

END

-- ===============================================================
-- Copyright (C) 2000 Paradyne Corporation.
--  ATM Extension Group
-- ==============================================================

PDN-DS3EXT-MIB DEFINITIONS ::= BEGIN

    IMPORTS
        MODULE-IDENTITY , OBJECT-TYPE, Integer32,  NOTIFICATION-TYPE
            FROM SNMPv2-SMI
        DisplayString,TruthValue
            FROM SNMPv2-TC
        pdn-interfaces
            FROM PDN-HEADER-MIB
        dsx3CurrentEntry ,dsx3IntervalEntry, dsx3TotalEntry
            FROM DS3-MIB
		PerfCurrentCount, PerfIntervalCount, PerfTotalCount 
		FROM PerfHist-TC-MIB;


-- ===============================================================
--
--   Ds3/E3 Extentions to the DS3-MIB 
--
--  Release: 1.0  05/26/99 (Initial Release) J.Strain
--
--  Last Updated:
--
--
--	This group extends the DS3-MIB.
--
-- ===============================================================
--
--  Extentions to the ATM MIB (RFC 2515)
--
-- ===============================================================

    pdnDs3MIB MODULE-IDENTITY
        LAST-UPDATED "0207050000Z"
        ORGANIZATION "Paradyne Networks
                      MIB Working Group"
        CONTACT-INFO
                      "Paradyne Networks
                       331 Newman Springs Road
                       Red Bank, NJ 07701
                       www.paradyne.com

                       General Comments to: mibwg_team@eng.paradyne.com"

        DESCRIPTION
        "This MIB Module extends the DS3-MIB defined in rfc2496"

        REVISION "0207100000Z"
        DESCRIPTION "M. Mohankumar
		     Changed the index of devDs3FreeRunTable to Augment
		     dsx3TotalEntry."
        REVISION "0207050000Z"
        DESCRIPTION "M. Mohankumar
		     Added devDs3FreeRunTable that has the free running
		     counters for physical performance stats."
        REVISION "0005260000Z"
        DESCRIPTION "J. Strain
				o	add devDs3ConfigTimingMarkerCode 		
				o	augment the DS3/E3 Near End Group
				o 	 to add EB,ES,SES,PlcpSEFS for current
				o	 , interval and total tables
            o  Initial Release"

        ::= {  pdn-interfaces 14 }

    devDs3Objects    OBJECT IDENTIFIER ::= { pdnDs3MIB 1 }
--    devDs3MIBTraps      OBJECT IDENTIFIER ::= { pdnDs3MIB 2 }
--    devDs3MIBTrapPrefix OBJECT IDENTIFIER ::= { pdnDs3MIB 3 }
--    devDs3MIBConformance OBJECT IDENTIFIER ::= { pdnDs3MIB 4 }


devDs3ConfigTable OBJECT-TYPE
    SYNTAX  SEQUENCE OF DevDs3ConfigEntry
    MAX-ACCESS  not-accessible
    STATUS  current
    DESCRIPTION
           "The Paradyne Ds3-MIB Table Augment."
    ::= { devDs3Objects  1 }

devDs3ConfigEntry OBJECT-TYPE
    SYNTAX  DevDs3ConfigEntry
    MAX-ACCESS  not-accessible
    STATUS  current
    DESCRIPTION
           "An entry in the Paradyne Ds3-MIB Table."
    INDEX   { devDs3ConfigIfIndex }
    ::= { devDs3ConfigTable  1 }

DevDs3ConfigEntry ::=
    SEQUENCE {
    devDs3ConfigIfIndex
        Integer32,

    devDs3ConfigFramingType
        INTEGER,

    devDs3ConfigIgnoreCbit
        INTEGER,

    devDs3ConfigTimingMarkerCode
        INTEGER
    }

devDs3ConfigIfIndex OBJECT-TYPE
    SYNTAX  Integer32
    MAX-ACCESS  read-only
    STATUS  current
    DESCRIPTION
           "The index value which uniquely identifies the
            interface for which this entry contains information
            on interface tests.  The interface identified by a
            particular value of this index is the same interface
            as identified by the same value of ifIndex from the
            Interfaces table of MIB II (RFC 1213)."
    ::= { devDs3ConfigEntry 1 }

devDs3ConfigFramingType OBJECT-TYPE
    SYNTAX  INTEGER {
                 direct(1),	 -- Direct Mapping of ATM Cells into a Ds3 C-Bit Parity Format
                 plcp(2)	 -- PLCP mapping of ATM Cells into a Ds3 C-Bit Parity Format
               }
    MAX-ACCESS  read-write
    STATUS  current
    DESCRIPTION
           "The option provides the support for Direct Mapping or Physicial Layer
            Convergence Protocol (PLCP) mapping of ATM Cells into a Ds3 C-Bit Parity Format"
    ::= { devDs3ConfigEntry  2 }

devDs3ConfigIgnoreCbit OBJECT-TYPE
    SYNTAX  INTEGER {
                 no(1),		-- allow the ability to disable the accumulation
                            -- of C-Bit errors and the generation of C-Bit Alarms
                 yes(2)		-- Do NOT allow the ability to disable the accumulation
                            -- of C-Bit errors and the generation of C-Bit Alarms

               }
    MAX-ACCESS  read-write
    STATUS  current
    DESCRIPTION
           "Since not all networks support the C-Bit, we allow the ability to disable the accumulation
            of C-Bit errors and the generation of C-Bit Alarms."
    ::= { devDs3ConfigEntry  3 }

devDs3ConfigTimingMarkerCode OBJECT-TYPE
    SYNTAX  INTEGER {
                 traceable(1),     	-- Code means: Timing source is traceable to a primary 
									--	reference source.

                 notTraceable(2)  	-- Code means: Timing source is not traceable to a primary
									--	 reference	source
               }
    MAX-ACCESS  read-write
    STATUS  current
    DESCRIPTION
           "The option supports the ability to send a 'Timing Marker' code to the far end."
    ::= { devDs3ConfigEntry  4 }
	
-- ===============================================================
--
--   Augmenting the DS3/E3 NearEnd Current Table ( RFC 2496 )
--
--

devDs3CurrentTable OBJECT-TYPE
    SYNTAX  SEQUENCE OF DevDs3CurrentEntry
    MAX-ACCESS  not-accessible
    STATUS  current
    DESCRIPTION
       "The Paradyne Extension to the Near End Current Table of the DS3-MIB."
    ::= { devDs3Objects 2   }

devDs3CurrentEntry OBJECT-TYPE
    SYNTAX  DevDs3CurrentEntry
    MAX-ACCESS  not-accessible
    STATUS  current
    DESCRIPTION
           "An entry in the Paradyne Extension to the dsx3CurrentTable of the DS3-MIB."
    AUGMENTS { dsx3CurrentEntry }
    ::= { devDs3CurrentTable 1 }

DevDs3CurrentEntry ::=
    SEQUENCE {

    devDs3CurrentEB
            PerfCurrentCount,
    devDs3CurrentES
            PerfCurrentCount,
    devDs3CurrentSES
            PerfCurrentCount,
    devDs3CurrentPlcpSEFS
            PerfCurrentCount

    }


devDs3CurrentEB OBJECT-TYPE
          SYNTAX  PerfCurrentCount
          MAX-ACCESS read-only
          STATUS current
          DESCRIPTION
		"The counter associated with the number of
                Errored Blocks"
          ::= { devDs3CurrentEntry 1}

devDs3CurrentES OBJECT-TYPE

          SYNTAX  PerfCurrentCount
          MAX-ACCESS read-only
          STATUS current
          DESCRIPTION
		"The counter associated with the number of
                Errored Seconds"
          ::= { devDs3CurrentEntry 2}

devDs3CurrentSES OBJECT-TYPE

          SYNTAX  PerfCurrentCount
          MAX-ACCESS read-only
          STATUS current
          DESCRIPTION
		"The counter associated with the number of
                 Severly Errored Seconds"
          ::= { devDs3CurrentEntry 3}

devDs3CurrentPlcpSEFS OBJECT-TYPE

          SYNTAX  PerfCurrentCount
          MAX-ACCESS read-only
          STATUS current
          DESCRIPTION
		"The counter associated with the number of
                PLCP Severely Errored Framing Seconds"
          ::= { devDs3CurrentEntry 4}


-- ===============================================================
--
--   Augmenting the DS3/E3 NearEnd Interval Table ( RFC 2496 )
--
--

devDs3IntervalTable OBJECT-TYPE
    SYNTAX  SEQUENCE OF DevDs3IntervalEntry
    MAX-ACCESS  not-accessible
    STATUS  current
    DESCRIPTION
       "The Paradyne Extension to the Near End Interval Table of the DS3-MIB."
    ::= { devDs3Objects 3 }

devDs3IntervalEntry OBJECT-TYPE
    SYNTAX  DevDs3IntervalEntry
    MAX-ACCESS  not-accessible
    STATUS  current
    DESCRIPTION
           "An entry in the Paradyne Extension to the dsx3IntervalTable of the DS3-MIB."
    AUGMENTS { dsx3IntervalEntry }
    ::= { devDs3IntervalTable 1 }

DevDs3IntervalEntry ::=
    SEQUENCE {

    devDs3IntervalEB 
			PerfIntervalCount,
    devDs3IntervalES 
			PerfIntervalCount,
    devDs3IntervalSES 
			PerfIntervalCount,
    devDs3IntervalPlcpSEFS 
			PerfIntervalCount

    }


devDs3IntervalEB OBJECT-TYPE

          SYNTAX  PerfIntervalCount
          MAX-ACCESS read-only
          STATUS current
          DESCRIPTION
		"The counter associated with the number of
                Errored Blocks"
          ::= { devDs3IntervalEntry 1}

devDs3IntervalES OBJECT-TYPE

          SYNTAX  PerfIntervalCount
          MAX-ACCESS read-only
          STATUS current
          DESCRIPTION
		"The counter associated with the number of
                Errored Seconds"
          ::= { devDs3IntervalEntry 2}

devDs3IntervalSES OBJECT-TYPE

          SYNTAX  PerfIntervalCount
          MAX-ACCESS read-only
          STATUS current
          DESCRIPTION
		"The counter associated with the number of
                 Severly Errored Seconds"
          ::= { devDs3IntervalEntry 3}

devDs3IntervalPlcpSEFS OBJECT-TYPE

          SYNTAX  PerfIntervalCount
          MAX-ACCESS read-only
          STATUS current
          DESCRIPTION
		"The counter associated with the number of
                PLCP Severely Errored Framing Seconds"
          ::= { devDs3IntervalEntry 4}

-- ===============================================================
--
--   Augmenting the DS3/E3 NearEnd Total Table ( RFC 2496 )
--
--

devDs3TotalTable OBJECT-TYPE
    SYNTAX  SEQUENCE OF DevDs3TotalEntry
    MAX-ACCESS  not-accessible
    STATUS  current
    DESCRIPTION
       "The Paradyne Extension to the Near End Total Table of the DS3-MIB."
    ::= { devDs3Objects 4 }

devDs3TotalEntry OBJECT-TYPE
    SYNTAX  DevDs3TotalEntry
    MAX-ACCESS  not-accessible
    STATUS  current
    DESCRIPTION
           "An entry in the Paradyne Extension to the dsx3TotalTable of the DS3-MIB."
    AUGMENTS { dsx3TotalEntry }
    ::= { devDs3TotalTable 1 }

DevDs3TotalEntry ::=
    SEQUENCE {

    devDs3TotalEB
            PerfTotalCount,
    devDs3TotalES
            PerfTotalCount,
    devDs3TotalSES
            PerfTotalCount,
    devDs3TotalPlcpSEFS
            PerfTotalCount

    }


devDs3TotalEB OBJECT-TYPE

          SYNTAX  PerfTotalCount
          MAX-ACCESS read-only
          STATUS current
          DESCRIPTION
		"The counter associated with the number of
                Errored Blocks"
          ::= { devDs3TotalEntry 1}

devDs3TotalES OBJECT-TYPE

          SYNTAX  PerfTotalCount
          MAX-ACCESS read-only
          STATUS current
          DESCRIPTION
		"The counter associated with the number of
                Errored Seconds"
          ::= { devDs3TotalEntry 2}

devDs3TotalSES OBJECT-TYPE

          SYNTAX  PerfTotalCount
          MAX-ACCESS read-only
          STATUS current
          DESCRIPTION
		"The counter associated with the number of
                 Severly Errored Seconds"
          ::= { devDs3TotalEntry 3}

devDs3TotalPlcpSEFS OBJECT-TYPE

          SYNTAX  PerfTotalCount
          MAX-ACCESS read-only
          STATUS current
          DESCRIPTION
		"The counter associated with the number of
                PLCP Severely Errored Framing Seconds"
          ::= { devDs3TotalEntry 4}

-- The Paradyne Free Running Statistics Table
--
-- This table contains the performance stats in the form of free running counters
--

devDs3FreeRunTable OBJECT-TYPE
    SYNTAX  SEQUENCE OF DevDs3FreeRunEntry
    MAX-ACCESS  not-accessible
    STATUS  current
    DESCRIPTION
       "The Paradyne Free Running Total of the performance stats."
    ::= { devDs3Objects 5 }

devDs3FreeRunEntry OBJECT-TYPE
    SYNTAX  DevDs3FreeRunEntry
    MAX-ACCESS  not-accessible
    STATUS  current
    DESCRIPTION
       "An entry in the Paradyne Free Running Total Table."
    AUGMENTS { dsx3TotalEntry }
    ::= { devDs3FreeRunTable 1 }

DevDs3FreeRunEntry ::=
    SEQUENCE {
	devDs3FreeRunPES 	PerfTotalCount,
	devDs3FreeRunPSES 	PerfTotalCount,
	devDs3FreeRunPSEFS 	PerfTotalCount,
	devDs3FreeRunUAS 	PerfTotalCount,
	devDs3FreeRunLCV 	PerfTotalCount,
	devDs3FreeRunPCV 	PerfTotalCount,
	devDs3FreeRunLES 	PerfTotalCount,
	devDs3FreeRunCCV 	PerfTotalCount,
	devDs3FreeRunCES 	PerfTotalCount,
	devDs3FreeRunCSES 	PerfTotalCount
    }
    
devDs3FreeRunPES OBJECT-TYPE
    SYNTAX  PerfTotalCount
    MAX-ACCESS read-only
    STATUS current
    DESCRIPTION
       "The counter associated with the number of
        P bit Errored Seconds."
    ::= { devDs3FreeRunEntry 1 }

devDs3FreeRunPSES OBJECT-TYPE
    SYNTAX  PerfTotalCount
    MAX-ACCESS read-only
    STATUS current
    DESCRIPTION
       "The counter associated with the number of
        P bit Severely Errored Seconds."
    ::= { devDs3FreeRunEntry 2 }

devDs3FreeRunPSEFS OBJECT-TYPE
    SYNTAX  PerfTotalCount
    MAX-ACCESS read-only
    STATUS current
    DESCRIPTION
       "The counter associated with the number of
        Severely Errored Frame Seconds."
    ::= { devDs3FreeRunEntry 3 }

devDs3FreeRunUAS OBJECT-TYPE
    SYNTAX  PerfTotalCount
    MAX-ACCESS read-only
    STATUS current
    DESCRIPTION
       "The counter associated with the number of
        Unavailable Seconds."
    ::= { devDs3FreeRunEntry 4 }

devDs3FreeRunLCV OBJECT-TYPE
    SYNTAX  PerfTotalCount
    MAX-ACCESS read-only
    STATUS current
    DESCRIPTION
       "The counter associated with the number of
        Line Coding Violations."
    ::= { devDs3FreeRunEntry 5 }

devDs3FreeRunPCV OBJECT-TYPE
    SYNTAX  PerfTotalCount
    MAX-ACCESS read-only
    STATUS current
    DESCRIPTION
       "The counter associated with the number of
        P bit Coding Violations."
    ::= { devDs3FreeRunEntry 6 }

devDs3FreeRunLES OBJECT-TYPE
    SYNTAX  PerfTotalCount
    MAX-ACCESS read-only
    STATUS current
    DESCRIPTION
       "The counter associated with the number of
        Line Erroed Seconds."
    ::= { devDs3FreeRunEntry 7 }

devDs3FreeRunCCV OBJECT-TYPE
    SYNTAX  PerfTotalCount
    MAX-ACCESS read-only
    STATUS current
    DESCRIPTION
       "The counter associated with the number of
        C bit Coding Violations."
    ::= { devDs3FreeRunEntry 8 }

devDs3FreeRunCES OBJECT-TYPE
    SYNTAX  PerfTotalCount
    MAX-ACCESS read-only
    STATUS current
    DESCRIPTION
       "The counter associated with the number of
        C bit Errored Seconds."
    ::= { devDs3FreeRunEntry 9 }

devDs3FreeRunCSES OBJECT-TYPE
    SYNTAX  PerfTotalCount
    MAX-ACCESS read-only
    STATUS current
    DESCRIPTION
       "The counter associated with the number of
        C bit Severly Errored Seconds."
    ::= { devDs3FreeRunEntry 10 }

END
