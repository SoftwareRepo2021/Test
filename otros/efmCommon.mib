EFM-COMMON-MIB DEFINITIONS ::= BEGIN

   IMPORTS
     MODULE-IDENTITY, mib-2, OBJECT-TYPE, Counter32, Counter64, Unsigned32, Integer32, NOTIFICATION-TYPE
       FROM SNMPv2-SMI
     TEXTUAL-CONVENTION, MacAddress, TimeStamp
       FROM SNMPv2-TC
     MODULE-COMPLIANCE, OBJECT-GROUP, NOTIFICATION-GROUP
       FROM SNMPv2-CONF
     ifIndex
       FROM IF-MIB
     ietfDrafts                        
       FROM Zhone
     CounterBasedGauge64, Dot3Oui
       FROM HCNUM-TC;






-- the code was generate using the following pahrser command
-- /vob/zhonetools/bin/pahrser.pl rfc2856.mib rfc2571.mib efmCommon.mib
-- there is problems using Counter64/CounterBasedGauge64 so the elements
-- using these are hand coded.
-- when generating code the Counter64 causes error, so change to Unsigned 32
-- and fix generated code with an array of size 2.


     efmOamMIB MODULE-IDENTITY
       LAST-UPDATED "200503220000Z"  -- March 22, 2005
       ORGANIZATION
         "IETF Ethernet Interfaces and Hub MIB Working Group"
       CONTACT-INFO
         "WG Charter:
           http://www.ietf.org/html.charters/hubmib-charter.html
         Mailing lists:
           General Discussion: hubmib@ietf.org
           To Subscribe: hubmib-requests@ietf.org
           In Body: subscribe your_email_address
         Chair: Dan Romascanu, Avaya
           Tel:  +972-3-645-8414
           Email: dromasca at avaya dot com
         Editor: Matt Squire
           Hatteras Networks
           Tel:    +1-919-991-5460
           Fax:    +1-919-991-0743
           E-mail: msquire at hatterasnetworks dot com
         "
       DESCRIPTION
         "The MIB module for managing the new Ethernet OAM features
         introduced by the Ethernet in the First Mile task force (IEEE
         802.3ah).  The functionality presented here is based on IEEE
         802.3ah [802.3ah], released in October, 2004.

         In particular, this MIB focused on the changes to Clause 30 of
         the draft that are not specific to any physical layer.  These
         changes are primarily reflected in the new OAM features
         developed under this project, that can be applied to any
         Ethernet like interface. The OAM features are described in
         Clause 57 of [802.3ah].

         The following reference is used throughout this MIB module:

           [802.3ah] refers to:
             IEEE Std 802.3ah-2004: 'Draft amendment to -
             Information technology - Telecommunications and
             information exchange between systems - Local and
             metropolitan are networks - Specific requirements - Part
             3: Carrier sense multiple access with collision detection
             (CSMA/CD) access method and physical layer specifications
             - Media Access Control Parameters, Physical Layers and
             Management Parameters for subscriber access networks',
             October 2004.

           [802-2001] refers to:
             'IEEE Standard for LAN/MAN (Local Area
             Network/Metropolitan Area Network): Overview and
             Architecture', IEEE 802, June 2001.

         Copyright (c) The Internet Society (2005). This version of
         this MIB module is part of RFC XXXX; See the RFC itself for
         full legal notices. "
  -- RFC Editor: Update XXXX to appropriate RFC number
  -- RFC Editor: Remove these notes
       REVISION    "200503220000Z"  -- March 22, 2005
       DESCRIPTION "Initial version, published as RFC XXXX."
  -- RFC Editor: Update XXXX to appropriate RFC number
  -- RFC Editor: Remove these notes

--        ::= { mib-2 XXX }
        ::= { ietfDrafts 6 }
  -- RFC Editor: Replace value with IANA assigned number
  -- RFC Editor: Remove these notes


     --
     -- Sections of the EFM OAM MIB
     --
        dot3OamMIB         OBJECT IDENTIFIER ::= { efmOamMIB 1 }
        dot3OamConformance OBJECT IDENTIFIER ::= { efmOamMIB 2 }


     --
     -- Textual conventions for OAM MIB
     --
--     Dot3Oui ::= TEXTUAL-CONVENTION
--       STATUS       current
--       DESCRIPTION
--         "24-bit Organizationally Unique Identifier.  Information on
--         OUIs can be found in IEEE 802-2001 [802-2001] Clause 9."
--       SYNTAX       OCTET STRING(SIZE(3))


     ------------------------------------------------------------------
     --
     -- Ethernet OAM Control group
     --


     dot3OamTable OBJECT-TYPE
       SYNTAX      SEQUENCE OF Dot3OamEntry
       MAX-ACCESS  not-accessible
       STATUS      current
       DESCRIPTION
         "Primary controls and status for the OAM capabilities of an
         Ethernet like interface.  There will be one row in this table
         for each Ethernet like interface in the system that supports
         the Ethernet OAM functions defined in [802.3ah]."
       ::= { dot3OamMIB 1 }

     dot3OamEntry OBJECT-TYPE
       SYNTAX     Dot3OamEntry
       MAX-ACCESS not-accessible
       STATUS     current
       DESCRIPTION
         "An entry in the table, containing information on the Ethernet
         OAM function for a single Ethernet like interface."
       INDEX       { ifIndex }
       ::= { dot3OamTable 1 }

     Dot3OamEntry ::=
       SEQUENCE {
         dot3OamAdminState                  INTEGER,
         dot3OamOperStatus                  INTEGER,
         dot3OamMode                        INTEGER,
         dot3OamMaxOamPduSize               Integer32,
         dot3OamConfigRevision              Unsigned32,
         dot3OamFunctionsSupported          BITS
       }

--

     dot3OamAdminState OBJECT-TYPE
       SYNTAX      INTEGER {
                     disabled(1),
                     enabled(2)
                   }
       MAX-ACCESS  read-write
       STATUS      current
       DESCRIPTION
         "This object is used to provision the default administrative
         OAM mode for this interface.  This object represents the
         desired state of OAM for this interface.

         The dot3OamAdminState always starts in the disabled(1) state
         until an explicity management action or configuration
         information retained by the system causes a transition to the
         enabled(2) state.

         Note that the value of this object is ignored when the
         interface is not operating in full-duplex mode. OAM is not
         supported on half-duplex links.  "
       REFERENCE   "[802.3ah], 30.3.6.1.2"
       ::= { dot3OamEntry 1 }

--

     dot3OamOperStatus OBJECT-TYPE
       SYNTAX      INTEGER {
                     disabled(1),
                     linkfault(2),
                     passiveWait(3),
                     activeSendLocal(4),
                     sendLocalAndRemote(5),
                     sendLocalAndRemoteOk(6),
                     oamPeeringLocallyRejected(7),
                     oamPeeringRemotelyRejected(8),
                     operational(9)
                   }
       MAX-ACCESS  read-only
       STATUS      current
       DESCRIPTION
         "At initialization and failure conditions, two OAM entities on
         the same full-duplex Ethernet link begin a discovery phase to
         determine what OAM capabilities may be used on that link.  The
         progress of this initialization is controlled by the OAM
         sublayer.

         This value is always disabled(1) if OAM is disabled on this
         interface via the dot3OamAdminState.

         If the link has detected a fault and is transmitting OAMPDUs
         with a link fault indication, the value is linkFault(2).

         The passiveWait(3) state is returned only by OAM entities in
         passive mode (dot3OamMode) and reflects the state in which the
         OAM entity is waiting to see if the peer device is OAM
         capable.  The activeSendLocal(4) is used by active mode
         devices (dot3OamMode) and reflects the OAM entity actively
         trying to discover whether the peer has OAM capability but has
         not yet made that determination.

         The state sendLocalAndRemote(5) reflects that the local OAM
         entity has discovered the peer but has not yet accepted or
         rejected the configuration of the peer.  The local device can,
         for whatever reason, decide that the peer device is
         unacceptable and decline OAM peering.  If the local OAM entity
         rejects the peer OAM entity, the state becomes
         oamPeeringLocallyRejected(7).  If the OAM peering is allowed
         by the local device, the state moves to
         sendLocalAndRemoteOk(6).  Note that both the
         sendLocalAndRemote(5) and oamPeeringLocallyRejected(7) states
         fall within the state SEND_LOCAL_REMOTE of the Discovery state
         diagram [802.3ah, Figure 57-5], with the difference being
         whether the local OAM client has actively rejected the peering
         or has just not indicated any decision yet.  Whether a peering
         decision has been made is indicated via the local flags field
         in the OAMPDU (reflected in the aOAMLocalFlagsField of
         30.3.6.1.10).

         If the remote OAM entity rejects the peering, the state
         becomes oamPeeringRemotelyRejected(8).  Note that both the
         sendLocalAndRemoteOk(6) and oamPeeringRemotelyRejected(8)
         states fall within the state SEND_LOCAL_REMOTE_OK of the
         Discovery state diagram [802.3ah, Figure 57-5], with the
         difference being whether the remote OAM client has rejected
         the peering or has just not yet decided.  This is indicated
         via the remote flags field in the OAM PDU (reflected in the
         aOAMRemoteFlagsField of 30.3.6.1.11).

         When the local OAM entity learns that both it and the remote
         OAM entity have accepted the peering, the state moves to
         operational(9) corresponding to the SEND_ANY state of the
         Discovery state diagram [802.3ah, Figure 57-5].  "
       REFERENCE   "[802.3ah], 30.3.6.1.4, 30.3.6.1.10, 30.3.6.1.11"
       ::= { dot3OamEntry 2 }

--

     dot3OamMode OBJECT-TYPE
       SYNTAX      INTEGER {
                     active(1),
                     passive(2)
                   }
       MAX-ACCESS  read-write
       STATUS      current
       DESCRIPTION
         "This object configures the mode of OAM operation for this
         Ethernet like interface.  OAM on Ethernet interfaces may be in
         'active' mode or 'passive' mode.  These two modes differ in
         that active mode provides additional capabilities to initiate
         monitoring activities with the remote OAM peer entity, while
         passive mode generally waits for the peer to initiate OAM
         actions with it.  As an example, an active OAM entity can put
         the remote OAM entity in a loopback state, where a passive OAM
         entity cannot.

         The default value of dot3OamMode is dependent on the type of
         system on which this Ethernet like interface resides.  The
         default value should be 'active(1)' unless it is known that
         this system should take on a subservient role to the other
         device connected over this interface.

         Changing this value results in incrementing the configuration
         revision field of locally generated OAMPDUs (30.3.6.1.12) and
         potentially re-doing the OAM discovery process if the
         dot3OamOperStatus was already operational(9).  "
       REFERENCE   "[802.3ah], 30.3.6.1.3"
       ::= { dot3OamEntry 3 }

--

     dot3OamMaxOamPduSize OBJECT-TYPE
       SYNTAX      Integer32 (64..1522)
       UNITS       "bytes"
       MAX-ACCESS  read-only
       STATUS      current
       DESCRIPTION
         "The largest OAMPDU that the OAM entity supports.  OAM
         entities exchange maximum OAMPDU sizes and negotiate to use
         the smaller of the two maximum OAMPDU sizes between the peers.
         This value is determined by the local implementation.
         "
       REFERENCE   "[802.3ah], 30.3.6.1.8"
       ::= { dot3OamEntry 4 }

--

     dot3OamConfigRevision OBJECT-TYPE
       SYNTAX      Unsigned32
       MAX-ACCESS  read-only
       STATUS      current
       DESCRIPTION
         "The configuration revision of the OAM entity as reflected in
         the latest OAMPDU sent by the OAM entity.  The config revision
         is used by OAM entities to indicate configuration changes have
         occured which might require the peer OAM entity to re-evaluate
         whether the peering is allowed.  See local_satisfied in
         [802.3ah, 57.3.1.2].  "
       REFERENCE   "[802.3ah], 30.3.6.1.12"
       ::= { dot3OamEntry 5 }

--

     dot3OamFunctionsSupported OBJECT-TYPE
       SYNTAX      BITS {
                     unidirectionalSupport (0),
                     loopbackSupport(1),
                     eventSupport(2),
                     variableSupport(3)
                   }
       MAX-ACCESS  read-only
       STATUS      current
       DESCRIPTION
         "The OAM functions supported on this Ethernet like interface.
         OAM consists of separate functional sets beyond the basic
         discovery process which is always required.  These functional
         groups can be supported independently by any implementation.
         These values are communicated to the peer via the local
         configuration field of Information OAMPDUs.  "
       REFERENCE   "[802.3ah], 30.3.6.1.6"
       ::= { dot3OamEntry 6 }


     ------------------------------------------------------------------
     --
     -- Ethernet OAM Peer group
     --


     dot3OamPeerTable OBJECT-TYPE
       SYNTAX      SEQUENCE OF Dot3OamPeerEntry
       MAX-ACCESS  not-accessible
       STATUS      current
       DESCRIPTION
         "Information about the OAM peer for a particular Ethernet like
         interface. OAM entities communicate with a single OAM peer
         entity on full-duplex Ethernet links on which OAM is enabled
         and operating properly.

         In certain states, the OAM peer information is not available.
         Whether peer information is available is communicated via the
         dot3OamPeerStatus object.  When this object is inactive, all
         other information in the row is to be considered invalid.  "
       ::= { dot3OamMIB 2 }

     dot3OamPeerEntry OBJECT-TYPE
       SYNTAX      Dot3OamPeerEntry
       MAX-ACCESS  not-accessible
       STATUS      current
       DESCRIPTION
         "An entry in the table, containing information on the peer OAM
         entity for a single Ethernet like interface.

         Note that there is at most one OAM peer for each Ethernet like
         interface.  There is exactly one row in this table for each
         Ethernet like interface supporting OAM.  "
       INDEX       { ifIndex }
       ::= { dot3OamPeerTable 1 }


     Dot3OamPeerEntry ::=
       SEQUENCE {
         dot3OamPeerStatus                   INTEGER,
         dot3OamPeerMacAddress               MacAddress,
         dot3OamPeerVendorOui                Dot3Oui,
         dot3OamPeerVendorInfo               Unsigned32,
         dot3OamPeerMode                     INTEGER,
         dot3OamPeerMaxOamPduSize            Integer32,
         dot3OamPeerConfigRevision           Unsigned32,
         dot3OamPeerFunctionsSupported       BITS
       }

--

     dot3OamPeerStatus OBJECT-TYPE
       SYNTAX      INTEGER {
                     active(1),
                     inactive(2)
                   }
       MAX-ACCESS  read-only
       STATUS      current
       DESCRIPTION
         "This object indicates whether the information in this row
         should be considered valid.  When active(1), the information
         is valid and represents the current peer of the OAM entity.
         When inactive(2), the information in this row is invalid.

         A value of inactive(2) is returned if the dot3OamOperStatus is
         disabled, passiveWait, or activeSendLocal.  For all other
         values of dot3OamOperStatus, a value of active(1) is returned.
         "
       ::= { dot3OamPeerEntry 1 }

--

     dot3OamPeerMacAddress OBJECT-TYPE
       SYNTAX      MacAddress
       MAX-ACCESS  read-only
       STATUS      current
       DESCRIPTION
         "The MAC address of the peer OAM entity.  The MAC address is
         derived from the most recently received OAMPDU.  This value is
         initialized to all zeros (0x000000000000).  This value is
         invalid if the dot3OamPeerStatus is inactive.

         An OAMPDU is indicated by a valid frame with (1) destination
         MAC address equal to that of the reserved MAC address for Slow
         Protocols (See 43B of [802.3ah]), (2) a lengthOrType field
         equal to the reserved type for Slow Protocols, (3) and a Slow
         Protocols subtype equal to that of the subtype reserved for
         OAM.  "
       REFERENCE   "[802.3ah], 30.3.6.1.5."
       ::= { dot3OamPeerEntry 2 }


--

     dot3OamPeerVendorOui OBJECT-TYPE
       SYNTAX      Dot3Oui
       MAX-ACCESS  read-only
       STATUS      current
       DESCRIPTION
         "The OUI of the OAM peer as reflected in the latest
         Information OAMPDU received with a Local Information TLV.  The
         OUI can be used to identify the vendor of the remote OAM
         entity.  This value is initialized to all zeros (0x000000).
         This value is considered invalid if the dot3OamPeerStatus is
         inactive.

         An Information OAMPDU is indicated by a valid frame with (1)
         destination MAC address equal to that of the reserved MAC
         address for Slow Protocols (See 43B of [802.3ah]), (2) a
         lengthOrType field equal to the reserved type for Slow
         Protocols, (3) a Slow Protocols subtype equal to that of the
         subtype reserved for OAM, (4) a OAM code that equals the code
         reserved for Information OAMPDUs.  "
       REFERENCE   "[802.3ah], 30.3.6.1.16."
       ::= { dot3OamPeerEntry 3 }


--

     dot3OamPeerVendorInfo OBJECT-TYPE
       SYNTAX      Unsigned32
       MAX-ACCESS  read-only
       STATUS      current
       DESCRIPTION
         "The Vendor Info of the OAM peer as reflected in the latest
         Information OAMPDU received with a Local Information TLV.  The
         vendor information field is within the Local Information TLV,
         and can be used to determine additional information about the
         peer entity.  The format of the vendor information is
         unspecified within the 32-bit field.  This value is intialized
         to all zeros (0x00000000).  This value is invalid if the
         dot3OamPeerStatus is inactive.

         An Information OAMPDU is indicated by a valid frame with (1)
         destination MAC address equal to that of the reserved MAC
         address for Slow Protocols (See 43B of [802.3ah]), (2) a
         lengthOrType field equal to the reserved type for Slow
         Protocols, (3) a Slow Protocols subtype equal to that of the
         subtype reserved for OAM, and (4) a OAM code that equals the
         code reserved for Information OAMPDUs.  "
       REFERENCE   "[802.3ah], 30.3.6.1.17."
       ::= { dot3OamPeerEntry 4 }

--


     dot3OamPeerMode OBJECT-TYPE
       SYNTAX      INTEGER {
                     active(1),
                     passive(2),
                     unknown(3)
                   }
       MAX-ACCESS  read-only
       STATUS      current
       DESCRIPTION
         "The mode of the OAM peer as reflected in the latest
         Information OAMPDU received with a Local Information TLV.  The
         mode of the peer can be determined from the Configuration
         field in the Local Information TLV of the last Information
         OAMPDU received from the peer.  This value is initialized to
         unknown(3), and is not valid if the dot3OamPeerStatus is
         inactive.

         An Information OAMPDU is indicated by a valid frame with (1)
         destination MAC address equal to that of the reserved MAC
         address for Slow Protocols (See 43B of [802.3ah]), (2) a
         lengthOrType field equal to the reserved type for Slow
         Protocols, (3) a Slow Protocols subtype equal to that of the
         subtype reserved for OAM, and (4) a OAM code that equals the
         code reserved for Information OAMPDUs.  "
       REFERENCE   "[802.3ah], 30.3.6.1.7."
       ::= { dot3OamPeerEntry 5 }

--

     dot3OamPeerMaxOamPduSize OBJECT-TYPE
       SYNTAX      Integer32 (64..1522)
       UNITS       "bytes"
       MAX-ACCESS  read-only
       STATUS      current
       DESCRIPTION
         "The maximum size of OAMPDU supported by the peer as reflected
         in the latest Information OAMPDU received with a Local
         Information TLV.   Ethernet OAM on this interface must not use
         OAMPDUs that exceed this size.  The maximum OAMPDU size can be
         determined from the PDU Configuration field of the Local
         Information TLV of the last Information OAMPDU received from
         the peer.  This value is initialized to 64, and is invalid if
         the dot3OamPeerStatus is inactive.

         An Information OAMPDU is indicated by a valid frame with (1)
         destination MAC address equal to that of the reserved MAC
         address for Slow Protocols (See 43B of [802.3ah]), (2) a
         lengthOrType field equal to the reserved type for Slow
         Protocols, (3) a Slow Protocols subtype equal to that of the
         subtype reserved for OAM, and (4) a OAM code that equals the
         code reserved for Information OAMPDUs.  "
       REFERENCE   "[802.3ah], 30.3.6.1.9."
       ::= { dot3OamPeerEntry 6 }


--

     dot3OamPeerConfigRevision OBJECT-TYPE
       SYNTAX      Unsigned32
       MAX-ACCESS  read-only
       STATUS      current
       DESCRIPTION
         "The configuration revision of the OAM peer as reflected in
         the latest OAMPDU.  This attribute is changed by the peer
         whenever it has a local configuration change for Ethernet OAM
         this interface.  This value is initialized to all zeros
         (0x00000000), and is invalid if the dot3OamPeerStatus is
         inactive.

         The configuration revision can be determined from the Revision
         field of the Local Information TLV of the most recently
         received Information OAMPDU with a Local Information TLV.

         An Information OAMPDU is indicated by a valid frame with (1)
         destination MAC address equal to that of the reserved MAC
         address for Slow Protocols (See 43B of [802.3ah]), (2) a
         lengthOrType field equal to the reserved type for Slow
         Protocols, (3) a Slow Protocols subtype equal to that of the
         subtype reserved for OAM, and (4) a OAM code that equals the
         code reserved for Information OAMPDUs.  "
       REFERENCE   "[802.3ah], 30.3.6.1.13."
       ::= { dot3OamPeerEntry 7 }


--

     dot3OamPeerFunctionsSupported OBJECT-TYPE
       SYNTAX      BITS {
                     unidirectionalSupport (0),
                     loopbackSupport(1),
                     eventSupport(2),
                     variableSupport(3)
                   }
       MAX-ACCESS  read-only
       STATUS      current
       DESCRIPTION
         "The OAM functions supported on this Ethernet like interface.
         OAM consists of separate functionality sets above the basic
         discovery process.  This value indicates the capabilities of
         the peer OAM entity with respect to these functions.  This
         value is initialized so all bits are clear, and is invalid if
         the dot3OamPeerStatus is inactive.

         The capbilities of the OAM peer can be determined from the
         configuration field of the Local Information TLV of the most
         recently received Information OAMPDU with a Local Information
         TLV.

         An Information OAMPDU is indicated by a valid frame with (1)
         destination MAC address equal to that of the reserved MAC
         address for Slow Protocols (See 43B of [802.3ah]), (2) a
         lengthOrType field equal to the reserved type for Slow
         Protocols, (3) a Slow Protocols subtype equal to that of the
         subtype reserved for OAM, and (4) a OAM code that equals the
         code reserved for Information OAMPDUs.  "
       REFERENCE   "[802.3ah], REFERENCE 30.3.6.1.7."
       ::= { dot3OamPeerEntry 8 }


     ------------------------------------------------------------------
     --
     -- Ethernet OAM Loopback group
     --


     dot3OamLoopbackTable OBJECT-TYPE
       SYNTAX      SEQUENCE OF Dot3OamLoopbackEntry
       MAX-ACCESS  not-accessible
       STATUS      current
       DESCRIPTION
         "This table contains methods to control the loopback state of
         the local link as well as indicating the status of the
         loopback function.

         Loopback can be used to place the remote OAM entity in a state
         where every received frame (except OAMPDUs) are echoed back
         over the same interface on which they were received.   In this
         state, at the remote entity, 'normal' traffic is disabled as
         only the looped back frames are transmitted on the interface.
         Loopback is thus an intrusive operation that prohibits normal
         data flow and should be used accordingly.  "
       ::= { dot3OamMIB 3 }

     dot3OamLoopbackEntry OBJECT-TYPE
       SYNTAX      Dot3OamLoopbackEntry
       MAX-ACCESS  not-accessible
       STATUS      current
       DESCRIPTION
         "An entry in the table, containing information on the loopback
         status for a single Ethernet like interface.  There is an
         entry in this table for every Ethernet like interface on which
         supports OAM and loopback function within OAM (as indicated in
         dot3OamFunctionsSupported).  "
       INDEX       { ifIndex }
       ::= { dot3OamLoopbackTable 1 }

     Dot3OamLoopbackEntry ::=
       SEQUENCE {
         dot3OamLoopbackCommand            INTEGER,
         dot3OamLoopbackStatus             INTEGER,
         dot3OamLoopbackIgnoreRx           INTEGER
       }

--

     dot3OamLoopbackCommand OBJECT-TYPE
       SYNTAX      INTEGER {
                     noLoopback (1),
                     startRemoteLoopback (2),
                     stopRemoteLoopback (3)
                   }
       MAX-ACCESS  read-write
       STATUS      current
       DESCRIPTION
         "This attribute initiates or terminates remote loopback with
         an OAM peer.  Writing startRemoteLoopback(2) to this attribute
         cause the local OAM client to send a loopback OAMPDU to the
         OAM peer with the loopback enable flags set.  Writing
         stopRemoteLoopback(3) to this attribute will cause the local
         OAM client to send a loopback OAMPDU to the OAM peer with the
         loopback enable flags cleared.  Writing noLoopback to this
         attribute has no effect.

         Writes to this attribute are ignored unless the OAM status of
         this interface is 'operational' (dot3OamOperStatus).

         The attribute always returns noLoopback on a read.  To
         determine the loopback status, use the attribute
         dot3OamLoopbackStatus.  "
       REFERENCE   "[802.3ah], 57.2.11"
       ::= { dot3OamLoopbackEntry 1 }

--

     dot3OamLoopbackStatus OBJECT-TYPE
       SYNTAX      INTEGER {
                     noLoopback (1),
                     initiatingLoopback (2),
                     remoteLoopback (3),
                     terminatingLoopback (4),
                     localLoopback (5),
                     unknown (6)
                   }
       MAX-ACCESS  read-only
       STATUS      current
       DESCRIPTION
         "The loopback status of the OAM entity.  This status is
         determined by a combination of the local parser and
         multiplexer states, the remote parser and multiplexer states,
         as well as by the actions of the local OAM client.  When
         operating in normal mode with no loopback in progress, the
         status reads noLoopback(1).

         If the OAM client has sent an Loopback OAMPDU and is waiting
         for a response, where the local parser and multiplexer states
         are DISCARD (see [802.3ah, 57.2.11.1]), the status is
         'initiatingLoopback'.  In this case, the local OAM entity has
         yet to receive any acknowledgement that the remote OAM entity
         has received its loopback command request.

         If the local OAM client knows that the remote OAM entity is in
         loopback mode (via the remote state information as described
         in [802.3ah, 57.2.11.1, 30.3.6.1.15]), the status is
         remoteLoopback(3).  If the local OAM client is in the process
         of terminating the remote loopback [802.3ah, 57.2.11.3,
         30.3.6.1.14], with its local multiplexer and parser states in
         DISCARD, the status is terminatingLoopback(4).  If the remote
         OAM client has put the local OAM entity in loopback mode as
         indicated by its local parser state, the status is
         localLoopback(5).

         The unknown(6) status indicates the parser and multiplexer
         combination is unexpected.  This status may be returned if the
         OAM loopback is in a transition state but should not persist.

         The values of this attribute correspond to the following
         values of the local and remote parser and multiplexer states.

           value            LclPrsr   LclMux    RmtPrsr   RmtMux
           noLoopback         FWD       FWD       FWD       FWD
           initLoopback     DISCARD   DISCARD     FWD       FWD
           rmtLoopback      DISCARD     FWD      LPBK    DISCARD
           tmtngLoopback    DISCARD   DISCARD    LPBK    DISCARD
           lclLoopback        LPBK    DISCARD   DISCARD     FWD
           unknown            ***   any other combination   ***
         "
       REFERENCE   "[802.3ah], REFERENCE 57.2.11, 30.3.61.14,
         30.3.6.1.15"
       ::= { dot3OamLoopbackEntry 2 }

--

     dot3OamLoopbackIgnoreRx OBJECT-TYPE
       SYNTAX      INTEGER { ignore(1), process(2) }
       MAX-ACCESS  read-write
       STATUS      current
       DESCRIPTION
         "Since OAM loopback is a distruptive operation (user traffic
         does not pass), this attribute provides a mechanism to provide
         controls over whether received OAM loopback commands are
         processed or ignored.  When the value is ignore(1), received
         loopback commands are ignored.  When the value is process(2),
         OAM loopback commands are processed.  The default value is to
         ignore loopback commands (ignore(1)).

         The attribute has no meaning if the local OAM entity does not
         support the loopback function (as defined in
         dot3OamFunctionsSupported).  "
       REFERENCE   "[802.3ah], REFERENCE 57.2.11, 30.3.61.14,
         30.3.6.1.15"
       ::= { dot3OamLoopbackEntry 3 }


     ------------------------------------------------------------------
     --
     -- Ethernet OAM Statistics group
     --


     dot3OamStatsTable OBJECT-TYPE
       SYNTAX      SEQUENCE OF Dot3OamStatsEntry
       MAX-ACCESS  not-accessible
       STATUS      current
       DESCRIPTION
         "Statistics for the OAM function on a particular Ethernet like
         interface."
       ::= { dot3OamMIB 4 }

     dot3OamStatsEntry OBJECT-TYPE
       SYNTAX      Dot3OamStatsEntry
       MAX-ACCESS  not-accessible
       STATUS      current
       DESCRIPTION
         "An entry in the table, containing statistics information on
         the Ethernet OAM function for a single Ethernet like
         interface."
       INDEX       { ifIndex }
       ::= { dot3OamStatsTable 1 }

     Dot3OamStatsEntry ::=
       SEQUENCE {
                 dot3OamInformationTx                Counter32,
                 dot3OamInformationRx                Counter32,
                 dot3OamUniqueEventNotificationTx    Counter32,
                 dot3OamUniqueEventNotificationRx    Counter32,
                 dot3OamDuplicateEventNotificationTx Counter32,
                 dot3OamDuplicateEventNotificationRx Counter32,
                 dot3OamLoopbackControlTx            Counter32,
                 dot3OamLoopbackControlRx            Counter32,
                 dot3OamVariableRequestTx            Counter32,
                 dot3OamVariableRequestRx            Counter32,
                 dot3OamVariableResponseTx           Counter32,
                 dot3OamVariableResponseRx           Counter32,
                 dot3OamOrgSpecificTx                Counter32,
                 dot3OamOrgSpecificRx                Counter32,
                 dot3OamUnsupportedCodesTx           Counter32,
                 dot3OamUnsupportedCodesRx           Counter32,
                 dot3OamFramesLostDueToOam           Counter32
                }


--

     dot3OamInformationTx OBJECT-TYPE
       SYNTAX      Counter32
       UNITS       "frames"
       MAX-ACCESS  read-only
       STATUS      current
       DESCRIPTION
         "A count of the number of Information OAMPDUs transmitted on
         this interface.

         An Information OAMPDU is indicated by a valid frame with (1)
         destination MAC address equal to that of the reserved MAC
         address for Slow Protocols (See 43B of [802.3ah]), (2) a
         lengthOrType field equal to the reserved type for Slow
         Protocols, (3) a Slow Protocols subtype equal to that of the
         subtype reserved for OAM, and (4) an OAMPDU code equals the
         OAM Information code.

         Discontinuities of this counter can occur at re-initialization
         of the management system, and at other times as indicated by
         the value of the ifCounterDiscontinuityTime.  "
       REFERENCE   "[802.3ah], 30.3.6.1.20."
       ::= { dot3OamStatsEntry 1 }

--

     dot3OamInformationRx OBJECT-TYPE
       SYNTAX      Counter32
       UNITS       "frames"
       MAX-ACCESS  read-only
       STATUS      current
       DESCRIPTION
         "A count of the number of Information OAMPDUs received on this
         interface.

         An Information OAMPDU is indicated by a valid frame with (1)
         destination MAC address equal to that of the reserved MAC
         address for Slow Protocols (See 43B of [802.3ah]), (2) a
         lengthOrType field equal to the reserved type for Slow
         Protocols, (3) a Slow Protocols subtype equal to that of the
         subtype reserved for OAM, and (4) an OAMPDU code equals the
         OAM Information code.

         Discontinuities of this counter can occur at re-initialization
         of the management system, and at other times as indicated by
         the value of the ifCounterDiscontinuityTime.  "
       REFERENCE   "[802.3ah], 30.3.6.1.21."
       ::= { dot3OamStatsEntry 2 }

--

     dot3OamUniqueEventNotificationTx OBJECT-TYPE
       SYNTAX      Counter32
       UNITS       "frames"
       MAX-ACCESS  read-only
       STATUS      current
       DESCRIPTION
         "A count of the number of unique Event OAMPDUs transmitted on
         this interface.  Event notifications may be sent in duplicate
         to increase the probability of successfully being received,
         given the possiblity that a frame may be lost in transit.

         An Event Notification OAMPDU is indicated by a valid frame
         with (1) destination MAC address equal to that of the reserved
         MAC address for Slow Protocols (See 43B of [802.3ah]), (2) a
         lengthOrType field equal to the reserved type for Slow
         Protocols, (3) a Slow Protocols subtype equal to that of the
         subtype reserved for OAM, and (4) an OAMPDU code equals the
         OAM Event code.

         A unique Event Notification OAMPDU is indicated as an Event
         Notification OAMPDU with a Sequence Number field that is
         distinct from the previously transmitted Event Notification
         OAMPDU Sequence Number.

         Discontinuities of this counter can occur at re-initialization
         of the management system, and at other times as indicated by
         the value of the ifCounterDiscontinuityTime.  "

       REFERENCE   "[802.3ah], 30.3.6.1.22."
       ::= { dot3OamStatsEntry 3 }

--

     dot3OamUniqueEventNotificationRx OBJECT-TYPE
       SYNTAX      Counter32
       UNITS       "frames"
       MAX-ACCESS  read-only
       STATUS      current
       DESCRIPTION
         "A count of the number of unique Event OAMPDUs received on
         this interface.  Event notification OAMPDUs may be sent in
         duplicate to increase the probability of successfully being
         received, given the possiblity that a frame may be lost in
         transit.

         An Event Notification OAMPDU is indicated by a valid frame
         with (1) destination MAC address equal to that of the reserved
         MAC address for Slow Protocols (See 43B of [802.3ah]), (2) a
         lengthOrType field equal to the reserved type for Slow
         Protocols, (3) a Slow Protocols subtype equal to that of the
         subtype reserved for OAM, and (4) an OAMPDU code equals the
         OAM Event code.

         A unique Event Notification OAMPDU is indicated as an Event
         Notification OAMPDU with a Sequence Number field that is
         distinct from the previously received Event Notification
         OAMPDU Sequence Number.

         Discontinuities of this counter can occur at re-initialization
         of the management system, and at other times as indicated by
         the value of the ifCounterDiscontinuityTime.  "
       REFERENCE   "[802.3ah], 30.3.6.1.24."
       ::= { dot3OamStatsEntry 4 }

--

     dot3OamDuplicateEventNotificationTx OBJECT-TYPE
       SYNTAX      Counter32
       UNITS       "frames"
       MAX-ACCESS  read-only
       STATUS      current
       DESCRIPTION
         "A count of the number of duplicate Event OAMPDUs transmitted
         on this interface.  Event notification OAMPDUs may be sent in
         duplicate to increase the probability of successfully being
         received, given the possiblity that a frame may be lost in
         transit.

         An Event Notification OAMPDU is indicated by a valid frame
         with (1) destination MAC address equal to that of the reserved
         MAC address for Slow Protocols (See 43B of [802.3ah]), (2) a
         lengthOrType field equal to the reserved type for Slow
         Protocols, (3) a Slow Protocols subtype equal to that of the
         subtype reserved for OAM, and (4) an OAMPDU code equals the
         OAM Event code.

         A duplicate Event Notification OAMPDU is indicated as an Event
         Notification OAMPDU with a Sequence Number field that is
         identical to the previously transmitted Event Notification
         OAMPDU Sequence Number.

         Discontinuities of this counter can occur at re-initialization
         of the management system, and at other times as indicated by
         the value of the ifCounterDiscontinuityTime.  "
       REFERENCE   "[802.3ah], 30.3.6.1.23."
       ::= { dot3OamStatsEntry 5 }

--

     dot3OamDuplicateEventNotificationRx OBJECT-TYPE
       SYNTAX      Counter32
       UNITS       "frames"
       MAX-ACCESS  read-only
       STATUS      current
       DESCRIPTION
         "A count of the number of duplicate Event OAMPDUs received on
         this interface.  Event notification OAMPDUs may be sent in
         duplicate to increase the probability of successfully being
         received, given the possiblity that a frame may be lost in
         transit.

         An Event Notification OAMPDU is indicated by a valid frame
         with (1) destination MAC address equal to that of the reserved
         MAC address for Slow Protocols (See 43B of [802.3ah]), (2) a
         lengthOrType field equal to the reserved type for Slow
         Protocols, (3) a Slow Protocols subtype equal to that of the
         subtype reserved for OAM, and (4) an OAMPDU code equals the
         OAM Event code.

         A duplicate Event Notification OAMPDU is indicated as an Event
         Notification OAMPDU with a Sequence Number field that is
         identical to the previously received Event Notification OAMPDU
         Sequence Number.

         Discontinuities of this counter can occur at re-initialization
         of the management system, and at other times as indicated by
         the value of the ifCounterDiscontinuityTime.  "
       REFERENCE   "[802.3ah], 30.3.6.1.25."
       ::= { dot3OamStatsEntry 6 }

--

     dot3OamLoopbackControlTx OBJECT-TYPE
       SYNTAX      Counter32
       UNITS       "frames"
       MAX-ACCESS  read-only
       STATUS      current
       DESCRIPTION
         "A count of the number of Loopback Control OAMPDUs transmitted
         on this interface.

         An Loopback Conrol OAMPDU is indicated by a valid frame with
         (1) destination MAC address equal to that of the reserved MAC
         address for Slow Protocols (See 43B of [802.3ah]), (2) a
         lengthOrType field equal to the reserved type for Slow
         Protocols, (3) a Slow Protocols subtype equal to that of the
         subtype reserved for OAM, and (4) an OAMPDU code equals the
         OAM Loopback Control code.

         Discontinuities of this counter can occur at re-initialization
         of the management system, and at other times as indicated by
         the value of the ifCounterDiscontinuityTime.  "
       REFERENCE   "[802.3ah], 30.3.6.1.26."
       ::= { dot3OamStatsEntry 7 }

--

     dot3OamLoopbackControlRx OBJECT-TYPE
       SYNTAX      Counter32
       UNITS       "frames"
       MAX-ACCESS  read-only
       STATUS      current
       DESCRIPTION
         "A count of the number of Loopback Control OAMPDUs transmitted
         on this interface.

         An Loopback Control OAMPDU is indicated by a valid frame with
         (1) destination MAC address equal to that of the reserved MAC
         address for Slow Protocols (See 43B of [802.3ah]), (2) a
         lengthOrType field equal to the reserved type for Slow
         Protocols, (3) a Slow Protocols subtype equal to that of the
         subtype reserved for OAM, and (4) an OAMPDU code equals the
         OAM Loopback Control code.

         Discontinuities of this counter can occur at re-initialization
         of the management system, and at other times as indicated by
         the value of the ifCounterDiscontinuityTime.  "
       REFERENCE   "[802.3ah], 30.3.6.1.27."
       ::= { dot3OamStatsEntry 8 }

--

     dot3OamVariableRequestTx OBJECT-TYPE
       SYNTAX      Counter32
       UNITS       "frames"
       MAX-ACCESS  read-only
       STATUS      current
       DESCRIPTION
         "A count of the number of Variable Request OAMPDUs transmitted
         on this interface.

         An Variable Request OAMPDU is indicated by a valid frame with
         (1) destination MAC address equal to that of the reserved MAC
         address for Slow Protocols (See 43B of [802.3ah]), (2) a
         lengthOrType field equal to the reserved type for Slow
         Protocols, (3) a Slow Protocols subtype equal to that of the
         subtype reserved for OAM, and (4) an OAMPDU code equals the
         OAM Variable Request code.

         Discontinuities of this counter can occur at re-initialization
         of the management system, and at other times as indicated by
         the value of the ifCounterDiscontinuityTime.  "
       REFERENCE   "[802.3ah], 30.3.6.1.28."
       ::= { dot3OamStatsEntry 9 }

--

     dot3OamVariableRequestRx OBJECT-TYPE
       SYNTAX      Counter32
       UNITS       "frames"
       MAX-ACCESS  read-only
       STATUS      current
       DESCRIPTION
         "A count of the number of Variable Request OAMPDUs received on
         this interface.

         An Variable Request OAMPDU is indicated by a valid frame with
         (1) destination MAC address equal to that of the reserved MAC
         address for Slow Protocols (See 43B of [802.3ah]), (2) a
         lengthOrType field equal to the reserved type for Slow
         Protocols, (3) a Slow Protocols subtype equal to that of the
         subtype reserved for OAM, and (4) an OAMPDU code equals the
         OAM Variable Request code.

         Discontinuities of this counter can occur at re-initialization
         of the management system, and at other times as indicated by
         the value of the ifCounterDiscontinuityTime.  "
       REFERENCE   "[802.3ah], 30.3.6.1.29."
       ::= { dot3OamStatsEntry 10 }

--

     dot3OamVariableResponseTx OBJECT-TYPE
       SYNTAX      Counter32
       UNITS       "frames"
       MAX-ACCESS  read-only
       STATUS      current
       DESCRIPTION
         "A count of the number of Variable Response OAMPDUs
         transmitted on this interface.

         An Variable Response OAMPDU is indicated by a valid frame with
         (1) destination MAC address equal to that of the reserved MAC
         address for Slow Protocols (See 43B of [802.3ah]), (2) a
         lengthOrType field equal to the reserved type for Slow
         Protocols, (3) a Slow Protocols subtype equal to that of the
         subtype reserved for OAM, and (4) an OAMPDU code equals the
         OAM Variable Response code.

         Discontinuities of this counter can occur at re-initialization
         of the management system, and at other times as indicated by
         the value of the ifCounterDiscontinuityTime.  "
       REFERENCE   "[802.3ah], 30.3.6.1.30."
       ::= { dot3OamStatsEntry 11 }

--

     dot3OamVariableResponseRx OBJECT-TYPE
       SYNTAX      Counter32
       UNITS       "frames"
       MAX-ACCESS  read-only
       STATUS      current
       DESCRIPTION
         "A count of the number of Variable Response OAMPDUs received
         on this interface.

         An Variable Response OAMPDU is indicated by a valid frame with
         (1) destination MAC address equal to that of the reserved MAC
         address for Slow Protocols (See 43B of [802.3ah]), (2) a
         lengthOrType field equal to the reserved type for Slow
         Protocols, (3) a Slow Protocols subtype equal to that of the
         subtype reserved for OAM, and (4) an OAMPDU code equals the
         OAM Variable Response code.

         Discontinuities of this counter can occur at re-initialization
         of the management system, and at other times as indicated by
         the value of the ifCounterDiscontinuityTime.  "
       REFERENCE   "[802.3ah], 30.3.6.1.31."
       ::= { dot3OamStatsEntry 12 }

--

      dot3OamOrgSpecificTx OBJECT-TYPE
       SYNTAX      Counter32
       UNITS       "frames"
       MAX-ACCESS  read-only
       STATUS      current
       DESCRIPTION
         "A count of the number of Organization Specific OAMPDUs
         transmitted on this interface.

         An Organization Specific OAMPDU is indicated by a valid frame
         with (1) destination MAC address equal to that of the reserved
         MAC address for Slow Protocols (See 43B of [802.3ah]), (2) a
         lengthOrType field equal to the reserved type for Slow
         Protocols, (3) a Slow Protocols subtype equal to that of the
         subtype reserved for OAM, and (4) an OAMPDU code equals the
         OAM Organization Specific code.

         Discontinuities of this counter can occur at re-initialization
         of the management system, and at other times as indicated by
         the value of the ifCounterDiscontinuityTime.  "
       REFERENCE   "[802.3ah], 30.3.6.1.32."
       ::= { dot3OamStatsEntry 13 }

--

     dot3OamOrgSpecificRx OBJECT-TYPE
       SYNTAX      Counter32
       UNITS       "frames"
       MAX-ACCESS  read-only
       STATUS      current
       DESCRIPTION

         "A count of the number of Organization Specific OAMPDUs
         received on this interface.

         An Organization Specific OAMPDU is indicated by a valid frame
         with (1) destination MAC address equal to that of the reserved
         MAC address for Slow Protocols (See 43B of [802.3ah]), (2) a
         lengthOrType field equal to the reserved type for Slow
         Protocols, (3) a Slow Protocols subtype equal to that of the
         subtype reserved for OAM, and (4) an OAMPDU code equals the
         OAM Organization Specific code.

         Discontinuities of this counter can occur at re-initialization
         of the management system, and at other times as indicated by
         the value of the ifCounterDiscontinuityTime.  "
       REFERENCE   "[802.3ah], 30.3.6.1.33."
       ::= { dot3OamStatsEntry 14 }

--

     dot3OamUnsupportedCodesTx OBJECT-TYPE
       SYNTAX      Counter32
       UNITS       "frames"
       MAX-ACCESS  read-only
       STATUS      current
       DESCRIPTION
         "A count of the number of OAMPDUs transmitted on this
         interface with an unsupported op-code.

         An unsupported opcode OAMPDU is indicated by a valid frame
         with (1) destination MAC address equal to that of the reserved
         MAC address for Slow Protocols (See 43B of [802.3ah]), (2) a
         lengthOrType field equal to the reserved type for Slow
         Protocols, (3) a Slow Protocols subtype equal to that of the
         subtype reserved for OAM, and (4) an OAMPDU code equals the
         opcode for a function that is not supported by the device.

         Discontinuities of this counter can occur at re-initialization
         of the management system, and at other times as indicated by
         the value of the ifCounterDiscontinuityTime.  "
       REFERENCE   "[802.3ah], 30.3.6.1.18."
       ::= { dot3OamStatsEntry 15 }

--

     dot3OamUnsupportedCodesRx OBJECT-TYPE
       SYNTAX      Counter32
       UNITS       "frames"
       MAX-ACCESS  read-only
       STATUS      current
       DESCRIPTION
         "A count of the number of OAMPDUs received on this interface
         with an unsupported op-code.

         An unsupported opcode OAMPDU is indicated by a valid frame
         with (1) destination MAC address equal to that of the reserved
         MAC address for Slow Protocols (See 43B of [802.3ah]), (2) a
         lengthOrType field equal to the reserved type for Slow
         Protocols, (3) a Slow Protocols subtype equal to that of the
         subtype reserved for OAM, and (4) an OAMPDU code equals the
         opcode for a function that is not supported by the device.

         Discontinuities of this counter can occur at re-initialization
         of the management system, and at other times as indicated by
         the value of the ifCounterDiscontinuityTime.  "
       REFERENCE   "[802.3ah], 30.3.6.1.19."
       ::= { dot3OamStatsEntry 16 }

--

     dot3OamFramesLostDueToOam OBJECT-TYPE
       SYNTAX      Counter32
       UNITS       "frames"
       MAX-ACCESS  read-only
       STATUS      current
       DESCRIPTION
         "A count of the number of frames that were dropped by the OAM
         multiplexer.  Since the OAM mulitplexer has multiple inputs
         and a single output, there may be cases where frames are
         dropped due to transmit resource contention.  This counter is
         incremented whenever a frame is dropped by the OAM layer.
         When this counter is incremented, no other counters in this
         MIB are incremented.

         Discontinuities of this counter can occur at re-initialization
         of the management system, and at other times as indicated by
         the value of the ifCounterDiscontinuityTime.  "
       REFERENCE   "[802.3ah], 30.3.6.1.46."
       ::= { dot3OamStatsEntry 17 }


     ------------------------------------------------------------------
     --
     -- Ethernet OAM Event Configuration group
     --


     dot3OamEventConfigTable OBJECT-TYPE
       SYNTAX     SEQUENCE OF Dot3OamEventConfigEntry
       MAX-ACCESS not-accessible
       STATUS     current
       DESCRIPTION
         "Ethernet OAM includes the ability to generate and receive
         event notifications to indicate various link problems.  This
         table contains the mechanisms to configure the thresholds to
         generate the standard Ethernet OAM events.

         These events are:
           - Errored Symbol Period Event.  Generated when the number of
             symbol errors exceeds a threshold within a given window
             defined by a number of symbols (e.g. 1,000 symbols out of
             1,000,000 had errors).
           - Errored Frame Period Event.  Generated when the number of
             frame errors exceeds a threshold within a given window
             defined by a number of frames (e.g. 10 frames out of 1000
             had errors).
           - Errored Frame Event.  Generated when the number of frame
             errors exceeds a threshold within a given window defined
             by a period of time (e.g. 10 frames in 1 second had
             errors).
           - Errored Frame Seconds Summary Event.  Generated when the
             number of errored frame seconds exceeds a threshold within
             a given time period (e.g. 10 errored frame seconds within
             the last 100 seconds).  An errored frame second is defined
             as a 1 second interval which had >0 frame errors.
         "
       ::= { dot3OamMIB 5 }

     dot3OamEventConfigEntry OBJECT-TYPE
       SYNTAX      Dot3OamEventConfigEntry
       MAX-ACCESS  not-accessible
       STATUS      current
       DESCRIPTION
         "Event configuration information is available for every
         Ethernet like interface that supports OAM and the event
         function of OAM as indicated in the dot3OamFunctionsSupported
         attribute.

         Event configuration controls when the local management entity
         sends Event Notification OAMPDUs to its OAM peer.  "
       INDEX       { ifIndex }
       ::= { dot3OamEventConfigTable 1 }

     Dot3OamEventConfigEntry ::=
       SEQUENCE {
                 dot3OamErrSymPeriodWindowHi        Unsigned32,
                 dot3OamErrSymPeriodWindowLo        Unsigned32,
                 dot3OamErrSymPeriodThresholdHi     Unsigned32,
                 dot3OamErrSymPeriodThresholdLo     Unsigned32,
                 dot3OamErrSymPeriodEvNotifEnable   INTEGER,
                 dot3OamErrFramePeriodWindow        Unsigned32,
                 dot3OamErrFramePeriodThreshold     Unsigned32,
                 dot3OamErrFramePeriodEvNotifEnable INTEGER,
                 dot3OamErrFrameWindow              Unsigned32,
                 dot3OamErrFrameThreshold           Unsigned32,
                 dot3OamErrFrameEvNotifEnable       INTEGER,
                 dot3OamErrFrameSecsSummaryWindow   Integer32,
                 dot3OamErrFrameSecsSummaryThreshold Integer32,
                 dot3OamErrFrameSecsEvNotifEnable   INTEGER,
           dot3OamDyingGaspEnable             INTEGER,
           dot3OamCriticalEventEnable         INTEGER
               }


--

     dot3OamErrSymPeriodWindowHi OBJECT-TYPE
       SYNTAX      Unsigned32
       UNITS       "2^32 symbols"
       MAX-ACCESS  read-write
       STATUS      current
       DESCRIPTION
         "The two objects dot3OamErrSymPeriodWindowHi and
         dot3OamErrSymPeriodLo together form an unsigned 64-bit
         integer representing the number of symbols over which this
         threshold event is defined.  This is defined as

       dot3OamErrSymPeriodWindow = ((2^32)*dot3OamErrSymPeriodWindowHi)
                                         + dot3OamErrSymPeriodWindowLo

         If dot3OamErrSymPeriodThreshold symbol errors occur within a
         window of dot3OamErrSymPeriodWindow symbols, an Event
         Notification OAMPDU should be generated with an Errored Symbol
         Period Event TLV indicating the threshold has been crossed in
         this window.

         The default value for dot3OamErrSymPeriodWindow is the number
         of symbols in one second for the underlying physical layer."
       REFERENCE   "[802.3ah], 30.3.6.1.34"
       ::= { dot3OamEventConfigEntry 1 }

--

     dot3OamErrSymPeriodWindowLo OBJECT-TYPE
       SYNTAX      Unsigned32
       UNITS       "symbols"
       MAX-ACCESS  read-write
       STATUS      current
       DESCRIPTION
         "The two objects dot3OamErrSymPeriodWindowHi and
         dot3OamErrSymPeriodWindowLo together form an unsigned 64-bit
         integer representing the number of symbols over which this
         threshold event is defined.  This is defined as

       dot3OamErrSymPeriodWindow = ((2^32)*dot3OamErrSymPeriodWindowHi)
                                         + dot3OamErrSymPeriodWindowLo

         If dot3OamErrSymPeriodThreshold symbol errors occur within a
         window of dot3OamErrSymPeriodWindow symbols, an Event
         Notification OAMPDU should be generated with an Errored Symbol
         Period Event TLV indicating the threshold has been crossed in
         this window.

         The default value for dot3OamErrSymPeriodWindow is the number
         of symbols in one second for the underlying physical layer. "
       REFERENCE   "[802.3ah], 30.3.6.1.34"
       ::= { dot3OamEventConfigEntry 2 }

--

     dot3OamErrSymPeriodThresholdHi OBJECT-TYPE
       SYNTAX      Unsigned32
       UNITS       "2^32 symbols"
       MAX-ACCESS  read-write
       STATUS      current
       DESCRIPTION
         "The two objects dot3OamErrSymPeriodThresholdHi and
         dot3OamErrSymPeriodThresholdLo together form an unsigned
         64-bit integer representing the number of symbol errors that
         must occur within a given window to cause this event.

         This is defined as

           dot3OamErrSymPeriodThreshold =
                             ((2^32) * dot3OamErrSymPeriodThresholdHi)
                                     + dot3OamErrSymPeriodThresholdLo


         If dot3OamErrSymPeriodThreshold symbol errors occur within a
         window of dot3OamErrSymPeriodWindow symbols, an Event
         Notification OAMPDU should be generated with an Errored Symbol
         Period Event TLV indicating the threshold has been crossed in
         this window.

         The default value for dot3OamErrSymPeriodThreshold is one
         symbol errors.  "
       REFERENCE   "[802.3ah], 30.3.6.1.34"
       ::= { dot3OamEventConfigEntry 3 }

--

     dot3OamErrSymPeriodThresholdLo OBJECT-TYPE
       SYNTAX      Unsigned32
       UNITS       "symbols"
       MAX-ACCESS  read-write
       STATUS      current
       DESCRIPTION
         "The two objects dot3OamErrSymPeriodThresholdHi and
         dot3OamErrSymPeriodThresholdLo together form an unsigned
         64-bit integer representing the number of symbol errors that
         must occur within a given window to cause this event.

         This is defined as

           dot3OamErrSymPeriodThreshold =
                             ((2^32) * dot3OamErrSymPeriodThresholdHi)
                                     + dot3OamErrSymPeriodThresholdLo


         If dot3OamErrSymPeriodThreshold symbol errors occur within a
         window of dot3OamErrSymPeriodWindow symbols, an Event
         Notification OAMPDU should be generated with an Errored Symbol
         Period Event TLV indicating the threshold has been crossed in
         this window.

         The default value for dot3OamErrSymPeriodThreshold is one
         symbol error.  "
       REFERENCE   "[802.3ah], 30.3.6.1.34"
       ::= { dot3OamEventConfigEntry 4 }

--

     dot3OamErrSymPeriodEvNotifEnable OBJECT-TYPE
       SYNTAX      INTEGER { enabled(1), disabled(2) }
       MAX-ACCESS  read-write
       STATUS      current
       DESCRIPTION
         "Indicates whether the occurence of Errored Symbol Period
         Events should result in Event Notification OAMPDUs generated
         by the OAM layer.

         By default, this object should have the value enabled(1) for
         Ethernet like interfaces that support OAM.  If the OAM layer
         does not support event notifications (as indicated via the
         dot3OamFunctionsSupported attribute), this value is ignored.
         "
       ::= { dot3OamEventConfigEntry 5 }

--

     dot3OamErrFramePeriodWindow OBJECT-TYPE
       SYNTAX      Unsigned32
       UNITS       "frames"
       MAX-ACCESS  read-write
       STATUS      current
       DESCRIPTION
         "The number of frames over which the threshold is defined.
  The
         default value of the window is the number of minimum size
         Ethernet frames that can be received over the physical layer
  in
         one second.

         If dot3OamErrFramePeriodThreshold frame errors occur within a
         window of dot3OamErrFramePeriodWindow frames, an Event
         Notification OAMPDU should be generated with an Errored Frame
         Period Event TLV indicating the threshold has been crossed in
         this window.  "
       REFERENCE   "[802.3ah], 30.3.6.1.38"
       ::= { dot3OamEventConfigEntry 6 }

--

     dot3OamErrFramePeriodThreshold OBJECT-TYPE
       SYNTAX      Unsigned32
       UNITS       "frames"
       MAX-ACCESS  read-write
       STATUS      current
       DESCRIPTION
         "The number of frame errors that must occur for this event to
         be triggered.  The default value is one frame error.

         If dot3OamErrFramePeriodThreshold frame errors occur within a
         window of dot3OamErrFramePeriodWindow frames, an Event
         Notification OAMPDU should be generated with an Errored Frame
         Period Event TLV indicating the threshold has been crossed in
         this window.  "
       REFERENCE   "[802.3ah], 30.3.6.1.38"
       ::= { dot3OamEventConfigEntry 7 }

--

     dot3OamErrFramePeriodEvNotifEnable OBJECT-TYPE
       SYNTAX      INTEGER { enabled(1), disabled(2) }
       MAX-ACCESS  read-write
       STATUS      current
       DESCRIPTION
         "Indicates whether the occurence of an Errored Frame Period
         Event should result in an Event Notification OAMPDU generated
         by the OAM layer.

         By default, this object should have the value enabled(1) for
         Ethernet like interfaces that support OAM.  If the OAM layer
         does not support event notifications (as indicated via the
         dot3OamFunctionsSupported attribute), this value is ignored. "
       ::= { dot3OamEventConfigEntry 8 }

--

     dot3OamErrFrameWindow OBJECT-TYPE
       SYNTAX      Unsigned32
       UNITS       "tenths of a second"
       MAX-ACCESS  read-write
       STATUS      current
       DESCRIPTION
         "The amount of time (in 100ms increments) over which the
         threshold is defined.  The default value is 10 (1 second).

        If dot3OamErrFrameThreshold frame errors occur within a window
        of dot3OamErrFrameWindow seconds (measured in tenths of
        seconds), an Event Notification OAMPDU should be generated with
        an Errored Frame Event TLV indicating the threshold has been
        crossed in this window.  "
       REFERENCE   "[802.3ah], 30.3.6.1.36"
       ::= { dot3OamEventConfigEntry 9 }

--


     dot3OamErrFrameThreshold OBJECT-TYPE
       SYNTAX      Unsigned32
       UNITS       "frames"
       MAX-ACCESS  read-write
       STATUS      current
       DESCRIPTION
         "The number of frame errors that must occur for this event to
         be triggered.  The default value is one frame error.

         If dot3OamErrFrameThreshold frame errors occur within a window
         of dot3OamErrFrameWindow (in tenths of seconds), an Event
         Notification OAMPDU should be generated with an Errored Frame
         Event TLV indicating the threshold has been crossed in this
         window.  "
       REFERENCE   "[802.3ah], 30.3.6.1.36"
       ::= { dot3OamEventConfigEntry 10 }

--

     dot3OamErrFrameEvNotifEnable OBJECT-TYPE
       SYNTAX      INTEGER { enabled(1), disabled(2) }
       MAX-ACCESS  read-write
       STATUS      current
       DESCRIPTION
         "Indicates whether the occurence of an Errored Frame Event
         should result in an Event Notification OAMPDU generated by the
         OAM layer.

         By default, this object should have the value enabled(1) for
         Ethernet like interfaces that support OAM.  If the OAM layer
         does not support event notifications (as indicated via the
         dot3OamFunctionsSupported attribute), this value is ignored. "
       ::= { dot3OamEventConfigEntry 11 }

--

     dot3OamErrFrameSecsSummaryWindow OBJECT-TYPE
       SYNTAX      Integer32 (100..9000)
       UNITS       "tenths of a second"
       MAX-ACCESS  read-write
       STATUS      current
       DESCRIPTION
         "The amount of time (in 100ms intervals) over which the
         threshold is defined.  The default value is 100 (10 seconds).

         If dot3OamErrFrameSecsSummaryThreshold frame errors occur
         within a window of dot3OamErrFrameSecsSummaryWindow (in tenths
         of seconds), an Event Notification OAMPDU should be generated
         with an Errored Frame Seconds Summary Event TLV indicating the
         threshold has been crossed in this window.  "
       REFERENCE   "[802.3ah], 30.3.6.1.40"
       ::= { dot3OamEventConfigEntry 12 }

--

     dot3OamErrFrameSecsSummaryThreshold OBJECT-TYPE
       SYNTAX      Integer32 (1..900)
       UNITS       "errored frame seconds"
       MAX-ACCESS  read-write
       STATUS      current
       DESCRIPTION
         "The number of errored frame seconds that must occur for this
         event to be triggered.  The default value is one errored frame
         second.

         If dot3OamErrFrameSecsSummaryThreshold frame errors occur
         within a window of dot3OamErrFrameSecsSummaryWindow (in tenths
         of seconds), an Event Notification OAMPDU should be generated
         with an Errored Frame Seconds Summary Event TLV indicating the
         threshold has been crossed in this window.  "
       REFERENCE   "[802.3ah], 30.3.6.1.40"
       ::= { dot3OamEventConfigEntry 13 }

--

     dot3OamErrFrameSecsEvNotifEnable OBJECT-TYPE
       SYNTAX      INTEGER { enabled(1), disabled(2) }
       MAX-ACCESS  read-write
       STATUS      current
       DESCRIPTION
         "Indicates whether the occurence of an Errored Frame Seconds
         Summary Event should result in an Event Notification OAMPDU
         generated by the OAM layer.

         By default, this object should have the value enabled(1) for
         Ethernet like interfaces that support OAM.  If the OAM layer
         does not support event notifications (as indicated via the
         dot3OamFunctionsSupported attribute), this value is ignored."
       ::= { dot3OamEventConfigEntry 14 }

--

     dot3OamDyingGaspEnable OBJECT-TYPE
       SYNTAX      INTEGER { enabled(1), disabled(2) }
       MAX-ACCESS  read-write
       STATUS      current
       DESCRIPTION
         "Indicates whether the local device should attempt to indicate
         a dying gasp fault via the OAMPDU flags field to its peer OAM
         entity.  If the system does not support dying gasp capability,
         setting this object has no effect, and reading the object
         should always result in 'disabled(2)'.

         By default, this object should have the value enabled(1) for
         Ethernet like interfaces that support OAM.  If the OAM layer
         does not support event notifications (as indicated via the
         dot3OamFunctionsSupported attribute), this value is ignored."
       ::= { dot3OamEventConfigEntry 15 }

--

     dot3OamCriticalEventEnable OBJECT-TYPE
       SYNTAX      INTEGER { enabled(1), disabled(2) }
       MAX-ACCESS  read-write
       STATUS      current
       DESCRIPTION
         "Indicates whether the local device should attempt to indicate
         a critical event fault via the OAMPDU flags field to its peer
         OAM entity.  If the system does not support critical event
         capability, setting this object has no effect, and reading the
         object should always result in 'disabled(2)'.

         By default, this object should have the value enabled(1) for
         Ethernet like interfaces that support OAM.  If the OAM layer
         does not support event notifications (as indicated via the
         dot3OamFunctionsSupported attribute), this value is ignored."
       ::= { dot3OamEventConfigEntry 16 }


     ------------------------------------------------------------------
     --
     -- Ethernet OAM Event Status group
     --

     dot3OamEventLogTable   OBJECT-TYPE
       SYNTAX       SEQUENCE OF Dot3OamEventLogEntry
       MAX-ACCESS   not-accessible
       STATUS       current
       DESCRIPTION
         "This table records a history of the events that have occurred
         at the Ethernet OAM level.  These events can include locally
         detected events, which may result in locally generated
         OAMPDUs, and remotely detected events, which are detected by
         the OAM peer entity and signaled to the local entity via
         Ethernet OAM.  Ethernet OAM events can be signaled by Event
         Notification OAMPDUs or by the flags field in any OAMPDU.  "
         ::= { dot3OamMIB 6 }

     dot3OamEventLogEntry OBJECT-TYPE
       SYNTAX      Dot3OamEventLogEntry
       MAX-ACCESS  not-accessible
       STATUS      current
       DESCRIPTION "An entry in the dot3OamEventLogTable."
       INDEX       { ifIndex, dot3OamEventLogIndex }
       ::= { dot3OamEventLogTable 1 }

     Dot3OamEventLogEntry ::=
       SEQUENCE {
         dot3OamEventLogIndex                Unsigned32,
         dot3OamEventLogTimestamp            TimeStamp,
         dot3OamEventLogOui                  Dot3Oui,
         dot3OamEventLogType                 Unsigned32,
         dot3OamEventLogLocation             INTEGER,
         dot3OamEventLogWindowHi             Unsigned32,
         dot3OamEventLogWindowLo             Unsigned32,
         dot3OamEventLogThresholdHi          Unsigned32,
         dot3OamEventLogThresholdLo          Unsigned32,
         dot3OamEventLogValue                Counter64,
         dot3OamEventLogRunningTotal         Counter64,
         dot3OamEventLogEventTotal           Unsigned32
       }

     dot3OamEventLogIndex       OBJECT-TYPE
       SYNTAX      Unsigned32
       MAX-ACCESS  not-accessible
       STATUS      current
       DESCRIPTION
         "An arbitrary integer for identifiying individual events
         within the event log.  "
       ::= { dot3OamEventLogEntry 1 }

--

     dot3OamEventLogTimestamp  OBJECT-TYPE
       SYNTAX      TimeStamp
       MAX-ACCESS  read-only
       STATUS      current
       DESCRIPTION
         "The value of sysUpTime at the time of the logged event.  For
         locally generated events, the time of the event can be
         accurately retrieved from sysUpTime.  For remotely generated
         events, the time of the event is indicated by the reception of
         the Event Notification OAMPDU indicating the event occurred on
         the peer.  A system may attempt to adjust the timestamp value
         to more accurately reflect the time of the event at the peer
         OAM entity by using other information, such as that found in
         the timestamp found of the Event Notification TLVs, which
         provides an indication of the relative time between events at
         the peer entity.  "
       ::= { dot3OamEventLogEntry 2 }

--

     dot3OamEventLogOui  OBJECT-TYPE
       SYNTAX      Dot3Oui
       MAX-ACCESS  read-only
       STATUS      current
       DESCRIPTION
         "The OUI of the entity defining the object type.  All IEEE
         802.3 defined events (as appearing in [802.3ah] except for the
         Organizationally Unique Event TLVs) use the IEEE 802.3 OUI of
         0x0180C2.  Organizations defining their own Event Notification
         TLVs include their OUI in the Event Notification TLV which
         gets reflected here.  "
       ::= { dot3OamEventLogEntry 3 }

--


     dot3OamEventLogType      OBJECT-TYPE
       SYNTAX      Unsigned32
       MAX-ACCESS  read-only
       STATUS      current
       DESCRIPTION
         "The type of event that generated this entry in the event log.

         When the OUI is the IEEE 802.3 OUI of 0x0180C2, the following
         event types are defined:
             erroredSymbolEvent(1),
             erroredFramePeriodEvent (2),
             erroredFrameEvent(3),
             erroredFrameSecondsEvent(4),
             linkFault(256),
             dyingGaspEvent(257),
             criticalLinkEvent(258)
         The first four are considered threshold crossing events as
         they are generated when a metric exceeds a given value within
         a specified window.  The other three are not threshold
         crossing events.

         When the OUI is not 0x0180C2, then some other organization has
         defined the event space.  If event subtyping is known to the
         implementation, it may be reflected here.  Otherwise, this
         value should return all Fs (0xFFFFFFFF).
         "
       REFERENCE   "[802.3ah], 30.3.6.1.10 and 57.5.3."
       ::= { dot3OamEventLogEntry 4 }

--

     dot3OamEventLogLocation OBJECT-TYPE
       SYNTAX      INTEGER { local(1), remote(2) }
       MAX-ACCESS  read-only
       STATUS      current
       DESCRIPTION
         "Whether this event occurred locally, or was received from the
         OAM peer via Ethernet OAM."
       ::= { dot3OamEventLogEntry 5 }

--

     dot3OamEventLogWindowHi      OBJECT-TYPE
       SYNTAX      Unsigned32
       MAX-ACCESS  read-only
       STATUS      current
       DESCRIPTION
         "If the event represents a threshold crossing event, the two
         objects dot3OamEventWindowHi and dot3OamEventWindowLo form an
         unsigned 64-bit integer yielding the window over which the
         value was measured for the threshold crossing event (e.g. 5,
         when 11 occurrences happened in 5 seconds while the threshold
         was 10).   The two objects are combined as:

         dot3OamEventLogWindow = ((2^32) * dot3OamEventLogWindowHi)
                                         + dot3OamEventLogWindowLo


         Otherwise, this value is returned as all F's (0xFFFFFFFF) and
         adds no useful information.  "
       REFERENCE   "[802.3ah], 30.3.6.1.37 and 57.5.3.2."
       ::= { dot3OamEventLogEntry 6 }

--

     dot3OamEventLogWindowLo      OBJECT-TYPE
       SYNTAX      Unsigned32
       MAX-ACCESS  read-only
       STATUS      current
       DESCRIPTION
         "If the event represents a threshold crossing event, the two
         objects dot3OamEventWindowHi and dot3OamEventWindowLo form an
         unsigned 64-bit integer yielding the window over which the
         value was measured for the threshold crossing event (e.g. 5,
         when 11 occurrences happened in 5 seconds while the threshold
         was 10).   The two objects are combined as:

         dot3OamEventLogWindow = ((2^32) * dot3OamEventLogWindowHi)
                                         + dot3OamEventLogWindowLo

         Otherwise, this value is returned as all F's (0xFFFFFFFF) and
         adds no useful information.  "
       REFERENCE   "[802.3ah], 30.3.6.1.37 and 57.5.3.2."
       ::= { dot3OamEventLogEntry 7 }

--

     dot3OamEventLogThresholdHi      OBJECT-TYPE
       SYNTAX      Unsigned32
       MAX-ACCESS  read-only
       STATUS      current
       DESCRIPTION
         "If the event represents a threshold crossing event, the two
         objects dot3OamEventThresholdHi and dot3OamEventThresholdLo
         form an unsigned 64-bit integer yielding the value that was
         crossed for the threshold crossing event (e.g. 10, when 11
         occurrences happened in 5 seconds while the threshold was 10).
         The two objects are combined as:

       dot3OamEventLogThreshold = ((2^32) * dot3OamEventLogThresholdHi)
                                          + dot3OamEventLogThresholdLo

         Otherwise, this value is returned as all F's (0xFFFFFFFF) and
         adds no useful information.  "
       REFERENCE   "[802.3ah], 30.3.6.1.37 and 57.5.3.2."
       ::= { dot3OamEventLogEntry 8 }

--


     dot3OamEventLogThresholdLo      OBJECT-TYPE
       SYNTAX      Unsigned32
       MAX-ACCESS  read-only
       STATUS      current
       DESCRIPTION
         "If the event represents a threshold crossing event, the two
         objects dot3OamEventThresholdHi and dot3OamEventThresholdLo
         form an unsigned 64-bit integer yielding the value that was
         crossed for the threshold crossing event (e.g. 10, when 11
         occurrences happened in 5 seconds while the threshold was 10).
         The two objects are combined as:

       dot3OamEventLogThreshold = ((2^32) * dot3OamEventLogThresholdHi)
                                          + dot3OamEventLogThresholdLo

         Otherwise, this value is returned as all F's (0xFFFFFFFF) and
         adds no useful information.  "
       REFERENCE   "[802.3ah], 30.3.6.1.37 and 57.5.3.2."
       ::= { dot3OamEventLogEntry 9 }

--


     dot3OamEventLogValue      OBJECT-TYPE
       SYNTAX      Counter64
       MAX-ACCESS  read-only
       STATUS      current
       DESCRIPTION
         "If the event represents a threshold crossing event, this
         value indicates the value of the parameter within the given
         window that generated this event (e.g. 11, when 11 occurrences
         happened in 5 seconds while the threshold was 10).

         Otherwise, this value is returned as all F's
         (0xFFFFFFFFFFFFFFFF) and adds no useful information.
         "
       REFERENCE   "[802.3ah], 30.3.6.1.37 and 57.5.3.2."
       ::= { dot3OamEventLogEntry 10 }

--

     dot3OamEventLogRunningTotal      OBJECT-TYPE
       SYNTAX      Counter64
       MAX-ACCESS  read-only
       STATUS      current
       DESCRIPTION
         "This value respresents the total number of times this
         occurence has happened since the last reset (e.g. 3253, when
         3253 symbol errors have occurred since the last reset, which
         has resulted in 51 symbol error threshold crossing events
         since the last reset).  "
       REFERENCE   "[802.3ah], 30.3.6.1.37 and 57.5.3.2."
       ::= { dot3OamEventLogEntry 11 }

--

     dot3OamEventLogEventTotal      OBJECT-TYPE
       SYNTAX      Unsigned32
       MAX-ACCESS  read-only
       STATUS      current
       DESCRIPTION
         "This value respresents the total number of times one or ore
         of these occurences have resulted in an event (e.g. 51 when
         3253 symbol errors have occurred since the last reset, which
         has resulted in 51 symbol error threshold crossing events
         since the last reset).  "
       REFERENCE   "[802.3ah], 30.3.6.1.37 and 57.5.3.2."
       ::= { dot3OamEventLogEntry 12 }


     ------------------------------------------------------------------
     --
     -- Ethernet OAM Notifications
     --

     dot3OamNotifs OBJECT IDENTIFIER ::= { dot3OamMIB 7 }
     dot3OamNotifsPrefix OBJECT IDENTIFIER ::= {dot3OamNotifs 0}

     dot3OamThresholdEvent NOTIFICATION-TYPE
       OBJECTS { ifIndex,
                 dot3OamEventLogTimestamp,
                 dot3OamEventLogOui,
                 dot3OamEventLogType,
                 dot3OamEventLogLocation,
                 dot3OamEventLogWindowHi,
                 dot3OamEventLogWindowLo,
                 dot3OamEventLogThresholdHi,
                 dot3OamEventLogThresholdLo,
                 dot3OamEventLogValue,
                 dot3OamEventLogRunningTotal,
                 dot3OamEventLogEventTotal
               }
       STATUS  current
       DESCRIPTION
         "A dot3OamThresholdEvent notification is sent when a local or
         remote threshold crossing event is detected.  A local
         threshold crossing event is detected by the local entity,
         while a remote threshold crossing event is detected by the
         reception of an Ethernet OAM Event Notification OAMPDU
         indicating a threshold event.

         This notification should not be sent more than once per
         second.

         The management entity should periodically check
         dot3OamEventLogTable to detect any missed events."
      ::= { dot3OamNotifsPrefix 1 }


     dot3OamNonThresholdEvent NOTIFICATION-TYPE
       OBJECTS { ifIndex,
                 dot3OamEventLogTimestamp,
                 dot3OamEventLogOui,
                 dot3OamEventLogType,
                 dot3OamEventLogLocation,
                 dot3OamEventLogEventTotal
               }
       STATUS  current
       DESCRIPTION
         "A dot3OamNonThresholdEvent notification is sent when a local
         or remote non-threshold crossing event is detected.  A local
         event is detected by the local entity, while a remote event is
         detected by the reception of an Ethernet OAM Event
         Notification OAMPDU indicating a non-threshold crossing event.

         This notification should not be sent more than once per
         second.

         The management entity should periodically check
         dot3OamEventLogTable to detect any missed events."
      ::= { dot3OamNotifsPrefix 2 }


     ------------------------------------------------------------------
     --
     -- Ethernet OAM Compliance group
     --


     dot3OamGroups OBJECT IDENTIFIER ::= { dot3OamConformance 1 }
     dot3OamCompliances OBJECT IDENTIFIER ::= { dot3OamConformance 2 }

     -- Compliance statements

     dot3OamCompliance MODULE-COMPLIANCE
       STATUS          current
       DESCRIPTION "The compliance statement for managed entities
                    supporting OAM on Ethernet like interfaces.
                    "
     MODULE   -- this module
       MANDATORY-GROUPS { dot3OamControlGroup,
                          dot3OamPeerGroup,
                          dot3OamStatsBaseGroup
                        }

       GROUP       dot3OamLoopbackGroup
       DESCRIPTION
         "This group is mandatory for all IEEE 802.3 OAM
         implementations that support loopback functionality. "

       GROUP       dot3OamErrSymbolPeriodEventGroup
       DESCRIPTION
         "This group is mandatory for all IEEE 802.3 OAM
         implementations that support event functionality. "

       GROUP       dot3OamErrFramePeriodEventGroup
       DESCRIPTION
         "This group is mandatory for all IEEE 802.3 OAM
         implementations that support event functionality. "

       GROUP       dot3OamErrFrameEventGroup
       DESCRIPTION
         "This group is mandatory for all IEEE 802.3 OAM
         implementations that support event functionality. "

       GROUP       dot3OamErrFrameSecsSummaryEventGroup
       DESCRIPTION
         "This group is mandatory for all IEEE 802.3 OAM
         implementations that support event functionality. "

       GROUP dot3OamFlagEventGroup
       DESCRIPTION
         "This group is optional for all IEEE 802.3 OAM
         implementations.  The ability to send critical events or
         dying gasp events is not required in any system."

       GROUP       dot3OamEventLogGroup
       DESCRIPTION
         "This group is optional for all IEEE 802.3 OAM
         implementations. "

       GROUP       dot3OamNotificationGroup
       DESCRIPTION
         "This group is optional for all IEEE 802.3 OAM
         implementations. "

       ::= { dot3OamCompliances 1}


    dot3OamControlGroup OBJECT-GROUP
       OBJECTS     {   dot3OamAdminState,
                       dot3OamOperStatus,
                       dot3OamMode,
                       dot3OamMaxOamPduSize,
                       dot3OamConfigRevision,
                       dot3OamFunctionsSupported
                   }
       STATUS      current
       DESCRIPTION
         "A collection of objects providing the abilities,
         configuration, and status of an Ethernet OAM entity.  "
       ::= { dot3OamGroups 1 }

    dot3OamPeerGroup OBJECT-GROUP
       OBJECTS     {   dot3OamPeerStatus,
                       dot3OamPeerMacAddress,
                       dot3OamPeerVendorOui,
                       dot3OamPeerVendorInfo,
                       dot3OamPeerMode,
                       dot3OamPeerFunctionsSupported,
                       dot3OamPeerMaxOamPduSize,
                       dot3OamPeerConfigRevision
                   }
       STATUS      current
       DESCRIPTION
         "A collection of objects providing the abilities,
         configuration, and status of a peer Ethernet OAM entity.  "
       ::= { dot3OamGroups 2 }

    dot3OamStatsBaseGroup OBJECT-GROUP
       OBJECTS     {   dot3OamInformationTx,
                       dot3OamInformationRx,
                       dot3OamUniqueEventNotificationTx,
                       dot3OamUniqueEventNotificationRx,
                       dot3OamDuplicateEventNotificationTx,
                       dot3OamDuplicateEventNotificationRx,
                       dot3OamLoopbackControlTx,
                       dot3OamLoopbackControlRx,
                       dot3OamVariableRequestTx,
                       dot3OamVariableRequestRx,
                       dot3OamVariableResponseTx,
                       dot3OamVariableResponseRx,
                       dot3OamOrgSpecificTx,
                       dot3OamOrgSpecificRx,
                       dot3OamUnsupportedCodesTx,
                       dot3OamUnsupportedCodesRx,
                       dot3OamFramesLostDueToOam
                   }
       STATUS      current
       DESCRIPTION
         "A collection of objects providing the statistics for the
         number of various transmit and recieve events for OAM on an
         Ethernet like interface.  Note that all of these counters must
         be supported even if the related function (as described in
         dot3OamFunctionsSupported) is not supported.  "
       ::= { dot3OamGroups 3 }

    dot3OamLoopbackGroup OBJECT-GROUP
       OBJECTS     {   dot3OamLoopbackCommand,
                       dot3OamLoopbackStatus,
                       dot3OamLoopbackIgnoreRx
                   }
       STATUS      current
       DESCRIPTION
         "A collection of objects for controlling the OAM remote
         loopback function.  "
       ::= { dot3OamGroups 4 }

    dot3OamErrSymbolPeriodEventGroup OBJECT-GROUP
       OBJECTS     {   dot3OamErrSymPeriodWindowHi,
                       dot3OamErrSymPeriodWindowLo,
                       dot3OamErrSymPeriodThresholdHi,
                       dot3OamErrSymPeriodThresholdLo,
                       dot3OamErrSymPeriodEvNotifEnable
                   }
       STATUS      current
       DESCRIPTION
         "A collection of objects for configuring the thresholds for an
         Errored Symbol Period Event.

         Each [802.3ah] defined Event Notification TLV has its own
         conformance group because each event can be implemented
         independently of any other.  "
       ::= { dot3OamGroups 5 }

    dot3OamErrFramePeriodEventGroup OBJECT-GROUP
       OBJECTS     {   dot3OamErrFramePeriodWindow,
                       dot3OamErrFramePeriodThreshold,
                       dot3OamErrFramePeriodEvNotifEnable
                   }
       STATUS      current
       DESCRIPTION
         "A collection of objects for configuring the thresholds for an
         Errored Frame Period Event.

         Each [802.3ah] defined Event Notification TLV has its own
         conformance group because each event can be implemented
         independently of any other.  "
       ::= { dot3OamGroups 6 }

    dot3OamErrFrameEventGroup OBJECT-GROUP
       OBJECTS     {   dot3OamErrFrameWindow,
                       dot3OamErrFrameThreshold,
                       dot3OamErrFrameEvNotifEnable
                   }
       STATUS      current
       DESCRIPTION
         "A collection of objects for configuring the thresholds for an
         Errored Frame Event.

         Each [802.3ah] defined Event Notification TLV has its own
         conformance group because each event can be implemented
         independently of any other.  "
       ::= { dot3OamGroups 7 }

    dot3OamErrFrameSecsSummaryEventGroup OBJECT-GROUP
       OBJECTS     {   dot3OamErrFrameSecsSummaryWindow,
                       dot3OamErrFrameSecsSummaryThreshold,
                       dot3OamErrFrameSecsEvNotifEnable
                   }
       STATUS      current
       DESCRIPTION
         "A collection of objects for configuring the thresholds for an
         Errored Frame Seconds Summary Event.

         Each [802.3ah] defined Event Notification TLV has its own
         conformance group because each event can be implemented
         independently of any other.  "
       ::= { dot3OamGroups 8 }

    dot3OamFlagEventGroup OBJECT-GROUP
       OBJECTS     {   dot3OamDyingGaspEnable,
                       dot3OamCriticalEventEnable
                   }
       STATUS      current
       DESCRIPTION
         "A collection of objects for configuring the sending OAMPDUs
         with the critical event flag or dying gasp flag enabled.  "
       ::= { dot3OamGroups 9 }

    dot3OamEventLogGroup OBJECT-GROUP
      OBJECTS {  dot3OamEventLogTimestamp,
                 dot3OamEventLogOui,
                 dot3OamEventLogType,
                 dot3OamEventLogLocation,
                 dot3OamEventLogWindowHi,
                 dot3OamEventLogWindowLo,
                 dot3OamEventLogThresholdHi,
                 dot3OamEventLogThresholdLo,
                 dot3OamEventLogValue,
                 dot3OamEventLogRunningTotal,
                 dot3OamEventLogEventTotal
               }
      STATUS      current
      DESCRIPTION
         "A collection of objects for configuring the thresholds for an
         Errored Frame Seconds Summary Event and maintaining the event
         information.  "
       ::= { dot3OamGroups 10 }

    dot3OamNotificationGroup NOTIFICATION-GROUP
      NOTIFICATIONS {
                  dot3OamThresholdEvent,
                  dot3OamNonThresholdEvent
                    }
      STATUS      current
      DESCRIPTION
        "A collection of notifications used by Ethernet OAM to signal
        to a management entity that local or remote events have occured
        on a specified Ethernet link."
      ::= { dot3OamGroups 11 }


     END
