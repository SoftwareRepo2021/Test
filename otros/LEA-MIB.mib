LEA-MIB DEFINITIONS ::= BEGIN

--
-- Top-level infrastructure of the LEA enterprise MIB tree
--

IMPORTS
    MODULE-IDENTITY, enterprises FROM SNMPv2-SMI;

lea MODULE-IDENTITY
    LAST-UPDATED "20021004000Z"
    ORGANIZATION "www.leacom.fr"
    CONTACT-INFO
	 "postal:   Regis Urvoy
                    52/54 rue du capitaine Guynemer
                    92415 Courbevoie Cedex
                    France

          email:    regis.urvoy@leacom.fr"
    DESCRIPTION
	"Top-level infrastructure of the LEA enterprise MIB tree"
    REVISION     "200209260000Z"
    DESCRIPTION
	"Beta 1"
    ::= { enterprises 14841}


--
--  LEA enterprise-specific management objects
--

leaSplitters                OBJECT IDENTIFIER ::= {lea 1}
leaExperimental             OBJECT IDENTIFIER ::= {lea 9999}

END
