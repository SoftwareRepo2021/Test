--
-- phyGPON.mib
-- MIB generated by MG-SOFT Visual MIB Builder Version 3.0 Build 285
-- Monday, April 17, 2017 at 13:15:57
--

	Zhone-GPON-MIB DEFINITIONS ::= BEGIN
 
		IMPORTS
			InterfaceIndex			
				FROM IF-MIB			
			OBJECT-GROUP, NOTIFICATION-GROUP			
				FROM SNMPv2-CONF			
			Integer32, Unsigned32, Counter64, OBJECT-TYPE, MODULE-IDENTITY, 
			OBJECT-IDENTITY, NOTIFICATION-TYPE			
				FROM SNMPv2-SMI			
			TruthValue, TEXTUAL-CONVENTION			
				FROM SNMPv2-TC			
			zhoneRegPls, zhoneRegCpe, zhoneRegMux, zhoneRegSechtor, zhoneRegWtn, 
			zhoneRegMalc, zhonePls, zhoneZedge, zhoneZplex, sechtor100, 
			sechtor300, zhoneWtn, zhoneMalc, zhoneZmsProduct, zhoneSystem, 
			zhoneShelf, zhoneCard, zhoneSubscriber, zhoneInterfaceTranslation, zhoneInterfaceGroup, 
			zhoneMasterAgent, zhoneTrapModules, zhoneGenWtn, zhoneZAP, zhoneVoiceStats, 
			zhoneIp, zhoneAtm, zhoneVoice, zhoneVoip, zhonePpp, 
			zhoneIma, zhoneBridge, zhoneVideo, zhoneIsdn, zhoneCes, 
			zhoneSs7, zhoneClass5, zhoneBonding, zhoneEnet, zhoneDsx, 
			zhoneOcx, zhoneDsl, zhoneConsole, zhoneRadio, zhoneSonet, 
			zhoneDs3Ext, zhoneLineTypes, zhoneApon, zhoneVdsl, zhoneGpon, 
			zhoneSlotIndex, zhoneModules, zhoneShelfIndex, zhoneSlotIndex, zhoneGroups, 
			zhoneShelfSlotGroup, zhoneShelfSlotCompliance, apsMIB, sipTC, sipCommonMIB, 
			sipUAMIB, pktcIetfSigMib, efmOamMIB, efmCuMIB, zhoneDrafts			
				FROM Zhone			
			ZhoneAdminString, ZhoneRowStatus, ZhoneEnabledFlag			
				FROM Zhone-TC;
	
	
-- /vob/zhonetools/bin/pahrser.pl rfc2233.mib Zhone.mib 
-- Zhone-TC.mib phyGPON.mib 
-- 
-- /vob/EPILOGUE/binaries/emissary/solaris/mibcomp rfc2514.mib 
-- rfc1907.mib iftype.mib rfc2233.mib Zhone.mib Zhone-TC.mib 
-- -stub -o gponHdlrs.c phyGPON.mib
-- 
-- 
-- 
-- 
-- 
-- 
-- 
-- 
-- 
-- 
-- 
-- 
-- 
-- 
-- 
-- 
-- 
-- 
-- 
-- 
-- 
-- 
-- 
-- 
-- 
		-- 1.3.6.1.4.1.5504.6.111
		zhoneGponOltMIB MODULE-IDENTITY 
			LAST-UPDATED "201703290207Z"		-- March 29, 2017 at 02:07 GMT
			ORGANIZATION 
				"Zhone Technologies, Inc."
			CONTACT-INFO 
				"Zhone Technologies, Inc.
				@ Zhone Way
				7001 Oakport Street
				Oakland, CA  94621
				USA
				Toll-Free: +1 877-ZHONE20 (+1 877-946-6320)
				Tel: +1-510-777-7000
				Fax: +1-510-777-7001
				E-mail: support@zhone.com
				"
			DESCRIPTION 
				"This is the Zhone GPON mib which contains SNMP objects for 
				GPON ONU configuration, alarms, and status.It also includes 
				the GPON OLT status information."
			REVISION "201703291355Z"		-- March 29, 2017 at 13:55 GMT
			DESCRIPTION 
				"Add key-exchange-interval to olt-config"
			REVISION "201703080338Z"		-- March 08, 2017 at 03:38 GMT
			DESCRIPTION 
				"Added poePowerApplyFailure(24) enum on zhoneGponOnuStatusWord"
			REVISION "201702030207Z"		-- February 03, 2017 at 02:07 GMT
			DESCRIPTION 
				"Changed the feature flag of GponUpgradeByState from GPON to CPE_PROF"
			REVISION "201612190358Z"		-- December 19, 2016 at 03:58 GMT
			DESCRIPTION 
				"Changed the feature flag of GponOmciStatusProfile from GPON to CPE_PROF"
			REVISION "201606231107Z"		-- June 23, 2016 at 11:07 GMT
			DESCRIPTION 
				"Change of feature flag from GPON to CPE_PROF for gpon-omci-onu-alarms-id
				profiles to support this profile in AE line cards as well."
			REVISION "201605231648Z"		-- May 23, 2016 at 16:48 GMT
			DESCRIPTION 
				"Added alloc-id-info and snmp-alloc-id-info."
			REVISION "201604250255Z"		-- April 25, 2016 at 02:55 GMT
			DESCRIPTION 
				"Change of feature flag from GPON to CPE_PROF for gpon-onu-status, gpon-omci-onu-image-upgrade
				and gpon-cmd profiles to support this profile in AE line cards as well"
			REVISION "201504232315Z"		-- April 23, 2015 at 23:15 GMT
			DESCRIPTION 
				"Added olt-rx-pwr, ont-rx-pwr and onu-distance in GponOltOnuConfigProfile."
			REVISION "201501211340Z"		-- January 21, 2015 at 13:40 GMT
			DESCRIPTION 
				"1. Added zhoneGponSerialNoModelId to the zhoneGponSerialNoTable.
				2. Added zhoneGponSerialNoModelId to the zhoneGponSerialNumberFound trap."
			REVISION "201410290138Z"		-- October 29, 2014 at 01:38 GMT
			DESCRIPTION 
				"Added new bit onuRebooted in zhoneGponOnuStatusWord field."
			REVISION "201409180447Z"		-- September 18, 2014 at 04:47 GMT
			DESCRIPTION 
				"Added new field link-status-alarm-Severity in gpon-olt-onu-config profile."
			REVISION "201406111738Z"		-- June 11, 2014 at 17:38 GMT
			DESCRIPTION 
				"Added cmd operations for auto-cfg enable/disable"
			REVISION "201405271037Z"		-- May 27, 2014 at 10:37 GMT
			DESCRIPTION 
				"Added zhoneGponOltOnuConfigAutoConfigState."
			REVISION "201401221652Z"		-- January 22, 2014 at 16:52 GMT
			DESCRIPTION 
				"Add gponOltStatusConfiguredOnuCount, gponOltStatusActiveOnuCount"
			REVISION "201312191408Z"		-- December 19, 2013 at 14:08 GMT
			DESCRIPTION 
				"Added ONU auto-assign trap."
			REVISION "201312121525Z"		-- December 12, 2013 at 15:25 GMT
			DESCRIPTION 
				"Added zhoneGponSerialNoTimeStamp"
			REVISION "201310021545Z"		-- October 02, 2013 at 15:45 GMT
			DESCRIPTION 
				"Add method to gpon image upgrade table
				Add linkonly to zhoneGponOltOnuConfigLineStatusTraps"
			REVISION "201306101225Z"		-- June 10, 2013 at 12:25 GMT
			DESCRIPTION 
				"Added omciState entries postCfgError and omciErrAndPostCfgErr."
			REVISION "201305161425Z"		-- May 16, 2013 at 14:25 GMT
			DESCRIPTION 
				"Added append and revert to ME profile row status."
			REVISION "201305081601Z"		-- May 08, 2013 at 16:01 GMT
			DESCRIPTION 
				"Update alarms text description."
			REVISION "201305011425Z"		-- May 01, 2013 at 14:25 GMT
			DESCRIPTION 
				"Add OLT Next Gem Port available object"
			REVISION "201212051154Z"		-- December 05, 2012 at 11:54 GMT
			DESCRIPTION 
				"Add more states for zhoneGponOnuOmciState"
			REVISION "201210191424Z"		-- October 19, 2012 at 14:24 GMT
			DESCRIPTION 
				"Changed the default value of zhoneGponPortConfigEncrypted
				to true."
			REVISION "201210090916Z"		-- October 09, 2012 at 09:16 GMT
			DESCRIPTION 
				"Added a new enum onuSet2default to the
				object zhoneGponCmdOperation."
			REVISION "201208231453Z"		-- August 23, 2012 at 14:53 GMT
			DESCRIPTION 
				"Added data sync fields to OnuConfigProfile."
			REVISION "201111101814Z"		-- November 10, 2011 at 18:14 GMT
			DESCRIPTION 
				"Add auto-rssi rogueDetect mode."
			REVISION "201110171943Z"		-- October 17, 2011 at 19:43 GMT
			DESCRIPTION 
				"add rogueOnu to onuStatusWord"
			REVISION "201106141504Z"		-- June 14, 2011 at 15:04 GMT
			DESCRIPTION 
				"Made zhoneGponOltStatusWord read-only."
			REVISION "201106021902Z"		-- June 02, 2011 at 19:02 GMT
			DESCRIPTION 
				"Added zhoneGponOltStatusWordTrap"
			REVISION "201104080950Z"		-- April 08, 2011 at 09:50 GMT
			DESCRIPTION 
				"Changed th object name zhoneCpeTrafficManagementProfileIndex to
				zhoneGponPortConfigTrafficManagementProfileIndex"
			REVISION "201103141200Z"		-- March 14, 2011 at 12:00 GMT
			DESCRIPTION 
				"Removed QUICK-ACCESS for the object
				zhoneCpeTrafficManagementProfileIndex"
			REVISION "201103011049Z"		-- March 01, 2011 at 10:49 GMT
			DESCRIPTION 
				"1.Removed  rate, priority and weight
				  fields from the zhoneGponPortConfigTable.
				2.Added zhoneCpeTrafficManagementProfileIndex
				  to the zhoneGponPortConfig table."
			REVISION "201102081708Z"		-- February 08, 2011 at 17:08 GMT
			DESCRIPTION 
				"Add rogue onu detection"
			REVISION "201101241656Z"		-- January 24, 2011 at 16:56 GMT
			DESCRIPTION 
				"Remove gponOnuConnection table.
				This is now cpeConnection table in phyCPE mib."
			REVISION "201101171136Z"		-- January 17, 2011 at 11:36 GMT
			DESCRIPTION 
				"zhoneGponOnuDistance"
			REVISION "201011041036Z"		-- November 04, 2010 at 10:36 GMT
			DESCRIPTION 
				"Add 3 zhoneGponOltOnuConfigEntry RxPower objects."
			REVISION "201010281449Z"		-- October 28, 2010 at 14:49 GMT
			DESCRIPTION 
				"Added kbps rate limits for
				zhoneGponPortConfigUpstreamSIR and
				zhoneGponPortConfigUpstreamPIR
				Added an additional enum value oltactive
				to zhoneGponOltOpticStatus"
			REVISION "201010191440Z"		-- October 19, 2010 at 14:40 GMT
			DESCRIPTION 
				"Added 4 Bip8 Objects to zhoneGponOltConfigEntry."
			REVISION "201009081018Z"		-- September 08, 2010 at 10:18 GMT
			DESCRIPTION 
				"Added 6 new objects to the zhoneGponPortConfigTable
				Added 4 new objects to the zhoneGponOltOnuConfigTable"
			REVISION "201009011625Z"		-- September 01, 2010 at 16:25 GMT
			DESCRIPTION 
				"Add ONU Id as a row creation
				parameter for gpon port."
			REVISION "201009011210Z"		-- September 01, 2010 at 12:10 GMT
			DESCRIPTION 
				"Added additional values to the TpType"
			REVISION "201008131529Z"		-- August 13, 2010 at 15:29 GMT
			DESCRIPTION 
				"Added a new table zhoneGponOnuConnection.
				Added a new Textual Convention TpType"
			REVISION "201008101635Z"		-- August 10, 2010 at 16:35 GMT
			DESCRIPTION 
				"Add enum values for zhoneGponOnuOmciState "
			REVISION "201007270808Z"		-- July 27, 2010 at 08:08 GMT
			DESCRIPTION 
				"Add Tx Preamble to GPON Olt Config"
			REVISION "201007191423Z"		-- July 19, 2010 at 14:23 GMT
			DESCRIPTION 
				"Add zhoneGponOltStatisticsClear and
				zhoneGponUpstreamOntStatisticsClear objects."
			REVISION "201006111421Z"		-- June 11, 2010 at 14:21 GMT
			DESCRIPTION 
				"Added zhoneGponOntVersion to zhoneGponOnuStatusTable."
			REVISION "201006011802Z"		-- June 01, 2010 at 18:02 GMT
			DESCRIPTION 
				"Add zhoneGponUpstreamMessageErrorMessage."
			REVISION "201005130902Z"		-- May 13, 2010 at 09:02 GMT
			DESCRIPTION 
				"Update GponCacRc"
			REVISION "201005120900Z"		-- May 12, 2010 at 09:00 GMT
			DESCRIPTION 
				"1. Add more enum values to zhoneGponOmciOnuPortAdminAutoDetect
				2. Add zhoneGponOmciOnuImageDownloadProgressPercentage
				3. Add zhoneGponUpgradeProgressPercentage
				4. Add more enum values to GponCacRc
				5. Clean up compile warning 
				6. Add missing descriptions to the zhone Groups."
			REVISION "201004131119Z"		-- April 13, 2010 at 11:19 GMT
			DESCRIPTION 
				"Added zhoneGponOltStatisticsUpstreamPonValidPkts"
			REVISION "201004051137Z"		-- April 05, 2010 at 11:37 GMT
			DESCRIPTION 
				"Added zhoneGponOltStatisticsTable and
				zhoneGponUpstreamOntStatisticsTable."
			REVISION "201003310752Z"		-- March 31, 2010 at 07:52 GMT
			DESCRIPTION 
				"Add activateCommit to zhoneGponOmciOnuImageUpgradeAction"
			REVISION "201003161133Z"		-- March 16, 2010 at 11:33 GMT
			DESCRIPTION 
				"Add zhoneGponOntRxPower"
			REVISION "201001131301Z"		-- January 13, 2010 at 13:01 GMT
			DESCRIPTION 
				"1.  Change default zhoneGponOltOnuConfigAutoUpgrade to enabled"
			REVISION "200912160732Z"		-- December 16, 2009 at 07:32 GMT
			DESCRIPTION 
				"Update zhoneGponPortConfigTable comments"
			REVISION "200911140954Z"		-- November 14, 2009 at 09:54 GMT
			DESCRIPTION 
				"Add zhoneGponOltConfigProtectionSwitchoverTimer"
			REVISION "200911130913Z"		-- November 13, 2009 at 09:13 GMT
			DESCRIPTION 
				"Added zhoneGponOmciOnuPortAdminAutoDetect
				to the zhoneGponOmciOnuPortAdminTable"
			REVISION "200910091131Z"		-- October 09, 2009 at 11:31 GMT
			DESCRIPTION 
				"Changed the maximum limit of
				zhoneGponTrafficProfileDbaFixedUsCbrBw
				to 454208"
			REVISION "200909241304Z"		-- September 24, 2009 at 13:04 GMT
			DESCRIPTION 
				"Add value ranges to GPON Traffic
				Profile bandwidth fields"
			REVISION "200909181840Z"		-- September 18, 2009 at 18:40 GMT
			DESCRIPTION 
				"Add useRegId to onu-config"
			REVISION "200909160719Z"		-- September 16, 2009 at 07:19 GMT
			DESCRIPTION 
				"Add more values to zhoneGponPortStatusDbaStatus
				and update the it's comments"
			REVISION "200909151100Z"		-- September 15, 2009 at 11:00 GMT
			DESCRIPTION 
				"Change some defaults in olt-onu-config-profile."
			REVISION "200909140638Z"		-- September 14, 2009 at 06:38 GMT
			DESCRIPTION 
				"1. add GponCacRc data type
				2. add zhoneGponPortStatusDbaStatus to zhoneGponPortStatusTable
				3. add allocId info to zhoneGponOltDbaStatus"
			REVISION "200908281445Z"		-- August 28, 2009 at 14:45 GMT
			DESCRIPTION 
				"Changed zhoneGponOltOpticAlarms
				to Read-Only"
			REVISION "200908191224Z"		-- August 19, 2009 at 12:24 GMT
			DESCRIPTION 
				"Add olt optics status 
				word and trap."
			REVISION "200907310632Z"		-- July 31, 2009 at 06:32 GMT
			DESCRIPTION 
				"Add zhoneGponCmd objects"
			REVISION "200907161002Z"		-- July 16, 2009 at 10:02 GMT
			DESCRIPTION 
				"Add zhoneGponOltOpticStatus
				to the zhoneGponOltStatusTable."
			REVISION "200907071112Z"		-- July 07, 2009 at 11:12 GMT
			DESCRIPTION 
				"Add the GponUpgradeByState table.
				Also add some fields to the
				zhoneGponOnuOmciImageUpgradeTable."
			REVISION "200906160836Z"		-- June 16, 2009 at 08:36 GMT
			DESCRIPTION 
				"1. Add zhoneGponOltOnuConfigAutoUpgrade
				2. Add zhoneGponOltOnuConfigSerialNoVendorSpecificFsan"
			REVISION "200906111549Z"		-- June 11, 2009 at 15:49 GMT
			DESCRIPTION 
				"Modified the zhoneGponOnuStatusTable by removing zhoneGponOnuOpticTxPower
				and changing zhoneGponOnuOpticRxPower to zhoneGponOnuOpticRssi
				Also Added the following two new tables
				1.zhoneGponOltStatusTable
				2.zhoneGponOltDbaStatusTable
				"
			REVISION "200905221553Z"		-- May 22, 2009 at 15:53 GMT
			DESCRIPTION 
				"Added the following 2 new objects to the GponOltConfigTable:
				
				1.zhoneGponOltConfigDbaCycle
				2.zhoneGponOltConfigSrDbaReportingBlockSize
				
				Added the following 6 new objects to the GponTrafficProfileTable:
				
				1.zhoneGponTrafficProfileDbaFixedUsUbrBw
				2.zhoneGponTrafficProfileDbaFixedUsCbrBw
				3.zhoneGponTrafficProfileDbaAssuredUsBw
				4.zhoneGponTrafficProfileDbaMaxUsBw
				5.zhoneGponTrafficProfileExtraUsBwType
				6.zhoneGponTrafficProfileDbaEnabled"
			REVISION "200905181508Z"		-- May 18, 2009 at 15:08 GMT
			DESCRIPTION 
				"Added zhoneGponOnuOpticTxPower and zhoneGponOnuOpticRxPower to
				the zhoneGponOnuStatusTable"
			REVISION "200902181138Z"		-- February 18, 2009 at 11:38 GMT
			DESCRIPTION 
				"Add trap enable flags to onu-config.
				Modify description of onu alarms text."
			REVISION "200901150704Z"		-- January 15, 2009 at 07:04 GMT
			DESCRIPTION 
				"Add zhoneGponOmciOnuImageUpgradeTable"
			REVISION "200901061133Z"		-- January 06, 2009 at 11:33 GMT
			DESCRIPTION 
				"1. Add zhoneGponOmciOnuReboot
				2. Add zhoneGponOmciOnuPortAdminTable"
			REVISION "200812100942Z"		-- December 10, 2008 at 09:42 GMT
			DESCRIPTION 
				"Add zhoneGponOmciStatusTable"
			REVISION "200811111407Z"		-- November 11, 2008 at 14:07 GMT
			DESCRIPTION 
				"Rework zhoneGponPortConfigTable to support
				dynamic GEM port operations."
			REVISION "200810091708Z"		-- October 09, 2008 at 17:08 GMT
			DESCRIPTION 
				"Add current and previous Omci statistics tables."
			REVISION "200809220755Z"		-- September 22, 2008 at 07:55 GMT
			DESCRIPTION 
				"1. add zhoneGponPortConfigTrafficProfile
				2. update zhoneGponOnuStatusTable
				3. add zhoneGponTrafficProfileTable
				4. add zhoneGponPortStatusTable"
			REVISION "200808120739Z"		-- August 12, 2008 at 07:39 GMT
			DESCRIPTION 
				"1. Add comments to OMCI profile tables containing instructions
				   on the creation and updates of omci data.
				2. Change OMCI row status variable definitions to reflect new omci
				   operations.
				3. Add omci objects
				4. Change size of zhoneOnuOmciMEProfileOmciCommadns to 64K to allow
				   better memory management.
				5. Change size of zhoneOnuOmciGenericProfileOmciCommands to 15K to allow
				   better memory management.
				6. Change size of zhoneOnuOmciSpecificProfileOmciCommands to 15K to allow
				   better memory management."
			REVISION "200806251449Z"		-- June 25, 2008 at 14:49 GMT
			DESCRIPTION 
				"1. add zhoneOnuOmciMEProfileTable
				2. add zhoneOnuOmciGenericProfileTable
				3. add zhoneOnuOmciSpecificProfileTable"
			REVISION "200806121737Z"		-- June 12, 2008 at 17:37 GMT
			DESCRIPTION 
				"Add GPON OMCI ONU Alarms:
				1. Add zhoneGponOmciOnuAlarmsTrap
				2. Add zhoneGponOmciOnuAlarmsTable"
			REVISION "200805231539Z"		-- May 23, 2008 at 15:39 GMT
			DESCRIPTION 
				"Added zhoneGponOltOnuConfigMEProfileName to OltOnuConfigTable
				Added zhoneGponOltOnuConfigGenericProfileName to OltOnuConfigTable
				"
			REVISION "200708221734Z"		-- August 22, 2007 at 17:34 GMT
			DESCRIPTION 
				"Add omci filename and onu status change trap"
			REVISION "200703191735Z"		-- March 19, 2007 at 17:35 GMT
			DESCRIPTION 
				"add comments on alloc-id fields"
			REVISION "200703011927Z"		-- March 01, 2007 at 19:27 GMT
			DESCRIPTION 
				"Add serial number table.
				Change ONU serial number format."
			REVISION "200610271606Z"		-- October 27, 2006 at 16:06 GMT
			DESCRIPTION 
				"Initial revision."
			::= { zhoneModules 111 }

		
	
--
-- Textual conventions
--
	
		OnuUpgradeState ::= TEXTUAL-CONVENTION
			STATUS current
			DESCRIPTION 
				"Onu upgrade state, for queries and reporting."
			SYNTAX INTEGER
				{
				none(0),
				queued(1),
				noUpgrade(2),
				downloading(3),
				complete(4),
				error(5),
				aborted(6),
				fileError(7),
				downloaded(8)
				}

		GponCacRc ::= TEXTUAL-CONVENTION
			STATUS current
			DESCRIPTION 
				"This object contains the result code of the last GPON CAC request
				for the OLT.
				
				ok                - GPON CAC requrest approved
				
				noReq             - GPON CAC request has not been performed
				 
				badParms          - Internal error.  Bad pointer or index value 
				                    parameter to a GPON CAC procedure call
				
				cfgLookup         - Internal error.  Failed to look up a config
				                    record ( OLT, ONU, traffic profile, etc )
				
				genError          - Internal error.  Invalid value was found
				                    inside a profile so a switch statement failed
				
				maxOnuGemPorts    - Each ONU supports a limited number of GEM ports
				
				maxOltAllocIds    - Each OLT supports a limited number of allocIds
				
				maxOltDbaAllocIds - Each OLT supports a limited number of DBA-enabled allocIds 
				
				maxBw             - An attempt was made to create a new GEM port or 
				                    modifying an existing GEM port but the there is no 
				                    available total bandwidth
				
				maxCbrBw          - An attempt was made to create a new GEM port or 
				                    modifying an existing GEM port but the there is no 
				                    available CBR bandwidth
				
				trafficClassChg   - An attempt was made to change a GEM port traffic 
				                    profile index.  The change was not allowed because 
				                    the new traffic profile has a different traffic class
				
				dbaStatusChg      - An attempt was made to change a GEM port traffic 
				                    profile index. The change was not allowed because 
				                    the new traffic profile has a different DBA Enabled 
				                    status
				
				testCreateInvalidParms - GEM Port cannot be created because there are
				                         invalid paramater values used to create the GEM Port.
				
				
				testCreateMissingParms - GEM Port cannot be created because there are
				                         missing paramater values used to create the GEM Port.
				
				testCreateAlreadyExistsIfIndex - GEM Port cannot be created because a GEM
				                                 Port already exists with the specified ifIndex
				
				testCreateAlreadyExistsSSPS - GEM Port cannot be created because a GEM Port
				                              already exists with the specified shelf, slot,
				                              port and subPort values. 
				
				testCreateOnuDoesNotExist - GEM Port cannot be created because the specified
					                    GEM Port ONU does not exist
								
				testCreateOnuNotRegistered - GEM Port cannot be created because the GEM 
				    	                     Port ONU has not been registered with the LINERR
							 	
				testCreateCannotFindPrimary - GEM Port cannot be created because the GEM
				  	                      Port Primary OLT cannot be located 
								
				testCreateCannotAddToSecondary - GEM Port cannot be created on the secondary
					                         OLT of an OLT line redundancy group"
			SYNTAX INTEGER
				{
				ok(1),
				noReq(2),
				badParms(3),
				cfgLookup(4),
				genError(5),
				maxOnuGemPorts(6),
				maxOltAllocIds(7),
				maxOltDbaAllocIds(8),
				maxBw(9),
				maxCbrBw(10),
				trafficClassChg(11),
				dbaStatusChg(12),
				testCreateInvalidParms(13),
				testCreateMissingParms(14),
				testCreateAlreadyExistsIfIndex(15),
				testCreateAlreadyExistsSSPS(16),
				testCreateOnuDoesNotExist(17),
				testCreateOnuNotRegistered(18),
				testCreateCannotFindPrimary(19),
				testCreateCannotAddToSecondary(20)
				}

	
--
-- Node definitions
--
	
		-- 1.3.6.1.4.1.5504.5.14.1
		zhoneGponObjectID OBJECT IDENTIFIER ::= { zhoneGpon 1 }

		
		-- 1.3.6.1.4.1.5504.5.14.1.1
		zhoneGponOltConfigTable OBJECT-TYPE
			SYNTAX SEQUENCE OF ZhoneGponOltConfigEntry
			MAX-ACCESS not-accessible
			STATUS current
			DESCRIPTION
				"Configuration parameters that apply to one OLT. This profile is
				auto-created."
			::= { zhoneGponObjectID 1 }

		
		-- 1.3.6.1.4.1.5504.5.14.1.1.1
		zhoneGponOltConfigEntry OBJECT-TYPE
			SYNTAX ZhoneGponOltConfigEntry
			MAX-ACCESS not-accessible
			STATUS current
			DESCRIPTION
				"One row of the gpon olt config entry table."
			INDEX { zhoneGponOltIfIndex }
			::= { zhoneGponOltConfigTable 1 }

		
		ZhoneGponOltConfigEntry ::=
			SEQUENCE { 
				zhoneGponOltIfIndex
					InterfaceIndex,
				zhoneGponOltConfigMaxRtPropagationDelay
					Integer32,
				zhoneGponOltConfigMaxOnuResponseTime
					Integer32,
				zhoneGponOltConfigPreassignedEqD
					Integer32,
				zhoneGponOltConfigLosAlpha
					Integer32,
				zhoneGponOltConfigLofAlpha
					Integer32,
				zhoneGponOltConfigLoamAlpha
					Integer32,
				zhoneGponOltConfigScrambler
					ZhoneEnabledFlag,
				zhoneGponOltConfigFecMode
					ZhoneEnabledFlag,
				zhoneGponOltConfigAutoLearn
					ZhoneEnabledFlag,
				zhoneGponOltConfigPowerLevel
					Unsigned32,
				zhoneGponOltConfigGuardBitCount
					Integer32,
				zhoneGponOltConfigDbaMode
					INTEGER,
				zhoneGponOltConfigGemBlockSize
					Integer32,
				zhoneGponOltConfigUsBerInterval
					Integer32,
				zhoneGponOltConfigDsBerInterval
					Integer32,
				zhoneGponOltConfigBerSfThreshold
					Integer32,
				zhoneGponOltConfigBerSdThreshold
					Integer32,
				zhoneGponOltConfigFecRequest
					ZhoneEnabledFlag,
				zhoneGponOltConfigKeyExchange
					ZhoneEnabledFlag,
				zhoneGponOltConfigMinRtPropagationDelay
					Integer32,
				zhoneGponOltConfigMinOnuResponseTime
					Integer32,
				zhoneGponOltConfigEqDMeasureCycles
					Integer32,
				zhoneGponOltConfigDriftControlInterval
					Integer32,
				zhoneGponOltConfigDriftControlLimit
					Integer32,
				zhoneGponOltConfigAllocCycleLength
					Integer32,
				zhoneGponOltConfigMinUsAlloc
					Integer32,
				zhoneGponOltConfigAckTimeout
					Integer32,
				zhoneGponOltConfigPlsMaxAllocSize
					Integer32,
				zhoneGponOltConfigDbaCycle
					Unsigned32,
				zhoneGponOltConfigSrDbaReportingBlockSize
					Unsigned32,
				zhoneGponOltConfigProtectionSwitchoverTimer
					Unsigned32,
				zhoneGponOltConfigPreambleOverride
					ZhoneEnabledFlag,
				zhoneGponOltConfigPreambleType0
					OCTET STRING,
				zhoneGponOltConfigPreambleType1
					OCTET STRING,
				zhoneGponOltConfigPreambleType3PreRange
					OCTET STRING,
				zhoneGponOltConfigPreambleType3PostRange
					OCTET STRING,
				zhoneGponOltConfigPreambleType3Pattern
					OCTET STRING,
				zhoneGponOltConfigBipErrorMonitoring
					INTEGER,
				zhoneGponOltConfigBipErrorsPerSampleThreshold
					Integer32,
				zhoneGponOltConfigBipErroredSamplesThreshold
					Integer32,
				zhoneGponOltConfigBipMaxSampleGap
					Integer32,
				zhoneGponOltConfigRogueOnuDetection
					INTEGER,
				zhoneGponOltConfigRogueOnuDetectFrequency
					Integer32,
				zhoneGponOltConfigRogueOnuRxPowerThreshold
					Integer32,
				zhoneGponOltConfigKeyExchangeInterval
					Integer32
			 }

		-- 1.3.6.1.4.1.5504.5.14.1.1.1.1
		zhoneGponOltIfIndex OBJECT-TYPE
			SYNTAX InterfaceIndex
			MAX-ACCESS not-accessible
			STATUS current
			DESCRIPTION
				"The ifIndex of the physical olt interface."
			::= { zhoneGponOltConfigEntry 1 }

		
		-- 1.3.6.1.4.1.5504.5.14.1.1.1.2
		zhoneGponOltConfigMaxRtPropagationDelay OBJECT-TYPE
			SYNTAX Integer32
			UNITS "usec"
			MAX-ACCESS read-write
			STATUS current
			DESCRIPTION
				"Maximum round trip propagation delay. Combined with max ONU response 
				time and preassigned delay determins maximum logical PON distance. 
				Default 200 usec for 20 dm."
			DEFVAL { 200 }
			::= { zhoneGponOltConfigEntry 2 }

		
		-- 1.3.6.1.4.1.5504.5.14.1.1.1.3
		zhoneGponOltConfigMaxOnuResponseTime OBJECT-TYPE
			SYNTAX Integer32
			UNITS "usec"
			MAX-ACCESS read-write
			STATUS current
			DESCRIPTION
				"Combined with max rt propagation delay, determins maximum logical 
				PON distance."
			DEFVAL { 50 }
			::= { zhoneGponOltConfigEntry 3 }

		
		-- 1.3.6.1.4.1.5504.5.14.1.1.1.4
		zhoneGponOltConfigPreassignedEqD OBJECT-TYPE
			SYNTAX Integer32
			UNITS "usec"
			MAX-ACCESS read-write
			STATUS current
			DESCRIPTION
				"Combined with max rt propagation delay and max onu response time 
				determines max logical PON distance."
			DEFVAL { 0 }
			::= { zhoneGponOltConfigEntry 4 }

		
		-- 1.3.6.1.4.1.5504.5.14.1.1.1.5
		zhoneGponOltConfigLosAlpha OBJECT-TYPE
			SYNTAX Integer32
			MAX-ACCESS read-write
			STATUS current
			DESCRIPTION
				"Number of loss-of-signal occurrences to trigger alarm."
			DEFVAL { 4 }
			::= { zhoneGponOltConfigEntry 5 }

		
		-- 1.3.6.1.4.1.5504.5.14.1.1.1.6
		zhoneGponOltConfigLofAlpha OBJECT-TYPE
			SYNTAX Integer32
			MAX-ACCESS read-write
			STATUS current
			DESCRIPTION
				"Number of loss-of-frame occurrences to trigger alarm."
			DEFVAL { 4 }
			::= { zhoneGponOltConfigEntry 6 }

		
		-- 1.3.6.1.4.1.5504.5.14.1.1.1.7
		zhoneGponOltConfigLoamAlpha OBJECT-TYPE
			SYNTAX Integer32
			MAX-ACCESS read-write
			STATUS current
			DESCRIPTION
				"Number of loss-of-OAM occurrences to trigger alarm."
			DEFVAL { 3 }
			::= { zhoneGponOltConfigEntry 7 }

		
		-- 1.3.6.1.4.1.5504.5.14.1.1.1.8
		zhoneGponOltConfigScrambler OBJECT-TYPE
			SYNTAX ZhoneEnabledFlag
			MAX-ACCESS read-write
			STATUS current
			DESCRIPTION
				"Description."
			DEFVAL { enabled }
			::= { zhoneGponOltConfigEntry 8 }

		
		-- 1.3.6.1.4.1.5504.5.14.1.1.1.9
		zhoneGponOltConfigFecMode OBJECT-TYPE
			SYNTAX ZhoneEnabledFlag
			MAX-ACCESS read-write
			STATUS current
			DESCRIPTION
				"Enables or disables forward error correction."
			DEFVAL { disabled }
			::= { zhoneGponOltConfigEntry 9 }

		
		-- 1.3.6.1.4.1.5504.5.14.1.1.1.10
		zhoneGponOltConfigAutoLearn OBJECT-TYPE
			SYNTAX ZhoneEnabledFlag
			MAX-ACCESS read-write
			STATUS current
			DESCRIPTION
				"Enable or disable password auto-learn mode."
			DEFVAL { enabled }
			::= { zhoneGponOltConfigEntry 10 }

		
		-- 1.3.6.1.4.1.5504.5.14.1.1.1.11
		zhoneGponOltConfigPowerLevel OBJECT-TYPE
			SYNTAX Unsigned32
			UNITS "db"
			MAX-ACCESS read-write
			STATUS current
			DESCRIPTION
				"Olt power level. For the Broadlight 3000, values will be rounded down
				to one of 0, 3, or 6."
			DEFVAL { 0 }
			::= { zhoneGponOltConfigEntry 11 }

		
		-- 1.3.6.1.4.1.5504.5.14.1.1.1.12
		zhoneGponOltConfigGuardBitCount OBJECT-TYPE
			SYNTAX Integer32
			UNITS "bits"
			MAX-ACCESS read-write
			STATUS current
			DESCRIPTION
				"Number of guard bits for upstream transmission."
			DEFVAL { 32 }
			::= { zhoneGponOltConfigEntry 12 }

		
		-- 1.3.6.1.4.1.5504.5.14.1.1.1.13
		zhoneGponOltConfigDbaMode OBJECT-TYPE
			SYNTAX INTEGER
				{
				predictive(1),
				piggyback(2),
				wholeReport(3)
				}
			MAX-ACCESS read-write
			STATUS current
			DESCRIPTION
				"Working DBA mode."
			DEFVAL { predictive }
			::= { zhoneGponOltConfigEntry 13 }

		
		-- 1.3.6.1.4.1.5504.5.14.1.1.1.14
		zhoneGponOltConfigGemBlockSize OBJECT-TYPE
			SYNTAX Integer32
			UNITS "bytes"
			MAX-ACCESS read-write
			STATUS current
			DESCRIPTION
				"Basic unit in bytes used by all ONUs for DBA reports
				of their queue occupancy (for piggyback and whole-report
				DBA only)."
			DEFVAL { 16 }
			::= { zhoneGponOltConfigEntry 14 }

		
		-- 1.3.6.1.4.1.5504.5.14.1.1.1.15
		zhoneGponOltConfigUsBerInterval OBJECT-TYPE
			SYNTAX Integer32
			UNITS "msec"
			MAX-ACCESS read-write
			STATUS current
			DESCRIPTION
				"Interval for upstream bit error rate calculation."
			DEFVAL { 5000 }
			::= { zhoneGponOltConfigEntry 15 }

		
		-- 1.3.6.1.4.1.5504.5.14.1.1.1.16
		zhoneGponOltConfigDsBerInterval OBJECT-TYPE
			SYNTAX Integer32
			UNITS "msec"
			MAX-ACCESS read-write
			STATUS current
			DESCRIPTION
				"Interval used for downstream bit error rate calculation."
			DEFVAL { 5000 }
			::= { zhoneGponOltConfigEntry 16 }

		
		-- 1.3.6.1.4.1.5504.5.14.1.1.1.17
		zhoneGponOltConfigBerSfThreshold OBJECT-TYPE
			SYNTAX Integer32 (3..8)
			MAX-ACCESS read-write
			STATUS current
			DESCRIPTION
				"Threshold is 10**(-N) for signal fail."
			DEFVAL { 3 }
			::= { zhoneGponOltConfigEntry 17 }

		
		-- 1.3.6.1.4.1.5504.5.14.1.1.1.18
		zhoneGponOltConfigBerSdThreshold OBJECT-TYPE
			SYNTAX Integer32 (4..9)
			MAX-ACCESS read-write
			STATUS current
			DESCRIPTION
				"Threshold is 10**(-N) for signal degrade. 
				Must exceed sf threshold."
			DEFVAL { 5 }
			::= { zhoneGponOltConfigEntry 18 }

		
		-- 1.3.6.1.4.1.5504.5.14.1.1.1.19
		zhoneGponOltConfigFecRequest OBJECT-TYPE
			SYNTAX ZhoneEnabledFlag
			MAX-ACCESS read-write
			STATUS current
			DESCRIPTION
				"Indicates whether OLT turns on FEC indication for all Alloc-Id
				in the Upstream Bandwidth Map."
			DEFVAL { disabled }
			::= { zhoneGponOltConfigEntry 19 }

		
		-- 1.3.6.1.4.1.5504.5.14.1.1.1.20
		zhoneGponOltConfigKeyExchange OBJECT-TYPE
			SYNTAX ZhoneEnabledFlag
			MAX-ACCESS read-write
			STATUS current
			DESCRIPTION
				"Specifies whether Single Key exchange should be performed 
				during ONU activation process."
			DEFVAL { disabled }
			::= { zhoneGponOltConfigEntry 20 }

		
		-- 1.3.6.1.4.1.5504.5.14.1.1.1.21
		zhoneGponOltConfigMinRtPropagationDelay OBJECT-TYPE
			SYNTAX Integer32
			UNITS "usec"
			MAX-ACCESS read-write
			STATUS current
			DESCRIPTION
				"If closest ONU location is known, GPON_stack uses 
				this value in order to limit the size of the quiet zone."
			DEFVAL { 0 }
			::= { zhoneGponOltConfigEntry 21 }

		
		-- 1.3.6.1.4.1.5504.5.14.1.1.1.22
		zhoneGponOltConfigMinOnuResponseTime OBJECT-TYPE
			SYNTAX Integer32
			UNITS "usec"
			MAX-ACCESS read-write
			STATUS current
			DESCRIPTION
				"GPON_stack uses this value in order to limit the
				size of the quiet zone."
			DEFVAL { 10 }
			::= { zhoneGponOltConfigEntry 22 }

		
		-- 1.3.6.1.4.1.5504.5.14.1.1.1.23
		zhoneGponOltConfigEqDMeasureCycles OBJECT-TYPE
			SYNTAX Integer32
			MAX-ACCESS read-write
			STATUS current
			DESCRIPTION
				"Defines the number of measurement cycles in the Ranging process."
			DEFVAL { 5 }
			::= { zhoneGponOltConfigEntry 23 }

		
		-- 1.3.6.1.4.1.5504.5.14.1.1.1.24
		zhoneGponOltConfigDriftControlInterval OBJECT-TYPE
			SYNTAX Integer32
			UNITS "msec"
			MAX-ACCESS read-write
			STATUS current
			DESCRIPTION
				"Defines the interval of periodic monitoring on 
				drifts of upstream data."
			DEFVAL { 1000 }
			::= { zhoneGponOltConfigEntry 24 }

		
		-- 1.3.6.1.4.1.5504.5.14.1.1.1.25
		zhoneGponOltConfigDriftControlLimit OBJECT-TYPE
			SYNTAX Integer32
			UNITS "bits"
			MAX-ACCESS read-write
			STATUS current
			DESCRIPTION
				"Indicates the limit of upstream data drift."
			DEFVAL { 3 }
			::= { zhoneGponOltConfigEntry 25 }

		
		-- 1.3.6.1.4.1.5504.5.14.1.1.1.26
		zhoneGponOltConfigAllocCycleLength OBJECT-TYPE
			SYNTAX Integer32 (1..10)
			UNITS "msec"
			MAX-ACCESS read-write
			STATUS current
			DESCRIPTION
				"Alloc-ID assignment map cycle length."
			DEFVAL { 2 }
			::= { zhoneGponOltConfigEntry 26 }

		
		-- 1.3.6.1.4.1.5504.5.14.1.1.1.27
		zhoneGponOltConfigMinUsAlloc OBJECT-TYPE
			SYNTAX Integer32
			UNITS "bytes"
			MAX-ACCESS read-write
			STATUS current
			DESCRIPTION
				"Size of minimal upstream allocation per frame."
			DEFVAL { 16 }
			::= { zhoneGponOltConfigEntry 27 }

		
		-- 1.3.6.1.4.1.5504.5.14.1.1.1.28
		zhoneGponOltConfigAckTimeout OBJECT-TYPE
			SYNTAX Integer32
			UNITS "msec"
			MAX-ACCESS read-write
			STATUS current
			DESCRIPTION
				"Timeout length of Acknowledge message."
			DEFVAL { 2000 }
			::= { zhoneGponOltConfigEntry 28 }

		
		-- 1.3.6.1.4.1.5504.5.14.1.1.1.29
		zhoneGponOltConfigPlsMaxAllocSize OBJECT-TYPE
			SYNTAX Integer32
			UNITS "bytes"
			MAX-ACCESS read-write
			STATUS current
			DESCRIPTION
				"Indecates a size of unassigned allocation that should be attached
				to the end of ranging window."
			DEFVAL { 120 }
			::= { zhoneGponOltConfigEntry 29 }

		
		-- 1.3.6.1.4.1.5504.5.14.1.1.1.30
		zhoneGponOltConfigDbaCycle OBJECT-TYPE
			SYNTAX Unsigned32 (2..10)
			UNITS "msec"
			MAX-ACCESS read-write
			STATUS current
			DESCRIPTION
				"The Dynamic Bandwidth Allocation(dba) cycle determines the DBA interval
				size. Its an integer multiplicant of 2 milli seconds. The range of values
				for the dba cycle can be between 2ms-10ms."
			DEFVAL { 2 }
			::= { zhoneGponOltConfigEntry 30 }

		
		-- 1.3.6.1.4.1.5504.5.14.1.1.1.31
		zhoneGponOltConfigSrDbaReportingBlockSize OBJECT-TYPE
			SYNTAX Unsigned32
			UNITS "bytes"
			MAX-ACCESS read-write
			STATUS current
			DESCRIPTION
				"For DBA of SR type, the block size defines the resolution of the status
				reports per PON link.The default value is 48 bytes."
			DEFVAL { 48 }
			::= { zhoneGponOltConfigEntry 31 }

		
		-- 1.3.6.1.4.1.5504.5.14.1.1.1.32
		zhoneGponOltConfigProtectionSwitchoverTimer OBJECT-TYPE
			SYNTAX Unsigned32
			UNITS "msec"
			MAX-ACCESS read-write
			STATUS current
			DESCRIPTION
				"If we receive LOS alarm for a link in Active state, the link state
				changes to Switch Over Pending state. If the actual switch-over does
				not happen after this protection-switchover-timeout expires, the link
				will go back to Active state"
			DEFVAL { 500 }
			::= { zhoneGponOltConfigEntry 32 }

		
		-- 1.3.6.1.4.1.5504.5.14.1.1.1.33
		zhoneGponOltConfigPreambleOverride OBJECT-TYPE
			SYNTAX ZhoneEnabledFlag
			MAX-ACCESS read-write
			STATUS current
			DESCRIPTION
				"Used to force the OLT to use the Preamble configuration in the
				OLT configuration profile.  Otherwise the Preamble configuration
				will be determined at runtime and based on the SFP.
				"
			DEFVAL { disabled }
			::= { zhoneGponOltConfigEntry 33 }

		
		-- 1.3.6.1.4.1.5504.5.14.1.1.1.34
		zhoneGponOltConfigPreambleType0 OBJECT-TYPE
			SYNTAX OCTET STRING (SIZE (0..4))
			MAX-ACCESS read-write
			STATUS current
			DESCRIPTION
				"Byte number for preamble type 0.
				
				This string represents a hex value with range 0x00 to 0xFF.
				
				String must have the following format: 0xNN   where
				where N is  0..9, A..F,  a..f
				"
			DEFVAL { "0x00" }
			::= { zhoneGponOltConfigEntry 34 }

		
		-- 1.3.6.1.4.1.5504.5.14.1.1.1.35
		zhoneGponOltConfigPreambleType1 OBJECT-TYPE
			SYNTAX OCTET STRING (SIZE (0..4))
			MAX-ACCESS read-write
			STATUS current
			DESCRIPTION
				"Byte number for preamble type 1.
				
				This string represents a hex value with range 0x00 to 0xFF.
				
				String must have the following format: 0xNN   where
				where N is  0..9, A..F,  a..f
				"
			DEFVAL { "0x00" }
			::= { zhoneGponOltConfigEntry 35 }

		
		-- 1.3.6.1.4.1.5504.5.14.1.1.1.36
		zhoneGponOltConfigPreambleType3PreRange OBJECT-TYPE
			SYNTAX OCTET STRING (SIZE (0..4))
			MAX-ACCESS read-write
			STATUS current
			DESCRIPTION
				"Byte number for preamble type 3 pre-ranging.
				
				This string represents a hex value with range 0x00 to 0xFF.
				
				String must have the following format: 0xNN   where
				where N is  0..9, A..F,  a..f
				"
			DEFVAL { "0x0b" }
			::= { zhoneGponOltConfigEntry 36 }

		
		-- 1.3.6.1.4.1.5504.5.14.1.1.1.37
		zhoneGponOltConfigPreambleType3PostRange OBJECT-TYPE
			SYNTAX OCTET STRING (SIZE (0..4))
			MAX-ACCESS read-write
			STATUS current
			DESCRIPTION
				"Byte number for preamble type 3 post-ranging.
				
				This string represents a hex value with range 0x00 to 0xFF.
				
				String must have the following format: 0xNN   where
				where N is  0..9, A..F,  a..f
				"
			DEFVAL { "0x08" }
			::= { zhoneGponOltConfigEntry 37 }

		
		-- 1.3.6.1.4.1.5504.5.14.1.1.1.38
		zhoneGponOltConfigPreambleType3Pattern OBJECT-TYPE
			SYNTAX OCTET STRING (SIZE (0..4))
			MAX-ACCESS read-write
			STATUS current
			DESCRIPTION
				"Preamble type 3 pattern.
				
				This string represents a hex value with range 0x00 to 0xFF.
				
				String must have the following format: 0xNN   where
				where N is  0..9, A..F,  a..f
				"
			DEFVAL { "0xaa" }
			::= { zhoneGponOltConfigEntry 38 }

		
		-- 1.3.6.1.4.1.5504.5.14.1.1.1.39
		zhoneGponOltConfigBipErrorMonitoring OBJECT-TYPE
			SYNTAX INTEGER
				{
				disabled(1),
				monitorOnly(2),
				blockOnError(3)
				}
			MAX-ACCESS read-write
			STATUS current
			DESCRIPTION
				"If in disabled mode, do not report BIP errors, do not disable ONU and
				do not throw any traps.
				                
				If in monitorOnly mode, monitor BIP errors and if BIP Error
				Threshold exceeded, set appropriate zhoneGponOnuStatusWord
				bits based on the type of BIP errors and throw zhoneGponOnuError
				trap.
				                
				If in blockOnError mode, monitor BIP errors and if BIP Error
				Threshold exceeded, block traffic, disable ONU ranging, set
				appropriate zhoneGponOnuStatusWord bits based on the type of
				BIP errors, and throw zhoneGponOnuError and
				linkDownTrap traps."
			DEFVAL { monitorOnly }
			::= { zhoneGponOltConfigEntry 39 }

		
		-- 1.3.6.1.4.1.5504.5.14.1.1.1.40
		zhoneGponOltConfigBipErrorsPerSampleThreshold OBJECT-TYPE
			SYNTAX Integer32
			MAX-ACCESS read-write
			STATUS current
			DESCRIPTION
				"If the number of BIP errors per sample exceeds this threshold,
				it is counted as an errored sample."
			DEFVAL { 100 }
			::= { zhoneGponOltConfigEntry 40 }

		
		-- 1.3.6.1.4.1.5504.5.14.1.1.1.41
		zhoneGponOltConfigBipErroredSamplesThreshold OBJECT-TYPE
			SYNTAX Integer32
			MAX-ACCESS read-write
			STATUS current
			DESCRIPTION
				"If the number of errored samples exceed this sample threshold,
				report and disable the onu if in blockOnError mode, 
				otherwise simply report the threshold as being exceeded."
			DEFVAL { 10 }
			::= { zhoneGponOltConfigEntry 41 }

		
		-- 1.3.6.1.4.1.5504.5.14.1.1.1.42
		zhoneGponOltConfigBipMaxSampleGap OBJECT-TYPE
			SYNTAX Integer32
			MAX-ACCESS read-write
			STATUS current
			DESCRIPTION
				"If two adjancent errored samples were taken farther apart than
				this threshold, do not count the earlier sample as an errored sample."
			DEFVAL { 10 }
			::= { zhoneGponOltConfigEntry 42 }

		
		-- 1.3.6.1.4.1.5504.5.14.1.1.1.43
		zhoneGponOltConfigRogueOnuDetection OBJECT-TYPE
			SYNTAX INTEGER
				{
				disabled(1),
				rogueRssi(2),
				backgroundProcess(3),
				autoRssi(4)
				}
			MAX-ACCESS read-write
			STATUS current
			DESCRIPTION
				"Controls detection of rogue ONU on fiber.
				Values are:
				1. detection disabled
				2. detect via measurement from rssi process
				3. detect via indication from background process.
				4. normally off, but switch to rssi mode if
				   rogue is suspected."
			DEFVAL { disabled }
			::= { zhoneGponOltConfigEntry 43 }

		
		-- 1.3.6.1.4.1.5504.5.14.1.1.1.44
		zhoneGponOltConfigRogueOnuDetectFrequency OBJECT-TYPE
			SYNTAX Integer32 (1..60)
			UNITS "seconds"
			MAX-ACCESS read-write
			STATUS current
			DESCRIPTION
				"Frequency in seconds for detection 
				background task."
			DEFVAL { 10 }
			::= { zhoneGponOltConfigEntry 44 }

		
		-- 1.3.6.1.4.1.5504.5.14.1.1.1.45
		zhoneGponOltConfigRogueOnuRxPowerThreshold OBJECT-TYPE
			SYNTAX Integer32
			MAX-ACCESS read-write
			STATUS current
			DESCRIPTION
				"Power level below which to report rssi
				rogue ONU."
			DEFVAL { -30 }
			::= { zhoneGponOltConfigEntry 45 }

		
		-- 1.3.6.1.4.1.5504.5.14.1.1.1.46
		zhoneGponOltConfigKeyExchangeInterval OBJECT-TYPE
			SYNTAX Integer32 (0 | 10..2147483647)
			UNITS "seconds"
			MAX-ACCESS read-write
			STATUS current
			DESCRIPTION
				"Periodicity for exchanging encryption key with ONUs on this OLT.
				A value of 0 disables periodic key exchange, i.e only send key once 
				during ranging., 
				The key-exchange parameter must be enabled for
				this value to take effect."
			DEFVAL { 3000 }
			::= { zhoneGponOltConfigEntry 46 }

		
		-- 1.3.6.1.4.1.5504.5.14.1.2
		zhoneGponOltOnuConfigTable OBJECT-TYPE
			SYNTAX SEQUENCE OF ZhoneGponOltOnuConfigEntry
			MAX-ACCESS not-accessible
			STATUS current
			DESCRIPTION
				"Configuration parameters applying to a single onu stacked on an olt.
				This profile is auto-created."
			::= { zhoneGponObjectID 2 }

		
		-- 1.3.6.1.4.1.5504.5.14.1.2.1
		zhoneGponOltOnuConfigEntry OBJECT-TYPE
			SYNTAX ZhoneGponOltOnuConfigEntry
			MAX-ACCESS not-accessible
			STATUS current
			DESCRIPTION
				"A row in the gpon olt-onu config table."
			INDEX { zhoneGponOltOnuIfIndex }
			::= { zhoneGponOltOnuConfigTable 1 }

		
		ZhoneGponOltOnuConfigEntry ::=
			SEQUENCE { 
				zhoneGponOltOnuIfIndex
					InterfaceIndex,
				zhoneGponOltOnuConfigSerialNoVendorId
					ZhoneAdminString,
				zhoneGponOltOnuConfigSerialNoVendorSpecific
					ZhoneAdminString,
				zhoneGponOltOnuConfigPassword
					ZhoneAdminString,
				zhoneGponOltOnuConfigAutoLearn
					ZhoneEnabledFlag,
				zhoneGponOltOnuConfigPowerLevel
					Integer32,
				zhoneGponOltOnuConfigUsBerInterval
					Integer32,
				zhoneGponOltOnuConfigDsBerInterval
					Integer32,
				zhoneGponOltOnuConfigOnuAdded
					TruthValue,
				zhoneGponOltOnuConfigOmciFileName
					ZhoneAdminString,
				zhoneGponOltOnuConfigMEProfileName
					ZhoneAdminString,
				zhoneGponOltOnuConfigGenericProfileName
					ZhoneAdminString,
				zhoneGponOltOnuConfigPhysicalTraps
					ZhoneEnabledFlag,
				zhoneGponOltOnuConfigOntTraps
					ZhoneEnabledFlag,
				zhoneGponOltOnuConfigLineStatusTraps
					INTEGER,
				zhoneGponOltOnuConfigAutoUpgrade
					ZhoneEnabledFlag,
				zhoneGponOltOnuConfigSerialNoVendorSpecificFsan
					OCTET STRING,
				zhoneGponOltOnuConfigUseRegId
					ZhoneEnabledFlag,
				zhoneGponOltOnuConfigModel
					OCTET STRING,
				zhoneGponOltOnuConfigOntVersion
					OCTET STRING,
				zhoneGponOltOnuConfigImageVersionActive
					OCTET STRING,
				zhoneGponOltOnuConfigImageVersionStandby
					OCTET STRING,
				zhoneGponOltOnuConfigUsRxPowerMonitoring
					INTEGER,
				zhoneGponOltOnuConfigUsRxPowerHighThreshold
					Integer32,
				zhoneGponOltOnuConfigUsRxPowerLowThreshold
					Integer32,
				zhoneGponOltOnuConfigDbaStatusReporting
					ZhoneEnabledFlag,
				zhoneGponOltOnuConfigOmciDataSync
					Unsigned32,
				zhoneGponOltOnuConfigSnmpDataSync
					Unsigned32,
				zhoneGponOltOnuConfigNextAvailableGemPort
					Integer32,
				zhoneGponOltOnuConfigAutoConfigState
					INTEGER,
				zhoneGponOltOnuConfigLinkStatusAlarmSeverity
					INTEGER,
				zhoneGponOltOnuConfigOltRxPower
					Integer32,
				zhoneGponOltOnuConfigOntRxPower
					Integer32,
				zhoneGponOltOnuConfigOnuDistance
					Unsigned32,
				zhoneGponOltOnuConfigSnmpAllocIdInfo
					Unsigned32
			 }

		-- 1.3.6.1.4.1.5504.5.14.1.2.1.1
		zhoneGponOltOnuIfIndex OBJECT-TYPE
			SYNTAX InterfaceIndex
			MAX-ACCESS not-accessible
			STATUS current
			DESCRIPTION
				"IfIndex of the onu interface stacked on the olt. "
			::= { zhoneGponOltOnuConfigEntry 1 }

		
		-- 1.3.6.1.4.1.5504.5.14.1.2.1.2
		zhoneGponOltOnuConfigSerialNoVendorId OBJECT-TYPE
			SYNTAX ZhoneAdminString (SIZE (0..4))
			MAX-ACCESS read-write
			STATUS current
			DESCRIPTION
				"This is a string of 4 ascii characters representing the 
				vendor ID portion of the onu serial number.
				Example: 'ZNTS' for Zhone."
			DEFVAL { "ZNTS" }
			::= { zhoneGponOltOnuConfigEntry 2 }

		
		-- 1.3.6.1.4.1.5504.5.14.1.2.1.3
		zhoneGponOltOnuConfigSerialNoVendorSpecific OBJECT-TYPE
			SYNTAX ZhoneAdminString (SIZE (1..10))
			MAX-ACCESS read-write
			STATUS current
			DESCRIPTION
				"This is a string of ascii decimal digits representing
				the vendor-specific portion of the onu serial number."
			DEFVAL { "0" }
			::= { zhoneGponOltOnuConfigEntry 3 }

		
		-- 1.3.6.1.4.1.5504.5.14.1.2.1.4
		zhoneGponOltOnuConfigPassword OBJECT-TYPE
			SYNTAX ZhoneAdminString (SIZE (0..10))
			MAX-ACCESS read-write
			STATUS current
			DESCRIPTION
				"Password (10 bytes)."
			DEFVAL { "" }
			::= { zhoneGponOltOnuConfigEntry 4 }

		
		-- 1.3.6.1.4.1.5504.5.14.1.2.1.5
		zhoneGponOltOnuConfigAutoLearn OBJECT-TYPE
			SYNTAX ZhoneEnabledFlag
			MAX-ACCESS read-write
			STATUS current
			DESCRIPTION
				"Indicates whether password is auto-learned."
			DEFVAL { enabled }
			::= { zhoneGponOltOnuConfigEntry 5 }

		
		-- 1.3.6.1.4.1.5504.5.14.1.2.1.6
		zhoneGponOltOnuConfigPowerLevel OBJECT-TYPE
			SYNTAX Integer32
			UNITS "db"
			MAX-ACCESS read-write
			STATUS current
			DESCRIPTION
				"Olt power level. For the Broadlight 3000, values will be rounded down
				to one of 0, 3, or 6."
			DEFVAL { 0 }
			::= { zhoneGponOltOnuConfigEntry 6 }

		
		-- 1.3.6.1.4.1.5504.5.14.1.2.1.7
		zhoneGponOltOnuConfigUsBerInterval OBJECT-TYPE
			SYNTAX Integer32
			UNITS "msec"
			MAX-ACCESS read-write
			STATUS current
			DESCRIPTION
				"Interval for upstream bit error rate calculation."
			DEFVAL { 5000 }
			::= { zhoneGponOltOnuConfigEntry 7 }

		
		-- 1.3.6.1.4.1.5504.5.14.1.2.1.8
		zhoneGponOltOnuConfigDsBerInterval OBJECT-TYPE
			SYNTAX Integer32
			UNITS "msec"
			MAX-ACCESS read-write
			STATUS current
			DESCRIPTION
				"Interval for downstream bit error rate."
			DEFVAL { 5000 }
			::= { zhoneGponOltOnuConfigEntry 8 }

		
		-- 1.3.6.1.4.1.5504.5.14.1.2.1.9
		zhoneGponOltOnuConfigOnuAdded OBJECT-TYPE
			SYNTAX TruthValue
			MAX-ACCESS read-write
			STATUS current
			DESCRIPTION
				"Indicates to Broadlight that onu is activated. 
				May not be used."
			DEFVAL { false }
			::= { zhoneGponOltOnuConfigEntry 9 }

		
		-- 1.3.6.1.4.1.5504.5.14.1.2.1.10
		zhoneGponOltOnuConfigOmciFileName OBJECT-TYPE
			SYNTAX ZhoneAdminString
			MAX-ACCESS read-write
			STATUS current
			DESCRIPTION
				"Name of OMCI configuration file for this ONT."
			DEFVAL { "" }
			::= { zhoneGponOltOnuConfigEntry 10 }

		
		-- 1.3.6.1.4.1.5504.5.14.1.2.1.11
		zhoneGponOltOnuConfigMEProfileName OBJECT-TYPE
			SYNTAX ZhoneAdminString
			MAX-ACCESS read-write
			STATUS current
			DESCRIPTION
				"This is the name of a Profile that contains OMCI commands which 
				can configure an ONU. It is expected that this Profile contain 
				OMCI commands that configure the Managed Entities (ME) on an
				ONU."
			DEFVAL { "" }
			::= { zhoneGponOltOnuConfigEntry 11 }

		
		-- 1.3.6.1.4.1.5504.5.14.1.2.1.12
		zhoneGponOltOnuConfigGenericProfileName OBJECT-TYPE
			SYNTAX ZhoneAdminString
			MAX-ACCESS read-write
			STATUS current
			DESCRIPTION
				"This is the name of a Profile that contains OMCI commands which 
				can configure an ONU. It is expected that this Profile contain 
				generic commands that are common to multiple ONUs."
			DEFVAL { "" }
			::= { zhoneGponOltOnuConfigEntry 12 }

		
		-- 1.3.6.1.4.1.5504.5.14.1.2.1.13
		zhoneGponOltOnuConfigPhysicalTraps OBJECT-TYPE
			SYNTAX ZhoneEnabledFlag
			MAX-ACCESS read-write
			STATUS current
			DESCRIPTION
				"If enabled, then an asynchronous notification from the ONT with 
				ME class ONT-G triggers an omciOnuAlarms trap. The alarm conditions 
				for this ME class are: equipment alarm, powering alarm, battery 
				missing, battery failure, battery low, physical intrusion alarm, 
				and self-test failure."
			DEFVAL { disabled }
			::= { zhoneGponOltOnuConfigEntry 13 }

		
		-- 1.3.6.1.4.1.5504.5.14.1.2.1.14
		zhoneGponOltOnuConfigOntTraps OBJECT-TYPE
			SYNTAX ZhoneEnabledFlag
			MAX-ACCESS read-write
			STATUS current
			DESCRIPTION
				"If enabled, then an asynchronous notification from the ONT 
				with ME class other than ONT-G triggers an omciOnuAlarms trap. "
			DEFVAL { disabled }
			::= { zhoneGponOltOnuConfigEntry 14 }

		
		-- 1.3.6.1.4.1.5504.5.14.1.2.1.15
		zhoneGponOltOnuConfigLineStatusTraps OBJECT-TYPE
			SYNTAX INTEGER
				{
				enabled(1),
				disabled(2),
				auto(3),
				linkonly(4)
				}
			MAX-ACCESS read-write
			STATUS current
			DESCRIPTION
				"If enabled, then gponOnuLineStatusChange traps, and also LinkUp/LinkDown 
				traps, are sent whenever line status changes between up and down. If 
				disabled, none of these traps is sent. If auto, then line status traps 
				are sent if the 'dying gasp' flag is on (for line down), or if the 
				'dying gasp' flag was on (for line up). Link down/up traps are not sent."
			DEFVAL { disabled }
			::= { zhoneGponOltOnuConfigEntry 15 }

		
		-- 1.3.6.1.4.1.5504.5.14.1.2.1.16
		zhoneGponOltOnuConfigAutoUpgrade OBJECT-TYPE
			SYNTAX ZhoneEnabledFlag
			MAX-ACCESS read-write
			STATUS current
			DESCRIPTION
				"If enabled, then the ONU s/w will be upgraded if the ONU version
				does not match the assoicated remote upgrade profile.  Changing
				this variable to disabled will not abort a remote software
				upgrade already in progress.
				"
			DEFVAL { enabled }
			::= { zhoneGponOltOnuConfigEntry 16 }

		
		-- 1.3.6.1.4.1.5504.5.14.1.2.1.17
		zhoneGponOltOnuConfigSerialNoVendorSpecificFsan OBJECT-TYPE
			SYNTAX OCTET STRING (SIZE (0..9))
			MAX-ACCESS read-write
			STATUS current
			DESCRIPTION
				"This is a string of ascii decimal digits representing
				the vendor-specific portion of the onu serial number
				in hex format ( FSAN ). "
			DEFVAL { "0" }
			::= { zhoneGponOltOnuConfigEntry 17 }

		
		-- 1.3.6.1.4.1.5504.5.14.1.2.1.18
		zhoneGponOltOnuConfigUseRegId OBJECT-TYPE
			SYNTAX ZhoneEnabledFlag
			MAX-ACCESS read-write
			STATUS current
			DESCRIPTION
				"If enabled, and if the onu is activated, then when an ONT
				is discovered with a registration ID that matches this ONU's
				password field, then the ONU will be auto-assigned to that
				ONT."
			DEFVAL { disabled }
			::= { zhoneGponOltOnuConfigEntry 18 }

		
		-- 1.3.6.1.4.1.5504.5.14.1.2.1.19
		zhoneGponOltOnuConfigModel OBJECT-TYPE
			SYNTAX OCTET STRING (SIZE (0..20))
			MAX-ACCESS read-only
			STATUS current
			DESCRIPTION
				"Model ID returned from this Onu."
			::= { zhoneGponOltOnuConfigEntry 19 }

		
		-- 1.3.6.1.4.1.5504.5.14.1.2.1.20
		zhoneGponOltOnuConfigOntVersion OBJECT-TYPE
			SYNTAX OCTET STRING (SIZE (0..14))
			MAX-ACCESS read-only
			STATUS current
			DESCRIPTION
				"This object defines the version of the ONT as defined by the vendor.
				The character value '0' indicates that the version information is not
				available or applicable."
			::= { zhoneGponOltOnuConfigEntry 20 }

		
		-- 1.3.6.1.4.1.5504.5.14.1.2.1.21
		zhoneGponOltOnuConfigImageVersionActive OBJECT-TYPE
			SYNTAX OCTET STRING (SIZE (0..64))
			MAX-ACCESS read-only
			STATUS current
			DESCRIPTION
				"Version information for the active s/w image."
			::= { zhoneGponOltOnuConfigEntry 21 }

		
		-- 1.3.6.1.4.1.5504.5.14.1.2.1.22
		zhoneGponOltOnuConfigImageVersionStandby OBJECT-TYPE
			SYNTAX OCTET STRING (SIZE (0..64))
			MAX-ACCESS read-only
			STATUS current
			DESCRIPTION
				"Version information for the standby s/w image."
			::= { zhoneGponOltOnuConfigEntry 22 }

		
		-- 1.3.6.1.4.1.5504.5.14.1.2.1.23
		zhoneGponOltOnuConfigUsRxPowerMonitoring OBJECT-TYPE
			SYNTAX INTEGER
				{
				disabled(1),
				monitorOnly(2),
				blockOnError(3)
				}
			MAX-ACCESS read-write
			STATUS current
			DESCRIPTION
				"If in disabled mode, do not report Upstream Onu Rx Power errors, 
				do not disable ONU and do not throw any traps.
				                                                
				If in monitorOnly mode, monitor Upstream Onu Rx Power levels and
				if level is outside of thresholds, set appropriate zhoneGponOnuStatusWord
				bits and throw zhoneGponOnuError trap.
				                                                
				If in blockOnError mode, monitor Upstream Onu Rx Power levels and
				if level is outside of thresholds, block traffic, disable ONU ranging,
				set appropriate zhoneGponOnuStatusWord bits and throw both zhoneGponOnuError
				and linkDownTrap traps."
			DEFVAL { monitorOnly }
			::= { zhoneGponOltOnuConfigEntry 23 }

		
		-- 1.3.6.1.4.1.5504.5.14.1.2.1.24
		zhoneGponOltOnuConfigUsRxPowerHighThreshold OBJECT-TYPE
			SYNTAX Integer32
			UNITS "dBm"
			MAX-ACCESS read-write
			STATUS current
			DESCRIPTION
				"Upstream Receive Power High Threshold value."
			DEFVAL { -10 }
			::= { zhoneGponOltOnuConfigEntry 24 }

		
		-- 1.3.6.1.4.1.5504.5.14.1.2.1.25
		zhoneGponOltOnuConfigUsRxPowerLowThreshold OBJECT-TYPE
			SYNTAX Integer32
			UNITS "dBm"
			MAX-ACCESS read-write
			STATUS current
			DESCRIPTION
				"Upstream Receive Power Low Threshold value."
			DEFVAL { -30 }
			::= { zhoneGponOltOnuConfigEntry 25 }

		
-- 
		-- 1.3.6.1.4.1.5504.5.14.1.2.1.26
		zhoneGponOltOnuConfigDbaStatusReporting OBJECT-TYPE
			SYNTAX ZhoneEnabledFlag
			MAX-ACCESS read-write
			STATUS current
			DESCRIPTION
				"There are two types of DBA, Status Reporting and Non Status Reporting.
				The value is enabled or disabled. The default is disabled."
			DEFVAL { disabled }
			::= { zhoneGponOltOnuConfigEntry 26 }

		
-- 
		-- 1.3.6.1.4.1.5504.5.14.1.2.1.27
		zhoneGponOltOnuConfigOmciDataSync OBJECT-TYPE
			SYNTAX Unsigned32
			MAX-ACCESS read-only
			STATUS current
			DESCRIPTION
				"If the MIB data sync value returned from the ONU on a MIB audit matches the MXK value, config not required."
			DEFVAL { 0 }
			::= { zhoneGponOltOnuConfigEntry 27 }

		
-- 
		-- 1.3.6.1.4.1.5504.5.14.1.2.1.28
		zhoneGponOltOnuConfigSnmpDataSync OBJECT-TYPE
			SYNTAX Unsigned32
			MAX-ACCESS read-only
			STATUS current
			DESCRIPTION
				"If the SNMP provisioning change value returned from the CPE matches the MXK value, config not required."
			DEFVAL { 0 }
			::= { zhoneGponOltOnuConfigEntry 28 }

		
		-- 1.3.6.1.4.1.5504.5.14.1.2.1.29
		zhoneGponOltOnuConfigNextAvailableGemPort OBJECT-TYPE
			SYNTAX Integer32 (257..3828)
			MAX-ACCESS read-only
			STATUS current
			DESCRIPTION
				"Next available GEM PORT for the ONU.  "
			::= { zhoneGponOltOnuConfigEntry 29 }

		
-- 
		-- 1.3.6.1.4.1.5504.5.14.1.2.1.30
		zhoneGponOltOnuConfigAutoConfigState OBJECT-TYPE
			SYNTAX INTEGER
				{
				init(1),
				done(2),
				disabled(3),
				error(4)
				}
			MAX-ACCESS read-only
			STATUS current
			DESCRIPTION
				"Track whether the ONU has been auto-configured."
			DEFVAL { init }
			::= { zhoneGponOltOnuConfigEntry 30 }

		
		-- 1.3.6.1.4.1.5504.5.14.1.2.1.31
		zhoneGponOltOnuConfigLinkStatusAlarmSeverity OBJECT-TYPE
			SYNTAX INTEGER
				{
				critical(1),
				major(2),
				minor(3)
				}
			MAX-ACCESS read-write
			STATUS current
			DESCRIPTION
				"Based on the severity set in this field LinkUp/LinkDown
				alarms are raised."
			DEFVAL { minor }
			::= { zhoneGponOltOnuConfigEntry 31 }

		
		-- 1.3.6.1.4.1.5504.5.14.1.2.1.32
		zhoneGponOltOnuConfigOltRxPower OBJECT-TYPE
			SYNTAX Integer32 (-600..200)
			UNITS "tenths of dB"
			MAX-ACCESS read-only
			STATUS current
			DESCRIPTION
				"RSSI power of the SFP per ONU. The value is in tenths of dB."
			::= { zhoneGponOltOnuConfigEntry 32 }

		
		-- 1.3.6.1.4.1.5504.5.14.1.2.1.33
		zhoneGponOltOnuConfigOntRxPower OBJECT-TYPE
			SYNTAX Integer32 (-600..200)
			UNITS "tenths of dB"
			MAX-ACCESS read-only
			STATUS current
			DESCRIPTION
				"Rx Power as reported by the ONT. The value is in tenths of dB."
			::= { zhoneGponOltOnuConfigEntry 33 }

		
		-- 1.3.6.1.4.1.5504.5.14.1.2.1.34
		zhoneGponOltOnuConfigOnuDistance OBJECT-TYPE
			SYNTAX Unsigned32
			MAX-ACCESS read-only
			STATUS current
			DESCRIPTION
				"Distance from Olt to Ont in meters, as computed from Eqd."
			::= { zhoneGponOltOnuConfigEntry 34 }

		
		-- 1.3.6.1.4.1.5504.5.14.1.2.1.35
		zhoneGponOltOnuConfigSnmpAllocIdInfo OBJECT-TYPE
			SYNTAX Unsigned32
			MAX-ACCESS read-only
			STATUS current
			DESCRIPTION
				"Alloc-id and tcont-index of this ONU's SNMP gemport.
				Generated by gponRP; saved here to avoid ONU reconfig on system reboot."
			DEFVAL { 0 }
			::= { zhoneGponOltOnuConfigEntry 35 }

		
		-- 1.3.6.1.4.1.5504.5.14.1.3
		zhoneGponPortConfigTable OBJECT-TYPE
			SYNTAX SEQUENCE OF ZhoneGponPortConfigEntry
			MAX-ACCESS not-accessible
			STATUS current
			DESCRIPTION
				"The gpon port is similiar to VCLs in ATM.  Data is transferred between
				OLT and ONU via ports. This profile is dynamically created during
				CLI bridge-add, host-add, interface-add commands but must be 
				explicitly created during SNMP operation.
				
				GEM ports can be created using a supplied I/F index value or
				using the next available I/F index value.   Since the GEM Port
				is a virtual device, ZMS prefers to supply the I/F index value
				because ZMS cannot lookup the newly created GEM port using
				shelf/slot/olt/port indexing ( virual devices do not support
				these values).
				
				How to create a GEM port using next available I/F Index value, 
				using a single SNMP packet with multiple var-binds:
				
				   1. Do an SNMP-Next of the object ifIndexNext to determine
				      the I/F index value of the new GEM port.  The SNMP-Next
				      will not result in the auto-increment of ifIndexNext.
						
				   2. Issue single SNMP set command containing the following:
				         zhoneGponPortConfigRowStatus.1 = create
				         zhoneGponPortConfigRowShelf.1 = 1
				         zhoneGponPortConfigRowSlot.1 = GEM port slot
				         zhoneGponPortConfigRowOlt.1 = GEM port OLT
				         zhoneGponPortConfigRowPort.1 = GEM Port ID value
				         zhoneGponPortConfigRowTrafficProfile.1 = traffic profile
				
				   The GEM port will be created using the next available ifIndex.
					  
				How to create a GEM port with a specified I/F index value, 
				using a single SNMP packet with multiple var-binds:
				
				   1. Do an SNMP-Get of the object ifIndexNext to determine
				      the next available I/F index value.  The SNMP-Get
				      will result in the auto-increment of ifIndexNext.
				
				   2. Issue single SNMP set command containing the following:
				         zhoneGponPortConfigRowStatus.aaa = create
				         zhoneGponPortConfigRowShelf.aaa = 1
				         zhoneGponPortConfigRowSlot.aaa = GEM port slot
				         zhoneGponPortConfigRowOlt.aaa = GEM port OLT
				         zhoneGponPortConfigRowPort.aaa = GEM Port ID value
				         zhoneGponPortConfigRowTrafficProfile.aaa = traffic profile
				
				      where aaa is the I/F index value collected in step 1.
				
				   A GEM Port cannot be created if an I/F translate record
				   already exists using the supplied I/F index value.
				
				How to delete a GEM port using a single SNMP packet:
				
				   1. Determine I/F index of GEM port config profile (aaa)
				
				   2. Issue single SNMP set command containing the following:
				         zhoneGponPortConfigRowStatus.aaa = destroy
				
				Special Notes:
				 
				   1. The deletion of a GEM port will be prevented if the GEM    
				      port supports bridges, interfaces, etc.
				
				   2. The GEM port ID value determines the GEM port ONU."
			::= { zhoneGponObjectID 3 }

		
		-- 1.3.6.1.4.1.5504.5.14.1.3.1
		zhoneGponPortConfigEntry OBJECT-TYPE
			SYNTAX ZhoneGponPortConfigEntry
			MAX-ACCESS not-accessible
			STATUS current
			DESCRIPTION
				"A row in the gpon port config table."
			INDEX { zhoneGponPortIfIndex }
			::= { zhoneGponPortConfigTable 1 }

		
		ZhoneGponPortConfigEntry ::=
			SEQUENCE { 
				zhoneGponPortIfIndex
					InterfaceIndex,
				zhoneGponPortConfigRowStatus
					ZhoneRowStatus,
				zhoneGponPortConfigMulticast
					TruthValue,
				zhoneGponPortConfigEncrypted
					TruthValue,
				zhoneGponPortConfigDirection
					INTEGER,
				zhoneGponPortConfigTrafficProfile
					Unsigned32,
				zhoneGponPortConfigRowShelf
					Unsigned32,
				zhoneGponPortConfigRowSlot
					Unsigned32,
				zhoneGponPortConfigRowOlt
					Unsigned32,
				zhoneGponPortConfigRowPort
					Unsigned32,
				zhoneGponPortConfigRowTrafficProfile
					Unsigned32,
				zhoneGponPortConfigRowOnuId
					Unsigned32,
				zhoneGponPortConfigTrafficManagementProfileIndex
					Unsigned32,
				zhoneGponPortConfigAllocIdInfo
					Unsigned32
			 }

		-- 1.3.6.1.4.1.5504.5.14.1.3.1.1
		zhoneGponPortIfIndex OBJECT-TYPE
			SYNTAX InterfaceIndex
			MAX-ACCESS not-accessible
			STATUS current
			DESCRIPTION
				"The ifIndex of the gpon-port interface stacked on the olt."
			::= { zhoneGponPortConfigEntry 1 }

		
		-- 1.3.6.1.4.1.5504.5.14.1.3.1.2
		zhoneGponPortConfigRowStatus OBJECT-TYPE
			SYNTAX ZhoneRowStatus
			MAX-ACCESS read-create
			STATUS current
			DESCRIPTION
				"The row status for the port config table. "
			::= { zhoneGponPortConfigEntry 2 }

		
		-- 1.3.6.1.4.1.5504.5.14.1.3.1.3
		zhoneGponPortConfigMulticast OBJECT-TYPE
			SYNTAX TruthValue
			MAX-ACCESS read-create
			STATUS current
			DESCRIPTION
				"Specifies whether this is a multicast or unicast port.
				If unicast, only one onu may be given, and the unicast-onu-id
				field is used. If multicast is true, then the multicast-onu-ids
				is used to name the onus."
			DEFVAL { false }
			::= { zhoneGponPortConfigEntry 3 }

		
		-- 1.3.6.1.4.1.5504.5.14.1.3.1.4
		zhoneGponPortConfigEncrypted OBJECT-TYPE
			SYNTAX TruthValue
			MAX-ACCESS read-create
			STATUS current
			DESCRIPTION
				"Specifies whether port-id PLOAM messages are encrypted. Must 
				be false if multicast."
			DEFVAL { true }
			::= { zhoneGponPortConfigEntry 4 }

		
		-- 1.3.6.1.4.1.5504.5.14.1.3.1.5
		zhoneGponPortConfigDirection OBJECT-TYPE
			SYNTAX INTEGER
				{
				down(1),
				up(2),
				bidirectional(3)
				}
			MAX-ACCESS read-create
			STATUS current
			DESCRIPTION
				"Direction of data for this port."
			DEFVAL { bidirectional }
			::= { zhoneGponPortConfigEntry 5 }

		
		-- 1.3.6.1.4.1.5504.5.14.1.3.1.6
		zhoneGponPortConfigTrafficProfile OBJECT-TYPE
			SYNTAX Unsigned32
			MAX-ACCESS read-create
			STATUS current
			DESCRIPTION
				"Index of GEM Port traffic profile for this port.  A zero value indicates 
				no GEM Port traffic profile has been selected."
			DEFVAL { 0 }
			::= { zhoneGponPortConfigEntry 6 }

		
		-- 1.3.6.1.4.1.5504.5.14.1.3.1.7
		zhoneGponPortConfigRowShelf OBJECT-TYPE
			SYNTAX Unsigned32
			MAX-ACCESS read-create
			STATUS current
			DESCRIPTION
				"This is a WRITE-ONLY variable used during port create/delete operations."
			DEFVAL { '0'b }
			::= { zhoneGponPortConfigEntry 7 }

		
		-- 1.3.6.1.4.1.5504.5.14.1.3.1.8
		zhoneGponPortConfigRowSlot OBJECT-TYPE
			SYNTAX Unsigned32
			MAX-ACCESS read-create
			STATUS current
			DESCRIPTION
				"This is a WRITE-ONLY variable used during port create/delete operations."
			DEFVAL { '0'b }
			::= { zhoneGponPortConfigEntry 8 }

		
		-- 1.3.6.1.4.1.5504.5.14.1.3.1.9
		zhoneGponPortConfigRowOlt OBJECT-TYPE
			SYNTAX Unsigned32
			MAX-ACCESS read-create
			STATUS current
			DESCRIPTION
				"This is a WRITE-ONLY variable used during port create/delete operations."
			DEFVAL { '0'b }
			::= { zhoneGponPortConfigEntry 9 }

		
		-- 1.3.6.1.4.1.5504.5.14.1.3.1.10
		zhoneGponPortConfigRowPort OBJECT-TYPE
			SYNTAX Unsigned32
			MAX-ACCESS read-create
			STATUS current
			DESCRIPTION
				"This is a WRITE-ONLY variable used during port create/delete operations."
			DEFVAL { '0'b }
			::= { zhoneGponPortConfigEntry 10 }

		
		-- 1.3.6.1.4.1.5504.5.14.1.3.1.11
		zhoneGponPortConfigRowTrafficProfile OBJECT-TYPE
			SYNTAX Unsigned32
			MAX-ACCESS read-create
			STATUS current
			DESCRIPTION
				"This is a WRITE-ONLY variable used during port create/delete operations."
			DEFVAL { '0'b }
			::= { zhoneGponPortConfigEntry 11 }

		
		-- 1.3.6.1.4.1.5504.5.14.1.3.1.12
		zhoneGponPortConfigRowOnuId OBJECT-TYPE
			SYNTAX Unsigned32
			MAX-ACCESS read-create
			STATUS current
			DESCRIPTION
				"The subPort of the ONU on which this GEM port is
				to be stacked. This is a write-only variable during
				row create."
			::= { zhoneGponPortConfigEntry 12 }

		
		-- 1.3.6.1.4.1.5504.5.14.1.3.1.13
		zhoneGponPortConfigTrafficManagementProfileIndex OBJECT-TYPE
			SYNTAX Unsigned32 (0..2147483647)
			MAX-ACCESS read-create
			STATUS current
			DESCRIPTION
				"This object points to the associated Traffic Management profile. If there is
				no traffic control for the GEM port, set it to 0."
			DEFVAL { 0 }
			::= { zhoneGponPortConfigEntry 13 }

		
		-- 1.3.6.1.4.1.5504.5.14.1.3.1.14
		zhoneGponPortConfigAllocIdInfo OBJECT-TYPE
			SYNTAX Unsigned32
			MAX-ACCESS read-only
			STATUS current
			DESCRIPTION
				"Alloc-id and tcont-index of this gemport.
				Generated by gponRP; saved here to avoid ONU reconfig on system reboot."
			DEFVAL { 0 }
			::= { zhoneGponPortConfigEntry 14 }

		
		-- 1.3.6.1.4.1.5504.5.14.1.4
		zhoneGponAllocIdTable OBJECT-TYPE
			SYNTAX SEQUENCE OF ZhoneGponAllocIdEntry
			MAX-ACCESS not-accessible
			STATUS current
			DESCRIPTION
				"Table for management of upstream bandwidth"
			::= { zhoneGponObjectID 4 }

		
		-- 1.3.6.1.4.1.5504.5.14.1.4.1
		zhoneGponAllocIdEntry OBJECT-TYPE
			SYNTAX ZhoneGponAllocIdEntry
			MAX-ACCESS not-accessible
			STATUS current
			DESCRIPTION
				"Entry in the gpon allocId table."
			INDEX { zhoneGponOltIfIndex, zhoneGponAllocIdIndex }
			::= { zhoneGponAllocIdTable 1 }

		
		ZhoneGponAllocIdEntry ::=
			SEQUENCE { 
				zhoneGponAllocIdIndex
					Integer32,
				zhoneGponAllocIdRowStatus
					ZhoneRowStatus,
				zhoneGponAllocIdOnuId
					Integer32,
				zhoneGponAllocIdGuaranteedBw
					Integer32,
				zhoneGponAllocIdTrafficClass
					INTEGER,
				zhoneGponAllocIdCompensated
					TruthValue
			 }

		-- 1.3.6.1.4.1.5504.5.14.1.4.1.1
		zhoneGponAllocIdIndex OBJECT-TYPE
			SYNTAX Integer32 (1..2147483647)
			MAX-ACCESS not-accessible
			STATUS current
			DESCRIPTION
				"An Id number which must be unique for a given OLT."
			::= { zhoneGponAllocIdEntry 1 }

		
		-- 1.3.6.1.4.1.5504.5.14.1.4.1.2
		zhoneGponAllocIdRowStatus OBJECT-TYPE
			SYNTAX ZhoneRowStatus
			MAX-ACCESS read-create
			STATUS current
			DESCRIPTION
				"Row status for the gpon alloc-id table."
			::= { zhoneGponAllocIdEntry 2 }

		
-- 
		-- 1.3.6.1.4.1.5504.5.14.1.4.1.3
		zhoneGponAllocIdOnuId OBJECT-TYPE
			SYNTAX Integer32
			MAX-ACCESS read-create
			STATUS current
			DESCRIPTION
				"The onu number for this olt to which we are allocating bandwidth.
				Cannot be greater than number of onus for the olt.
				This field cannot be changed once the alloc-id has been
				created."
			::= { zhoneGponAllocIdEntry 3 }

		
		-- 1.3.6.1.4.1.5504.5.14.1.4.1.4
		zhoneGponAllocIdGuaranteedBw OBJECT-TYPE
			SYNTAX Integer32
			UNITS "kilobits"
			MAX-ACCESS read-create
			STATUS current
			DESCRIPTION
				"Bandwidth guaranteed by this alloc-id. 
				This value is specified in kilobits per second. Only
				multiples of 512 are allowed, and the value may not
				exceed 2621440 (i.e. 2.5 gigabits per second).
				"
			::= { zhoneGponAllocIdEntry 4 }

		
		-- 1.3.6.1.4.1.5504.5.14.1.4.1.5
		zhoneGponAllocIdTrafficClass OBJECT-TYPE
			SYNTAX INTEGER
				{
				cbr(1),
				ubr(2)
				}
			MAX-ACCESS read-create
			STATUS current
			DESCRIPTION
				"Whether traffic is Constant Bit Rate or Unspecified Bit Rate."
			DEFVAL { ubr }
			::= { zhoneGponAllocIdEntry 5 }

		
		-- 1.3.6.1.4.1.5504.5.14.1.4.1.6
		zhoneGponAllocIdCompensated OBJECT-TYPE
			SYNTAX TruthValue
			MAX-ACCESS read-create
			STATUS current
			DESCRIPTION
				"For CBR, indicates whether compensated."
			DEFVAL { true }
			::= { zhoneGponAllocIdEntry 6 }

		
		-- 1.3.6.1.4.1.5504.5.14.1.5
		zhoneGponSerialNoTable OBJECT-TYPE
			SYNTAX SEQUENCE OF ZhoneGponSerialNoEntry
			MAX-ACCESS not-accessible
			STATUS current
			DESCRIPTION
				"Table of discovered serial numbers available
				for assignment to onus."
			::= { zhoneGponObjectID 5 }

		
		-- 1.3.6.1.4.1.5504.5.14.1.5.1
		zhoneGponSerialNoEntry OBJECT-TYPE
			SYNTAX ZhoneGponSerialNoEntry
			MAX-ACCESS not-accessible
			STATUS current
			DESCRIPTION
				"Row in the Gpon onu serial number table"
			INDEX { zhoneGponSerialNoOltLgIfIndex, zhoneGponSerialNoIndexId }
			::= { zhoneGponSerialNoTable 1 }

		
		ZhoneGponSerialNoEntry ::=
			SEQUENCE { 
				zhoneGponSerialNoOltLgIfIndex
					InterfaceIndex,
				zhoneGponSerialNoIndexId
					Unsigned32,
				zhoneGponSerialNoVendorId
					ZhoneAdminString,
				zhoneGponSerialNoVendorSpecific
					ZhoneAdminString,
				zhoneGponSerialNoTimeStamp
					OCTET STRING,
				zhoneGponSerialNoModelId
					OCTET STRING
			 }

		-- 1.3.6.1.4.1.5504.5.14.1.5.1.1
		zhoneGponSerialNoOltLgIfIndex OBJECT-TYPE
			SYNTAX InterfaceIndex
			MAX-ACCESS not-accessible
			STATUS current
			DESCRIPTION
				"Linegroup ifIndex of the Olt on which serial number
				was discovered."
			::= { zhoneGponSerialNoEntry 1 }

		
		-- 1.3.6.1.4.1.5504.5.14.1.5.1.2
		zhoneGponSerialNoIndexId OBJECT-TYPE
			SYNTAX Unsigned32
			MAX-ACCESS not-accessible
			STATUS current
			DESCRIPTION
				"An identifying number, unique within olt, 
				for this discovered onu serial number."
			::= { zhoneGponSerialNoEntry 2 }

		
		-- 1.3.6.1.4.1.5504.5.14.1.5.1.3
		zhoneGponSerialNoVendorId OBJECT-TYPE
			SYNTAX ZhoneAdminString (SIZE (0..4))
			MAX-ACCESS read-only
			STATUS current
			DESCRIPTION
				"The 4-character vendor id portion of serial number. "
			::= { zhoneGponSerialNoEntry 3 }

		
		-- 1.3.6.1.4.1.5504.5.14.1.5.1.4
		zhoneGponSerialNoVendorSpecific OBJECT-TYPE
			SYNTAX ZhoneAdminString (SIZE (1..10))
			MAX-ACCESS read-write
			STATUS current
			DESCRIPTION
				"Vendor specific portion of the unassigned onu
				serial number, a string of decimal digits."
			::= { zhoneGponSerialNoEntry 4 }

		
		-- 1.3.6.1.4.1.5504.5.14.1.5.1.5
		zhoneGponSerialNoTimeStamp OBJECT-TYPE
			SYNTAX OCTET STRING (SIZE (0..32))
			MAX-ACCESS read-only
			STATUS current
			DESCRIPTION
				"Time, as ascii string, that the serial number was discovered."
			::= { zhoneGponSerialNoEntry 5 }

		
		-- 1.3.6.1.4.1.5504.5.14.1.5.1.6
		zhoneGponSerialNoModelId OBJECT-TYPE
			SYNTAX OCTET STRING (SIZE (0..20))
			MAX-ACCESS read-only
			STATUS current
			DESCRIPTION
				"Model ID of the ONU, a string."
			::= { zhoneGponSerialNoEntry 6 }

		
		-- 1.3.6.1.4.1.5504.5.14.1.6
		zhoneGponTrapPrefix OBJECT-IDENTITY
			STATUS current
			DESCRIPTION 
				"Place-holder object for gpon traps, which must have a 
				final digit of 0 in OID."
			::= { zhoneGponObjectID 6 }

		
		-- 1.3.6.1.4.1.5504.5.14.1.6.0
		zhoneGponTraps OBJECT-IDENTITY
			STATUS current
			DESCRIPTION 
				"Traps raised by Gpon Rp."
			::= { zhoneGponTrapPrefix 0 }

		
		-- 1.3.6.1.4.1.5504.5.14.1.6.0.1
		zhoneGponSerialNumberFound NOTIFICATION-TYPE
			OBJECTS { zhoneGponSerialNoVendorId, zhoneGponSerialNoVendorSpecific, zhoneGponSerialNoModelId }
			STATUS current
			DESCRIPTION 
				"Notification that an ONU serial number has been
				discovered."
			::= { zhoneGponTraps 1 }

		
		-- 1.3.6.1.4.1.5504.5.14.1.6.0.2
		zhoneGponSerialNumberLost NOTIFICATION-TYPE
			OBJECTS { zhoneGponSerialNoVendorId, zhoneGponSerialNoVendorSpecific }
			STATUS current
			DESCRIPTION 
				"Notification that a previously discovered ONU
				serial number is no longer available."
			::= { zhoneGponTraps 2 }

		
		-- 1.3.6.1.4.1.5504.5.14.1.6.0.3
		zhoneGponOnuLineStatusChange NOTIFICATION-TYPE
			OBJECTS { zhoneGponOnuStatusWord }
			STATUS current
			DESCRIPTION 
				"Description."
			::= { zhoneGponTraps 3 }

		
		-- 1.3.6.1.4.1.5504.5.14.1.6.0.4
		zhoneGponOmciOnuAlarmsTrap NOTIFICATION-TYPE
			OBJECTS { zhoneGponOmciOnuAlarmsText }
			STATUS current
			DESCRIPTION 
				"Current active alarms for an ONU entity.   Alarms
				contained in the trap bindings will be for only one
				specific entity.   If an entity alarm is not contained
				in the trap bindings then the alarm is either not 
				active, not enabled, or not supported.
				
				If there are no alarms for the entity, then there
				will only be one alarm in the trap bindings and
				that alarm will have a value of zero and the alarm
				string will be 'None'."
			::= { zhoneGponTraps 4 }

		
		-- 1.3.6.1.4.1.5504.5.14.1.6.0.5
		zhoneGponOmciOnuDownloadStatusChange NOTIFICATION-TYPE
			OBJECTS { zhoneOnuOmciImageUpgradeDownloadStatus }
			STATUS current
			DESCRIPTION 
				"Trap will be raised for Image Download status changes."
			::= { zhoneGponTraps 5 }

		
		-- 1.3.6.1.4.1.5504.5.14.1.6.0.6
		zhoneGponOltOpticsAlarmsTrap NOTIFICATION-TYPE
			OBJECTS { zhoneGponOltOpticAlarms }
			STATUS current
			DESCRIPTION 
				"Raised when SFP reports optics alarms 
				condition for an SFP."
			::= { zhoneGponTraps 6 }

		
		-- 1.3.6.1.4.1.5504.5.14.1.6.0.7
		zhoneGponOnuError NOTIFICATION-TYPE
			OBJECTS { zhoneGponOnuStatusWord }
			STATUS current
			DESCRIPTION 
				"One of the ONU error conditions is present for the
				specified ONU.  Report zhoneGponOnuStatusWord to indicate
				which error has occurred."
			::= { zhoneGponTraps 7 }

		
		-- 1.3.6.1.4.1.5504.5.14.1.6.0.8
		zhoneGponRogueOnuTrap NOTIFICATION-TYPE
			OBJECTS { zhoneGponOltStatusWord }
			STATUS current
			DESCRIPTION 
				"A rogue ONU has been detected on this OLT
				by the background process"
			::= { zhoneGponTraps 8 }

		
		-- 1.3.6.1.4.1.5504.5.14.1.6.0.9
		zhoneGponRssiRogueOnuTrap NOTIFICATION-TYPE
			OBJECTS { zhoneGponOltStatusWord }
			STATUS current
			DESCRIPTION 
				"Rogue ONU has been detected by RSSI process
				on this OLT."
			::= { zhoneGponTraps 9 }

		
		-- 1.3.6.1.4.1.5504.5.14.1.6.0.10
		zhoneGponOltStatusWordTrap NOTIFICATION-TYPE
			OBJECTS { zhoneGponOltStatusWord }
			STATUS current
			DESCRIPTION 
				"Change in one of the gpol olt status word bits has been detected."
			::= { zhoneGponTraps 10 }

		
		-- 1.3.6.1.4.1.5504.5.14.1.6.0.11
		zhoneGponOnuAutoAssign NOTIFICATION-TYPE
			OBJECTS { zhoneGponSerialNoVendorId, zhoneGponSerialNoVendorSpecific, zhoneGponOltOnuConfigModel }
			STATUS current
			DESCRIPTION 
				"Notification that an ONU ID has been auto assigned."
			::= { zhoneGponTraps 11 }

		
		-- 1.3.6.1.4.1.5504.5.14.1.7
		zhoneGponOnuStatusTable OBJECT-TYPE
			SYNTAX SEQUENCE OF ZhoneGponOnuStatusEntry
			MAX-ACCESS not-accessible
			STATUS current
			DESCRIPTION
				"Current status of onu as reported from Gpon driver."
			::= { zhoneGponObjectID 7 }

		
		-- 1.3.6.1.4.1.5504.5.14.1.7.1
		zhoneGponOnuStatusEntry OBJECT-TYPE
			SYNTAX ZhoneGponOnuStatusEntry
			MAX-ACCESS not-accessible
			STATUS current
			DESCRIPTION
				"Row in the zhoneGponOnuStatusTable."
			INDEX { zhoneGponOltOnuIfIndex }
			::= { zhoneGponOnuStatusTable 1 }

		
		ZhoneGponOnuStatusEntry ::=
			SEQUENCE { 
				zhoneGponOnuStatusWord
					BITS,
				zhoneGponOnuOmciState
					INTEGER,
				zhoneGponOnuOpticRssi
					Integer32,
				zhoneGponOntRxPower
					Integer32,
				zhoneGponOntVersion
					OCTET STRING,
				zhoneGponOnuDistance
					Unsigned32
			 }

		-- 1.3.6.1.4.1.5504.5.14.1.7.1.1
		zhoneGponOnuStatusWord OBJECT-TYPE
			SYNTAX BITS
				{
				noAlarm(0),
				inactive(1),
				lossOfSignal(2),
				lossOfFrame(3),
				driftOfWindow(4),
				signalFail(5),
				signalDegrade(6),
				lossOfGemChanDelin(7),
				remoteDefect(8),
				transmitterFailure(9),
				startUpFailure(10),
				lossOfAck(11),
				dyingGasp(12),
				lossOfPloamSync(13),
				messageError(14),
				physEquipError(15),
				bit16notUsed(16),
				bit17notUsed(17),
				excessiveBipErrorsOnuDisabled(18),
				excessiveBipErrorsOnuNotDisabled(19),
				usRxPowerErrorOnuDisabled(20),
				usRxPowerErrorOnuNotDisabled(21),
				rogueOnu(22),
				manualOnuRebooted(23),
				poePowerApplyFailure(24)
				}
			MAX-ACCESS read-only
			STATUS current
			DESCRIPTION
				"Bit-encoded current onu status from gpon driver"
			::= { zhoneGponOnuStatusEntry 1 }

		
		-- 1.3.6.1.4.1.5504.5.14.1.7.1.2
		zhoneGponOnuOmciState OBJECT-TYPE
			SYNTAX INTEGER
				{
				waiting(1),
				pending(2),
				config(3),
				error(4),
				done(5),
				download(6),
				aborted(7),
				unknown(8),
				down(9),
				noConfig(10),
				rgComError(11),
				rgServiceSetupErr(12),
				omciFailed(13),
				omciErrAndRgComErr(14),
				omciErrAndRgServErr(15),
				postCfgError(16),
				omciErrAndPostCfgErr(17)
				}
			MAX-ACCESS read-only
			STATUS current
			DESCRIPTION
				"Current configuration status for ONU.
				1. queued for configuration (waiting)
				2. transitional state before configuration (pending)
				3. in process of configuration (config)
				4. unspecified error (error)
				5. configuration successful (done)
				6. image download in progress (download)
				7. image download aborted (aborted)
				8. state cannot be determined (unknown)
				9. ONU is down (down)
				10. no configuration has been attempted (noConfig)
				11. ONU unreachable for RG configuration (rgComError)
				12. Some RG commands failed, may impact service 
				    (rgServiceSetupErr)
				13. OMCI configuration failed (omciFailed)
				14. OMCI failed and also ONU unreachable for RG 
				    (omciErrAndRgComErr)
				15. OMCI failed and also RG commands failed
				    (omciErrAndRgServErr)
				16. Some post-config commands failed (postCfgError)
				17. OMCI failed and also some post-config commands failed
				    (omciErrAndPostCfgErr)"
			::= { zhoneGponOnuStatusEntry 2 }

		
		-- 1.3.6.1.4.1.5504.5.14.1.7.1.3
		zhoneGponOnuOpticRssi OBJECT-TYPE
			SYNTAX Integer32 (-600..200)
			UNITS "tenths of dB"
			MAX-ACCESS read-only
			STATUS current
			DESCRIPTION
				"RSSI power of the SFP per ONU. The value is in tenths of dB."
			::= { zhoneGponOnuStatusEntry 3 }

		
		-- 1.3.6.1.4.1.5504.5.14.1.7.1.4
		zhoneGponOntRxPower OBJECT-TYPE
			SYNTAX Integer32 (-600..200)
			UNITS "tenths of dB"
			MAX-ACCESS read-only
			STATUS current
			DESCRIPTION
				"Rx Power as reported by the ONT. The value is in tenths of dB."
			::= { zhoneGponOnuStatusEntry 4 }

		
		-- 1.3.6.1.4.1.5504.5.14.1.7.1.5
		zhoneGponOntVersion OBJECT-TYPE
			SYNTAX OCTET STRING (SIZE (0..14))
			MAX-ACCESS read-only
			STATUS current
			DESCRIPTION
				"This object defines the version of the ONT as defined by the vendor.
				The character value '0' indicates that the version information is not
				available or applicable.
				"
			::= { zhoneGponOnuStatusEntry 5 }

		
		-- 1.3.6.1.4.1.5504.5.14.1.7.1.6
		zhoneGponOnuDistance OBJECT-TYPE
			SYNTAX Unsigned32
			MAX-ACCESS read-only
			STATUS current
			DESCRIPTION
				"Distance from Olt to Ont in meters, as 
				computed from Eqd."
			::= { zhoneGponOnuStatusEntry 6 }

		
		-- 1.3.6.1.4.1.5504.5.14.1.8
		zhoneOnuOmciMEProfileTable OBJECT-TYPE
			SYNTAX SEQUENCE OF ZhoneOnuOmciMEProfileEntry
			MAX-ACCESS not-accessible
			STATUS current
			DESCRIPTION
				"Table containing the OMCI commands for the Managed Entities (ME) on an ONU.
				
				The following 'how to' examples demonstrate access of the object
				zhoneOnuOmciMEOmciCommands.
				
				How to create ME profile:
				   1. Determine ME profile instance <aaa>
				   2. Place file <filename> into uplink file system
				   3. Issue single SNMP set command containing the following:
				         zhoneOnuOmciMEProfileRowStatus.aaa = create
				         zhoneOnuOmciMEProfileName.aaa = ME profile name
				         zhoneOnuOmciMEProfileFilename.aaa = <filename>
				
				How to update existing ME profile from a file:
				   1. Determine ME profile instance <aaa>
				   2. Place file <filename> into uplink file system
				   3. Issue single SNMP set command containing the following:
				         zhoneOnuOmciMEProfileRowStatus.aaa = import
				         zhoneOnuOmciMEProfileName.aaa = ME profile name
				         zhoneOnuOmciMEProfileFilename.aaa = <filename>
				
				How to extract ME profile into a file:
				   1. Determine ME profile instance <aaa>
				   2. Issue single SNMP set command containing the following:
				         zhoneOnuOmciMEProfileRowStatus.aaa = export
				         zhoneOnuOmciMEProfileFilename.aaa = <filename>     
				   3. The file <filename> now exists on uplink file system
				
				How to delete ME profile:
				   1. Determine ME profile instance <aaa>
				   2. Issue single SNMP set command containing the following: 
				         zhoneOnuOmciMEProfileRowStatus.aaa = destroy"
			::= { zhoneGponObjectID 8 }

		
		-- 1.3.6.1.4.1.5504.5.14.1.8.1
		zhoneOnuOmciMEProfileEntry OBJECT-TYPE
			SYNTAX ZhoneOnuOmciMEProfileEntry
			MAX-ACCESS not-accessible
			STATUS current
			DESCRIPTION
				"Row in the ME Profile table."
			INDEX { zhoneOnuOmciMEProfileIndex }
			::= { zhoneOnuOmciMEProfileTable 1 }

		
		ZhoneOnuOmciMEProfileEntry ::=
			SEQUENCE { 
				zhoneOnuOmciMEProfileIndex
					Unsigned32,
				zhoneOnuOmciMEProfileRowStatus
					INTEGER,
				zhoneOnuOmciMEProfileName
					OCTET STRING,
				zhoneOnuOmciMEProfileOmciCommands
					OCTET STRING,
				zhoneOnuOmciMEProfileFileName
					OCTET STRING
			 }

		-- 1.3.6.1.4.1.5504.5.14.1.8.1.1
		zhoneOnuOmciMEProfileIndex OBJECT-TYPE
			SYNTAX Unsigned32
			MAX-ACCESS not-accessible
			STATUS current
			DESCRIPTION
				"A unique index for each row entry (1..n)."
			::= { zhoneOnuOmciMEProfileEntry 1 }

		
		-- 1.3.6.1.4.1.5504.5.14.1.8.1.2
		zhoneOnuOmciMEProfileRowStatus OBJECT-TYPE
			SYNTAX INTEGER
				{
				active(1),
				create(2),
				destroy(3),
				export(4),
				import(5),
				append(6),
				revert(7)
				}
			MAX-ACCESS read-create
			STATUS current
			DESCRIPTION
				"Row status for the Me profile entry.  Not really used for the
				configuration on the ONUs"
			::= { zhoneOnuOmciMEProfileEntry 2 }

		
		-- 1.3.6.1.4.1.5504.5.14.1.8.1.3
		zhoneOnuOmciMEProfileName OBJECT-TYPE
			SYNTAX OCTET STRING (SIZE (0..64))
			MAX-ACCESS read-create
			STATUS current
			DESCRIPTION
				"Name given to each row entry in the ME Profile table.
				
				The name must contain ascii printable characters and 
				cannot contain blanks or forward-slash characters.
				
				The name must be null-terminated and the null character
				is included in the object data length.
				
				The name must be unique in the ME profiles."
			::= { zhoneOnuOmciMEProfileEntry 3 }

		
-- 
		-- 1.3.6.1.4.1.5504.5.14.1.8.1.4
		zhoneOnuOmciMEProfileOmciCommands OBJECT-TYPE
			SYNTAX OCTET STRING (SIZE (0..64000))
			MAX-ACCESS read-create
			STATUS current
			DESCRIPTION
				"Contains the set of OMCI commands and the variable substitutions 
				used in configuring the ONUs.
				
				This object will go through some character substitution before being
				inserted into the database so the maximum string size will not
				be available.  Available string size will vary based on string
				contents but expect about 10 percent loss.
				
				This object cannot be accessed directly.  See the comments section for
				zhoneOnuCmciMEProfileTable on how to acces this object."
			::= { zhoneOnuOmciMEProfileEntry 4 }

		
		-- 1.3.6.1.4.1.5504.5.14.1.8.1.5
		zhoneOnuOmciMEProfileFileName OBJECT-TYPE
			SYNTAX OCTET STRING (SIZE (0..64))
			MAX-ACCESS read-create
			STATUS current
			DESCRIPTION
				"Name of file to be loaded into profile.
				
				This object is write-only and is not preserved."
			::= { zhoneOnuOmciMEProfileEntry 5 }

		
		-- 1.3.6.1.4.1.5504.5.14.1.9
		zhoneOnuOmciGenericProfileTable OBJECT-TYPE
			SYNTAX SEQUENCE OF ZhoneOnuOmciGenericProfileEntry
			MAX-ACCESS not-accessible
			STATUS current
			DESCRIPTION
				"Table containing Generic OMCI commands for an ONU.
				
				The Generic profile is 'created' from an existing ME profile.  During this
				operation, the 'variable' defintions from the ME profile are extracted
				from the ME profile and placed into the Generic profile.   
				
				The Generic profile is 'updated' from a file placed into the uplink's file system.
				
				The following 'how to' examples demonstrate access of the object
				zhoneOnuOmciGenericOmciCommands.
				
				How to create Generic profile from ME profile:
				   1. Determine Generic profile instance <aaa>
				   2. Issue single SNMP set command containing the following:
				         zhoneOnuOmciGenericProfileRowStatus.aaa = create
				         zhoneOnuOmciGenericProfileName.aaa = profile name
				         zhoneOnuOmciGenericProfileMESrcProfileName = ME profile source
				   3. Profile is now created and the profile will not contain
				      any variables and values.
				
				How to update existing Generic profile from a file:
				   1. Determine Generic profile instance <aaa>
				   2. Place file <filename> into uplink file system
				   3. Issue single SNMP set command containing the following:
				         zhoneOnuOmciGenericProfileRowStatus.aaa = import
				         zhoneOnuOmciGenericProfileFileName.aaa = <filename>
				
				How to extract Generic profile into a file:
				   1. Determine ME profile instance <aaa>
				   2. Issue single SNMP set command containing the following:
				         zhoneOnuOmciGenericProfileRowStatus.aaa = export
				         zhoneOnuOmciGenericProfileFilename.aaa = <filename>  
				   3. The file <filename> now exists on uplink file system
				
				How to delete Generic profile:
				   1. Determine Generic profile instance <aaa>
				   2. Issue single SNMP set command containing the following: 
				         zhoneOnuOmciGenericProfileRowStatus.aaa = destroy"
			::= { zhoneGponObjectID 9 }

		
		-- 1.3.6.1.4.1.5504.5.14.1.9.1
		zhoneOnuOmciGenericProfileEntry OBJECT-TYPE
			SYNTAX ZhoneOnuOmciGenericProfileEntry
			MAX-ACCESS not-accessible
			STATUS current
			DESCRIPTION
				"Row in the OMCI Generic Profile table"
			INDEX { zhoneOnuOmciGenericProfileIndex }
			::= { zhoneOnuOmciGenericProfileTable 1 }

		
		ZhoneOnuOmciGenericProfileEntry ::=
			SEQUENCE { 
				zhoneOnuOmciGenericProfileIndex
					Unsigned32,
				zhoneOnuOmciGenericProfileRowStatus
					INTEGER,
				zhoneOnuOmciGenericProfileName
					OCTET STRING,
				zhoneOnuOmciGenericProfileOmciCommands
					OCTET STRING,
				zhoneOnuOmciGenericProfileMESrcProfileName
					OCTET STRING,
				zhoneOnuOmciGenericProfileFileName
					OCTET STRING
			 }

		-- 1.3.6.1.4.1.5504.5.14.1.9.1.1
		zhoneOnuOmciGenericProfileIndex OBJECT-TYPE
			SYNTAX Unsigned32
			MAX-ACCESS not-accessible
			STATUS current
			DESCRIPTION
				"A unique index for each row entry ( 1..n )."
			::= { zhoneOnuOmciGenericProfileEntry 1 }

		
		-- 1.3.6.1.4.1.5504.5.14.1.9.1.2
		zhoneOnuOmciGenericProfileRowStatus OBJECT-TYPE
			SYNTAX INTEGER
				{
				active(1),
				create(2),
				destroy(3),
				export(4),
				import(5)
				}
			MAX-ACCESS read-create
			STATUS current
			DESCRIPTION
				"Row status for the Generic profile entry.  Not really used for the
				configuration of the ONUs"
			::= { zhoneOnuOmciGenericProfileEntry 2 }

		
		-- 1.3.6.1.4.1.5504.5.14.1.9.1.3
		zhoneOnuOmciGenericProfileName OBJECT-TYPE
			SYNTAX OCTET STRING (SIZE (0..64))
			MAX-ACCESS read-create
			STATUS current
			DESCRIPTION
				"Name given to each row entry in the Generic Profile table.
				
				The name must contain ascii printable characters and 
				cannot contain blanks or forward-slash characters.
				
				The name must be null-terminated and the null character
				is included in the object data length.
				
				The name must be unique in the Generic profiles."
			::= { zhoneOnuOmciGenericProfileEntry 3 }

		
		-- 1.3.6.1.4.1.5504.5.14.1.9.1.4
		zhoneOnuOmciGenericProfileOmciCommands OBJECT-TYPE
			SYNTAX OCTET STRING (SIZE (0..15000))
			MAX-ACCESS read-create
			STATUS current
			DESCRIPTION
				"Contains the generic set of OMCI commands and the variable substitutions 
				used in configuring the ONUs.
				
				This object will go through some character substitution before being
				inserted into the database so the maximum string size will not
				be available.  Available string size will vary based on string
				contents but expect about 10 percent loss."
			::= { zhoneOnuOmciGenericProfileEntry 4 }

		
		-- 1.3.6.1.4.1.5504.5.14.1.9.1.5
		zhoneOnuOmciGenericProfileMESrcProfileName OBJECT-TYPE
			SYNTAX OCTET STRING (SIZE (0..64))
			MAX-ACCESS read-create
			STATUS current
			DESCRIPTION
				"Name of ME profile used to create the Generic profile.  The value for this
				object is only initialized when the profile is created."
			::= { zhoneOnuOmciGenericProfileEntry 5 }

		
		-- 1.3.6.1.4.1.5504.5.14.1.9.1.6
		zhoneOnuOmciGenericProfileFileName OBJECT-TYPE
			SYNTAX OCTET STRING (SIZE (0..64))
			MAX-ACCESS read-create
			STATUS current
			DESCRIPTION
				"Name of file to be loaded into profile.
				
				This object is write-only and is not preserved."
			::= { zhoneOnuOmciGenericProfileEntry 6 }

		
		-- 1.3.6.1.4.1.5504.5.14.1.10
		zhoneOnuOmciSpecificProfileTable OBJECT-TYPE
			SYNTAX SEQUENCE OF ZhoneOnuOmciSpecificProfileEntry
			MAX-ACCESS not-accessible
			STATUS current
			DESCRIPTION
				"
				Table containing Specific OMCI commands for an ONU.
				
				The Specific profile is 'created' from existing ME and Generic profiles.  
				During this operation, the 'variable' defintions from the ME and Generic 
				profile are extracted from the profiles and placed into the Specific profile.
				The ME and Generic profile names are extracted from the ONU's Olt/Onu config
				profile.   
				
				The Specific profile is 'updated' from a file placed into the uplink's file system.
				
				The following 'how to' examples demonstrate access of the object
				zhoneOnuOmciSpecificOmciCommands.
				
				How to create Specific profile from ME and Generic profiles:
				   1. Determine Specific profile instance <aaa> (from ONU's ifIndex)
				   2. Issue single SNMP set command containing the following:
				         zhoneOnuOmciSpecificProfileRowStatus.aaa = create
				         zhoneOnuOmciSpecificProfileFileName = <filename>
				   3. The profile is now created and the omciCommands contents have
				      been placed into <filename>.  The name of the ME profile 
				      used to create the Speofic profile is installed
				      into zhoneOnuOmciSpecificProfileMESrcProfile.
				
				How to update existing Specific profile from a file:
				   1. Determine Specific profile instance <aaa> (from ONU's ifIndex)
				   2. Place file <filename> into uplink file system
				   3. Issue single SNMP set command containing the following:
				         zhoneOnuOmciGenericProfileRowStatus.aaa = import
				         zhoneOnuOmciGenericProfileFileName.aaa = <filename>
				
				How to extract Specific profile into a file:
				   1. Determine Specific profile instance <aaa> (from ONU's ifIndex)
				   2. Issue single SNMP set command containing the following:
				         zhoneOnuOmciGenericProfileRowStatus.aaa = export
				         zhoneOnuOmciGenericProfileFilename.aaa = <filename>  
				   3. The file <filename> now exists on uplink file system
				
				How to delete Specific profile:
				   1. Determine Specific profile instance <aaa> (from ONU's ifIndex)
				   2. Issue single SNMP set command containing the following: 
				         zhoneOnuOmciGenericProfileRowStatus.aaa = destroy"
			::= { zhoneGponObjectID 10 }

		
		-- 1.3.6.1.4.1.5504.5.14.1.10.1
		zhoneOnuOmciSpecificProfileEntry OBJECT-TYPE
			SYNTAX ZhoneOnuOmciSpecificProfileEntry
			MAX-ACCESS not-accessible
			STATUS current
			DESCRIPTION
				"Row in the OMCI Specific Profile table"
			INDEX { zhoneOnuOmciSpecificProfileIndex }
			::= { zhoneOnuOmciSpecificProfileTable 1 }

		
		ZhoneOnuOmciSpecificProfileEntry ::=
			SEQUENCE { 
				zhoneOnuOmciSpecificProfileIndex
					InterfaceIndex,
				zhoneOnuOmciSpecificProfileRowStatus
					INTEGER,
				zhoneOnuOmciSpecificProfileOmciCommands
					OCTET STRING,
				zhoneOnuOmciSpecificProfileMESrcProfileName
					OCTET STRING,
				zhoneOnuOmciSpecificProfileFileName
					OCTET STRING
			 }

		-- 1.3.6.1.4.1.5504.5.14.1.10.1.1
		zhoneOnuOmciSpecificProfileIndex OBJECT-TYPE
			SYNTAX InterfaceIndex
			MAX-ACCESS not-accessible
			STATUS current
			DESCRIPTION
				"A unique index for each row entry.  The index value
				corresponds to the ifIndex of the ONU which uses this profile."
			::= { zhoneOnuOmciSpecificProfileEntry 1 }

		
		-- 1.3.6.1.4.1.5504.5.14.1.10.1.2
		zhoneOnuOmciSpecificProfileRowStatus OBJECT-TYPE
			SYNTAX INTEGER
				{
				active(1),
				create(2),
				destroy(3),
				export(4),
				import(5)
				}
			MAX-ACCESS read-create
			STATUS current
			DESCRIPTION
				"Row status for the Specific Profile entry.  Not really used for the 
				configuration of the ONUs"
			::= { zhoneOnuOmciSpecificProfileEntry 2 }

		
		-- 1.3.6.1.4.1.5504.5.14.1.10.1.3
		zhoneOnuOmciSpecificProfileOmciCommands OBJECT-TYPE
			SYNTAX OCTET STRING (SIZE (0..8000))
			MAX-ACCESS read-create
			STATUS current
			DESCRIPTION
				"Contains the Specific set of OMCI commands and the variable substitutions 
				used in configuring the ONUs.
				
				This object will go through some character substitution before being
				inserted into the database so the maximum string size will not
				be available.  Available string size will vary based on string
				contents but expect about 10 percent loss."
			::= { zhoneOnuOmciSpecificProfileEntry 3 }

		
		-- 1.3.6.1.4.1.5504.5.14.1.10.1.4
		zhoneOnuOmciSpecificProfileMESrcProfileName OBJECT-TYPE
			SYNTAX OCTET STRING (SIZE (0..64))
			MAX-ACCESS read-create
			STATUS current
			DESCRIPTION
				"Name of ME profile used to create the Specific profile.  The value for this
				object is only initialized when the profile is created."
			::= { zhoneOnuOmciSpecificProfileEntry 4 }

		
		-- 1.3.6.1.4.1.5504.5.14.1.10.1.5
		zhoneOnuOmciSpecificProfileFileName OBJECT-TYPE
			SYNTAX OCTET STRING (SIZE (0..64))
			MAX-ACCESS read-create
			STATUS current
			DESCRIPTION
				"Name of file to be loaded into profile.
				
				This object is write-only and is not preserved."
			::= { zhoneOnuOmciSpecificProfileEntry 5 }

		
		-- 1.3.6.1.4.1.5504.5.14.1.11
		zhoneGponOmciOnuAlarmsTable OBJECT-TYPE
			SYNTAX SEQUENCE OF ZhoneGponOmciOnuAlarmsEntry
			MAX-ACCESS not-accessible
			STATUS current
			DESCRIPTION
				"A table of all GPON OMCI ONU alarms."
			::= { zhoneGponObjectID 11 }

		
		-- 1.3.6.1.4.1.5504.5.14.1.11.1
		zhoneGponOmciOnuAlarmsEntry OBJECT-TYPE
			SYNTAX ZhoneGponOmciOnuAlarmsEntry
			MAX-ACCESS not-accessible
			STATUS current
			DESCRIPTION
				"An entry for each ONU in the zhoneGponOmciOnuAlarmsTable."
			INDEX { zhoneGponOltOnuIfIndex }
			::= { zhoneGponOmciOnuAlarmsTable 1 }

		
		ZhoneGponOmciOnuAlarmsEntry ::=
			SEQUENCE { 
				zhoneGponOmciOnuAlarmsText
					OCTET STRING
			 }

		-- 1.3.6.1.4.1.5504.5.14.1.11.1.1
		zhoneGponOmciOnuAlarmsText OBJECT-TYPE
			SYNTAX OCTET STRING (SIZE (0..16000))
			MAX-ACCESS read-only
			STATUS current
			DESCRIPTION
				"This is a long ascii string which contains the GPON OMCI ONU 
				alarms.    Each line of text in this string has the following    
				format:
				
				    aaa,bbb,ccc,'aaaStr,'bbbStr',d\n
				
				    where aaa    : ME classId ( numeric decimal value )
				          bbb    : alarm index ( numeric decimal value )
				          ccc    : entityId ( numeric decimal value )
				          aaaStr : string version of ME name
				          bbbStr : string version of alarm name
				          d      : alarm severity ( 1=critical,  2=major, 3=minor, 4=warning )
				
				The ME classId is the standard value from the 'Managed entity identifiers' 
				table of G984.4.
				The alarm index is the zero-based index (G984.4 or G983.2)
				within the ME class.
				the entityId is the physical port number on the ONT.
				
				Here is a sample:
				
				    11,0,513,'PptpEthUni','LanLos',2\n
				    256,1,0,'OntG','PoweringAlarm',3\n
				
				If this string has zero length then there are no
				active alarms.
				
				If this string has a single entry with a classId of
				65535 then the alarm collection failed.
				
				WARNING! In this description, replace the sinqle quote
				characters with double quote characters!  The Zhone
				scripts have problems with double quote characters!"
			::= { zhoneGponOmciOnuAlarmsEntry 1 }

		
		-- 1.3.6.1.4.1.5504.5.14.1.12
		zhoneGponTrafficProfileTable OBJECT-TYPE
			SYNTAX SEQUENCE OF ZhoneGponTrafficProfileEntry
			MAX-ACCESS not-accessible
			STATUS current
			DESCRIPTION
				"A table of the GPON GEM Port Traffic profiles."
			::= { zhoneGponObjectID 12 }

		
		-- 1.3.6.1.4.1.5504.5.14.1.12.1
		zhoneGponTrafficProfileEntry OBJECT-TYPE
			SYNTAX ZhoneGponTrafficProfileEntry
			MAX-ACCESS not-accessible
			STATUS current
			DESCRIPTION
				"Row in the zhoneGponPortTrafProfileTable."
			INDEX { zhoneGponTrafficProfileIndex }
			::= { zhoneGponTrafficProfileTable 1 }

		
		ZhoneGponTrafficProfileEntry ::=
			SEQUENCE { 
				zhoneGponTrafficProfileIndex
					Unsigned32,
				zhoneGponTrafficProfileRowStatus
					ZhoneRowStatus,
				zhoneGponTrafficProfileGuaranteedUpstreamBw
					Integer32,
				zhoneGponTrafficProfileClass
					INTEGER,
				zhoneGponTrafficProfileCompensated
					TruthValue,
				zhoneGponTrafficProfileShared
					TruthValue,
				zhoneGponTrafficProfileDbaEnabled
					TruthValue,
				zhoneGponTrafficProfileDbaFixedUsUbrBw
					Unsigned32,
				zhoneGponTrafficProfileDbaFixedUsCbrBw
					Unsigned32,
				zhoneGponTrafficProfileDbaAssuredUsBw
					Unsigned32,
				zhoneGponTrafficProfileMaxUsBw
					Unsigned32,
				zhoneGponTrafficProfileExtraUsBwType
					INTEGER
			 }

		-- 1.3.6.1.4.1.5504.5.14.1.12.1.1
		zhoneGponTrafficProfileIndex OBJECT-TYPE
			SYNTAX Unsigned32
			MAX-ACCESS not-accessible
			STATUS current
			DESCRIPTION
				"Used to index an entry in the GEM port traffic profile table"
			::= { zhoneGponTrafficProfileEntry 1 }

		
		-- 1.3.6.1.4.1.5504.5.14.1.12.1.2
		zhoneGponTrafficProfileRowStatus OBJECT-TYPE
			SYNTAX ZhoneRowStatus
			MAX-ACCESS read-create
			STATUS current
			DESCRIPTION
				"The row status for the GEM Port Traffic profile. "
			::= { zhoneGponTrafficProfileEntry 2 }

		
		-- 1.3.6.1.4.1.5504.5.14.1.12.1.3
		zhoneGponTrafficProfileGuaranteedUpstreamBw OBJECT-TYPE
			SYNTAX Integer32 (0..1048576)
			UNITS "kilobits"
			MAX-ACCESS read-create
			STATUS current
			DESCRIPTION
				"Bandwidth guaranteed by this alloc-id. 
				This value is specified in kilobits per second. Only
				multiples of 512 are allowed, and the value may not
				exceed 2621440 (i.e. 2.5 gigabits per second).
				"
			DEFVAL { 0 }
			::= { zhoneGponTrafficProfileEntry 3 }

		
		-- 1.3.6.1.4.1.5504.5.14.1.12.1.4
		zhoneGponTrafficProfileClass OBJECT-TYPE
			SYNTAX INTEGER
				{
				cbr(1),
				ubr(2)
				}
			MAX-ACCESS read-create
			STATUS current
			DESCRIPTION
				"Whether traffic is Constant Bit Rate or Unspecified Bit Rate."
			DEFVAL { ubr }
			::= { zhoneGponTrafficProfileEntry 4 }

		
		-- 1.3.6.1.4.1.5504.5.14.1.12.1.5
		zhoneGponTrafficProfileCompensated OBJECT-TYPE
			SYNTAX TruthValue
			MAX-ACCESS read-create
			STATUS current
			DESCRIPTION
				"For CBR, indicates whether compensated."
			DEFVAL { false }
			::= { zhoneGponTrafficProfileEntry 5 }

		
		-- 1.3.6.1.4.1.5504.5.14.1.12.1.6
		zhoneGponTrafficProfileShared OBJECT-TYPE
			SYNTAX TruthValue
			MAX-ACCESS read-create
			STATUS current
			DESCRIPTION
				"TRUE if the GEM Port which uses this traffic descriptor shares and
				allocation ID with another GEM port.   FALSE otherwise.
				
				When used more than once in the same ONU, the GEM ports
				are assigned the same alloc-id value."
			DEFVAL { false }
			::= { zhoneGponTrafficProfileEntry 6 }

		
		-- 1.3.6.1.4.1.5504.5.14.1.12.1.7
		zhoneGponTrafficProfileDbaEnabled OBJECT-TYPE
			SYNTAX TruthValue
			MAX-ACCESS read-create
			STATUS current
			DESCRIPTION
				"A flag to indicate if dynamic or static bandwidth allocation is used.
				The default value of DbaEnabled is false."
			DEFVAL { false }
			::= { zhoneGponTrafficProfileEntry 7 }

		
		-- 1.3.6.1.4.1.5504.5.14.1.12.1.8
		zhoneGponTrafficProfileDbaFixedUsUbrBw OBJECT-TYPE
			SYNTAX Unsigned32 (0..1048576)
			UNITS "kilobits"
			MAX-ACCESS read-create
			STATUS current
			DESCRIPTION
				"Fixed UBR bandwidth will be always allocated UBR bandwidth. The min values
				of Fixed Ubr bandwidth can be 0 or 128kilo bits per second.Only multiples
				of 64 kilobits per second are allowed.
				"
			DEFVAL { 0 }
			::= { zhoneGponTrafficProfileEntry 8 }

		
		-- 1.3.6.1.4.1.5504.5.14.1.12.1.9
		zhoneGponTrafficProfileDbaFixedUsCbrBw OBJECT-TYPE
			SYNTAX Unsigned32 (0..454208)
			UNITS "kilobits"
			MAX-ACCESS read-create
			STATUS current
			DESCRIPTION
				"Fixed CBR bandwidth will be always allocated CBR bandwidth. The min value
				of Fixed Cbr bandwidth can be 0 or 512 kilobits per second.Only multiples
				of 64 kilo bits per second are allowed."
			DEFVAL { 0 }
			::= { zhoneGponTrafficProfileEntry 9 }

		
		-- 1.3.6.1.4.1.5504.5.14.1.12.1.10
		zhoneGponTrafficProfileDbaAssuredUsBw OBJECT-TYPE
			SYNTAX Unsigned32 (0..1048576)
			UNITS "kilobits"
			MAX-ACCESS read-create
			STATUS current
			DESCRIPTION
				"DBA Assured bandwidth will be allocated when traffic demand exists. The
				min value of Assured bandwidth can be 0 or 256 kilobits per second. Only
				multiples of 64 kilo bits per second are allowed.
				"
			DEFVAL { 0 }
			::= { zhoneGponTrafficProfileEntry 10 }

		
		-- 1.3.6.1.4.1.5504.5.14.1.12.1.11
		zhoneGponTrafficProfileMaxUsBw OBJECT-TYPE
			SYNTAX Unsigned32 (0..1048576)
			UNITS "kilobits"
			MAX-ACCESS read-create
			STATUS current
			DESCRIPTION
				"The Max Bandwidth value should be larger or equal to the sum of Fixed UBR,
				Fixed CBR and Assured.The increments should be done in the order of
				64 kilobits per second.The default value of maximum bandwidth is 0."
			DEFVAL { 0 }
			::= { zhoneGponTrafficProfileEntry 11 }

		
		-- 1.3.6.1.4.1.5504.5.14.1.12.1.12
		zhoneGponTrafficProfileExtraUsBwType OBJECT-TYPE
			SYNTAX INTEGER
				{
				nonassured(1),
				besteffort(2)
				}
			MAX-ACCESS read-create
			STATUS current
			DESCRIPTION
				"Extra Bandwidth = MaxBw - (Assured+FixedUbr+FixedCbr)
				 
				The two Extra bandwidth types supported are :
				
				1.nonassured
				2.besteffort
				
				By default the value is nonassured.Nonassured has higher priority for
				getting unused bandwidth than besteffort.
				"
			DEFVAL { nonassured }
			::= { zhoneGponTrafficProfileEntry 12 }

		
		-- 1.3.6.1.4.1.5504.5.14.1.13
		zhoneGponPortStatusTable OBJECT-TYPE
			SYNTAX SEQUENCE OF ZhoneGponPortStatusEntry
			MAX-ACCESS not-accessible
			STATUS current
			DESCRIPTION
				"Current status of GEM port as reported from Gpon driver."
			::= { zhoneGponObjectID 13 }

		
		-- 1.3.6.1.4.1.5504.5.14.1.13.1
		zhoneGponPortStatusEntry OBJECT-TYPE
			SYNTAX ZhoneGponPortStatusEntry
			MAX-ACCESS not-accessible
			STATUS current
			DESCRIPTION
				"Row in the zhoneGponPortStatusTable."
			INDEX { zhoneGponOltOnuIfIndex }
			::= { zhoneGponPortStatusTable 1 }

		
		ZhoneGponPortStatusEntry ::=
			SEQUENCE { 
				zhoneGponPortStatusAllocId
					Unsigned32,
				zhoneGponPortStatusDbaStatus
					INTEGER
			 }

		-- 1.3.6.1.4.1.5504.5.14.1.13.1.1
		zhoneGponPortStatusAllocId OBJECT-TYPE
			SYNTAX Unsigned32
			MAX-ACCESS read-only
			STATUS current
			DESCRIPTION
				"The current dynamic alloc-id value for the GEM port."
			DEFVAL { 0 }
			::= { zhoneGponPortStatusEntry 1 }

		
		-- 1.3.6.1.4.1.5504.5.14.1.13.1.2
		zhoneGponPortStatusDbaStatus OBJECT-TYPE
			SYNTAX INTEGER
				{
				sr(1),
				nsr(2),
				nsrError(3),
				notEnabled(4),
				notAvailable(5),
				notAdded(6),
				error(7)
				}
			MAX-ACCESS read-only
			STATUS current
			DESCRIPTION
				"The current DBA status for this GEM port.  
				 
				DBA status reporting is on a per-ONU basis.  All GEM ports
				on the ONU will report the same value.
				 
				Possible values:
				   sr           - DBA type is SR and there is no error
				   nsr          - DBA type is NSR and there is no error
				   nsrError     - DBA type is NSR and there is an error
				                  or the ONU does not support NSR
				   notEnabled   - DBA has been disabled
				   notAvailable - cannot communicate with ONU
				   notAdded     - ONU is not added to the OLT
				   error        - internal error prevents data collection
				   "
			::= { zhoneGponPortStatusEntry 2 }

		
		-- 1.3.6.1.4.1.5504.5.14.1.14
		zhoneGponOmciStatsCurrentTable OBJECT-TYPE
			SYNTAX SEQUENCE OF ZhoneGponOmciStatsCurrentEntry
			MAX-ACCESS not-accessible
			STATUS current
			DESCRIPTION
				"Table of current-interval statistics gathered via 
				OMCI from ONT's as specified in the ME profiles used 
				by that ONT."
			::= { zhoneGponObjectID 14 }

		
		-- 1.3.6.1.4.1.5504.5.14.1.14.1
		zhoneGponOmciStatsCurrentEntry OBJECT-TYPE
			SYNTAX ZhoneGponOmciStatsCurrentEntry
			MAX-ACCESS not-accessible
			STATUS current
			DESCRIPTION
				"Row in zhoneGponOmciStatsCurrentTable.
				Each row retrieves counters for the current 15-minute 
				interval for one managed entity on one logical port of
				one ONT."
			INDEX { zhoneGponOltOnuIfIndex, zhoneGponOmciStatsCurrentMEId, zhoneGponOmciStatsCurrentLogicalPort }
			::= { zhoneGponOmciStatsCurrentTable 1 }

		
		ZhoneGponOmciStatsCurrentEntry ::=
			SEQUENCE { 
				zhoneGponOmciStatsCurrentMEId
					Unsigned32,
				zhoneGponOmciStatsCurrentLogicalPort
					Unsigned32,
				zhoneGponOmciStatsCurrentText
					OCTET STRING
			 }

		-- 1.3.6.1.4.1.5504.5.14.1.14.1.1
		zhoneGponOmciStatsCurrentMEId OBJECT-TYPE
			SYNTAX Unsigned32
			MAX-ACCESS not-accessible
			STATUS current
			DESCRIPTION
				"This is the ID of the managed entity in the ITU G984.4 
				standard for the OMCI statistics we want to read."
			::= { zhoneGponOmciStatsCurrentEntry 1 }

		
		-- 1.3.6.1.4.1.5504.5.14.1.14.1.2
		zhoneGponOmciStatsCurrentLogicalPort OBJECT-TYPE
			SYNTAX Unsigned32
			MAX-ACCESS not-accessible
			STATUS current
			DESCRIPTION
				"This specifies which entity on the ONT we want the statistics for.
				This is a logical number (1,2,...) which is translated according to the
				ME profile into an entity ID which is included in the command to the ONT."
			::= { zhoneGponOmciStatsCurrentEntry 2 }

		
		-- 1.3.6.1.4.1.5504.5.14.1.14.1.3
		zhoneGponOmciStatsCurrentText OBJECT-TYPE
			SYNTAX OCTET STRING (SIZE (0..256))
			MAX-ACCESS read-only
			STATUS current
			DESCRIPTION
				"Blob of statistics information returned. Format is:
				 
				  PhysPort,I1,A1,I2,A2,...In,An
				
				  where
				
				     PhysPort - physical port ID value
				
				     Ii = attribute index (0-15, ascii-coded decimal integer) 
				          within ME according to G984,4 standard.
				     Ai = attribute value (counter, ascii-coded decimal integer)
				
				     n = number of attributes returned = number requested.
				          Maximum number of attributes per ME is 16."
			::= { zhoneGponOmciStatsCurrentEntry 3 }

		
		-- 1.3.6.1.4.1.5504.5.14.1.15
		zhoneGponOmciStatsPreviousTable OBJECT-TYPE
			SYNTAX SEQUENCE OF ZhoneGponOmciStatsPreviousEntry
			MAX-ACCESS not-accessible
			STATUS current
			DESCRIPTION
				"Table of previous-interval statistics gathered via 
				OMCI from ONT's as specified in the ME profiles used 
				by that ONT."
			::= { zhoneGponObjectID 15 }

		
		-- 1.3.6.1.4.1.5504.5.14.1.15.1
		zhoneGponOmciStatsPreviousEntry OBJECT-TYPE
			SYNTAX ZhoneGponOmciStatsPreviousEntry
			MAX-ACCESS not-accessible
			STATUS current
			DESCRIPTION
				"Row in zhoneGponOmciStatsPreviousTable.
				Each row retrieves counters for the last completed 
				15-minute interval for one managed entity on one logical 
				port of one ONT."
			INDEX { zhoneGponOltOnuIfIndex, zhoneGponOmciStatsPreviousMEId, zhoneGponOmciStatsPreviousLogicalPort }
			::= { zhoneGponOmciStatsPreviousTable 1 }

		
		ZhoneGponOmciStatsPreviousEntry ::=
			SEQUENCE { 
				zhoneGponOmciStatsPreviousMEId
					Unsigned32,
				zhoneGponOmciStatsPreviousLogicalPort
					Unsigned32,
				zhoneGponOmciStatsPreviousText
					OCTET STRING
			 }

		-- 1.3.6.1.4.1.5504.5.14.1.15.1.1
		zhoneGponOmciStatsPreviousMEId OBJECT-TYPE
			SYNTAX Unsigned32
			MAX-ACCESS not-accessible
			STATUS current
			DESCRIPTION
				"This is the ID of the managed entity in the ITU G984.4 
				standard for the OMCI statistics we want to read."
			::= { zhoneGponOmciStatsPreviousEntry 1 }

		
		-- 1.3.6.1.4.1.5504.5.14.1.15.1.2
		zhoneGponOmciStatsPreviousLogicalPort OBJECT-TYPE
			SYNTAX Unsigned32
			MAX-ACCESS not-accessible
			STATUS current
			DESCRIPTION
				"This specifies which entity on the ONT we want the statistics for.
				This is a logical number (1,2,...) which is translated according to the
				ME profile into an entity ID which is included in the command to the ONT."
			::= { zhoneGponOmciStatsPreviousEntry 2 }

		
		-- 1.3.6.1.4.1.5504.5.14.1.15.1.3
		zhoneGponOmciStatsPreviousText OBJECT-TYPE
			SYNTAX OCTET STRING (SIZE (0..256))
			MAX-ACCESS read-only
			STATUS current
			DESCRIPTION
				"Blob of statistics information returned. Format is:
				 
				  PhysPort,I1,A1,I2,A2,...In,An
				
				  where
				
				     PhysPort - physical port ID value
				
				     Ii = attribute index (0-15, ascii-coded decimal integer) 
				          within ME according to G984,4 standard.
				     Ai = attribute value (counter, ascii-coded decimal integer)
				
				     n = number of attributes returned = number requested.
				          Maximum number of attributes per ME is 16.
				
				"
			::= { zhoneGponOmciStatsPreviousEntry 3 }

		
		-- 1.3.6.1.4.1.5504.5.14.1.16
		zhoneGponOmciStatusTable OBJECT-TYPE
			SYNTAX SEQUENCE OF ZhoneGponOmciStatusEntry
			MAX-ACCESS not-accessible
			STATUS current
			DESCRIPTION
				"Table of current-interval statistics gathered via 
				OMCI from ONT's as specified in the ME profiles used 
				by that ONT."
			::= { zhoneGponObjectID 16 }

		
		-- 1.3.6.1.4.1.5504.5.14.1.16.1
		zhoneGponOmciStatusEntry OBJECT-TYPE
			SYNTAX ZhoneGponOmciStatusEntry
			MAX-ACCESS not-accessible
			STATUS current
			DESCRIPTION
				"Row in zhoneGponOmciStatsCurrentTable.
				Each row retrieves counters for the current 15-minute 
				interval for one managed entity on one logical port of
				one ONT."
			INDEX { zhoneGponOltOnuIfIndex, zhoneGponOmciStatusMEId, zhoneGponOmciStatusLogicalPort }
			::= { zhoneGponOmciStatusTable 1 }

		
		ZhoneGponOmciStatusEntry ::=
			SEQUENCE { 
				zhoneGponOmciStatusMEId
					Unsigned32,
				zhoneGponOmciStatusLogicalPort
					Unsigned32,
				zhoneGponOmciStatusText
					OCTET STRING
			 }

		-- 1.3.6.1.4.1.5504.5.14.1.16.1.1
		zhoneGponOmciStatusMEId OBJECT-TYPE
			SYNTAX Unsigned32
			MAX-ACCESS not-accessible
			STATUS current
			DESCRIPTION
				"This is the ID of the managed entity in the ITU G984.4 
				standard for the OMCI statistics we want to read."
			::= { zhoneGponOmciStatusEntry 1 }

		
		-- 1.3.6.1.4.1.5504.5.14.1.16.1.2
		zhoneGponOmciStatusLogicalPort OBJECT-TYPE
			SYNTAX Unsigned32
			MAX-ACCESS not-accessible
			STATUS current
			DESCRIPTION
				"This specifies which entity on the ONT we want the statistics for.
				This is a logical number (1,2,...) which is translated according to the
				ME profile into an entity ID which is included in the command to the ONT."
			::= { zhoneGponOmciStatusEntry 2 }

		
		-- 1.3.6.1.4.1.5504.5.14.1.16.1.3
		zhoneGponOmciStatusText OBJECT-TYPE
			SYNTAX OCTET STRING (SIZE (0..512))
			MAX-ACCESS read-only
			STATUS current
			DESCRIPTION
				"Blob of status information returned. Format is:
				 
				  PhysPort,attrId1,attrName1,attrNumValue1,attrStrValue1...
				  attrIdn,attrNamen,attrNumValuen,attrStrValuen
				
				  where
				
				     PhysPort - physical port ID value
				
				     attrIdn = index number (0-15) of the attribute within
				               the the ME (ascii decimal) 
				
				     attrNamen = name of the attribute (returned by OCS)
				
				     attrNumValuen = value of the attribute (ascii decimal)
				
				     attrStrValuen = interpreted value ( 'up', 'down', etc )
				
				     n = number of attributes returned = number requested.
				          Maximum number of attributes per ME is 16."
			::= { zhoneGponOmciStatusEntry 3 }

		
		-- 1.3.6.1.4.1.5504.5.14.1.17
		zhoneGponOmciOnuRebootTable OBJECT-TYPE
			SYNTAX SEQUENCE OF ZhoneGponOmciOnuRebootEntry
			MAX-ACCESS not-accessible
			STATUS current
			DESCRIPTION
				"Table of objects used to reboot an ONU via the OMCI."
			::= { zhoneGponObjectID 17 }

		
		-- 1.3.6.1.4.1.5504.5.14.1.17.1
		zhoneGponOmciOnuRebootEntry OBJECT-TYPE
			SYNTAX ZhoneGponOmciOnuRebootEntry
			MAX-ACCESS not-accessible
			STATUS current
			DESCRIPTION
				"A single entry in the table"
			INDEX { zhoneGponOltOnuIfIndex }
			::= { zhoneGponOmciOnuRebootTable 1 }

		
		ZhoneGponOmciOnuRebootEntry ::=
			SEQUENCE { 
				zhoneGponOmciOnuReboot
					INTEGER
			 }

		-- 1.3.6.1.4.1.5504.5.14.1.17.1.1
		zhoneGponOmciOnuReboot OBJECT-TYPE
			SYNTAX INTEGER
				{
				none(0),
				reboot(1)
				}
			MAX-ACCESS read-create
			STATUS current
			DESCRIPTION
				"Set this object to 'reboot to reboot an ONU.  The reboot 
				command is sent to the ONU over the OMCI.
				
				Successful transmission of the reboot command to the
				ONU does no guarantee the ONU will reboot.  The ONU may 
				be in a fatal lockup which prevents the processing of 
				the reboot command.
				"
			DEFVAL { none }
			::= { zhoneGponOmciOnuRebootEntry 1 }

		
		-- 1.3.6.1.4.1.5504.5.14.1.18
		zhoneGponOmciOnuPortAdminTable OBJECT-TYPE
			SYNTAX SEQUENCE OF ZhoneGponOmciOnuPortAdminEntry
			MAX-ACCESS not-accessible
			STATUS current
			DESCRIPTION
				"Table of objects used to configure the admin state
				of a physical port on an ONU."
			::= { zhoneGponObjectID 18 }

		
		-- 1.3.6.1.4.1.5504.5.14.1.18.1
		zhoneGponOmciOnuPortAdminEntry OBJECT-TYPE
			SYNTAX ZhoneGponOmciOnuPortAdminEntry
			MAX-ACCESS not-accessible
			STATUS current
			DESCRIPTION
				"A single entry in the table"
			INDEX { zhoneGponOltOnuIfIndex, zhoneGponOmciOnuPortAdminMEId, zhoneGponOmciOnuPortAdminLogicalPort }
			::= { zhoneGponOmciOnuPortAdminTable 1 }

		
		ZhoneGponOmciOnuPortAdminEntry ::=
			SEQUENCE { 
				zhoneGponOmciOnuPortAdminMEId
					Unsigned32,
				zhoneGponOmciOnuPortAdminLogicalPort
					Unsigned32,
				zhoneGponOmciOnuPortAdminState
					INTEGER,
				zhoneGponOmciOnuPortAdminAutoDetect
					INTEGER
			 }

		-- 1.3.6.1.4.1.5504.5.14.1.18.1.1
		zhoneGponOmciOnuPortAdminMEId OBJECT-TYPE
			SYNTAX Unsigned32
			MAX-ACCESS not-accessible
			STATUS current
			DESCRIPTION
				"This is the ID of the managed entity in the ITU G984.4 
				standard."
			::= { zhoneGponOmciOnuPortAdminEntry 1 }

		
		-- 1.3.6.1.4.1.5504.5.14.1.18.1.2
		zhoneGponOmciOnuPortAdminLogicalPort OBJECT-TYPE
			SYNTAX Unsigned32
			MAX-ACCESS not-accessible
			STATUS current
			DESCRIPTION
				"This specifies which entity on the ONT we want.  This is a logical 
				number (1,2,...) which is translated according to the ME profile 
				into an entity ID which is included in the command to the ONT."
			::= { zhoneGponOmciOnuPortAdminEntry 2 }

		
		-- 1.3.6.1.4.1.5504.5.14.1.18.1.3
		zhoneGponOmciOnuPortAdminState OBJECT-TYPE
			SYNTAX INTEGER
				{
				none(0),
				up(1),
				down(2)
				}
			MAX-ACCESS read-create
			STATUS current
			DESCRIPTION
				"This object is used to place an ONU physical port in a
				DOWN or UP state.  This state is a configuration parameter
				and is preserved."
			DEFVAL { none }
			::= { zhoneGponOmciOnuPortAdminEntry 3 }

		
		-- 1.3.6.1.4.1.5504.5.14.1.18.1.4
		zhoneGponOmciOnuPortAdminAutoDetect OBJECT-TYPE
			SYNTAX INTEGER
				{
				none(0),
				auto(1),
				tenFull(2),
				hundredFull(3),
				thousandFull(4),
				tenAuto(5),
				tenHalf(6),
				hundredHalf(7),
				thousandHalf(8),
				thousandAuto(9),
				autoFull(10),
				autoHalf(11),
				hundredAuto(12)
				}
			MAX-ACCESS read-create
			STATUS current
			DESCRIPTION
				"This object is used to set the auto detection rate of an ONU
				physical port.This state is a configuration parameter and
				is preserved."
			DEFVAL { auto }
			::= { zhoneGponOmciOnuPortAdminEntry 4 }

		
		-- 1.3.6.1.4.1.5504.5.14.1.19
		zhoneGponOmciOnuImageUpgradeTable OBJECT-TYPE
			SYNTAX SEQUENCE OF ZhoneGponOmciOnuImageUpgradeEntry
			MAX-ACCESS not-accessible
			STATUS current
			DESCRIPTION
				"This table is used to perform ONU software upgrades.
				There is one table entry for each ONU.
				Each ONU is addressed by it's ifIndex."
			::= { zhoneGponObjectID 19 }

		
		-- 1.3.6.1.4.1.5504.5.14.1.19.1
		zhoneGponOmciOnuImageUpgradeEntry OBJECT-TYPE
			SYNTAX ZhoneGponOmciOnuImageUpgradeEntry
			MAX-ACCESS not-accessible
			STATUS current
			DESCRIPTION
				"An entry for one ONU."
			INDEX { zhoneGponOltOnuIfIndex }
			::= { zhoneGponOmciOnuImageUpgradeTable 1 }

		
		ZhoneGponOmciOnuImageUpgradeEntry ::=
			SEQUENCE { 
				zhoneGponOmciOnuImageUpgradeAction
					INTEGER,
				zhoneOnuOmciImageUpgradeFilename
					OCTET STRING,
				zhoneGponOmciOnuImageUpgradePartition
					INTEGER,
				zhoneOnuOmciImageUpgradeImageVersionPartition0
					OCTET STRING,
				zhoneOnuOmciImageUpgradeImageVersionPartition1
					OCTET STRING,
				zhoneOnuOmciImageUpgradeIsCommittedPartition0
					INTEGER,
				zhoneOnuOmciImageUpgradeIsCommittedPartition1
					INTEGER,
				zhoneOnuOmciImageUpgradeIsActivatedPartition0
					INTEGER,
				zhoneOnuOmciImageUpgradeIsActivatedPartition1
					INTEGER,
				zhoneOnuOmciImageUpgradeIsValidPartition0
					INTEGER,
				zhoneOnuOmciImageUpgradeIsValidPartition1
					INTEGER,
				zhoneOnuOmciImageUpgradeDownloadStatus
					OnuUpgradeState,
				zhoneGponOmciOnuImageUpgradeModel
					OCTET STRING,
				zhoneGponOmciOnuImageUpgradeStartTime
					OCTET STRING,
				zhoneGponOmciOnuImageUpgradeWillBeActivated
					TruthValue,
				zhoneGponOmciOnuImageUpgradeWillBeCommitted
					TruthValue,
				zhoneGponOmciOnuImageUpgradeType
					INTEGER,
				zhoneGponOmciOnuImageDownloadProgressPercentage
					INTEGER,
				zhoneGponOmciOnuImageUpgradeMethod
					INTEGER
			 }

		-- 1.3.6.1.4.1.5504.5.14.1.19.1.1
		zhoneGponOmciOnuImageUpgradeAction OBJECT-TYPE
			SYNTAX INTEGER
				{
				none(0),
				download(1),
				activate(2),
				commit(3),
				downloadActivate(4),
				downloadActivateCommit(5),
				abortDownload(6),
				activateCommit(7)
				}
			MAX-ACCESS read-create
			STATUS current
			DESCRIPTION
				"Which software upgrade action to perform."
			DEFVAL { none }
			::= { zhoneGponOmciOnuImageUpgradeEntry 1 }

		
		-- 1.3.6.1.4.1.5504.5.14.1.19.1.2
		zhoneOnuOmciImageUpgradeFilename OBJECT-TYPE
			SYNTAX OCTET STRING (SIZE (0..64))
			MAX-ACCESS read-create
			STATUS current
			DESCRIPTION
				"Name of file to be loaded downloaded to ONU.
				Required on download actions."
			::= { zhoneGponOmciOnuImageUpgradeEntry 2 }

		
		-- 1.3.6.1.4.1.5504.5.14.1.19.1.3
		zhoneGponOmciOnuImageUpgradePartition OBJECT-TYPE
			SYNTAX INTEGER
				{
				none(0),
				partitionNumber0(1),
				partitionNumber1(2)
				}
			MAX-ACCESS read-create
			STATUS current
			DESCRIPTION
				"Optional on all actions.  Indicates which partition or 
				'none'in which case default is to use inactive partition
				for download or activate action, or to the uncommitted 
				partion for commit action.
				On a read, returns the partition used for current or 
				latest upgrade."
			DEFVAL { none }
			::= { zhoneGponOmciOnuImageUpgradeEntry 3 }

		
		-- 1.3.6.1.4.1.5504.5.14.1.19.1.4
		zhoneOnuOmciImageUpgradeImageVersionPartition0 OBJECT-TYPE
			SYNTAX OCTET STRING (SIZE (0..64))
			MAX-ACCESS read-only
			STATUS current
			DESCRIPTION
				"Version information for s/w image loaded into partition 0."
			::= { zhoneGponOmciOnuImageUpgradeEntry 4 }

		
		-- 1.3.6.1.4.1.5504.5.14.1.19.1.5
		zhoneOnuOmciImageUpgradeImageVersionPartition1 OBJECT-TYPE
			SYNTAX OCTET STRING (SIZE (0..64))
			MAX-ACCESS read-only
			STATUS current
			DESCRIPTION
				"Version information for s/w image loaded into partition 1."
			::= { zhoneGponOmciOnuImageUpgradeEntry 5 }

		
		-- 1.3.6.1.4.1.5504.5.14.1.19.1.6
		zhoneOnuOmciImageUpgradeIsCommittedPartition0 OBJECT-TYPE
			SYNTAX INTEGER
				{
				none(0),
				true(1),
				false(2)
				}
			MAX-ACCESS read-only
			STATUS current
			DESCRIPTION
				"Current commit status for partition 0."
			::= { zhoneGponOmciOnuImageUpgradeEntry 6 }

		
		-- 1.3.6.1.4.1.5504.5.14.1.19.1.7
		zhoneOnuOmciImageUpgradeIsCommittedPartition1 OBJECT-TYPE
			SYNTAX INTEGER
				{
				none(0),
				true(1),
				false(2)
				}
			MAX-ACCESS read-only
			STATUS current
			DESCRIPTION
				"Current commit status for partition 1."
			::= { zhoneGponOmciOnuImageUpgradeEntry 7 }

		
		-- 1.3.6.1.4.1.5504.5.14.1.19.1.8
		zhoneOnuOmciImageUpgradeIsActivatedPartition0 OBJECT-TYPE
			SYNTAX INTEGER
				{
				none(0),
				true(1),
				false(2)
				}
			MAX-ACCESS read-only
			STATUS current
			DESCRIPTION
				"Current activated status for partition 0."
			::= { zhoneGponOmciOnuImageUpgradeEntry 8 }

		
		-- 1.3.6.1.4.1.5504.5.14.1.19.1.9
		zhoneOnuOmciImageUpgradeIsActivatedPartition1 OBJECT-TYPE
			SYNTAX INTEGER
				{
				none(0),
				true(1),
				false(2)
				}
			MAX-ACCESS read-only
			STATUS current
			DESCRIPTION
				"Current activated status for partition 1."
			::= { zhoneGponOmciOnuImageUpgradeEntry 9 }

		
		-- 1.3.6.1.4.1.5504.5.14.1.19.1.10
		zhoneOnuOmciImageUpgradeIsValidPartition0 OBJECT-TYPE
			SYNTAX INTEGER
				{
				none(0),
				true(1),
				false(2)
				}
			MAX-ACCESS read-only
			STATUS current
			DESCRIPTION
				"Current valid status for partition 0."
			::= { zhoneGponOmciOnuImageUpgradeEntry 10 }

		
		-- 1.3.6.1.4.1.5504.5.14.1.19.1.11
		zhoneOnuOmciImageUpgradeIsValidPartition1 OBJECT-TYPE
			SYNTAX INTEGER
				{
				none(0),
				true(1),
				false(2)
				}
			MAX-ACCESS read-only
			STATUS current
			DESCRIPTION
				"Current valid status for partition 0."
			::= { zhoneGponOmciOnuImageUpgradeEntry 11 }

		
		-- 1.3.6.1.4.1.5504.5.14.1.19.1.12
		zhoneOnuOmciImageUpgradeDownloadStatus OBJECT-TYPE
			SYNTAX OnuUpgradeState
			MAX-ACCESS read-only
			STATUS current
			DESCRIPTION
				"Current s/w image download status."
			::= { zhoneGponOmciOnuImageUpgradeEntry 12 }

		
		-- 1.3.6.1.4.1.5504.5.14.1.19.1.13
		zhoneGponOmciOnuImageUpgradeModel OBJECT-TYPE
			SYNTAX OCTET STRING (SIZE (0..20))
			MAX-ACCESS read-only
			STATUS current
			DESCRIPTION
				"Model id read from this onu."
			::= { zhoneGponOmciOnuImageUpgradeEntry 13 }

		
		-- 1.3.6.1.4.1.5504.5.14.1.19.1.14
		zhoneGponOmciOnuImageUpgradeStartTime OBJECT-TYPE
			SYNTAX OCTET STRING (SIZE (0..32))
			MAX-ACCESS read-only
			STATUS current
			DESCRIPTION
				"Start time, as ascii string, of most recent upgrade."
			::= { zhoneGponOmciOnuImageUpgradeEntry 14 }

		
		-- 1.3.6.1.4.1.5504.5.14.1.19.1.15
		zhoneGponOmciOnuImageUpgradeWillBeActivated OBJECT-TYPE
			SYNTAX TruthValue
			MAX-ACCESS read-only
			STATUS current
			DESCRIPTION
				"If true, the downloaded image will be activated when
				download completes."
			::= { zhoneGponOmciOnuImageUpgradeEntry 15 }

		
		-- 1.3.6.1.4.1.5504.5.14.1.19.1.16
		zhoneGponOmciOnuImageUpgradeWillBeCommitted OBJECT-TYPE
			SYNTAX TruthValue
			MAX-ACCESS read-only
			STATUS current
			DESCRIPTION
				"If true, this image will be committed on successful activation."
			::= { zhoneGponOmciOnuImageUpgradeEntry 16 }

		
		-- 1.3.6.1.4.1.5504.5.14.1.19.1.17
		zhoneGponOmciOnuImageUpgradeType OBJECT-TYPE
			SYNTAX INTEGER
				{
				none(0),
				manual(1),
				auto(2),
				bulk(3)
				}
			MAX-ACCESS read-only
			STATUS current
			DESCRIPTION
				"Indicates the reason for the upgrade."
			::= { zhoneGponOmciOnuImageUpgradeEntry 17 }

		
		-- 1.3.6.1.4.1.5504.5.14.1.19.1.18
		zhoneGponOmciOnuImageDownloadProgressPercentage OBJECT-TYPE
			SYNTAX INTEGER (0..100)
			UNITS "percent"
			MAX-ACCESS read-only
			STATUS current
			DESCRIPTION
				"Image download progress.  This object is only valid during image download."
			DEFVAL { 0 }
			::= { zhoneGponOmciOnuImageUpgradeEntry 18 }

		
		-- 1.3.6.1.4.1.5504.5.14.1.19.1.19
		zhoneGponOmciOnuImageUpgradeMethod OBJECT-TYPE
			SYNTAX INTEGER
				{
				omci(1),
				tftp(2)
				}
			MAX-ACCESS read-only
			STATUS current
			DESCRIPTION
				"The download method used for upgrading this ONU.
				TFTP is used where possible, else OMCI (default)."
			DEFVAL { omci }
			::= { zhoneGponOmciOnuImageUpgradeEntry 19 }

		
		-- 1.3.6.1.4.1.5504.5.14.1.20
		zhoneGponOltStatusTable OBJECT-TYPE
			SYNTAX SEQUENCE OF ZhoneGponOltStatusEntry
			MAX-ACCESS not-accessible
			STATUS current
			DESCRIPTION
				"Current Status of OLT as reported from the Gpon Driver."
			::= { zhoneGponObjectID 20 }

		
		-- 1.3.6.1.4.1.5504.5.14.1.20.1
		zhoneGponOltStatusEntry OBJECT-TYPE
			SYNTAX ZhoneGponOltStatusEntry
			MAX-ACCESS not-accessible
			STATUS current
			DESCRIPTION
				"Row in the zhoneGponOltStatusTable."
			INDEX { zhoneGponOltIfIndex }
			::= { zhoneGponOltStatusTable 1 }

		
		ZhoneGponOltStatusEntry ::=
			SEQUENCE { 
				zhoneGponOltOpticTemperature
					Integer32,
				zhoneGponOltOpticVoltage
					Unsigned32,
				zhoneGponOltOpticTxBiasCurrent
					Unsigned32,
				zhoneGponOltOpticTxPower
					Integer32,
				zhoneGponOltOpticStatus
					INTEGER,
				zhoneGponOltOpticAlarms
					BITS,
				zhoneGponOltStatusWord
					BITS,
				zhoneGponOltConfiguredOnuCount
					Unsigned32,
				zhoneGponOltActiveOnuCount
					Unsigned32
			 }

		-- 1.3.6.1.4.1.5504.5.14.1.20.1.1
		zhoneGponOltOpticTemperature OBJECT-TYPE
			SYNTAX Integer32 (-128..128)
			UNITS "celcius"
			MAX-ACCESS read-only
			STATUS current
			DESCRIPTION
				"Internally measured Tranceiver Temperature of the OLT in Celcius."
			::= { zhoneGponOltStatusEntry 1 }

		
		-- 1.3.6.1.4.1.5504.5.14.1.20.1.2
		zhoneGponOltOpticVoltage OBJECT-TYPE
			SYNTAX Unsigned32 (0..655)
			UNITS "hundredths of volts"
			MAX-ACCESS read-only
			STATUS current
			DESCRIPTION
				"Internally measured Tranceiver Supply Voltage of the OLT in Volts.
				The measured value will be in the order of hundredths of Volts."
			::= { zhoneGponOltStatusEntry 2 }

		
		-- 1.3.6.1.4.1.5504.5.14.1.20.1.3
		zhoneGponOltOpticTxBiasCurrent OBJECT-TYPE
			SYNTAX Unsigned32 (0..131)
			UNITS "milliAmperes"
			MAX-ACCESS read-only
			STATUS current
			DESCRIPTION
				"Measured Tx Bias current per OLT in milli Amperes."
			::= { zhoneGponOltStatusEntry 3 }

		
		-- 1.3.6.1.4.1.5504.5.14.1.20.1.4
		zhoneGponOltOpticTxPower OBJECT-TYPE
			SYNTAX Integer32 (-600..200)
			UNITS "tenths of dB"
			MAX-ACCESS read-only
			STATUS current
			DESCRIPTION
				"Measured Tx Output Power of the OLT in dB.
				The measured value will be in tenths of dB."
			::= { zhoneGponOltStatusEntry 4 }

		
		-- 1.3.6.1.4.1.5504.5.14.1.20.1.5
		zhoneGponOltOpticStatus OBJECT-TYPE
			SYNTAX INTEGER
				{
				ok(1),
				warning(2),
				alarm(4),
				sfpnotpresent(8),
				oltactive(16)
				}
			MAX-ACCESS read-only
			STATUS current
			DESCRIPTION
				"When the End Of Life(EOL) Alarm bit is set an alarm will be raised. Alarm
				is set at about 150% of original current.Alarm will be level Major. It
				will be cleared when the SFP is replaced, or when the Alarm bit is cleared.
				Warning indication will be provided when user asks for status. Warning is
				set when EOL is at about 130% original current."
			::= { zhoneGponOltStatusEntry 5 }

		
		-- 1.3.6.1.4.1.5504.5.14.1.20.1.6
		zhoneGponOltOpticAlarms OBJECT-TYPE
			SYNTAX BITS
				{
				tempHigh(0),
				tempLow(1),
				vccHigh(2),
				vccLow(3),
				txBiasHigh(4),
				txBiasLow(5),
				txPwrHigh(6),
				txPwrLow(7),
				rxPwrHigh(8),
				rxPwrLow(9)
				}
			MAX-ACCESS read-only
			STATUS current
			DESCRIPTION
				"Bitmap of alarm conditions present, as reported
				from the SFP."
			::= { zhoneGponOltStatusEntry 6 }

		
		-- 1.3.6.1.4.1.5504.5.14.1.20.1.7
		zhoneGponOltStatusWord OBJECT-TYPE
			SYNTAX BITS
				{
				noAlarm(0),
				notused1(1),
				notused2(2),
				notused3(3),
				notused4(4),
				notused5(5),
				lossOfSignal(6),
				notused7(7),
				notused8(8),
				outOfService(9),
				rogueOnu(10),
				rogueOnuRssi(11),
				sgmiiGeLinkDown(12)
				}
			MAX-ACCESS read-only
			STATUS current
			DESCRIPTION
				"The bit-coded OLT status word."
			::= { zhoneGponOltStatusEntry 7 }

		
		-- 1.3.6.1.4.1.5504.5.14.1.20.1.8
		zhoneGponOltConfiguredOnuCount OBJECT-TYPE
			SYNTAX Unsigned32
			MAX-ACCESS read-only
			STATUS current
			DESCRIPTION
				"Count of the ONUs on this OLT where onu-added = TRUE."
			::= { zhoneGponOltStatusEntry 8 }

		
		-- 1.3.6.1.4.1.5504.5.14.1.20.1.9
		zhoneGponOltActiveOnuCount OBJECT-TYPE
			SYNTAX Unsigned32
			MAX-ACCESS read-only
			STATUS current
			DESCRIPTION
				"Number of ONUs on this OLT currently in operational state UP."
			::= { zhoneGponOltStatusEntry 9 }

		
		-- 1.3.6.1.4.1.5504.5.14.1.21
		zhoneGponOltDbaStatusTable OBJECT-TYPE
			SYNTAX SEQUENCE OF ZhoneGponOltDbaStatusEntry
			MAX-ACCESS not-accessible
			STATUS current
			DESCRIPTION
				"Current status of OLT DBA as reported from CAC."
			::= { zhoneGponObjectID 21 }

		
		-- 1.3.6.1.4.1.5504.5.14.1.21.1
		zhoneGponOltDbaStatusEntry OBJECT-TYPE
			SYNTAX ZhoneGponOltDbaStatusEntry
			MAX-ACCESS not-accessible
			STATUS current
			DESCRIPTION
				"Row in the zhoneGponOltDbaStatusTable."
			INDEX { zhoneGponOltIfIndex }
			::= { zhoneGponOltDbaStatusTable 1 }

		
		ZhoneGponOltDbaStatusEntry ::=
			SEQUENCE { 
				zhoneGponOltDbaTotalAvailableBw
					Unsigned32,
				zhoneGponOltDbaTotalAvailableCompensatedCbrBw
					Unsigned32,
				zhoneGponOltDbaAllocatedUbrBw
					Unsigned32,
				zhoneGponOltDbaAllocatedCbrBw
					Unsigned32,
				zhoneGponOltDbaAllocatedCompensatedCbrBw
					Unsigned32,
				zhoneGponOltDbaAllocatedAssuredBw
					Unsigned32,
				zhoneGponOltDbaAllocatedNonAssuredBw
					Unsigned32,
				zhoneGponOltDbaAllocatedBestEffortBw
					Unsigned32,
				zhoneGponOltDbaMaxAllocIds
					Unsigned32,
				zhoneGponOltDbaAvailAllocIds
					Unsigned32,
				zhoneGponOltDbaUsedAllocIds
					Unsigned32,
				zhoneGponOltDbaMaxDbaAllocIds
					Unsigned32,
				zhoneGponOltDbaAvailDbaAllocIds
					Unsigned32,
				zhoneGponOltDbaUsedDbaAllocIds
					Unsigned32,
				zhoneGponOltDbaTotalOltGemPorts
					Unsigned32,
				zhoneGponOltDbaLastCacRc
					GponCacRc
			 }

		-- 1.3.6.1.4.1.5504.5.14.1.21.1.1
		zhoneGponOltDbaTotalAvailableBw OBJECT-TYPE
			SYNTAX Unsigned32
			UNITS "kilobits"
			MAX-ACCESS read-only
			STATUS current
			DESCRIPTION
				"The Total Available DBA Bandwidth per OLT.The unit is Kilobits( 1000 bits)."
			::= { zhoneGponOltDbaStatusEntry 1 }

		
		-- 1.3.6.1.4.1.5504.5.14.1.21.1.2
		zhoneGponOltDbaTotalAvailableCompensatedCbrBw OBJECT-TYPE
			SYNTAX Unsigned32
			UNITS "kilobits"
			MAX-ACCESS read-only
			STATUS current
			DESCRIPTION
				"The Total Available DBA Compensated CBR bandwidth per OLT.
				The unit is Kilobits(1000 bits)."
			::= { zhoneGponOltDbaStatusEntry 2 }

		
		-- 1.3.6.1.4.1.5504.5.14.1.21.1.3
		zhoneGponOltDbaAllocatedUbrBw OBJECT-TYPE
			SYNTAX Unsigned32
			UNITS "kilobits"
			MAX-ACCESS read-only
			STATUS current
			DESCRIPTION
				"The Total Available DBA Allocated UBR bandwidth per OLT.
				The unit is Kilobits(1000 bits)."
			::= { zhoneGponOltDbaStatusEntry 3 }

		
		-- 1.3.6.1.4.1.5504.5.14.1.21.1.4
		zhoneGponOltDbaAllocatedCbrBw OBJECT-TYPE
			SYNTAX Unsigned32
			UNITS "kilobits"
			MAX-ACCESS read-only
			STATUS current
			DESCRIPTION
				"The Total Available DBA Allocated CBR bandwidth per OLT.
				The unit is Kilobits(1000 bits)."
			::= { zhoneGponOltDbaStatusEntry 4 }

		
		-- 1.3.6.1.4.1.5504.5.14.1.21.1.5
		zhoneGponOltDbaAllocatedCompensatedCbrBw OBJECT-TYPE
			SYNTAX Unsigned32
			UNITS "kilobits"
			MAX-ACCESS read-only
			STATUS current
			DESCRIPTION
				"The Total Available DBA Allocated CBR Compensated bandwidth per OLT.
				The unit is Kilobits(1000 bits)."
			::= { zhoneGponOltDbaStatusEntry 5 }

		
		-- 1.3.6.1.4.1.5504.5.14.1.21.1.6
		zhoneGponOltDbaAllocatedAssuredBw OBJECT-TYPE
			SYNTAX Unsigned32
			UNITS "kilobits"
			MAX-ACCESS read-only
			STATUS current
			DESCRIPTION
				"The Total Available DBA Allocated Assured bandwidth per OLT.
				The unit is Kilobits(1000 bits)."
			::= { zhoneGponOltDbaStatusEntry 6 }

		
		-- 1.3.6.1.4.1.5504.5.14.1.21.1.7
		zhoneGponOltDbaAllocatedNonAssuredBw OBJECT-TYPE
			SYNTAX Unsigned32
			UNITS "kilobits"
			MAX-ACCESS read-only
			STATUS current
			DESCRIPTION
				"The Total Available DBA Allocated Non Assured bandwidth per OLT.
				The unit is Kilobits(1000 bits)."
			::= { zhoneGponOltDbaStatusEntry 7 }

		
		-- 1.3.6.1.4.1.5504.5.14.1.21.1.8
		zhoneGponOltDbaAllocatedBestEffortBw OBJECT-TYPE
			SYNTAX Unsigned32
			UNITS "kilobits"
			MAX-ACCESS read-only
			STATUS current
			DESCRIPTION
				"The Total Available DBA Allocated Best Effort bandwidth per OLT.
				The unit is Kilobits(1000 bits)."
			::= { zhoneGponOltDbaStatusEntry 8 }

		
		-- 1.3.6.1.4.1.5504.5.14.1.21.1.9
		zhoneGponOltDbaMaxAllocIds OBJECT-TYPE
			SYNTAX Unsigned32
			MAX-ACCESS read-only
			STATUS current
			DESCRIPTION
				"Maximum number of alloc-Ids supported by this OLT."
			DEFVAL { 0 }
			::= { zhoneGponOltDbaStatusEntry 9 }

		
		-- 1.3.6.1.4.1.5504.5.14.1.21.1.10
		zhoneGponOltDbaAvailAllocIds OBJECT-TYPE
			SYNTAX Unsigned32
			MAX-ACCESS read-only
			STATUS current
			DESCRIPTION
				"Total number of available alloc-Ids for this OLT."
			DEFVAL { 0 }
			::= { zhoneGponOltDbaStatusEntry 10 }

		
		-- 1.3.6.1.4.1.5504.5.14.1.21.1.11
		zhoneGponOltDbaUsedAllocIds OBJECT-TYPE
			SYNTAX Unsigned32
			MAX-ACCESS read-only
			STATUS current
			DESCRIPTION
				"Total number of alloc-Ids in use for this OLT."
			DEFVAL { 0 }
			::= { zhoneGponOltDbaStatusEntry 11 }

		
		-- 1.3.6.1.4.1.5504.5.14.1.21.1.12
		zhoneGponOltDbaMaxDbaAllocIds OBJECT-TYPE
			SYNTAX Unsigned32
			MAX-ACCESS read-only
			STATUS current
			DESCRIPTION
				"Maximum number of DBA alloc-Ids supported by this OLT."
			DEFVAL { 0 }
			::= { zhoneGponOltDbaStatusEntry 12 }

		
		-- 1.3.6.1.4.1.5504.5.14.1.21.1.13
		zhoneGponOltDbaAvailDbaAllocIds OBJECT-TYPE
			SYNTAX Unsigned32
			MAX-ACCESS read-only
			STATUS current
			DESCRIPTION
				"Total number of available DBA alloc-Ids for this OLT."
			DEFVAL { 0 }
			::= { zhoneGponOltDbaStatusEntry 13 }

		
		-- 1.3.6.1.4.1.5504.5.14.1.21.1.14
		zhoneGponOltDbaUsedDbaAllocIds OBJECT-TYPE
			SYNTAX Unsigned32
			MAX-ACCESS read-only
			STATUS current
			DESCRIPTION
				"Total number of DBA alloc-Ids in use for this OLT."
			DEFVAL { 0 }
			::= { zhoneGponOltDbaStatusEntry 14 }

		
		-- 1.3.6.1.4.1.5504.5.14.1.21.1.15
		zhoneGponOltDbaTotalOltGemPorts OBJECT-TYPE
			SYNTAX Unsigned32
			MAX-ACCESS read-only
			STATUS current
			DESCRIPTION
				"Total number GEM Ports currently on this OLT."
			DEFVAL { 0 }
			::= { zhoneGponOltDbaStatusEntry 15 }

		
		-- 1.3.6.1.4.1.5504.5.14.1.21.1.16
		zhoneGponOltDbaLastCacRc OBJECT-TYPE
			SYNTAX GponCacRc
			MAX-ACCESS read-only
			STATUS current
			DESCRIPTION
				"This object contains the result code of the last GPON CAC request
				for the OLT."
			::= { zhoneGponOltDbaStatusEntry 16 }

		
		-- 1.3.6.1.4.1.5504.5.14.1.22
		zhoneGponUpgradeByStateTable OBJECT-TYPE
			SYNTAX SEQUENCE OF ZhoneGponUpgradeByStateEntry
			MAX-ACCESS not-accessible
			STATUS current
			DESCRIPTION
				"Information about onu upgrade."
			::= { zhoneGponObjectID 22 }

		
		-- 1.3.6.1.4.1.5504.5.14.1.22.1
		zhoneGponUpgradeByStateEntry OBJECT-TYPE
			SYNTAX ZhoneGponUpgradeByStateEntry
			MAX-ACCESS not-accessible
			STATUS current
			DESCRIPTION
				"Row in onu upgrade table."
			INDEX { zhoneOnuOmciImageUpgradeDownloadStatus, zhoneSlotIndex, zhoneGponUpgradeOlt, zhoneGponUpgradeOnu }
			::= { zhoneGponUpgradeByStateTable 1 }

		
		ZhoneGponUpgradeByStateEntry ::=
			SEQUENCE { 
				zhoneGponUpgradeOlt
					Integer32,
				zhoneGponUpgradeOnu
					Integer32,
				zhoneGponUpgradeModel
					OCTET STRING,
				zhoneGponUpgradeStartTime
					OCTET STRING,
				zhoneGponUpgradeIfIndex
					InterfaceIndex,
				zhoneGponUpgradeByStateOnuState
					OnuUpgradeState,
				zhoneGponUpgradeByStateWillBeActivated
					TruthValue,
				zhoneGponUpgradeByStateWillBeCommitted
					TruthValue,
				zhoneGponUpgradeByStateUpgradeType
					INTEGER,
				zhoneGponUpgradeByStatePartition
					INTEGER,
				zhoneGponUpgradeProgressPercentage
					INTEGER,
				zhoneGponUpgradeByStateMethod
					INTEGER
			 }

		-- 1.3.6.1.4.1.5504.5.14.1.22.1.1
		zhoneGponUpgradeOlt OBJECT-TYPE
			SYNTAX Integer32 (1..32)
			MAX-ACCESS not-accessible
			STATUS current
			DESCRIPTION
				"Olt number on the card."
			::= { zhoneGponUpgradeByStateEntry 1 }

		
		-- 1.3.6.1.4.1.5504.5.14.1.22.1.2
		zhoneGponUpgradeOnu OBJECT-TYPE
			SYNTAX Integer32 (1..128)
			MAX-ACCESS not-accessible
			STATUS current
			DESCRIPTION
				"Onu number within olt."
			::= { zhoneGponUpgradeByStateEntry 2 }

		
		-- 1.3.6.1.4.1.5504.5.14.1.22.1.3
		zhoneGponUpgradeModel OBJECT-TYPE
			SYNTAX OCTET STRING (SIZE (0..20))
			MAX-ACCESS read-only
			STATUS current
			DESCRIPTION
				"Model ID returned from this Onu."
			::= { zhoneGponUpgradeByStateEntry 3 }

		
		-- 1.3.6.1.4.1.5504.5.14.1.22.1.4
		zhoneGponUpgradeStartTime OBJECT-TYPE
			SYNTAX OCTET STRING (SIZE (0..32))
			MAX-ACCESS read-only
			STATUS current
			DESCRIPTION
				"Last upgrade start time, as ascii string"
			::= { zhoneGponUpgradeByStateEntry 4 }

		
		-- 1.3.6.1.4.1.5504.5.14.1.22.1.5
		zhoneGponUpgradeIfIndex OBJECT-TYPE
			SYNTAX InterfaceIndex
			MAX-ACCESS read-only
			STATUS current
			DESCRIPTION
				"Onu ifIndex"
			::= { zhoneGponUpgradeByStateEntry 5 }

		
		-- 1.3.6.1.4.1.5504.5.14.1.22.1.6
		zhoneGponUpgradeByStateOnuState OBJECT-TYPE
			SYNTAX OnuUpgradeState
			MAX-ACCESS read-only
			STATUS current
			DESCRIPTION
				"The actual upgrade state of the onu."
			::= { zhoneGponUpgradeByStateEntry 6 }

		
		-- 1.3.6.1.4.1.5504.5.14.1.22.1.7
		zhoneGponUpgradeByStateWillBeActivated OBJECT-TYPE
			SYNTAX TruthValue
			MAX-ACCESS read-only
			STATUS current
			DESCRIPTION
				"If true, the image will be activated if download is successful."
			::= { zhoneGponUpgradeByStateEntry 7 }

		
		-- 1.3.6.1.4.1.5504.5.14.1.22.1.8
		zhoneGponUpgradeByStateWillBeCommitted OBJECT-TYPE
			SYNTAX TruthValue
			MAX-ACCESS read-only
			STATUS current
			DESCRIPTION
				"If true, image will be committed after successful activation."
			::= { zhoneGponUpgradeByStateEntry 8 }

		
		-- 1.3.6.1.4.1.5504.5.14.1.22.1.9
		zhoneGponUpgradeByStateUpgradeType OBJECT-TYPE
			SYNTAX INTEGER
				{
				none(0),
				manual(1),
				auto(2),
				bulk(3)
				}
			MAX-ACCESS read-only
			STATUS current
			DESCRIPTION
				"Indicates the reason for the upgrade."
			::= { zhoneGponUpgradeByStateEntry 9 }

		
		-- 1.3.6.1.4.1.5504.5.14.1.22.1.10
		zhoneGponUpgradeByStatePartition OBJECT-TYPE
			SYNTAX INTEGER
				{
				none(0),
				partitionNumber0(1),
				partitionNumber1(2)
				}
			MAX-ACCESS read-only
			STATUS current
			DESCRIPTION
				"If upgrade has been requested, this is the image partition
				of the latest upgrade."
			::= { zhoneGponUpgradeByStateEntry 10 }

		
		-- 1.3.6.1.4.1.5504.5.14.1.22.1.11
		zhoneGponUpgradeProgressPercentage OBJECT-TYPE
			SYNTAX INTEGER (0..100)
			UNITS "percent"
			MAX-ACCESS read-only
			STATUS current
			DESCRIPTION
				"Image download progress.  This object is only valid during image download."
			DEFVAL { 0 }
			::= { zhoneGponUpgradeByStateEntry 11 }

		
		-- 1.3.6.1.4.1.5504.5.14.1.22.1.12
		zhoneGponUpgradeByStateMethod OBJECT-TYPE
			SYNTAX INTEGER
				{
				omci(1),
				tftp(2)
				}
			MAX-ACCESS read-only
			STATUS current
			DESCRIPTION
				"The download method used for upgrading this ONU.
				TFTP is used where possible, else OMCI (default)."
			::= { zhoneGponUpgradeByStateEntry 12 }

		
		-- 1.3.6.1.4.1.5504.5.14.1.23
		zhoneGponCmd OBJECT IDENTIFIER ::= { zhoneGponObjectID 23 }
-- The GPON Command objects are used to send commands to the
-- GPON Line RP.
-- 
-- At this time, commands can only be sent to a single ONU.
-- Shelf and OLT command filters are not supported.   
-- 
-- Command Examples:
-- 
--   GPON ONU Resync for ONU 5/1/2:
--      zhoneGponCmdOperation.0 = 2 (resync)
--      zhoneGponCmdFilterMask.0 = 70.00.00.00
--      zhoneGponCmdSlot.0 = 5
--      zhoneGponCmdOlt.0 = 1 
--      zhoneGponCmdOnu.0 = 2  
		
		-- 1.3.6.1.4.1.5504.5.14.1.23.1
		zhoneGponCmdOperation OBJECT-TYPE
			SYNTAX INTEGER
				{
				onuApply(1),
				onuResync(2),
				onuReboot(3),
				onuSet2default(4),
				onuEnableAutoCfg(5),
				onuDisableAutoCfg(6)
				}
			MAX-ACCESS read-write
			STATUS current
			DESCRIPTION
				"GPON Command operation.  
				
				This object must be supplied with each operation."
			DEFVAL { onuApply }
			::= { zhoneGponCmd 1 }

		
		-- 1.3.6.1.4.1.5504.5.14.1.23.2
		zhoneGponCmdFilterMask OBJECT-TYPE
			SYNTAX BITS
				{
				filterShelf(0),
				filterSlot(1),
				filterOlt(2),
				filterOnu(3)
				}
			MAX-ACCESS read-write
			STATUS current
			DESCRIPTION
				"GPON Command operation filter.  
				
				This object must be supplied with each operation."
			::= { zhoneGponCmd 2 }

		
		-- 1.3.6.1.4.1.5504.5.14.1.23.3
		zhoneGponCmdShelf OBJECT-TYPE
			SYNTAX Unsigned32 (1)
			MAX-ACCESS read-write
			STATUS current
			DESCRIPTION
				"GPON command 'SHELF' filter value.  
				
				This parameter is for future use and is currently not supported."
			DEFVAL { 1 }
			::= { zhoneGponCmd 3 }

		
		-- 1.3.6.1.4.1.5504.5.14.1.23.4
		zhoneGponCmdSlot OBJECT-TYPE
			SYNTAX Unsigned32 (1..32)
			MAX-ACCESS read-write
			STATUS current
			DESCRIPTION
				"GPON command 'SLOT' filter value.  
				
				If this object is included in the SNMP packet then the 
				associated filter must be enabled in the filter (zhoneGponCmdFilterMask)."
			DEFVAL { 1 }
			::= { zhoneGponCmd 4 }

		
		-- 1.3.6.1.4.1.5504.5.14.1.23.5
		zhoneGponCmdOlt OBJECT-TYPE
			SYNTAX Unsigned32
			MAX-ACCESS read-write
			STATUS current
			DESCRIPTION
				"GPON command 'OLT' filter value.  
				
				If this object is included in the SNMP packet then the 
				associated filter must be enabled in the filter (zhoneGponCmdFilterMask)."
			DEFVAL { 1 }
			::= { zhoneGponCmd 5 }

		
		-- 1.3.6.1.4.1.5504.5.14.1.23.6
		zhoneGponCmdOnu OBJECT-TYPE
			SYNTAX Unsigned32
			MAX-ACCESS read-write
			STATUS current
			DESCRIPTION
				"GPON command 'ONU' filter value.  
				
				If this object is included in the SNMP packet then the 
				associated filter must be enabled in the filter (zhoneGponCmdFilterMask)."
			DEFVAL { 1 }
			::= { zhoneGponCmd 6 }

		
		-- 1.3.6.1.4.1.5504.5.14.1.24
		zhoneGponOltStatisticsTable OBJECT-TYPE
			SYNTAX SEQUENCE OF ZhoneGponOltStatisticsEntry
			MAX-ACCESS not-accessible
			STATUS current
			DESCRIPTION
				"Per OLT statistics gathered from Broadlight device."
			::= { zhoneGponObjectID 24 }

		
		-- 1.3.6.1.4.1.5504.5.14.1.24.1
		zhoneGponOltStatisticsEntry OBJECT-TYPE
			SYNTAX ZhoneGponOltStatisticsEntry
			MAX-ACCESS not-accessible
			STATUS current
			DESCRIPTION
				"Per OLT statistics gathered from Broadlight device."
			INDEX { zhoneGponOltIfIndex }
			::= { zhoneGponOltStatisticsTable 1 }

		
		ZhoneGponOltStatisticsEntry ::=
			SEQUENCE { 
				zhoneGponOltStatisticsUpstreamValidGemFrames
					Counter64,
				zhoneGponOltStatisticsUpstreamDiscardedFrames
					Counter64,
				zhoneGponOltStatisticsUpstreamGemFrames
					Counter64,
				zhoneGponOltStatisticsUpstreamOmciFrames
					Counter64,
				zhoneGponOltStatisticsUpstreamPloamFrames
					Counter64,
				zhoneGponOltStatisticsUpstreamIdlePloamFrames
					Counter64,
				zhoneGponOltStatisticsDownstreamValidGemFrames
					Counter64,
				zhoneGponOltStatisticsDownstreamDiscardedFrames
					Counter64,
				zhoneGponOltStatisticsDownstreamGemFrames
					Counter64,
				zhoneGponOltStatisticsDownstreamOmciFrames
					Counter64,
				zhoneGponOltStatisticsDownstreamPloamFrames
					Counter64,
				zhoneGponOltStatisticsDownstreamIdlePloamFrames
					Counter64,
				zhoneGponOltStatisticsDownstreamPonValidEthernetPkts
					Counter64,
				zhoneGponOltStatisticsDownstreamPonCpuPkts
					Counter64,
				zhoneGponOltStatisticsDownstreamTxBytes
					Counter64,
				zhoneGponOltStatisticsUpstreamPonValidPkts
					Counter64,
				zhoneGponOltStatisticsUpstreamPonValidNotIdlePloams
					Counter64,
				zhoneGponOltStatisticsUpstreamPonErrorPloams
					Counter64,
				zhoneGponOltStatisticsUpstreamPonInvalidPkts
					Counter64,
				zhoneGponOltStatisticsUpstreamDroppedPktsInactivePorts
					Counter64,
				zhoneGponOltStatisticsUpstreamDroppedPloamsFifoFull
					Counter64,
				zhoneGponOltStatisticsDownstreamTmValidPkts
					Counter64,
				zhoneGponOltStatisticsDownstreamTmCrcPkts
					Counter64,
				zhoneGponOltStatisticsDownstreamTmDroppedCpuPkts
					Counter64,
				zhoneGponOltStatisticsDownstreamTmMacLookupMiss
					Counter64,
				zhoneGponOltStatisticsDownstreamTmPktsForwardedFromHmToPon
					Counter64,
				zhoneGponOltStatisticsDownstreamTmPktsDroppedGemPidNotEnabled
					Counter64,
				zhoneGponOltStatisticsDownstreamTmQ0ValidPkts
					Counter64,
				zhoneGponOltStatisticsDownstreamTmQ0DroppedPkts
					Counter64,
				zhoneGponOltStatisticsDownstreamTmQ1ValidPkts
					Counter64,
				zhoneGponOltStatisticsDownstreamTmQ1DroppedPkts
					Counter64,
				zhoneGponOltStatisticsDownstreamTmQ2ValidPkts
					Counter64,
				zhoneGponOltStatisticsDownstreamTmQ2DroppedPkts
					Counter64,
				zhoneGponOltStatisticsDownstreamTmQ3ValidPkts
					Counter64,
				zhoneGponOltStatisticsDownstreamTmQ3DroppedPkts
					Counter64,
				zhoneGponOltStatisticsDownstreamTmQ4ValidPkts
					Counter64,
				zhoneGponOltStatisticsDownstreamTmQ4DroppedPkts
					Counter64,
				zhoneGponOltStatisticsDownstreamTmQ5ValidPkts
					Counter64,
				zhoneGponOltStatisticsDownstreamTmQ5DroppedPkts
					Counter64,
				zhoneGponOltStatisticsDownstreamTmQ6ValidPkts
					Counter64,
				zhoneGponOltStatisticsDownstreamTmQ6DroppedPkts
					Counter64,
				zhoneGponOltStatisticsDownstreamTmQ7ValidPkts
					Counter64,
				zhoneGponOltStatisticsDownstreamTmQ7DroppedPkts
					Counter64,
				zhoneGponOltStatisticsUpstreamTmDroppedCpuPkts
					Counter64,
				zhoneGponOltStatisticsUpstreamTmDroppedPktsCrcError
					Counter64,
				zhoneGponOltStatisticsUpstreamTmDroppedPktsSecurity
					Counter64,
				zhoneGponOltStatisticsUpstreamTmLearnFailures
					Counter64,
				zhoneGponOltStatisticsUpstreamTmQ0ValidPkts
					Counter64,
				zhoneGponOltStatisticsUpstreamTmQ0DroppedPkts
					Counter64,
				zhoneGponOltStatisticsUpstreamTmQ1ValidPkts
					Counter64,
				zhoneGponOltStatisticsUpstreamTmQ1DroppedPkts
					Counter64,
				zhoneGponOltStatisticsUpstreamTmQ2ValidPkts
					Counter64,
				zhoneGponOltStatisticsUpstreamTmQ2DroppedPkts
					Counter64,
				zhoneGponOltStatisticsUpstreamTmQ3ValidPkts
					Counter64,
				zhoneGponOltStatisticsUpstreamTmQ3DroppedPkts
					Counter64,
				zhoneGponOltStatisticsUpstreamTmQ4ValidPkts
					Counter64,
				zhoneGponOltStatisticsUpstreamTmQ4DroppedPkts
					Counter64,
				zhoneGponOltStatisticsUpstreamTmQ5ValidPkts
					Counter64,
				zhoneGponOltStatisticsUpstreamTmQ5DroppedPkts
					Counter64,
				zhoneGponOltStatisticsUpstreamTmQ6ValidPkts
					Counter64,
				zhoneGponOltStatisticsUpstreamTmQ6DroppedPkts
					Counter64,
				zhoneGponOltStatisticsUpstreamTmQ7ValidPkts
					Counter64,
				zhoneGponOltStatisticsUpstreamTmQ7DroppedPkts
					Counter64,
				zhoneGponOltStatisticsClearStats
					TruthValue
			 }

		-- 1.3.6.1.4.1.5504.5.14.1.24.1.1
		zhoneGponOltStatisticsUpstreamValidGemFrames OBJECT-TYPE
			SYNTAX Counter64
			MAX-ACCESS read-only
			STATUS current
			DESCRIPTION
				"UpstreamValidGemFrames counter."
			::= { zhoneGponOltStatisticsEntry 1 }

		
		-- 1.3.6.1.4.1.5504.5.14.1.24.1.2
		zhoneGponOltStatisticsUpstreamDiscardedFrames OBJECT-TYPE
			SYNTAX Counter64
			MAX-ACCESS read-only
			STATUS current
			DESCRIPTION
				"UpstreamDiscardedFrames counter."
			::= { zhoneGponOltStatisticsEntry 2 }

		
		-- 1.3.6.1.4.1.5504.5.14.1.24.1.3
		zhoneGponOltStatisticsUpstreamGemFrames OBJECT-TYPE
			SYNTAX Counter64
			MAX-ACCESS read-only
			STATUS current
			DESCRIPTION
				"UpstreamGemFrames counter."
			::= { zhoneGponOltStatisticsEntry 3 }

		
		-- 1.3.6.1.4.1.5504.5.14.1.24.1.4
		zhoneGponOltStatisticsUpstreamOmciFrames OBJECT-TYPE
			SYNTAX Counter64
			MAX-ACCESS read-only
			STATUS current
			DESCRIPTION
				"UpstreamOmciFrames counter."
			::= { zhoneGponOltStatisticsEntry 4 }

		
		-- 1.3.6.1.4.1.5504.5.14.1.24.1.5
		zhoneGponOltStatisticsUpstreamPloamFrames OBJECT-TYPE
			SYNTAX Counter64
			MAX-ACCESS read-only
			STATUS current
			DESCRIPTION
				"UpstreamPloamFrames counter."
			::= { zhoneGponOltStatisticsEntry 5 }

		
		-- 1.3.6.1.4.1.5504.5.14.1.24.1.6
		zhoneGponOltStatisticsUpstreamIdlePloamFrames OBJECT-TYPE
			SYNTAX Counter64
			MAX-ACCESS read-only
			STATUS current
			DESCRIPTION
				"UpstreamIdlePloamFrames counter."
			::= { zhoneGponOltStatisticsEntry 6 }

		
		-- 1.3.6.1.4.1.5504.5.14.1.24.1.7
		zhoneGponOltStatisticsDownstreamValidGemFrames OBJECT-TYPE
			SYNTAX Counter64
			MAX-ACCESS read-only
			STATUS current
			DESCRIPTION
				"DownstreamValidGemFrames counter."
			::= { zhoneGponOltStatisticsEntry 7 }

		
		-- 1.3.6.1.4.1.5504.5.14.1.24.1.8
		zhoneGponOltStatisticsDownstreamDiscardedFrames OBJECT-TYPE
			SYNTAX Counter64
			MAX-ACCESS read-only
			STATUS current
			DESCRIPTION
				"DownstreamDiscardedFrames counter."
			::= { zhoneGponOltStatisticsEntry 8 }

		
		-- 1.3.6.1.4.1.5504.5.14.1.24.1.9
		zhoneGponOltStatisticsDownstreamGemFrames OBJECT-TYPE
			SYNTAX Counter64
			MAX-ACCESS read-only
			STATUS current
			DESCRIPTION
				"DownstreamGemFrames counter."
			::= { zhoneGponOltStatisticsEntry 9 }

		
		-- 1.3.6.1.4.1.5504.5.14.1.24.1.10
		zhoneGponOltStatisticsDownstreamOmciFrames OBJECT-TYPE
			SYNTAX Counter64
			MAX-ACCESS read-only
			STATUS current
			DESCRIPTION
				"DownstreamOmciFrames counter."
			::= { zhoneGponOltStatisticsEntry 10 }

		
		-- 1.3.6.1.4.1.5504.5.14.1.24.1.11
		zhoneGponOltStatisticsDownstreamPloamFrames OBJECT-TYPE
			SYNTAX Counter64
			MAX-ACCESS read-only
			STATUS current
			DESCRIPTION
				"DownstreamPloamFrames counter."
			::= { zhoneGponOltStatisticsEntry 11 }

		
		-- 1.3.6.1.4.1.5504.5.14.1.24.1.12
		zhoneGponOltStatisticsDownstreamIdlePloamFrames OBJECT-TYPE
			SYNTAX Counter64
			MAX-ACCESS read-only
			STATUS deprecated
			DESCRIPTION
				"DownstreamIdlePloamFrames counter."
			::= { zhoneGponOltStatisticsEntry 12 }

		
		-- 1.3.6.1.4.1.5504.5.14.1.24.1.13
		zhoneGponOltStatisticsDownstreamPonValidEthernetPkts OBJECT-TYPE
			SYNTAX Counter64
			MAX-ACCESS read-only
			STATUS current
			DESCRIPTION
				"DownstreamPonValidEthernetPkts counter."
			::= { zhoneGponOltStatisticsEntry 13 }

		
		-- 1.3.6.1.4.1.5504.5.14.1.24.1.14
		zhoneGponOltStatisticsDownstreamPonCpuPkts OBJECT-TYPE
			SYNTAX Counter64
			MAX-ACCESS read-only
			STATUS current
			DESCRIPTION
				"DownstreamPonCpuPkts counter."
			::= { zhoneGponOltStatisticsEntry 14 }

		
		-- 1.3.6.1.4.1.5504.5.14.1.24.1.15
		zhoneGponOltStatisticsDownstreamTxBytes OBJECT-TYPE
			SYNTAX Counter64
			MAX-ACCESS read-only
			STATUS current
			DESCRIPTION
				"DownstreamTxBytes counter."
			::= { zhoneGponOltStatisticsEntry 15 }

		
		-- 1.3.6.1.4.1.5504.5.14.1.24.1.16
		zhoneGponOltStatisticsUpstreamPonValidPkts OBJECT-TYPE
			SYNTAX Counter64
			MAX-ACCESS read-only
			STATUS current
			DESCRIPTION
				"Description."
			::= { zhoneGponOltStatisticsEntry 16 }

		
		-- 1.3.6.1.4.1.5504.5.14.1.24.1.17
		zhoneGponOltStatisticsUpstreamPonValidNotIdlePloams OBJECT-TYPE
			SYNTAX Counter64
			MAX-ACCESS read-only
			STATUS current
			DESCRIPTION
				"UpstreamPonValidNotIdlePloams counter."
			::= { zhoneGponOltStatisticsEntry 17 }

		
		-- 1.3.6.1.4.1.5504.5.14.1.24.1.18
		zhoneGponOltStatisticsUpstreamPonErrorPloams OBJECT-TYPE
			SYNTAX Counter64
			MAX-ACCESS read-only
			STATUS current
			DESCRIPTION
				"UpstreamPonErrorPloams counter."
			::= { zhoneGponOltStatisticsEntry 18 }

		
		-- 1.3.6.1.4.1.5504.5.14.1.24.1.19
		zhoneGponOltStatisticsUpstreamPonInvalidPkts OBJECT-TYPE
			SYNTAX Counter64
			MAX-ACCESS read-only
			STATUS current
			DESCRIPTION
				"UpstreamPonInvalidPkts counter."
			::= { zhoneGponOltStatisticsEntry 19 }

		
		-- 1.3.6.1.4.1.5504.5.14.1.24.1.20
		zhoneGponOltStatisticsUpstreamDroppedPktsInactivePorts OBJECT-TYPE
			SYNTAX Counter64
			MAX-ACCESS read-only
			STATUS current
			DESCRIPTION
				"UpstreamDroppedPktsInactivePorts counter."
			::= { zhoneGponOltStatisticsEntry 20 }

		
		-- 1.3.6.1.4.1.5504.5.14.1.24.1.21
		zhoneGponOltStatisticsUpstreamDroppedPloamsFifoFull OBJECT-TYPE
			SYNTAX Counter64
			MAX-ACCESS read-only
			STATUS current
			DESCRIPTION
				"UpstreamDroppedPloamsFifoFull counter."
			::= { zhoneGponOltStatisticsEntry 21 }

		
		-- 1.3.6.1.4.1.5504.5.14.1.24.1.22
		zhoneGponOltStatisticsDownstreamTmValidPkts OBJECT-TYPE
			SYNTAX Counter64
			MAX-ACCESS read-only
			STATUS current
			DESCRIPTION
				"DownstreamTmValidPkts counter."
			::= { zhoneGponOltStatisticsEntry 22 }

		
		-- 1.3.6.1.4.1.5504.5.14.1.24.1.23
		zhoneGponOltStatisticsDownstreamTmCrcPkts OBJECT-TYPE
			SYNTAX Counter64
			MAX-ACCESS read-only
			STATUS current
			DESCRIPTION
				"DownstreamTmCrcPkts counter."
			::= { zhoneGponOltStatisticsEntry 23 }

		
		-- 1.3.6.1.4.1.5504.5.14.1.24.1.24
		zhoneGponOltStatisticsDownstreamTmDroppedCpuPkts OBJECT-TYPE
			SYNTAX Counter64
			MAX-ACCESS read-only
			STATUS current
			DESCRIPTION
				"DownstreamTmDroppedCpuPkts counter."
			::= { zhoneGponOltStatisticsEntry 24 }

		
		-- 1.3.6.1.4.1.5504.5.14.1.24.1.25
		zhoneGponOltStatisticsDownstreamTmMacLookupMiss OBJECT-TYPE
			SYNTAX Counter64
			MAX-ACCESS read-only
			STATUS current
			DESCRIPTION
				"DownstreamTmMacLookupMiss counter."
			::= { zhoneGponOltStatisticsEntry 25 }

		
		-- 1.3.6.1.4.1.5504.5.14.1.24.1.26
		zhoneGponOltStatisticsDownstreamTmPktsForwardedFromHmToPon OBJECT-TYPE
			SYNTAX Counter64
			MAX-ACCESS read-only
			STATUS current
			DESCRIPTION
				"DownstreamTmPktsForwardedFromHmToPon counter."
			::= { zhoneGponOltStatisticsEntry 26 }

		
		-- 1.3.6.1.4.1.5504.5.14.1.24.1.27
		zhoneGponOltStatisticsDownstreamTmPktsDroppedGemPidNotEnabled OBJECT-TYPE
			SYNTAX Counter64
			MAX-ACCESS read-only
			STATUS current
			DESCRIPTION
				"DownstreamTmPktsDroppedGemPidNotEnabled counter."
			::= { zhoneGponOltStatisticsEntry 27 }

		
		-- 1.3.6.1.4.1.5504.5.14.1.24.1.28
		zhoneGponOltStatisticsDownstreamTmQ0ValidPkts OBJECT-TYPE
			SYNTAX Counter64
			MAX-ACCESS read-only
			STATUS current
			DESCRIPTION
				"DownstreamTmQ0ValidPkts counter."
			::= { zhoneGponOltStatisticsEntry 28 }

		
		-- 1.3.6.1.4.1.5504.5.14.1.24.1.29
		zhoneGponOltStatisticsDownstreamTmQ0DroppedPkts OBJECT-TYPE
			SYNTAX Counter64
			MAX-ACCESS read-only
			STATUS current
			DESCRIPTION
				"DownstreamTmQ0DroppedPkts counter."
			::= { zhoneGponOltStatisticsEntry 29 }

		
		-- 1.3.6.1.4.1.5504.5.14.1.24.1.30
		zhoneGponOltStatisticsDownstreamTmQ1ValidPkts OBJECT-TYPE
			SYNTAX Counter64
			MAX-ACCESS read-only
			STATUS current
			DESCRIPTION
				"DownstreamTmQ1ValidPkts counter."
			::= { zhoneGponOltStatisticsEntry 30 }

		
		-- 1.3.6.1.4.1.5504.5.14.1.24.1.31
		zhoneGponOltStatisticsDownstreamTmQ1DroppedPkts OBJECT-TYPE
			SYNTAX Counter64
			MAX-ACCESS read-only
			STATUS current
			DESCRIPTION
				"DownstreamTmQ1DroppedPkts counter."
			::= { zhoneGponOltStatisticsEntry 31 }

		
		-- 1.3.6.1.4.1.5504.5.14.1.24.1.32
		zhoneGponOltStatisticsDownstreamTmQ2ValidPkts OBJECT-TYPE
			SYNTAX Counter64
			MAX-ACCESS read-only
			STATUS current
			DESCRIPTION
				"DownstreamTmQ2ValidPkts counter."
			::= { zhoneGponOltStatisticsEntry 32 }

		
		-- 1.3.6.1.4.1.5504.5.14.1.24.1.33
		zhoneGponOltStatisticsDownstreamTmQ2DroppedPkts OBJECT-TYPE
			SYNTAX Counter64
			MAX-ACCESS read-only
			STATUS current
			DESCRIPTION
				"DownstreamTmQ2DroppedPkts counter."
			::= { zhoneGponOltStatisticsEntry 33 }

		
		-- 1.3.6.1.4.1.5504.5.14.1.24.1.34
		zhoneGponOltStatisticsDownstreamTmQ3ValidPkts OBJECT-TYPE
			SYNTAX Counter64
			MAX-ACCESS read-only
			STATUS current
			DESCRIPTION
				"DownstreamTmQ3ValidPkts counter."
			::= { zhoneGponOltStatisticsEntry 34 }

		
		-- 1.3.6.1.4.1.5504.5.14.1.24.1.35
		zhoneGponOltStatisticsDownstreamTmQ3DroppedPkts OBJECT-TYPE
			SYNTAX Counter64
			MAX-ACCESS read-only
			STATUS current
			DESCRIPTION
				"DownstreamTmQ3DroppedPkts counter."
			::= { zhoneGponOltStatisticsEntry 35 }

		
		-- 1.3.6.1.4.1.5504.5.14.1.24.1.36
		zhoneGponOltStatisticsDownstreamTmQ4ValidPkts OBJECT-TYPE
			SYNTAX Counter64
			MAX-ACCESS read-only
			STATUS current
			DESCRIPTION
				"DownstreamTmQ4ValidPkts counter."
			::= { zhoneGponOltStatisticsEntry 36 }

		
		-- 1.3.6.1.4.1.5504.5.14.1.24.1.37
		zhoneGponOltStatisticsDownstreamTmQ4DroppedPkts OBJECT-TYPE
			SYNTAX Counter64
			MAX-ACCESS read-only
			STATUS current
			DESCRIPTION
				"DownstreamTmQ4DroppedPkts counter."
			::= { zhoneGponOltStatisticsEntry 37 }

		
		-- 1.3.6.1.4.1.5504.5.14.1.24.1.38
		zhoneGponOltStatisticsDownstreamTmQ5ValidPkts OBJECT-TYPE
			SYNTAX Counter64
			MAX-ACCESS read-only
			STATUS current
			DESCRIPTION
				"DownstreamTmQ5ValidPkts counter."
			::= { zhoneGponOltStatisticsEntry 38 }

		
		-- 1.3.6.1.4.1.5504.5.14.1.24.1.39
		zhoneGponOltStatisticsDownstreamTmQ5DroppedPkts OBJECT-TYPE
			SYNTAX Counter64
			MAX-ACCESS read-only
			STATUS current
			DESCRIPTION
				"DownstreamTmQ5DroppedPkts counter."
			::= { zhoneGponOltStatisticsEntry 39 }

		
		-- 1.3.6.1.4.1.5504.5.14.1.24.1.40
		zhoneGponOltStatisticsDownstreamTmQ6ValidPkts OBJECT-TYPE
			SYNTAX Counter64
			MAX-ACCESS read-only
			STATUS current
			DESCRIPTION
				"DownstreamTmQ6ValidPkts counter."
			::= { zhoneGponOltStatisticsEntry 40 }

		
		-- 1.3.6.1.4.1.5504.5.14.1.24.1.41
		zhoneGponOltStatisticsDownstreamTmQ6DroppedPkts OBJECT-TYPE
			SYNTAX Counter64
			MAX-ACCESS read-only
			STATUS current
			DESCRIPTION
				"DownstreamTmQ6DroppedPkts counter."
			::= { zhoneGponOltStatisticsEntry 41 }

		
		-- 1.3.6.1.4.1.5504.5.14.1.24.1.42
		zhoneGponOltStatisticsDownstreamTmQ7ValidPkts OBJECT-TYPE
			SYNTAX Counter64
			MAX-ACCESS read-only
			STATUS current
			DESCRIPTION
				"DownstreamTmQ7ValidPkts counter."
			::= { zhoneGponOltStatisticsEntry 42 }

		
		-- 1.3.6.1.4.1.5504.5.14.1.24.1.43
		zhoneGponOltStatisticsDownstreamTmQ7DroppedPkts OBJECT-TYPE
			SYNTAX Counter64
			MAX-ACCESS read-only
			STATUS current
			DESCRIPTION
				"DownstreamTmQ7DroppedPkts counter."
			::= { zhoneGponOltStatisticsEntry 43 }

		
		-- 1.3.6.1.4.1.5504.5.14.1.24.1.44
		zhoneGponOltStatisticsUpstreamTmDroppedCpuPkts OBJECT-TYPE
			SYNTAX Counter64
			MAX-ACCESS read-only
			STATUS current
			DESCRIPTION
				"UpstreamTmDroppedCpuPkts counter."
			::= { zhoneGponOltStatisticsEntry 44 }

		
		-- 1.3.6.1.4.1.5504.5.14.1.24.1.45
		zhoneGponOltStatisticsUpstreamTmDroppedPktsCrcError OBJECT-TYPE
			SYNTAX Counter64
			MAX-ACCESS read-only
			STATUS current
			DESCRIPTION
				"UpstreamTmDroppedPktsCrcError counter."
			::= { zhoneGponOltStatisticsEntry 45 }

		
		-- 1.3.6.1.4.1.5504.5.14.1.24.1.46
		zhoneGponOltStatisticsUpstreamTmDroppedPktsSecurity OBJECT-TYPE
			SYNTAX Counter64
			MAX-ACCESS read-only
			STATUS current
			DESCRIPTION
				"UpstreamTmDroppedPktsSecurity counter."
			::= { zhoneGponOltStatisticsEntry 46 }

		
		-- 1.3.6.1.4.1.5504.5.14.1.24.1.47
		zhoneGponOltStatisticsUpstreamTmLearnFailures OBJECT-TYPE
			SYNTAX Counter64
			MAX-ACCESS read-only
			STATUS current
			DESCRIPTION
				"UpstreamTmLearnFailures counter."
			::= { zhoneGponOltStatisticsEntry 47 }

		
		-- 1.3.6.1.4.1.5504.5.14.1.24.1.48
		zhoneGponOltStatisticsUpstreamTmQ0ValidPkts OBJECT-TYPE
			SYNTAX Counter64
			MAX-ACCESS read-only
			STATUS current
			DESCRIPTION
				"UpstreamTmQ0ValidPkts counter."
			::= { zhoneGponOltStatisticsEntry 48 }

		
		-- 1.3.6.1.4.1.5504.5.14.1.24.1.49
		zhoneGponOltStatisticsUpstreamTmQ0DroppedPkts OBJECT-TYPE
			SYNTAX Counter64
			MAX-ACCESS read-only
			STATUS current
			DESCRIPTION
				"UpstreamTmQ0DroppedPkts counter."
			::= { zhoneGponOltStatisticsEntry 49 }

		
		-- 1.3.6.1.4.1.5504.5.14.1.24.1.50
		zhoneGponOltStatisticsUpstreamTmQ1ValidPkts OBJECT-TYPE
			SYNTAX Counter64
			MAX-ACCESS read-only
			STATUS current
			DESCRIPTION
				"UpstreamTmQ1ValidPkts counter."
			::= { zhoneGponOltStatisticsEntry 50 }

		
		-- 1.3.6.1.4.1.5504.5.14.1.24.1.51
		zhoneGponOltStatisticsUpstreamTmQ1DroppedPkts OBJECT-TYPE
			SYNTAX Counter64
			MAX-ACCESS read-only
			STATUS current
			DESCRIPTION
				"UpstreamTmQ1DroppedPkts counter."
			::= { zhoneGponOltStatisticsEntry 51 }

		
		-- 1.3.6.1.4.1.5504.5.14.1.24.1.52
		zhoneGponOltStatisticsUpstreamTmQ2ValidPkts OBJECT-TYPE
			SYNTAX Counter64
			MAX-ACCESS read-only
			STATUS current
			DESCRIPTION
				"UpstreamTmQ2ValidPkts counter."
			::= { zhoneGponOltStatisticsEntry 52 }

		
		-- 1.3.6.1.4.1.5504.5.14.1.24.1.53
		zhoneGponOltStatisticsUpstreamTmQ2DroppedPkts OBJECT-TYPE
			SYNTAX Counter64
			MAX-ACCESS read-only
			STATUS current
			DESCRIPTION
				"UpstreamTmQ2DroppedPkts"
			::= { zhoneGponOltStatisticsEntry 53 }

		
		-- 1.3.6.1.4.1.5504.5.14.1.24.1.54
		zhoneGponOltStatisticsUpstreamTmQ3ValidPkts OBJECT-TYPE
			SYNTAX Counter64
			MAX-ACCESS read-only
			STATUS current
			DESCRIPTION
				"UpstreamTmQ3ValidPkts counter."
			::= { zhoneGponOltStatisticsEntry 54 }

		
		-- 1.3.6.1.4.1.5504.5.14.1.24.1.55
		zhoneGponOltStatisticsUpstreamTmQ3DroppedPkts OBJECT-TYPE
			SYNTAX Counter64
			MAX-ACCESS read-only
			STATUS current
			DESCRIPTION
				"UpstreamTmQ3DroppedPkts counter."
			::= { zhoneGponOltStatisticsEntry 55 }

		
		-- 1.3.6.1.4.1.5504.5.14.1.24.1.56
		zhoneGponOltStatisticsUpstreamTmQ4ValidPkts OBJECT-TYPE
			SYNTAX Counter64
			MAX-ACCESS read-only
			STATUS current
			DESCRIPTION
				"UpstreamTmQ4ValidPkts counter."
			::= { zhoneGponOltStatisticsEntry 56 }

		
		-- 1.3.6.1.4.1.5504.5.14.1.24.1.57
		zhoneGponOltStatisticsUpstreamTmQ4DroppedPkts OBJECT-TYPE
			SYNTAX Counter64
			MAX-ACCESS read-only
			STATUS current
			DESCRIPTION
				"UpstreamTmQ4DroppedPkts counter."
			::= { zhoneGponOltStatisticsEntry 57 }

		
		-- 1.3.6.1.4.1.5504.5.14.1.24.1.58
		zhoneGponOltStatisticsUpstreamTmQ5ValidPkts OBJECT-TYPE
			SYNTAX Counter64
			MAX-ACCESS read-only
			STATUS current
			DESCRIPTION
				"UpstreamTmQ5ValidPkts counter."
			::= { zhoneGponOltStatisticsEntry 58 }

		
		-- 1.3.6.1.4.1.5504.5.14.1.24.1.59
		zhoneGponOltStatisticsUpstreamTmQ5DroppedPkts OBJECT-TYPE
			SYNTAX Counter64
			MAX-ACCESS read-only
			STATUS current
			DESCRIPTION
				"UpstreamTmQ5DroppedPkts counter."
			::= { zhoneGponOltStatisticsEntry 59 }

		
		-- 1.3.6.1.4.1.5504.5.14.1.24.1.60
		zhoneGponOltStatisticsUpstreamTmQ6ValidPkts OBJECT-TYPE
			SYNTAX Counter64
			MAX-ACCESS read-only
			STATUS current
			DESCRIPTION
				"UpstreamTmQ6ValidPkts counter."
			::= { zhoneGponOltStatisticsEntry 60 }

		
		-- 1.3.6.1.4.1.5504.5.14.1.24.1.61
		zhoneGponOltStatisticsUpstreamTmQ6DroppedPkts OBJECT-TYPE
			SYNTAX Counter64
			MAX-ACCESS read-only
			STATUS current
			DESCRIPTION
				"UpstreamTmQ6DroppedPkts counter."
			::= { zhoneGponOltStatisticsEntry 61 }

		
		-- 1.3.6.1.4.1.5504.5.14.1.24.1.62
		zhoneGponOltStatisticsUpstreamTmQ7ValidPkts OBJECT-TYPE
			SYNTAX Counter64
			MAX-ACCESS read-only
			STATUS current
			DESCRIPTION
				"UpstreamTmQ7ValidPkts counter."
			::= { zhoneGponOltStatisticsEntry 62 }

		
		-- 1.3.6.1.4.1.5504.5.14.1.24.1.63
		zhoneGponOltStatisticsUpstreamTmQ7DroppedPkts OBJECT-TYPE
			SYNTAX Counter64
			MAX-ACCESS read-only
			STATUS current
			DESCRIPTION
				"UpstreamTmQ7DroppedPkts counter."
			::= { zhoneGponOltStatisticsEntry 63 }

		
		-- 1.3.6.1.4.1.5504.5.14.1.24.1.64
		zhoneGponOltStatisticsClearStats OBJECT-TYPE
			SYNTAX TruthValue
			MAX-ACCESS read-write
			STATUS current
			DESCRIPTION
				"Clear all statistics for the selected interface."
			::= { zhoneGponOltStatisticsEntry 64 }

		
		-- 1.3.6.1.4.1.5504.5.14.1.25
		zhoneGponUpstreamOntStatisticsTable OBJECT-TYPE
			SYNTAX SEQUENCE OF ZhoneGponUpstreamOntStatisticsEntry
			MAX-ACCESS not-accessible
			STATUS current
			DESCRIPTION
				"Per ONT Upstream Statistics provided by Broadlight."
			::= { zhoneGponObjectID 25 }

		
		-- 1.3.6.1.4.1.5504.5.14.1.25.1
		zhoneGponUpstreamOntStatisticsEntry OBJECT-TYPE
			SYNTAX ZhoneGponUpstreamOntStatisticsEntry
			MAX-ACCESS not-accessible
			STATUS current
			DESCRIPTION
				"Per ONT Upstream Statistics provided by Broadlight."
			INDEX { zhoneGponOltOnuIfIndex }
			::= { zhoneGponUpstreamOntStatisticsTable 1 }

		
		ZhoneGponUpstreamOntStatisticsEntry ::=
			SEQUENCE { 
				zhoneGponUpstreamOntStatisticsUpstreamBipErrors
					Counter64,
				zhoneGponUpstreamOntStatisticsFecCorrectedBytes
					Counter64,
				zhoneGponUpstreamOntStatisticsFecCorrectedCodewords
					Counter64,
				zhoneGponUpstreamOntStatisticsFecUncorrectedCodewords
					Counter64,
				zhoneGponUpstreamOntStatisticsTotalRxCodewords
					Counter64,
				zhoneGponUpstreamOntStatisticsUnreceivedBursts
					Counter64,
				zhoneGponUpstreamOntStatisticsBipErrors
					Counter64,
				zhoneGponUpstreamOntStatisticsRemoteBipErrors
					Counter64,
				zhoneGponUpstreamOntStatisticsDriftOfWindowIndications
					Counter64,
				zhoneGponUpstreamOntStatisticsMessageErrorMessage
					Counter64,
				zhoneGponUpstreamOntStatisticsClearStats
					TruthValue
			 }

		-- 1.3.6.1.4.1.5504.5.14.1.25.1.1
		zhoneGponUpstreamOntStatisticsUpstreamBipErrors OBJECT-TYPE
			SYNTAX Counter64
			MAX-ACCESS read-only
			STATUS current
			DESCRIPTION
				"UpstreamOntStatisticsUpstreamBipErrors counter."
			::= { zhoneGponUpstreamOntStatisticsEntry 1 }

		
		-- 1.3.6.1.4.1.5504.5.14.1.25.1.2
		zhoneGponUpstreamOntStatisticsFecCorrectedBytes OBJECT-TYPE
			SYNTAX Counter64
			MAX-ACCESS read-only
			STATUS current
			DESCRIPTION
				"UpstreamOntStatisticsFecCorrectedBytes counter."
			::= { zhoneGponUpstreamOntStatisticsEntry 2 }

		
		-- 1.3.6.1.4.1.5504.5.14.1.25.1.3
		zhoneGponUpstreamOntStatisticsFecCorrectedCodewords OBJECT-TYPE
			SYNTAX Counter64
			MAX-ACCESS read-only
			STATUS current
			DESCRIPTION
				"UpstreamOntStatisticsFecCorrectedCodewords counter."
			::= { zhoneGponUpstreamOntStatisticsEntry 3 }

		
		-- 1.3.6.1.4.1.5504.5.14.1.25.1.4
		zhoneGponUpstreamOntStatisticsFecUncorrectedCodewords OBJECT-TYPE
			SYNTAX Counter64
			MAX-ACCESS read-only
			STATUS current
			DESCRIPTION
				"UpstreamOntStatisticsFecUncorrectedCodewords counter."
			::= { zhoneGponUpstreamOntStatisticsEntry 4 }

		
		-- 1.3.6.1.4.1.5504.5.14.1.25.1.5
		zhoneGponUpstreamOntStatisticsTotalRxCodewords OBJECT-TYPE
			SYNTAX Counter64
			MAX-ACCESS read-only
			STATUS current
			DESCRIPTION
				"UpstreamOntStatisticsTotalRxCodewords counter."
			::= { zhoneGponUpstreamOntStatisticsEntry 5 }

		
		-- 1.3.6.1.4.1.5504.5.14.1.25.1.6
		zhoneGponUpstreamOntStatisticsUnreceivedBursts OBJECT-TYPE
			SYNTAX Counter64
			MAX-ACCESS read-only
			STATUS current
			DESCRIPTION
				"UpstreamOntStatisticsUnreceivedBursts counter."
			::= { zhoneGponUpstreamOntStatisticsEntry 6 }

		
		-- 1.3.6.1.4.1.5504.5.14.1.25.1.7
		zhoneGponUpstreamOntStatisticsBipErrors OBJECT-TYPE
			SYNTAX Counter64
			MAX-ACCESS read-only
			STATUS current
			DESCRIPTION
				"UpstreamOntStatisticsBipErrors counter."
			::= { zhoneGponUpstreamOntStatisticsEntry 7 }

		
		-- 1.3.6.1.4.1.5504.5.14.1.25.1.8
		zhoneGponUpstreamOntStatisticsRemoteBipErrors OBJECT-TYPE
			SYNTAX Counter64
			MAX-ACCESS read-only
			STATUS current
			DESCRIPTION
				"UpstreamOntStatisticsRemoteBipErrors counter."
			::= { zhoneGponUpstreamOntStatisticsEntry 8 }

		
		-- 1.3.6.1.4.1.5504.5.14.1.25.1.9
		zhoneGponUpstreamOntStatisticsDriftOfWindowIndications OBJECT-TYPE
			SYNTAX Counter64
			MAX-ACCESS read-only
			STATUS current
			DESCRIPTION
				"UpstreamOntStatisticsDriftOfWindowIndications counter."
			::= { zhoneGponUpstreamOntStatisticsEntry 9 }

		
		-- 1.3.6.1.4.1.5504.5.14.1.25.1.10
		zhoneGponUpstreamOntStatisticsMessageErrorMessage OBJECT-TYPE
			SYNTAX Counter64
			MAX-ACCESS read-only
			STATUS current
			DESCRIPTION
				"UpstreamOntStatisticsMessageErrorMessage counter."
			::= { zhoneGponUpstreamOntStatisticsEntry 10 }

		
		-- 1.3.6.1.4.1.5504.5.14.1.25.1.11
		zhoneGponUpstreamOntStatisticsClearStats OBJECT-TYPE
			SYNTAX TruthValue
			MAX-ACCESS read-write
			STATUS current
			DESCRIPTION
				"Clear all statistics for the selected interface."
			::= { zhoneGponUpstreamOntStatisticsEntry 11 }

		
		-- 1.3.6.1.4.1.5504.9.1.10
		zhoneGponOltConfigGroup OBJECT-GROUP
			OBJECTS { zhoneGponOltConfigMaxRtPropagationDelay, zhoneGponOltConfigMaxOnuResponseTime, zhoneGponOltConfigPreassignedEqD, zhoneGponOltConfigLosAlpha, zhoneGponOltConfigLofAlpha, 
				zhoneGponOltConfigLoamAlpha, zhoneGponOltConfigScrambler, zhoneGponOltConfigFecMode, zhoneGponOltConfigAutoLearn, zhoneGponOltConfigPowerLevel, 
				zhoneGponOltConfigGuardBitCount, zhoneGponOltConfigDbaMode, zhoneGponOltConfigGemBlockSize, zhoneGponOltConfigUsBerInterval, zhoneGponOltConfigDsBerInterval, 
				zhoneGponOltConfigBerSfThreshold, zhoneGponOltConfigBerSdThreshold, zhoneGponOltConfigFecRequest, zhoneGponOltConfigKeyExchange, zhoneGponOltConfigMinRtPropagationDelay, 
				zhoneGponOltConfigMinOnuResponseTime, zhoneGponOltConfigEqDMeasureCycles, zhoneGponOltConfigDriftControlInterval, zhoneGponOltConfigDriftControlLimit, zhoneGponOltConfigAllocCycleLength, 
				zhoneGponOltConfigMinUsAlloc, zhoneGponOltConfigAckTimeout, zhoneGponOltConfigPlsMaxAllocSize, zhoneGponOltConfigDbaCycle, zhoneGponOltConfigSrDbaReportingBlockSize, 
				zhoneGponOltConfigProtectionSwitchoverTimer, zhoneGponOltConfigPreambleOverride, zhoneGponOltConfigPreambleType0, zhoneGponOltConfigPreambleType1, zhoneGponOltConfigPreambleType3PreRange, 
				zhoneGponOltConfigPreambleType3PostRange, zhoneGponOltConfigPreambleType3Pattern, zhoneGponOltConfigBipErrorMonitoring, zhoneGponOltConfigBipErrorsPerSampleThreshold, zhoneGponOltConfigBipErroredSamplesThreshold, 
				zhoneGponOltConfigBipMaxSampleGap, zhoneGponOltConfigRogueOnuDetectFrequency, zhoneGponOltConfigKeyExchangeInterval, zhoneGponOltConfigRogueOnuRxPowerThreshold, zhoneGponOltConfigRogueOnuDetection
				 }
			STATUS current
			DESCRIPTION 
				"GPON OLT Config group"
			::= { zhoneGroups 10 }

		
		-- 1.3.6.1.4.1.5504.9.1.11
		zhoneGponOnuConfigGroup OBJECT-GROUP
			OBJECTS { zhoneGponOltOnuConfigSerialNoVendorId, zhoneGponOltOnuConfigSerialNoVendorSpecific, zhoneGponOltOnuConfigPassword, zhoneGponOltOnuConfigAutoLearn, zhoneGponOltOnuConfigPowerLevel, 
				zhoneGponOltOnuConfigUsBerInterval, zhoneGponOltOnuConfigDsBerInterval, zhoneGponOltOnuConfigOnuAdded, zhoneGponOltOnuConfigOmciFileName, zhoneGponOltOnuConfigMEProfileName, 
				zhoneGponOltOnuConfigGenericProfileName, zhoneGponOltOnuConfigPhysicalTraps, zhoneGponOltOnuConfigOntTraps, zhoneGponOltOnuConfigLineStatusTraps, zhoneGponOltOnuConfigAutoUpgrade, 
				zhoneGponOltOnuConfigSerialNoVendorSpecificFsan, zhoneGponOltOnuConfigUseRegId, zhoneGponOltOnuConfigModel, zhoneGponOltOnuConfigOntVersion, zhoneGponOltOnuConfigImageVersionActive, 
				zhoneGponOltOnuConfigImageVersionStandby, zhoneGponOltOnuConfigUsRxPowerMonitoring, zhoneGponOltOnuConfigUsRxPowerHighThreshold, zhoneGponOltOnuConfigUsRxPowerLowThreshold, zhoneGponOltOnuConfigDbaStatusReporting, 
				zhoneGponOltOnuConfigOmciDataSync, zhoneGponOltOnuConfigSnmpDataSync, zhoneGponOltOnuConfigNextAvailableGemPort, zhoneGponOltOnuConfigAutoConfigState, zhoneGponOltOnuConfigLinkStatusAlarmSeverity, 
				zhoneGponOltOnuConfigOltRxPower, zhoneGponOltOnuConfigOntRxPower, zhoneGponOltOnuConfigOnuDistance, zhoneGponOltOnuConfigSnmpAllocIdInfo }
			STATUS current
			DESCRIPTION 
				"GPON ONU Config group"
			::= { zhoneGroups 11 }

		
		-- 1.3.6.1.4.1.5504.9.1.12
		zhoneGponPortConfigGroup OBJECT-GROUP
			OBJECTS { zhoneGponPortConfigRowStatus, zhoneGponPortConfigMulticast, zhoneGponPortConfigEncrypted, zhoneGponPortConfigDirection, zhoneGponPortConfigTrafficProfile, 
				zhoneGponPortConfigRowShelf, zhoneGponPortConfigRowSlot, zhoneGponPortConfigRowOlt, zhoneGponPortConfigRowPort, zhoneGponPortConfigRowTrafficProfile, 
				zhoneGponPortConfigRowOnuId, zhoneGponPortConfigTrafficManagementProfileIndex, zhoneGponPortConfigAllocIdInfo }
			STATUS current
			DESCRIPTION 
				"GPON Port Config group"
			::= { zhoneGroups 12 }

		
		-- 1.3.6.1.4.1.5504.9.1.13
		zhoneGponAllocIdGroup OBJECT-GROUP
			OBJECTS { zhoneGponAllocIdRowStatus, zhoneGponAllocIdOnuId, zhoneGponAllocIdGuaranteedBw, zhoneGponAllocIdTrafficClass, zhoneGponAllocIdCompensated
				 }
			STATUS current
			DESCRIPTION 
				"GPON Allocation ID group"
			::= { zhoneGroups 13 }

		
		-- 1.3.6.1.4.1.5504.9.1.14
		zhoneGponSerialNoGroup OBJECT-GROUP
			OBJECTS { zhoneGponSerialNoVendorId, zhoneGponSerialNoVendorSpecific, zhoneGponSerialNoTimeStamp, zhoneGponSerialNoModelId }
			STATUS current
			DESCRIPTION 
				"GPON Serial Number group"
			::= { zhoneGroups 14 }

		
		-- 1.3.6.1.4.1.5504.9.1.15
		zhoneGponOnuStatusGroup OBJECT-GROUP
			OBJECTS { zhoneGponOnuStatusWord, zhoneGponOnuOmciState, zhoneGponOnuOpticRssi, zhoneGponOntRxPower, zhoneGponOntVersion
				 }
			STATUS current
			DESCRIPTION 
				"GPON ONU Status group"
			::= { zhoneGroups 15 }

		
		-- 1.3.6.1.4.1.5504.9.1.16
		zhoneOnuOmciMeProfileGroup OBJECT-GROUP
			OBJECTS { zhoneOnuOmciMEProfileRowStatus, zhoneOnuOmciMEProfileName, zhoneOnuOmciMEProfileOmciCommands, zhoneOnuOmciMEProfileFileName }
			STATUS current
			DESCRIPTION 
				"GPON OMCI ONU ME Profile group"
			::= { zhoneGroups 16 }

		
		-- 1.3.6.1.4.1.5504.9.1.17
		zhoneOnuOmciGenericProfileGroup OBJECT-GROUP
			OBJECTS { zhoneOnuOmciGenericProfileRowStatus, zhoneOnuOmciGenericProfileName, zhoneOnuOmciGenericProfileOmciCommands, zhoneOnuOmciGenericProfileFileName, zhoneOnuOmciGenericProfileMESrcProfileName
				 }
			STATUS current
			DESCRIPTION 
				"GPON OMCI ONU Generic Profile group"
			::= { zhoneGroups 17 }

		
		-- 1.3.6.1.4.1.5504.9.1.18
		zhoneOnuOmciSpecificProfileGroup OBJECT-GROUP
			OBJECTS { zhoneOnuOmciSpecificProfileRowStatus, zhoneOnuOmciSpecificProfileOmciCommands, zhoneOnuOmciSpecificProfileMESrcProfileName, zhoneOnuOmciSpecificProfileFileName }
			STATUS current
			DESCRIPTION 
				"GPON OMCI ONU Specific Profile group"
			::= { zhoneGroups 18 }

		
		-- 1.3.6.1.4.1.5504.9.1.19
		zhoneGponOmciOnuAlarmsGroup OBJECT-GROUP
			OBJECTS { zhoneGponOmciOnuAlarmsText, zhoneGponOmciStatsCurrentText, zhoneGponOmciStatsPreviousText }
			STATUS current
			DESCRIPTION 
				"GPON OMCI ONU Alarms group"
			::= { zhoneGroups 19 }

		
		-- 1.3.6.1.4.1.5504.9.1.20
		zhoneGponTrapGroup NOTIFICATION-GROUP
			NOTIFICATIONS { zhoneGponSerialNumberFound, zhoneGponSerialNumberLost, zhoneGponOnuLineStatusChange, zhoneGponOmciOnuAlarmsTrap, zhoneGponOmciOnuDownloadStatusChange, 
				zhoneGponOltOpticsAlarmsTrap, zhoneGponOnuError, zhoneGponRogueOnuTrap, zhoneGponRssiRogueOnuTrap, zhoneGponOltStatusWordTrap, 
				zhoneGponOnuAutoAssign }
			STATUS current
			DESCRIPTION 
				"Gpon Trap objects."
			::= { zhoneGroups 20 }

		
		-- 1.3.6.1.4.1.5504.9.1.21
		zhoneGponTrafficProfileGroup OBJECT-GROUP
			OBJECTS { zhoneGponTrafficProfileRowStatus, zhoneGponTrafficProfileClass, zhoneGponTrafficProfileDbaEnabled, zhoneGponTrafficProfileExtraUsBwType, zhoneGponTrafficProfileMaxUsBw, 
				zhoneGponTrafficProfileDbaAssuredUsBw, zhoneGponTrafficProfileDbaFixedUsCbrBw, zhoneGponTrafficProfileDbaFixedUsUbrBw, zhoneGponTrafficProfileCompensated, zhoneGponTrafficProfileGuaranteedUpstreamBw, 
				zhoneGponTrafficProfileShared }
			STATUS current
			DESCRIPTION 
				"Gpon Traffic Profile objects."
			::= { zhoneGroups 21 }

		
		-- 1.3.6.1.4.1.5504.9.1.22
		zhoneGponPortStatusGroup OBJECT-GROUP
			OBJECTS { zhoneGponPortStatusAllocId, zhoneGponPortStatusDbaStatus }
			STATUS current
			DESCRIPTION 
				"Gpon Port Status objects."
			::= { zhoneGroups 22 }

		
		-- 1.3.6.1.4.1.5504.9.1.24
		zhoneGponOmciStatusGroup OBJECT-GROUP
			OBJECTS { zhoneGponOmciStatusText, zhoneGponOnuDistance }
			STATUS current
			DESCRIPTION 
				"Gpon Omci Status objects."
			::= { zhoneGroups 24 }

		
		-- 1.3.6.1.4.1.5504.9.1.25
		zhoneGponOmciOnuRebootGroup OBJECT-GROUP
			OBJECTS { zhoneGponOmciOnuReboot }
			STATUS current
			DESCRIPTION 
				"Gpon Omci Reboot objects."
			::= { zhoneGroups 25 }

		
		-- 1.3.6.1.4.1.5504.9.1.26
		zhoneGponOmciOnuPortAdminGroup OBJECT-GROUP
			OBJECTS { zhoneGponOmciOnuPortAdminState, zhoneGponOmciOnuPortAdminAutoDetect }
			STATUS current
			DESCRIPTION 
				"Gpon Port Admin objects."
			::= { zhoneGroups 26 }

		
		-- 1.3.6.1.4.1.5504.9.1.27
		zhoneGponOmciOnuImageUpgradeGroup OBJECT-GROUP
			OBJECTS { zhoneGponOmciOnuPortAdminState, zhoneGponOmciOnuImageUpgradeAction, zhoneOnuOmciImageUpgradeFilename, zhoneGponOmciOnuImageUpgradePartition, zhoneOnuOmciImageUpgradeImageVersionPartition0, 
				zhoneOnuOmciImageUpgradeImageVersionPartition1, zhoneOnuOmciImageUpgradeIsCommittedPartition0, zhoneOnuOmciImageUpgradeIsCommittedPartition1, zhoneOnuOmciImageUpgradeIsActivatedPartition0, zhoneOnuOmciImageUpgradeIsActivatedPartition1, 
				zhoneOnuOmciImageUpgradeIsValidPartition0, zhoneOnuOmciImageUpgradeIsValidPartition1, zhoneOnuOmciImageUpgradeDownloadStatus, zhoneGponUpgradeModel, zhoneGponUpgradeStartTime, 
				zhoneGponUpgradeIfIndex, zhoneGponUpgradeByStateOnuState, zhoneGponOmciOnuImageUpgradeModel, zhoneGponOmciOnuImageUpgradeStartTime, zhoneGponOmciOnuImageUpgradeWillBeActivated, 
				zhoneGponOmciOnuImageUpgradeWillBeCommitted, zhoneGponUpgradeByStateWillBeActivated, zhoneGponUpgradeByStateWillBeCommitted, zhoneGponUpgradeProgressPercentage, zhoneGponOmciOnuImageDownloadProgressPercentage, 
				zhoneGponOmciOnuImageUpgradeMethod, zhoneGponUpgradeByStateMethod, zhoneGponUpgradeByStatePartition, zhoneGponOmciOnuImageUpgradeType, zhoneGponUpgradeByStateUpgradeType
				 }
			STATUS current
			DESCRIPTION 
				"Group of ONU Image Upgrade objects"
			::= { zhoneGroups 27 }

		
		-- 1.3.6.1.4.1.5504.9.1.28
		zhoneGponOltStatusGroup OBJECT-GROUP
			OBJECTS { zhoneGponOltOpticTemperature, zhoneGponOltOpticVoltage, zhoneGponOltOpticTxBiasCurrent, zhoneGponOltOpticTxPower, zhoneGponOltOpticStatus, 
				zhoneGponOltOpticAlarms, zhoneGponOltStatusWord, zhoneGponOltConfiguredOnuCount, zhoneGponOltActiveOnuCount }
			STATUS current
			DESCRIPTION 
				"GPON OLT Status Group."
			::= { zhoneGroups 28 }

		
		-- 1.3.6.1.4.1.5504.9.1.29
		zhoneGponeOltDbaStatusGroup OBJECT-GROUP
			OBJECTS { zhoneGponOltDbaTotalAvailableBw, zhoneGponOltDbaTotalAvailableCompensatedCbrBw, zhoneGponOltDbaAllocatedUbrBw, zhoneGponOltDbaAllocatedCbrBw, zhoneGponOltDbaAllocatedCompensatedCbrBw, 
				zhoneGponOltDbaAllocatedAssuredBw, zhoneGponOltDbaAllocatedNonAssuredBw, zhoneGponOltDbaAllocatedBestEffortBw, zhoneGponOltDbaMaxAllocIds, zhoneGponOltDbaAvailAllocIds, 
				zhoneGponOltDbaUsedAllocIds, zhoneGponOltDbaMaxDbaAllocIds, zhoneGponOltDbaAvailDbaAllocIds, zhoneGponOltDbaUsedDbaAllocIds, zhoneGponOltDbaTotalOltGemPorts, 
				zhoneGponOltDbaLastCacRc }
			STATUS current
			DESCRIPTION 
				"GPON OLT Dba Status Group."
			::= { zhoneGroups 29 }

		
		-- 1.3.6.1.4.1.5504.9.1.31
		zhoneGponCmdGroup OBJECT-GROUP
			OBJECTS { zhoneGponCmdOperation, zhoneGponCmdSlot, zhoneGponCmdOlt, zhoneGponCmdOnu, zhoneGponCmdFilterMask, 
				zhoneGponCmdShelf }
			STATUS current
			DESCRIPTION 
				"GPON Command objects"
			::= { zhoneGroups 31 }

		
		-- 1.3.6.1.4.1.5504.9.1.32
		zhoneGponOltStatisticsGroup OBJECT-GROUP
			OBJECTS { zhoneGponOltStatisticsUpstreamValidGemFrames, zhoneGponOltStatisticsUpstreamDiscardedFrames, zhoneGponOltStatisticsUpstreamGemFrames, zhoneGponOltStatisticsUpstreamOmciFrames, zhoneGponOltStatisticsUpstreamPloamFrames, 
				zhoneGponOltStatisticsUpstreamIdlePloamFrames, zhoneGponOltStatisticsDownstreamValidGemFrames, zhoneGponOltStatisticsDownstreamDiscardedFrames, zhoneGponOltStatisticsDownstreamGemFrames, zhoneGponOltStatisticsDownstreamOmciFrames, 
				zhoneGponOltStatisticsDownstreamPloamFrames, zhoneGponOltStatisticsDownstreamPonValidEthernetPkts, zhoneGponOltStatisticsDownstreamPonCpuPkts, zhoneGponOltStatisticsDownstreamTxBytes, zhoneGponOltStatisticsUpstreamPonValidNotIdlePloams, 
				zhoneGponOltStatisticsUpstreamPonErrorPloams, zhoneGponOltStatisticsUpstreamPonInvalidPkts, zhoneGponOltStatisticsUpstreamDroppedPktsInactivePorts, zhoneGponOltStatisticsUpstreamDroppedPloamsFifoFull, zhoneGponOltStatisticsDownstreamTmValidPkts, 
				zhoneGponOltStatisticsDownstreamTmCrcPkts, zhoneGponOltStatisticsDownstreamTmDroppedCpuPkts, zhoneGponOltStatisticsDownstreamTmMacLookupMiss, zhoneGponOltStatisticsDownstreamTmPktsForwardedFromHmToPon, zhoneGponOltStatisticsDownstreamTmPktsDroppedGemPidNotEnabled, 
				zhoneGponOltStatisticsDownstreamTmQ0ValidPkts, zhoneGponOltStatisticsDownstreamTmQ0DroppedPkts, zhoneGponOltStatisticsDownstreamTmQ1ValidPkts, zhoneGponOltStatisticsDownstreamTmQ1DroppedPkts, zhoneGponOltStatisticsDownstreamTmQ2ValidPkts, 
				zhoneGponOltStatisticsDownstreamTmQ2DroppedPkts, zhoneGponOltStatisticsDownstreamTmQ3ValidPkts, zhoneGponOltStatisticsDownstreamTmQ3DroppedPkts, zhoneGponOltStatisticsDownstreamTmQ4ValidPkts, zhoneGponOltStatisticsDownstreamTmQ4DroppedPkts, 
				zhoneGponOltStatisticsDownstreamTmQ5ValidPkts, zhoneGponOltStatisticsDownstreamTmQ5DroppedPkts, zhoneGponOltStatisticsDownstreamTmQ6ValidPkts, zhoneGponOltStatisticsDownstreamTmQ6DroppedPkts, zhoneGponOltStatisticsDownstreamTmQ7ValidPkts, 
				zhoneGponOltStatisticsDownstreamTmQ7DroppedPkts, zhoneGponOltStatisticsUpstreamTmDroppedCpuPkts, zhoneGponOltStatisticsUpstreamTmDroppedPktsCrcError, zhoneGponOltStatisticsUpstreamTmDroppedPktsSecurity, zhoneGponOltStatisticsUpstreamTmLearnFailures, 
				zhoneGponOltStatisticsUpstreamTmQ0ValidPkts, zhoneGponOltStatisticsUpstreamTmQ0DroppedPkts, zhoneGponOltStatisticsUpstreamTmQ1ValidPkts, zhoneGponOltStatisticsUpstreamTmQ1DroppedPkts, zhoneGponOltStatisticsUpstreamTmQ2ValidPkts, 
				zhoneGponOltStatisticsUpstreamTmQ2DroppedPkts, zhoneGponOltStatisticsUpstreamTmQ3ValidPkts, zhoneGponOltStatisticsUpstreamTmQ3DroppedPkts, zhoneGponOltStatisticsUpstreamTmQ4ValidPkts, zhoneGponOltStatisticsUpstreamTmQ4DroppedPkts, 
				zhoneGponOltStatisticsUpstreamTmQ5ValidPkts, zhoneGponOltStatisticsUpstreamTmQ5DroppedPkts, zhoneGponOltStatisticsUpstreamTmQ6ValidPkts, zhoneGponOltStatisticsUpstreamTmQ6DroppedPkts, zhoneGponOltStatisticsUpstreamTmQ7ValidPkts, 
				zhoneGponOltStatisticsUpstreamTmQ7DroppedPkts, zhoneGponOltStatisticsUpstreamPonValidPkts, zhoneGponOltStatisticsClearStats }
			STATUS current
			DESCRIPTION 
				"Gpon OLT Statistics objects."
			::= { zhoneGroups 32 }

		
		-- 1.3.6.1.4.1.5504.9.1.33
		zhoneGponUpstreamOntStatisticsGroup OBJECT-GROUP
			OBJECTS { zhoneGponUpstreamOntStatisticsUpstreamBipErrors, zhoneGponUpstreamOntStatisticsFecCorrectedBytes, zhoneGponUpstreamOntStatisticsFecCorrectedCodewords, zhoneGponUpstreamOntStatisticsFecUncorrectedCodewords, zhoneGponUpstreamOntStatisticsTotalRxCodewords, 
				zhoneGponUpstreamOntStatisticsUnreceivedBursts, zhoneGponUpstreamOntStatisticsBipErrors, zhoneGponUpstreamOntStatisticsRemoteBipErrors, zhoneGponUpstreamOntStatisticsDriftOfWindowIndications, zhoneGponUpstreamOntStatisticsMessageErrorMessage, 
				zhoneGponUpstreamOntStatisticsClearStats }
			STATUS current
			DESCRIPTION 
				"Gpon Upstream ONT Statistics objects."
			::= { zhoneGroups 33 }

		
		-- 1.3.6.1.4.1.5504.9.1.34
		zhoneGponDeprecated OBJECT-GROUP
			OBJECTS { zhoneGponOltStatisticsDownstreamIdlePloamFrames }
			STATUS deprecated
			DESCRIPTION 
				"Gpon Deprecated objects."
			::= { zhoneGroups 34 }

		
	
	END

--
-- phyGPON.mib
--
