--
-- phyCPE.mib
-- MIB generated by MG-SOFT Visual MIB Builder Version 3.0 Build 285
-- Monday, November 06, 2017 at 22:36:56
--

	Zhone-CPE-MIB DEFINITIONS ::= BEGIN
 
		IMPORTS
			InterfaceIndex			
				FROM IF-MIB			
			InetAddress, InetAddressIPv6			
				FROM INET-ADDRESS-MIB			
			SnmpAdminString			
				FROM SNMP-FRAMEWORK-MIB			
			OBJECT-GROUP			
				FROM SNMPv2-CONF			
			IpAddress, IpAddress, Integer32, Unsigned32, OBJECT-TYPE, 
			MODULE-IDENTITY, OBJECT-IDENTITY			
				FROM SNMPv2-SMI			
			PhysAddress, RowStatus, TruthValue, MacAddress, TEXTUAL-CONVENTION			
				FROM SNMPv2-TC			
			zhoneRegPls, zhoneRegCpe, zhoneRegMux, zhoneRegSechtor, zhoneRegWtn, 
			zhoneRegMalc, zhonePls, zhoneZedge, zhoneZplex, sechtor100, 
			sechtor300, zhoneWtn, zhoneMalc, zhoneZmsProduct, zhoneSystem, 
			zhoneShelf, zhoneCard, zhoneSubscriber, zhoneInterfaceTranslation, zhoneInterfaceGroup, 
			zhoneMasterAgent, zhoneTrapModules, zhoneGenWtn, zhoneZAP, zhoneVoiceStats, 
			zhoneIp, zhoneAtm, zhoneVoice, zhoneVoip, zhonePpp, 
			zhoneIma, zhoneBridge, zhoneVideo, zhoneIsdn, zhoneCes, 
			zhoneSs7, zhoneClass5, zhoneBonding, zhoneEnet, zhoneDsx, 
			zhoneOcx, zhoneDsl, zhoneConsole, zhoneRadio, zhoneSonet, 
			zhoneDs3Ext, zhoneLineTypes, zhoneApon, zhoneVdsl, zhoneGpon, 
			zhoneWdm, zhoneCpe, zhoneModules, zhoneShelfIndex, zhoneSlotIndex, 
			zhoneGroups, zhoneShelfSlotGroup, zhoneShelfSlotCompliance, apsMIB, sipTC, 
			sipCommonMIB, sipUAMIB, pktcIetfSigMib, efmOamMIB, efmCuMIB, 
			zhoneDrafts			
				FROM Zhone			
			ZhoneAdminString, ZhoneRowStatus, ZhoneEnabledFlag, ZhoneAdminState, TpType, 
			ZhoneAlarmSeverity, ZhoneCpeIfName, ZhoneMacIpAddrType			
				FROM Zhone-TC;
	
	
-- /vob/zhonetools/bin/pahrser.pl rfc2233.mib rfc2571.mib Zhone.mib 
-- Zhone-TC.mib INET-ADDRESS-MIB.mib phyCPE.mib 
-- 
-- /vob/EPILOGUE/binaries/emissary/solaris/mibcomp rfc2514.mib 
-- rfc1907.mib iftype.mib rfc2233.mib rfc2571.mib INET-ADDRESS-MIB.mib
-- Zhone.mib Zhone-TC.mib -stub -o cpeHdlrs.c phyCPE.mib
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
-- 
		-- 1.3.6.1.4.1.5504.6.118
		zhoneCpeMIB MODULE-IDENTITY 
			LAST-UPDATED "201710230507Z"		-- October 23, 2017 at 05:07 GMT
			ORGANIZATION 
				"Zhone Technologies, Inc."
			CONTACT-INFO 
				"Zhone Technologies, Inc.
				@ Zhone Way
				7001 Oakport Street
				Oakland, CA  94621
				USA
				Toll-Free: +1 877-ZHONE20 (+1 877-946-6320)
				Tel: +1-510-777-7000
				Fax: +1-510-777-7001
				E-mail: support@zhone.com
				"
			DESCRIPTION 
				"This is the Zhone CPE mib which contains SNMP objects for the 
				CPE voice and pseudowire."
			REVISION "201710230505Z"		-- October 23, 2017 at 05:05 GMT
			DESCRIPTION 
				"Added default value for destMac field
				of cpePweSubscriber profile as
				{000147000000H}."
			REVISION "201707100221Z"		-- July 10, 2017 at 02:21 GMT
			DESCRIPTION 
				"Added zhoneCpePppoeIdleDisconnectTime object to
				zhoneCpePppoe Table"
			REVISION "201705232352Z"		-- May 23, 2017 at 23:52 GMT
			DESCRIPTION 
				"Added radius nas identifer/tr69 username & password
				to zhoneCpeSystem group.
				Added tr69 authentication to 
				zhoneCpeSystemCommon group"
			REVISION "201705082131Z"		-- May 08, 2017 at 21:31 GMT
			DESCRIPTION 
				"Added zhoneCpeOnuModelEthSfpPorts to
				zhoneCpeOnuModelSpecificEthInfoTable."
			REVISION "201704050253Z"		-- April 05, 2017 at 02:53 GMT
			DESCRIPTION 
				"Added CPE model specific information tables
				for ethernet and wlan interface types:
				    1) zhoneCpeOnuModelSpecificEthInfoTable
				    2) zhoneCpeOnuModelSpecificWlanInfoTable
				    3) zhoneCpeOnuModelSpecificWlanRadioInfoTable"
			REVISION "201703280238Z"		-- March 28, 2017 at 02:38 GMT
			DESCRIPTION 
				"Changed the default of wmm-advertise in cpe-wlan to enabled"
			REVISION "201703192107Z"		-- March 19, 2017 at 21:07 GMT
			DESCRIPTION 
				"1.Added Objects on zhoneCpeIpServerTable - igmpv3,igmp-snooping-querier.
				2.Added Object on zhoneCpeWlanAdvancedTable - physical-radio-interface."
			REVISION "201701180239Z"		-- January 18, 2017 at 02:39 GMT
			DESCRIPTION 
				"Added CPE AutoCfg profile"
			REVISION "201611101435Z"		-- November 10, 2016 at 14:35 GMT
			DESCRIPTION 
				"Changed the index of zhoneCpeAccessCtrlIndexTable to
				zhoneCpeAccessCtrlListIndex
				Add zhoneCpeAccessCtrlListIndex as one of
				the indices to zhoneCpeAccessCtrlTable"
			REVISION "201611010402Z"		-- November 01, 2016 at 04:02 GMT
			DESCRIPTION 
				"Updated the default value of zhoneCpeWlanAdvGlobalMaxClients to 50"
			REVISION "201610041744Z"		-- October 04, 2016 at 17:44 GMT
			DESCRIPTION 
				"Added cpeAccessCtrl profiles to 
				zhoneGroups
				Set the defalt value of cpeAccessCtrlListType
				blacklist
				Added cpeEthSubscriberAccessControlProfileIndex
				to EthSubscriber gorup"
			REVISION "201609230247Z"		-- September 23, 2016 at 02:47 GMT
			DESCRIPTION 
				"Changed quitePeriod and authKeyTxEnabled to read-only mode"
			REVISION "201609131134Z"		-- September 13, 2016 at 11:34 GMT
			DESCRIPTION 
				"Add new MIB objects for CpeAccessCtrl & cpeAccessCtrlList profile
				Add new field to point to CpeAccessCtrlList in cpe-eth-subscriber
				and cpe-wlan-subscriber tables"
			REVISION "201608151441Z"		-- August 15, 2016 at 14:41 GMT
			DESCRIPTION 
				"Add modelIdFetch to global settings"
			REVISION "201607200200Z"		-- July 20, 2016 at 02:00 GMT
			DESCRIPTION 
				"Added 25 new fields related to 802.1x in cpe-system-common profile and authentication-mode field in cpe-eth-subscriber."
			REVISION "201606300201Z"		-- June 30, 2016 at 02:01 GMT
			DESCRIPTION 
				"Modified the data types of vendorId and vendorSpecific fields of the table cpe-inventory-data."
			REVISION "201606240456Z"		-- June 24, 2016 at 04:56 GMT
			DESCRIPTION 
				"Created a new table cpeConfigDataProfile.
				Removed the field zhoneCpeConfigAutoConfigState from the table 
				cpeConfigProfile.
				Moved the fields - zhoneCpeConfigModel, zhoneCpeConfigOntVersion, 
				zhoneCpeConfigImageVersionActive, zhoneCpeConfigImageVersionStandby, 
				zhoneCpeConfigSnmpDataSync from the table cpeConfigProfile to the 
				new table cpeInventoryDataProfile."
			REVISION "201606090630Z"		-- June 09, 2016 at 06:30 GMT
			DESCRIPTION 
				"1. add cpeMacIpLocationTable
				2. cpeVlanFilter.adminState default is UP"
			REVISION "201606072335Z"		-- June 07, 2016 at 23:35 GMT
			DESCRIPTION 
				"Added mac-bridge-port-info to cpe-connection."
			REVISION "201606030329Z"		-- June 03, 2016 at 03:29 GMT
			DESCRIPTION 
				"PowerRange from cpe-eth-subscriber profile is only valid for PoE ports. But default value for this field was low, which is changed to disabled now."
			REVISION "201605290603Z"		-- May 29, 2016 at 06:03 GMT
			DESCRIPTION 
				"Add etherType to cpeVlanFilterTableEntry"
			REVISION "201605160600Z"		-- May 16, 2016 at 06:00 GMT
			DESCRIPTION 
				"1. add cpeVlanFilterList
				2. add cpeVlanFilter
				3. add vlan-filter-list to cpeEthSubscriber profile"
			REVISION "201604230304Z"		-- April 23, 2016 at 03:04 GMT
			DESCRIPTION 
				"Changed options for ipv6-host-ip-option and ipv6-dns-type fields."
			REVISION "201604102222Z"		-- April 10, 2016 at 22:22 GMT
			DESCRIPTION 
				"Changed CoSubPort to CoSubport in default value of circuit-id."
			REVISION "201603232043Z"		-- March 23, 2016 at 20:43 GMT
			DESCRIPTION 
				"Added below 8 fields to cpe-system-common profile
				1.lan-service-mode
				2.stag-tpid
				3.bridge-loop-detect
				4.block-upstream-dhcp-offer
				5.block-downstream-dns-query
				6.cross-vlan-multicast
				7.prioritization-method
				8.scheduling-method 
				
				To address issue in mibcomp added zhnBridge.mib."
			REVISION "201603202127Z"		-- March 20, 2016 at 21:27 GMT
			DESCRIPTION 
				"Changed default value for decouple-service-template to enabled"
			REVISION "201602180045Z"		-- February 18, 2016 at 00:45 GMT
			DESCRIPTION 
				"Added 6 new fields ipv6-host-ip-option, ipv6-prefix-length, ipv6-gateway, ipv6-pri-dns, ipv6-sec-dns and ipv6-dns-type in cpe-ip-server profile.
				6 new fields ipv6-dhcp-server,  ipv6-dhcp-mode, ipv6-router-advertise,  ipv6-lease-time , ipv6-start-addr and ipv6-end-addr in cpe-dhcp-server profile.
				and 1 new field ipv6-address in cpe-if-vlan profile"
			REVISION "201601070357Z"		-- January 07, 2016 at 03:57 GMT
			DESCRIPTION 
				"Changed the syntax of zhoneCpeCondDhcpSrvVsi from ZhoneAdminString to OCTET STRING (0..255)"
			REVISION "201511242245Z"		-- November 24, 2015 at 22:45 GMT
			DESCRIPTION 
				"Added BeamformingTx & BeamformingRx to Cpe-wlan-adv prfile
				Added additional 2 options for cfgBandwidth."
			REVISION "201511232349Z"		-- November 23, 2015 at 23:49 GMT
			DESCRIPTION 
				"Made cpe-lldp-rem profile as persistent."
			REVISION "201511182145Z"		-- November 18, 2015 at 21:45 GMT
			DESCRIPTION 
				"Added two new values dot1xTerminationPoint and radiusTerminationPoint to TpType"
			REVISION "201511012212Z"		-- November 01, 2015 at 22:12 GMT
			DESCRIPTION 
				"Added two new fields conference-options and conference-uri to cpe-voip-features profile"
			REVISION "201510292149Z"		-- October 29, 2015 at 21:49 GMT
			DESCRIPTION 
				"Added two new fields device-discovery-notify and notification-interval in cpe-lldp-med-policy-list profile."
			REVISION "201510151530Z"		-- October 15, 2015 at 15:30 GMT
			DESCRIPTION 
				"Added the following 6 new fields to cpeWlanAdv.
				1) dualBandCfgBands
				2) dualBandCfgRegulatoryModes
				3) dualBandPreNetworkRadarCheck
				4) dualBandInNetworkRadarCheck
				5) dualBandCfgTpcMitigationModes and
				6) cfgBandWidth
				"
			REVISION "201506292327Z"		-- June 29, 2015 at 23:27 GMT
			DESCRIPTION 
				"Added quick index markup to description field of all the 5 cpe subscriber profiles"
			REVISION "201506160136Z"		-- June 16, 2015 at 01:36 GMT
			DESCRIPTION 
				"Added TpType ptpTerminationPoint"
			REVISION "201506131408Z"		-- June 13, 2015 at 14:08 GMT
			DESCRIPTION 
				"Added fields dest-mac, outer-mpls-label, inner-mpls-label, and ecid to cpe-pwe-subscriber."
			REVISION "201505312350Z"		-- May 31, 2015 at 23:50 GMT
			DESCRIPTION 
				"Added new field called description to cpe-voip-subscriber,cpe-eth-subscriber, cpe-rf-subscriber, cpe-pwe-subscribr & cpe-wlan-subscriber tables"
			REVISION "201505210041Z"		-- May 21, 2015 at 00:41 GMT
			DESCRIPTION 
				"Added pbx-feature related fields. pbx-number in CpeVoipServer, pbx-dialing in CpeVoipFeature."
			REVISION "201504091326Z"		-- April 09, 2015 at 13:26 GMT
			DESCRIPTION 
				"1. add cpeLldpRemoteRetVal"
			REVISION "201503161230Z"		-- March 16, 2015 at 12:30 GMT
			DESCRIPTION 
				"Added a new table - zhoneCpeLldpRemoteTable.
				Added a new textual convention SnmpAdminString."
			REVISION "201503160233Z"		-- March 16, 2015 at 02:33 GMT
			DESCRIPTION 
				"Added four fields dhcp-snooping, dhcp-server,option82-circuit-id 
				and option82-remote-id in cpe-ip-server"
			REVISION "201503032223Z"		-- March 03, 2015 at 22:23 GMT
			DESCRIPTION 
				"Added decoupleCpe to zhoneCpeCmdOperation."
			REVISION "201501280330Z"		-- January 28, 2015 at 03:30 GMT
			DESCRIPTION 
				"Added decouple-service-template in CpeCfgGlobalSettings profile."
			REVISION "201501060203Z"		-- January 06, 2015 at 02:03 GMT
			DESCRIPTION 
				"Add mtu in cpe-ip-server profile."
			REVISION "201411130108Z"		-- November 13, 2014 at 01:08 GMT
			DESCRIPTION 
				"Added two fields derived-mac-bpppoe and derived-mac-brouted in CpeCfgGlobalSettings profile."
			REVISION "201408181301Z"		-- August 18, 2014 at 13:01 GMT
			DESCRIPTION 
				"Added HookFlashTimerMin and HookFlashTimerMax to CpeVoipMedia."
			REVISION "201408070956Z"		-- August 07, 2014 at 09:56 GMT
			DESCRIPTION 
				"Changed zhoneCpeVoipMedia's packet period selection default values from 10ms to 20ms."
			REVISION "201407281138Z"		-- July 28, 2014 at 11:38 GMT
			DESCRIPTION 
				"Add ZhoneCpeTemplateType internal"
			REVISION "201407241303Z"		-- July 24, 2014 at 13:03 GMT
			DESCRIPTION 
				"Added cpe-eth-subscriber's custom-power-range."
			REVISION "201407161348Z"		-- July 16, 2014 at 13:48 GMT
			DESCRIPTION 
				"Add zhoneCfgCmdStatus and zhoneCfgCmdErrorCode"
			REVISION "201405051109Z"		-- May 05, 2014 at 11:09 GMT
			DESCRIPTION 
				"Adding ProfileName field to zhoneCpeAutoCfgRule"
			REVISION "201404181844Z"		-- April 18, 2014 at 18:44 GMT
			DESCRIPTION 
				"Increased voip subscriber username size from 25 to 50."
			REVISION "201404221549Z"		-- April 22, 2014 at 15:49 GMT
			DESCRIPTION 
				"Add fields to cpeServiceApplication
				and cpeCmd"
			REVISION "201403211135Z"		-- March 21, 2014 at 11:35 GMT
			DESCRIPTION 
				"Added a comment in the description for zhoneCpeSystemMgcpClientName."
			REVISION "201403131636Z"		-- March 13, 2014 at 16:36 GMT
			DESCRIPTION 
				"Added cpe-cfg-global-settings profile."
			REVISION "201403101127Z"		-- March 10, 2014 at 11:27 GMT
			DESCRIPTION 
				"Fix bugs in auto-cfg-rule"
			REVISION "201403071315Z"		-- March 07, 2014 at 13:15 GMT
			DESCRIPTION 
				"Add cpe service template objects to CpeCmd table"
			REVISION "201403051138Z"		-- March 05, 2014 at 11:38 GMT
			DESCRIPTION 
				"Added the following new fields to the zhoneCpeOnuModelInfoTable:
				
				zhoneCpeOnuSipSupported
				zhoneCpeOnuH248Supported
				zhoneCpeOnuMgcpSupported
				zhoneCpeOnuT1Supported
				zhoneCpeOnuSE1Supported
				zhoneCpeOnuNumberofPoePorts"
			REVISION "201402241307Z"		-- February 24, 2014 at 13:07 GMT
			DESCRIPTION 
				"Add auto-cfg-rule"
			REVISION "201402031252Z"		-- February 03, 2014 at 12:52 GMT
			DESCRIPTION 
				"Added cpe-lldp-med-policy-list and cpe-lldp-med-policy, as well as adding a field to cpe-eth-subscriber."
			REVISION "201401241531Z"		-- January 24, 2014 at 15:31 GMT
			DESCRIPTION 
				"Fix indexes for *EntryIndexNext.
				Correct index for condDhcp table."
			REVISION "201312160817Z"		-- December 16, 2013 at 08:17 GMT
			DESCRIPTION 
				"Add zhoneCpeCmd objects"
			REVISION "201312041335Z"		-- December 04, 2013 at 13:35 GMT
			DESCRIPTION 
				"Changed the range value for the following objects:
				1. zhoneCpeSystemCommonPowerShutdownDelay
				2. zhoneCpeSystemCommonPowerRestoreDelay
				"
			REVISION "201311181619Z"		-- November 18, 2013 at 16:19 GMT
			DESCRIPTION 
				"Added field Permanent to zhoneCpeCondDhcpSrv"
			REVISION "201309241435Z"		-- September 24, 2013 at 14:35 GMT
			DESCRIPTION 
				"Changed the default values for the following:
				
				1.zhoneCpeEthSubscriberPowerShed
				2.zhoneCpeEthSubscriberPowerRange
				"
			REVISION "201308191447Z"		-- August 19, 2013 at 14:47 GMT
			DESCRIPTION 
				"Add tftp download to onu model info table"
			REVISION "201308071054Z"		-- August 07, 2013 at 10:54 GMT
			DESCRIPTION 
				"Added the following to the zhoneCpeEthSubscriberTable:
				
				zhoneCpeEthSubscriberPowerShed
				zhoneCpeEthSubscriberPowerRange
				
				Added the following fields to the zhoneCpeSystemCommonTable:
				
				zhoneCpeSystemCommonPowerSupply
				zhoneCpeSystemCommonPowerShutdownDelay
				zhoneCpeSystemCommonPowerRestoreDelay
				"
			REVISION "201307251340Z"		-- July 25, 2013 at 13:40 GMT
			DESCRIPTION 
				"Increased voip subscriber password size from 25 to 32."
			REVISION "201307180854Z"		-- July 18, 2013 at 08:54 GMT
			DESCRIPTION 
				"Removed default values for cpe-system-common's acs-username and acs-password."
			REVISION "201306272326Z"		-- June 27, 2013 at 23:26 GMT
			DESCRIPTION 
				"Changed max value of warmLineTimer to 30000"
			REVISION "201306241143Z"		-- June 24, 2013 at 11:43 GMT
			DESCRIPTION 
				"Add cpe-cond-dhcp-srv and cpe-cond-dhcp-srv-list"
			REVISION "201306232358Z"		-- June 23, 2013 at 23:58 GMT
			DESCRIPTION 
				"Added range as 200..5000 and default value as 200 for WarmLineTimer."
			REVISION "201306061855Z"		-- June 06, 2013 at 18:55 GMT
			DESCRIPTION 
				"1. Added the following objects to the zhoneCpeVoipServerTable.
				   zhoneCpeVoipMgcpClientAddressMode
				   zhoneCpeVoipMgcpPersistentNotify
				2. Added zhoneCpeSystemMgcpClientName to the zhoneCpeSystemTable.
				3. Added zhoneCpeVoipSubscriberPhoneFollowsWan to the
				   zhoneCpeVoipSubscriberTable."
			REVISION "201306061126Z"		-- June 06, 2013 at 11:26 GMT
			DESCRIPTION 
				"Set zhoneCpeIpServer dns-type default value from 'proxy' to 'default'"
			REVISION "201306061003Z"		-- June 06, 2013 at 10:03 GMT
			DESCRIPTION 
				"Changing 54g rate in zhoneCpeWlanAdvanced to auto instead of 1m."
			REVISION "201306042314Z"		-- June 04, 2013 at 23:14 GMT
			DESCRIPTION 
				"Added hotLine,hotLineNumber, and warmLineTimer in cpe voip features profile"
			REVISION "201305150935Z"		-- May 15, 2013 at 09:35 GMT
			DESCRIPTION 
				"Added a new tpType for mgcp
				Added mgcp to the list zhoneCpeVoipServerSignallingProtocol"
			REVISION "201304221246Z"		-- April 22, 2013 at 12:46 GMT
			DESCRIPTION 
				"Add MGMT tpType"
			REVISION "201304111416Z"		-- April 11, 2013 at 14:16 GMT
			DESCRIPTION 
				"Added peak-burst-size field to the cpe-traffic-management profile"
			REVISION "201303181151Z"		-- March 18, 2013 at 11:51 GMT
			DESCRIPTION 
				"Added zhoneCpeVoipSipRegRetryTime
				to the zhoneCpeVoipServerTable."
			REVISION "201303011417Z"		-- March 01, 2013 at 14:17 GMT
			DESCRIPTION 
				"Added the following new fields to the zhoneCpeSystemCommonTable:
				
				1. zhoneCpeSystemCommonAdminPassword
				2. zhoneCpeSystemCommonSupportPassword
				3. zhoneCpeSystemCommonUserPassword"
			REVISION "201301112310Z"		-- January 11, 2013 at 23:10 GMT
			DESCRIPTION 
				"Split cpe-wlan into cpe-wlan and cpe-wlan-advanced"
			REVISION "201212181018Z"		-- December 18, 2012 at 10:18 GMT
			DESCRIPTION 
				"Add guided vlan/cos to cpe-connection"
			REVISION "201301021830Z"		-- January 02, 2013 at 18:30 GMT
			DESCRIPTION 
				"Add cpeDnsHost and cpeDnsHostList.
				Add fields to cpe-ip-server and cpe-system-common."
			REVISION "201211191229Z"		-- November 19, 2012 at 12:29 GMT
			DESCRIPTION 
				"Added the following objects to the zhoneCpeOnuModelInfoTable:
				zhoneCpeOnuNumberOfWlanPorts
				zhoneCpeOnuModelInfoRg
				zhoneCpeOnuModelInfoRgVoip
				zhoneCpeOnuModelInfoRgPwe"
			REVISION "201210310649Z"		-- October 31, 2012 at 06:49 GMT
			DESCRIPTION 
				"Add tr69TerminationPoint to tpType"
			REVISION "201209241048Z"		-- September 24, 2012 at 10:48 GMT
			DESCRIPTION 
				"Changed the maximum length of zhoneCpePppoeUsername
				from 25 to 64."
			REVISION "201208052350Z"		-- August 05, 2012 at 23:50 GMT
			DESCRIPTION 
				"Added zhoneCpeServiceApplicationTable."
			REVISION "201207121437Z"		-- July 12, 2012 at 14:37 GMT
			DESCRIPTION 
				"Added range for zhoneCpePppoeRetryInterval."
			REVISION "201207030957Z"		-- July 03, 2012 at 09:57 GMT
			DESCRIPTION 
				"Fixed defaut values for the objects in the following tables:
				
				1. zhoneCpeInterfaceVlanTable.
				2. zhoneCpeDhcpServerTable.
				3. zhoneCpeStaticRouteTable.
				4. zhoneCpePortFwdTable.
				5. zhoneCpeWlanTable."
			REVISION "201206211202Z"		-- June 21, 2012 at 12:02 GMT
			DESCRIPTION 
				"1. Fixed the range limits for the objects in the 
				   following table:
				
				1. zhoneCpeInterfaceVlanTable.
				2. zhoneCpeWlanTable.
				3. zhoneCpeDhcpServerTable.
				4. zhoneCpeStaticRouteTable.
				5. zhoneCpePortFwdTable.
				
				2. Changed the name of zhoneCpePortForwardingProfileIndex
				   to zhoneCpePortFwdListProfileIndex.
				3. Changed zhoneCpeIpServerNat type from ZhoneEnabledFlag
				   to INTEGER.
				4. Moved 2 objects from zhoneCpeInterfaceVlanTable to
				   zhoneCpeIpServerTable.
				5. Added zhoneCpeConnectionRgMode."
			REVISION "201206200952Z"		-- June 20, 2012 at 09:52 GMT
			DESCRIPTION 
				"Update the limits for the objects zhoneCpeWlanIndex,
				zhoneCpePortFwdListIndex, zhoneCpePortFwdEntryIndex."
			REVISION "201206121157Z"		-- June 12, 2012 at 11:57 GMT
			DESCRIPTION 
				"Fix the lower index values for the objects in the
				zhoneCpeOnuModelInfoTable."
			REVISION "201205202349Z"		-- May 20, 2012 at 23:49 GMT
			DESCRIPTION 
				"Added rtpDscp & SignalingDscp fields to cpeVoipServer
				Added DSCP field to cpePwe table."
			REVISION "201205091626Z"		-- May 09, 2012 at 16:26 GMT
			DESCRIPTION 
				"Changed lower limit of zhoneCpeSystemCommonIndex to 1
				Changed lower limit of zhoneCpeDhcpServerIndex to 1
				Added the following new tables:
				
				1. zhoneCpePppoeTable
				2. zhoneCpeWlanSubscriberTable
				3. zhoneCpeWlan
				4. zhoneCpeStaticRouteList
				5. zhoneCpeStaticRoute
				6. zhoneCpePortFwdList
				7. zhoneCpePortFwd"
			REVISION "201204300952Z"		-- April 30, 2012 at 09:52 GMT
			DESCRIPTION 
				"Made zhoneCpeInterfaceVlanIpAddress a quick access field."
			REVISION "201204251024Z"		-- April 25, 2012 at 10:24 GMT
			DESCRIPTION 
				"1. Changed the name of the object zhoneCpeInterfaceVlanConnectionType to zhoneCpeInterfaceVlanRgMode
				2. Added a new object zhoneCpeInterfaceVlanIgmpFunction to the zhoneCpeInterfaceVlanTable.
				3. Added default value for the object zhoneCpeDhcpServerLeaseTime.
				4. Fixed descriptions for a few objects.
				5. Fixed name mismatch for the objects in the zhoneCpeInterfaceVlanTable."
			REVISION "201204202245Z"		-- April 20, 2012 at 22:45 GMT
			DESCRIPTION 
				"Added default value for zhoneCpeInterfaceTranslateSlanTpId.
				Added range for zhoneCpeDhcpServerIndex and zhoneCpeSystemCommonIndex."
			REVISION "201204121615Z"		-- April 12, 2012 at 16:15 GMT
			DESCRIPTION 
				"Add new tpTypes and modelInfo column for RG-bridged."
			REVISION "201203281052Z"		-- March 28, 2012 at 10:52 GMT
			DESCRIPTION 
				"Added zhoneCpeDhcpServerProfileIndex and zhoneCpePortForwardingProfileIndex objects to the
				 zhoneCpeInterfaceVlanTable.
				Added ranges for the objects
				zhoneCpeSystemCommonProfileIndex
				zhoneCpeIpServerProfile
				zhoneCpeStaticRouteListProfileIndex"
			REVISION "201203260958Z"		-- March 26, 2012 at 09:58 GMT
			DESCRIPTION 
				"Removed zhoneCpeDhcpServerProfileIndex and
				zhoneCpePortForwardingProfileIndex objects from the zhoneCpeIpServerTable"
			REVISION "201203191043Z"		-- March 19, 2012 at 10:43 GMT
			DESCRIPTION 
				"Added new objects to the zhoneCpeIpServerTable
				Added the following new tables:
				zhoneCpeSystemTable
				zhoneCpeSystemCommon
				zhoneCpeInterfaceVlanTable
				zhoneCpeDhcpServer"
			REVISION "201202131549Z"		-- February 13, 2012 at 15:49 GMT
			DESCRIPTION 
				"Added the following 2 objects to the
				zhoneCpeVoipServerTable.
				
				1. zhoneCpeVoipDtmfEventsPassingMethod
				2. zhoneCpeVoipCasEventsPassingMethod"
			REVISION "201201281047Z"		-- January 28, 2012 at 10:47 GMT
			DESCRIPTION 
				"Added LineStatusAlarm and AlarmSeverity fields
				in cpeEthSubscriber, cpeRfSubscriber and cpePweSubscriber profiles."
			REVISION "201111111505Z"		-- November 11, 2011 at 15:05 GMT
			DESCRIPTION 
				"add outboundServer and portId to voip server."
			REVISION "201109231404Z"		-- September 23, 2011 at 14:04 GMT
			DESCRIPTION 
				"Added dscpToCos field to CpeConnection."
			REVISION "201109081416Z"		-- September 08, 2011 at 14:16 GMT
			DESCRIPTION 
				"Changed the min value of zhoneCpeVoipServerProfileIndex to 1.
				Removed the default value."
			REVISION "201107121517Z"		-- July 12, 2011 at 15:17 GMT
			DESCRIPTION 
				"Fix the enum value change error for the object zhoneCpeVoipCodecSelectionThirdOrder."
			REVISION "201107051415Z"		-- July 05, 2011 at 14:15 GMT
			DESCRIPTION 
				"Changed the limits for zhoneCpeTpIndex."
			REVISION "201106161118Z"		-- June 16, 2011 at 11:18 GMT
			DESCRIPTION 
				"Changed the default values in the zhoneCpePweTable for the following fields:
				1.zhoneCpePweTimingMode
				2.zhoneCpePweJitterBufMax
				3.zhoneCpePweJitterBufDesired
				4.zhoneCpePweChannelAssign"
			REVISION "201106030104Z"		-- June 03, 2011 at 01:04 GMT
			DESCRIPTION 
				"Changed zhoneCpeVideoAccessControlIndexNext as table."
			REVISION "201105230925Z"		-- May 23, 2011 at 09:25 GMT
			DESCRIPTION 
				"Added Quick Access for  the object zhoneCpeVideoAccessControlList.
				Added ranges for the object zhoneCpeGemPort.
				Changed one of the enum names for zhoneCpePweSignalling."
			REVISION "201105180015Z"		-- May 18, 2011 at 00:15 GMT
			DESCRIPTION 
				"Changed zhoneCpeSipDialPlanIndexNext as table entry."
			REVISION "201104271014Z"		-- April 27, 2011 at 10:14 GMT
			DESCRIPTION 
				"Changed the default value of zhoneCpeVideoProfileIndex
				to 0.
				Added default value to the MIB object zhoneCpePweChannelAssign.
				Added description to the BIT's field objects in the
				zhoneCpeVoipFeaturesTable.
				Changed description for zhoneCpePweSubscriberNearEndPort 
				and zhoneCpePweSubscriberFarEndPort."
			REVISION "201104121536Z"		-- April 12, 2011 at 15:36 GMT
			DESCRIPTION 
				"Remove the MIB object zhoneCpeSipServerIndexNext"
			REVISION "201103281007Z"		-- March 28, 2011 at 10:07 GMT
			DESCRIPTION 
				"Changed the description for some fields
				in the zhoneCpePweTable.
				Changed the range for zhoneCpeVoipSubscriberDisplayName
				to 0 to 25.
				Changed the default values for the objects in the
				zhoneCpeConnectionTable.
				Changed the maximum value for the following objects
				to 1310720kbps
				
				1.zhoneCpeTrafficManagementUpstreamSIR
				2.zhoneCpeTrafficManagementUpstreamPIR
				3.zhoneCpeTrafficManagementDownstreamSIR
				4.zhoneCpeTrafficManagementDownstreamPIR"
			REVISION "201103011029Z"		-- March 01, 2011 at 10:29 GMT
			DESCRIPTION 
				"1.Changed the lower limit for the object
				  zhoneCpeVoipMgcTerminationIdBase to 0.
				2.Added a new table zhoneCpeTrafficManagement.
				3.Removed the zhoneCpePots profile and added
				  the objects to the zhoneCpeVoipSubscriber profile.
				4.Removed the zhoneCpeEth profile and added the
				  objects to the zhoneCpeEthSubscriber and
				  zhoneCpeTrafficManagement profile.
				5.Removed 15 objects from the zhoneCpePwe profile.
				6.Removed zhoneCpeCes profile and added the objects
				  to the zhoneCpePwe and zhoneCpePweSubscriber profile.
				"
			REVISION "201102181451Z"		-- February 18, 2011 at 14:51 GMT
			DESCRIPTION 
				"1.Changed the default value of zhoneCpeIpServerNetmask
				  to ffffff00.
				2.Changed the default value of zhoneCpeVoipFeaturesAnnouncementType
				  to reordertone.
				3.Changed the MIB object zhoneCpePweLossPktClearPolicy
				  name to zhoneCpePweLossPacketClearPolicy.
				4.Changed the default value of zhoneCpePwePtypePayload
				  to 96.
				5.Changed the range of zhoneCpePwePtypeSignalling
				  to 0 to 127.
				6.Added zhoneCpeSipDialPlanIndexNext to the
				  zhoneCpeSipDialPlanTable."
			REVISION "201102031048Z"		-- February 03, 2011 at 10:48 GMT
			DESCRIPTION 
				"1.Added a new table zhoneCpeRfSubscriberTable.
				2.Changed the default value of the
				  CpeIpServerProfileIndex to 1."
			REVISION "201101191420Z"		-- January 19, 2011 at 14:20 GMT
			DESCRIPTION 
				"Object name correction for zhoneCpePweSignaling
				and zhoneCpeVoipServerSignalingProtocol"
			REVISION "201101201201Z"		-- January 20, 2011 at 12:01 GMT
			DESCRIPTION 
				"Move connection table from phyGPON
				(gponOnuConnection) to this mib
				(cpeConnection)."
			REVISION "201101121401Z"		-- January 12, 2011 at 14:01 GMT
			DESCRIPTION 
				"Added the following new tables:
				1.zhoneCpeEthSubscriberTable
				2.zhoneCpeEthTable
				3.zhoneCpeVideoTable
				4.zhoneCpeVideoAccessControlTable
				5.zhoneCpePweSubscriberTable
				6.zhoneCpePweTable
				7.zhoneCpeCesTable
				8.zhoneCpeOnuModelInfoTable
				
				Also added IndexNext as below:
				
				1.zhoneCpeSipDialPlan
				2.ZhoneCpeVoipServer
				3.zhoneCpeIpServer
				4.zhoneCpeVoipFeatures
				5.zhoneCpeVoipMedia
				6.zhoneCpePots
				7.zhoneCpeEth
				8.zhoneCpeVideo
				9.zhoneCpeVideoAccessControl
				10.zhoneCpePwe
				11.zhoneCpeCes"
			REVISION "201012171002Z"		-- December 17, 2010 at 10:02 GMT
			DESCRIPTION 
				"Changed the storage label and profile label for the object
				zhoneCpeIpServer."
			REVISION "201012091251Z"		-- December 09, 2010 at 12:51 GMT
			DESCRIPTION 
				"New MIB to support CPE voice and pseudo wire
				objects."
			::= { zhoneModules 118 }

		
	
--
-- Textual conventions
--
	
		ZhoneCpeTemplateType ::= TEXTUAL-CONVENTION
			STATUS current
			DESCRIPTION 
				"Specifies TemplateType as voip/pwe/wifi/data/video, or 
				'internal' to indicate a profile generated on the device.
				"
			SYNTAX INTEGER
				{
				voip(668),
				pwe(669),
				wifi(670),
				data(671),
				video(672),
				internal(999)
				}

		WlDualBandCfgBands ::= TEXTUAL-CONVENTION
			STATUS current
			DESCRIPTION 
				"Operational bands supported by a dual-band radio"
			SYNTAX INTEGER
				{
				bandUndefined(1),
				band2Dot4GHz(2),
				band5GHz(3)
				}

		WlDualBandCfgRegModes ::= TEXTUAL-CONVENTION
			STATUS current
			DESCRIPTION 
				"Regulatory modes supported by a dual-band radio."
			SYNTAX INTEGER
				{
				regModeDisabled(1),
				regMode802Dot11h(2),
				regMode802Dot11d(3)
				}

		WlDualBandCfgTpcMitigationLevels ::= TEXTUAL-CONVENTION
			STATUS current
			DESCRIPTION 
				"802.11h Transmission Power Control(TPC) mitigation levels."
			SYNTAX INTEGER
				{
				tpcOff(1),
				tpc2dB(2),
				tpc3dB(3),
				tpc4dB(4)
				}

		ZhoneShelfValue ::= TEXTUAL-CONVENTION
			STATUS current
			DESCRIPTION 
				"Index used to order the application of shelf access
				entries. Valid range is 1..255 and 0 is an invalid 
				value."
			SYNTAX Integer32 (1..255)

		ZhoneSlotValue ::= TEXTUAL-CONVENTION
			STATUS current
			DESCRIPTION 
				"The slot number of this card.  Valid range is 1..30 
				and 0 is an invalid value."
			SYNTAX Integer32 (1..30)

		Zhone32PortBitmask ::= TEXTUAL-CONVENTION
			STATUS current
			DESCRIPTION 
				"A bitmask representing ports on a device.  This textual convention
				is mostly used to represent presence of ports of a specific type
				on the device.  A bit value if 1 represents presence of the port.
				A bit value of 0 represents absence of the port."
			SYNTAX BITS
				{
				port1(0),
				port2(1),
				port3(2),
				port4(3),
				port5(4),
				port6(5),
				port7(6),
				port8(7),
				port9(8),
				port10(9),
				port11(10),
				port12(11),
				port13(12),
				port14(13),
				port15(14),
				port16(15),
				port17(16),
				port18(17),
				port19(18),
				port20(19),
				port21(20),
				port22(21),
				port23(22),
				port24(23),
				port25(24),
				port26(25),
				port27(26),
				port28(27),
				port29(28),
				port30(29),
				port31(30),
				port32(31)
				}

	
--
-- Node definitions
--
	
		-- 1.3.6.1.4.1.5504.5.16.1
		zhoneCpeObjectID OBJECT IDENTIFIER ::= { zhoneCpe 1 }

		
		-- 1.3.6.1.4.1.5504.5.16.1.1
		zhoneCpeSipDialPlan OBJECT-IDENTITY
			STATUS current
			DESCRIPTION 
				"Cpe Sip Dial plan for the VoIP feature."
			::= { zhoneCpeObjectID 1 }

		
		-- 1.3.6.1.4.1.5504.5.16.1.1.1
		zhoneCpeSipDialPlanIndexTable OBJECT-TYPE
			SYNTAX SEQUENCE OF ZhoneCpeSipDialPlanIndexEntry
			MAX-ACCESS not-accessible
			STATUS current
			DESCRIPTION
				"Table of next available index values for each CPE SIP Dialplan group."
			::= { zhoneCpeSipDialPlan 1 }

		
		-- 1.3.6.1.4.1.5504.5.16.1.1.1.1
		zhoneCpeSipDialPlanIndexEntry OBJECT-TYPE
			SYNTAX ZhoneCpeSipDialPlanIndexEntry
			MAX-ACCESS not-accessible
			STATUS current
			DESCRIPTION
				"Row in the zhoneCpeSipDialPlanIndexTable"
			INDEX { zhoneCpeVoipServerIndex }
			::= { zhoneCpeSipDialPlanIndexTable 1 }

		
		ZhoneCpeSipDialPlanIndexEntry ::=
			SEQUENCE { 
				zhoneCpeSipDialPlanIndexNext
					Unsigned32
			 }

		-- 1.3.6.1.4.1.5504.5.16.1.1.1.1.1
		zhoneCpeSipDialPlanIndexNext OBJECT-TYPE
			SYNTAX Unsigned32 (1..2147483647)
			MAX-ACCESS read-only
			STATUS current
			DESCRIPTION
				"This represents the next available index value for SIP dial plan profile."
			::= { zhoneCpeSipDialPlanIndexEntry 1 }

		
		-- 1.3.6.1.4.1.5504.5.16.1.1.2
		zhoneCpeSipDialPlanTable OBJECT-TYPE
			SYNTAX SEQUENCE OF ZhoneCpeSipDialPlanEntry
			MAX-ACCESS not-accessible
			STATUS current
			DESCRIPTION
				"Cpe Sip Dial plan table for the VoIP feature."
			::= { zhoneCpeSipDialPlan 2 }

		
		-- 1.3.6.1.4.1.5504.5.16.1.1.2.1
		zhoneCpeSipDialPlanEntry OBJECT-TYPE
			SYNTAX ZhoneCpeSipDialPlanEntry
			MAX-ACCESS not-accessible
			STATUS current
			DESCRIPTION
				"Row in the CpeSipDialPlan table."
			INDEX { zhoneCpeSipServerIndex, zhoneCpeSipDialPlanIndex }
			::= { zhoneCpeSipDialPlanTable 1 }

		
		ZhoneCpeSipDialPlanEntry ::=
			SEQUENCE { 
				zhoneCpeSipServerIndex
					Unsigned32,
				zhoneCpeSipDialPlanIndex
					Unsigned32,
				zhoneCpeSipDialPlanRowStatus
					ZhoneRowStatus,
				zhoneCpeSipDialPlanFormat
					INTEGER,
				zhoneCpeSipDialPlanString
					OCTET STRING
			 }

		-- 1.3.6.1.4.1.5504.5.16.1.1.2.1.1
		zhoneCpeSipServerIndex OBJECT-TYPE
			SYNTAX Unsigned32 (1..2147483647)
			MAX-ACCESS not-accessible
			STATUS current
			DESCRIPTION
				"This represents the SIP dial plan server index value."
			::= { zhoneCpeSipDialPlanEntry 1 }

		
		-- 1.3.6.1.4.1.5504.5.16.1.1.2.1.2
		zhoneCpeSipDialPlanIndex OBJECT-TYPE
			SYNTAX Unsigned32 (1..2147483647)
			MAX-ACCESS not-accessible
			STATUS current
			DESCRIPTION
				"This represents the SIP dial plan index value."
			::= { zhoneCpeSipDialPlanEntry 2 }

		
		-- 1.3.6.1.4.1.5504.5.16.1.1.2.1.3
		zhoneCpeSipDialPlanRowStatus OBJECT-TYPE
			SYNTAX ZhoneRowStatus
			MAX-ACCESS read-create
			STATUS current
			DESCRIPTION
				"Used to create, modify or delete an entry in this table."
			DEFVAL { active }
			::= { zhoneCpeSipDialPlanEntry 3 }

		
		-- 1.3.6.1.4.1.5504.5.16.1.1.2.1.4
		zhoneCpeSipDialPlanFormat OBJECT-TYPE
			SYNTAX INTEGER
				{
				h248(1),
				nsc(2),
				vendorspecific(3)
				}
			MAX-ACCESS read-create
			STATUS current
			DESCRIPTION
				"DialPlanFormat defines the dial plan format standard that is supported
				in the ONT for VoIP."
			DEFVAL { h248 }
			::= { zhoneCpeSipDialPlanEntry 4 }

		
		-- 1.3.6.1.4.1.5504.5.16.1.1.2.1.5
		zhoneCpeSipDialPlanString OBJECT-TYPE
			SYNTAX OCTET STRING (SIZE (1..64))
			MAX-ACCESS read-create
			STATUS current
			DESCRIPTION
				"SipDialPlan contains a dial plan used by the VoIP service."
			::= { zhoneCpeSipDialPlanEntry 5 }

		
		-- 1.3.6.1.4.1.5504.5.16.1.2
		zhoneCpeVoipServer OBJECT-IDENTITY
			STATUS current
			DESCRIPTION 
				"Cpe Voip Server for the VoIP feature."
			::= { zhoneCpeObjectID 2 }

		
		-- 1.3.6.1.4.1.5504.5.16.1.2.1
		zhoneCpeVoipServerIndexNext OBJECT-TYPE
			SYNTAX Integer32
			MAX-ACCESS read-only
			STATUS current
			DESCRIPTION
				"This object contains an appropriate value to be used for the zhoneCpeVoipServerIndex
				when creating entries in the zhoneCpeVoipServerTable. The value 0 indicates that
				no unassigned entries are available. To obtain the zhoneCpeVoipServerIndex value
				for a new entry, the manager issues a management protocol retrieval
				operation to obtain the current value of this object.  After each retrieval,
				the agent should modify the value to the next unassigned index.
				
				After a manager retrieves a value the agent will determine through its local
				policy when this index value will be made available for reuse."
			::= { zhoneCpeVoipServer 1 }

		
		-- 1.3.6.1.4.1.5504.5.16.1.2.2
		zhoneCpeVoipServerTable OBJECT-TYPE
			SYNTAX SEQUENCE OF ZhoneCpeVoipServerEntry
			MAX-ACCESS not-accessible
			STATUS current
			DESCRIPTION
				"Cpe Voip Server table for the VoIP feature."
			::= { zhoneCpeVoipServer 2 }

		
		-- 1.3.6.1.4.1.5504.5.16.1.2.2.1
		zhoneCpeVoipServerEntry OBJECT-TYPE
			SYNTAX ZhoneCpeVoipServerEntry
			MAX-ACCESS not-accessible
			STATUS current
			DESCRIPTION
				"Row in the VoipServer table."
			INDEX { zhoneCpeVoipServerIndex }
			::= { zhoneCpeVoipServerTable 1 }

		
		ZhoneCpeVoipServerEntry ::=
			SEQUENCE { 
				zhoneCpeVoipServerIndex
					Unsigned32,
				zhoneCpeVoipServerRowStatus
					ZhoneRowStatus,
				zhoneCpeVoipProfileName
					ZhoneAdminString,
				zhoneCpeVoipPrimaryServer
					InetAddress,
				zhoneCpeVoipSecondaryServer
					InetAddress,
				zhoneCpeVoipServerSignallingProtocol
					INTEGER,
				zhoneCpeVoipSipRegExpirationTime
					Unsigned32,
				zhoneCpeVoipSipReRegHeadStartTime
					Unsigned32,
				zhoneCpeVoipSipDomain
					InetAddress,
				zhoneCpeVoipSipRegistrar
					InetAddress,
				zhoneCpeVoipSoftSwitch
					ZhoneAdminString,
				zhoneCpeVoipMgcVersion
					Integer32,
				zhoneCpeVoipMgcMessageFormat
					INTEGER,
				zhoneCpeVoipMgcMaximumRetryTime
					Integer32,
				zhoneCpeVoipMgcMaximumRetryAttempts
					Integer32,
				zhoneCpeVoipMgcServiceChangeDelay
					Integer32,
				zhoneCpeVoipMgcTerminationIdBase
					OCTET STRING,
				zhoneCpeVoipReleaseTimer
					Integer32,
				zhoneCpeVoipRohTimer
					Integer32,
				zhoneCpeVoipDscpMark
					Integer32,
				zhoneCpeVoipPiggyBackEvents
					ZhoneEnabledFlag,
				zhoneCpeVoipOobToneEvents
					ZhoneEnabledFlag,
				zhoneCpeVoipOobDtmfEvents
					ZhoneEnabledFlag,
				zhoneCpeVoipOobCasEvents
					ZhoneEnabledFlag,
				zhoneCpeVoipPartialDialTimeout
					Integer32,
				zhoneCpeVoipCriticalDialTimeout
					Integer32,
				zhoneCpeVoipServerOutboundServer
					InetAddress,
				zhoneCpeVoipServerPortId
					Integer32,
				zhoneCpeVoipDtmfEventsPassingMethod
					INTEGER,
				zhoneCpeVoipCasEventsPassingMethod
					INTEGER,
				zhoneCpeVoipRtpDscp
					OCTET STRING,
				zhoneCpeVoipSignalingDscp
					OCTET STRING,
				zhoneCpeVoipSipRegRetryTime
					Unsigned32,
				zhoneCpeVoipMgcpClientAddressMode
					INTEGER,
				zhoneCpeVoipMgcpPersistentNotify
					ZhoneEnabledFlag,
				zhoneCpeVoipPbxNumber
					OCTET STRING
			 }

		-- 1.3.6.1.4.1.5504.5.16.1.2.2.1.1
		zhoneCpeVoipServerIndex OBJECT-TYPE
			SYNTAX Unsigned32 (1..2147483647)
			MAX-ACCESS not-accessible
			STATUS current
			DESCRIPTION
				"This represents the CPE Voip Server Index value."
			::= { zhoneCpeVoipServerEntry 1 }

		
		-- 1.3.6.1.4.1.5504.5.16.1.2.2.1.2
		zhoneCpeVoipServerRowStatus OBJECT-TYPE
			SYNTAX ZhoneRowStatus
			MAX-ACCESS read-create
			STATUS current
			DESCRIPTION
				"Used to create, modify or delete an entry in this table."
			DEFVAL { active }
			::= { zhoneCpeVoipServerEntry 2 }

		
		-- 1.3.6.1.4.1.5504.5.16.1.2.2.1.3
		zhoneCpeVoipProfileName OBJECT-TYPE
			SYNTAX ZhoneAdminString
			MAX-ACCESS read-create
			STATUS current
			DESCRIPTION
				"CPE Voip Server profile for the VoIP services for the dynamic bridging.
				This field is only writable upon creation and must be unique within its
				table.
				"
			::= { zhoneCpeVoipServerEntry 3 }

		
		-- 1.3.6.1.4.1.5504.5.16.1.2.2.1.4
		zhoneCpeVoipPrimaryServer OBJECT-TYPE
			SYNTAX InetAddress
			MAX-ACCESS read-create
			STATUS current
			DESCRIPTION
				"This attribute contains the name (IP address or resolved name) of
				the primary MGC or SIP proxy server that controls the signaling messages."
			::= { zhoneCpeVoipServerEntry 4 }

		
		-- 1.3.6.1.4.1.5504.5.16.1.2.2.1.5
		zhoneCpeVoipSecondaryServer OBJECT-TYPE
			SYNTAX InetAddress
			MAX-ACCESS read-create
			STATUS current
			DESCRIPTION
				"This attribute contains the name (IP address or resolved name) of the
				secondary or backup MGC that controls the signalling messages."
			::= { zhoneCpeVoipServerEntry 5 }

		
		-- 1.3.6.1.4.1.5504.5.16.1.2.2.1.6
		zhoneCpeVoipServerSignallingProtocol OBJECT-TYPE
			SYNTAX INTEGER
				{
				sip(1),
				sipplar(2),
				h248(3),
				mgcp(4)
				}
			MAX-ACCESS read-create
			STATUS current
			DESCRIPTION
				"This attribute specifies the VoIP signalling protocol to use."
			DEFVAL { h248 }
			::= { zhoneCpeVoipServerEntry 6 }

		
		-- 1.3.6.1.4.1.5504.5.16.1.2.2.1.7
		zhoneCpeVoipSipRegExpirationTime OBJECT-TYPE
			SYNTAX Unsigned32 (0..2147483647)
			UNITS "seconds"
			MAX-ACCESS read-create
			STATUS current
			DESCRIPTION
				"Sip Reg Expiration Time specifies the SIP registration expiration time
				in seconds. If its value is 0, the SIP agent does not add an expiration
				time to the registration requests and does not perform re-registration.
				The default value is 3600 seconds."
			DEFVAL { 3600 }
			::= { zhoneCpeVoipServerEntry 7 }

		
		-- 1.3.6.1.4.1.5504.5.16.1.2.2.1.8
		zhoneCpeVoipSipReRegHeadStartTime OBJECT-TYPE
			SYNTAX Unsigned32 (0..2147483647)
			UNITS "seconds"
			MAX-ACCESS read-create
			STATUS current
			DESCRIPTION
				"Sip ReReg Head Star Time specifies the time in seconds prior to timeout
				that causes the SIP agent to start the re-registration process.
				The default value is 360 seconds."
			DEFVAL { 360 }
			::= { zhoneCpeVoipServerEntry 8 }

		
		-- 1.3.6.1.4.1.5504.5.16.1.2.2.1.9
		zhoneCpeVoipSipDomain OBJECT-TYPE
			SYNTAX InetAddress
			MAX-ACCESS read-create
			STATUS current
			DESCRIPTION
				"This attribute contains the host or domain part of the SIP address of record for users connected to this ONT."
			::= { zhoneCpeVoipServerEntry 9 }

		
		-- 1.3.6.1.4.1.5504.5.16.1.2.2.1.10
		zhoneCpeVoipSipRegistrar OBJECT-TYPE
			SYNTAX InetAddress
			MAX-ACCESS read-create
			STATUS current
			DESCRIPTION
				"Sip Registrar points to a network address ME that contains the name (IP
				25 address or resolved name) of the registrar server for SIP signalling
				messages."
			::= { zhoneCpeVoipServerEntry 10 }

		
		-- 1.3.6.1.4.1.5504.5.16.1.2.2.1.11
		zhoneCpeVoipSoftSwitch OBJECT-TYPE
			SYNTAX ZhoneAdminString
			MAX-ACCESS read-create
			STATUS current
			DESCRIPTION
				"Soft switch identifies the SIP gateway softswitch vendor. The format is
				four ASCII coded alphabetic characters [A..Z] as defined in ANSI T1.220.
				A 30 value of four null characters indicates no particular vendor."
			::= { zhoneCpeVoipServerEntry 11 }

		
		-- 1.3.6.1.4.1.5504.5.16.1.2.2.1.12
		zhoneCpeVoipMgcVersion OBJECT-TYPE
			SYNTAX Integer32 (0..255)
			MAX-ACCESS read-create
			STATUS current
			DESCRIPTION
				"This integer attribute reports the version of the Megaco protocol in use."
			DEFVAL { 0 }
			::= { zhoneCpeVoipServerEntry 12 }

		
		-- 1.3.6.1.4.1.5504.5.16.1.2.2.1.13
		zhoneCpeVoipMgcMessageFormat OBJECT-TYPE
			SYNTAX INTEGER
				{
				long(1),
				short(2),
				binary(3)
				}
			MAX-ACCESS read-create
			STATUS current
			DESCRIPTION
				"This attribute defines the message format."
			DEFVAL { long }
			::= { zhoneCpeVoipServerEntry 13 }

		
		-- 1.3.6.1.4.1.5504.5.16.1.2.2.1.14
		zhoneCpeVoipMgcMaximumRetryTime OBJECT-TYPE
			SYNTAX Integer32 (0..65535)
			MAX-ACCESS read-create
			STATUS current
			DESCRIPTION
				"This attribute specifies the maximum retry time for MGC transactions,
				in seconds. The default value 0 specifies vendor-specific implementation."
			DEFVAL { 0 }
			::= { zhoneCpeVoipServerEntry 14 }

		
		-- 1.3.6.1.4.1.5504.5.16.1.2.2.1.15
		zhoneCpeVoipMgcMaximumRetryAttempts OBJECT-TYPE
			SYNTAX Integer32 (0..65535)
			MAX-ACCESS read-create
			STATUS current
			DESCRIPTION
				"This attribute specifies the maximum number of times a message is
				retransmitted to the MGC. The default value 0 specifies vendor specific
				implementation."
			DEFVAL { 0 }
			::= { zhoneCpeVoipServerEntry 15 }

		
		-- 1.3.6.1.4.1.5504.5.16.1.2.2.1.16
		zhoneCpeVoipMgcServiceChangeDelay OBJECT-TYPE
			SYNTAX Integer32 (0..65535)
			UNITS "seconds"
			MAX-ACCESS read-create
			STATUS current
			DESCRIPTION
				"The attribute specifies the service status delay time for changes in
				line service status. This attribute is specified in seconds. The default
				value 0 specifies no delay."
			DEFVAL { 0 }
			::= { zhoneCpeVoipServerEntry 16 }

		
		-- 1.3.6.1.4.1.5504.5.16.1.2.2.1.17
		zhoneCpeVoipMgcTerminationIdBase OBJECT-TYPE
			SYNTAX OCTET STRING (SIZE (0..25))
			MAX-ACCESS read-create
			STATUS current
			DESCRIPTION
				"The attribute specifies the base string for the H.248 physical termination
				id(s) for this ONT. This string is intended to uniquely identify an ONT.
				Vendor specific termination identifiers (i.e. port ids) are optionally
				added to this string to uniquely identify a termination on a specific ONT."
			::= { zhoneCpeVoipServerEntry 17 }

		
		-- 1.3.6.1.4.1.5504.5.16.1.2.2.1.18
		zhoneCpeVoipReleaseTimer OBJECT-TYPE
			SYNTAX Integer32 (0..255)
			UNITS "seconds"
			MAX-ACCESS read-create
			STATUS current
			DESCRIPTION
				"This attribute contains a release timer defined in seconds. The value 0
				specifies that the ONT is to use its internal default. The default value
				of this 45 attribute is 10 seconds."
			DEFVAL { 10 }
			::= { zhoneCpeVoipServerEntry 18 }

		
		-- 1.3.6.1.4.1.5504.5.16.1.2.2.1.19
		zhoneCpeVoipRohTimer OBJECT-TYPE
			SYNTAX Integer32 (0..255)
			UNITS "seconds"
			MAX-ACCESS read-create
			STATUS current
			DESCRIPTION
				"This attribute defines the time in seconds for the receiver off hook
				condition before ROH tone is applied. The value 0 disables ROH timing.
				The default value is 15 seconds."
			DEFVAL { 15 }
			::= { zhoneCpeVoipServerEntry 19 }

		
		-- 1.3.6.1.4.1.5504.5.16.1.2.2.1.20
		zhoneCpeVoipDscpMark OBJECT-TYPE
			SYNTAX Integer32 (0..255)
			MAX-ACCESS read-create
			STATUS current
			DESCRIPTION
				"Diffserv code point to be used for outgoing RTP packets for this profile.
				The default value is expedited forwarding (EF) = 0x2E."
			DEFVAL { 46 }
			::= { zhoneCpeVoipServerEntry 20 }

		
		-- 1.3.6.1.4.1.5504.5.16.1.2.2.1.21
		zhoneCpeVoipPiggyBackEvents OBJECT-TYPE
			SYNTAX ZhoneEnabledFlag
			MAX-ACCESS read-create
			STATUS current
			DESCRIPTION
				"Enables or disables RTP piggyback events."
			DEFVAL { disabled }
			::= { zhoneCpeVoipServerEntry 21 }

		
		-- 1.3.6.1.4.1.5504.5.16.1.2.2.1.22
		zhoneCpeVoipOobToneEvents OBJECT-TYPE
			SYNTAX ZhoneEnabledFlag
			MAX-ACCESS read-create
			STATUS current
			DESCRIPTION
				"Enables or disables handling of tones via RTP tone events per RFC 4733."
			DEFVAL { disabled }
			::= { zhoneCpeVoipServerEntry 22 }

		
		-- 1.3.6.1.4.1.5504.5.16.1.2.2.1.23
		zhoneCpeVoipOobDtmfEvents OBJECT-TYPE
			SYNTAX ZhoneEnabledFlag
			MAX-ACCESS read-create
			STATUS current
			DESCRIPTION
				"Enables or disables handling of DTMF via RTP DTMF events per RFC 4733."
			DEFVAL { disabled }
			::= { zhoneCpeVoipServerEntry 23 }

		
		-- 1.3.6.1.4.1.5504.5.16.1.2.2.1.24
		zhoneCpeVoipOobCasEvents OBJECT-TYPE
			SYNTAX ZhoneEnabledFlag
			MAX-ACCESS read-create
			STATUS current
			DESCRIPTION
				"Enables or disables handling of CAS via RTP CAS events per RFC 4733."
			DEFVAL { disabled }
			::= { zhoneCpeVoipServerEntry 24 }

		
		-- 1.3.6.1.4.1.5504.5.16.1.2.2.1.25
		zhoneCpeVoipPartialDialTimeout OBJECT-TYPE
			SYNTAX Integer32 (0..65535)
			UNITS "milli seconds"
			MAX-ACCESS read-create
			STATUS current
			DESCRIPTION
				"This attribute defines the partial dial timeout for digit map processing
				in milliseconds. The default value is 16000 ms."
			DEFVAL { 16000 }
			::= { zhoneCpeVoipServerEntry 25 }

		
		-- 1.3.6.1.4.1.5504.5.16.1.2.2.1.26
		zhoneCpeVoipCriticalDialTimeout OBJECT-TYPE
			SYNTAX Integer32 (0..65535)
			UNITS "milli seconds"
			MAX-ACCESS read-create
			STATUS current
			DESCRIPTION
				"This attribute defines the critical dial timeout for digit map processing
				in milliseconds. The default value is 4000 ms."
			DEFVAL { 4000 }
			::= { zhoneCpeVoipServerEntry 26 }

		
		-- 1.3.6.1.4.1.5504.5.16.1.2.2.1.27
		zhoneCpeVoipServerOutboundServer OBJECT-TYPE
			SYNTAX InetAddress
			MAX-ACCESS read-create
			STATUS current
			DESCRIPTION
				"This attribute contains the name (IP address or resolved name) of
				the outbound proxy server for SIP signalling messages."
			::= { zhoneCpeVoipServerEntry 27 }

		
		-- 1.3.6.1.4.1.5504.5.16.1.2.2.1.28
		zhoneCpeVoipServerPortId OBJECT-TYPE
			SYNTAX Integer32 (-1..32767)
			MAX-ACCESS read-create
			STATUS current
			DESCRIPTION
				"This attribute specifies the TCP/UDP port number of the VoIP protocol. 
				The default value -1 select the default port number for the VoIP 
				protocol. It is 2944 for H.248 and 5060 for SIP.
				"
			::= { zhoneCpeVoipServerEntry 28 }

		
		-- 1.3.6.1.4.1.5504.5.16.1.2.2.1.29
		zhoneCpeVoipDtmfEventsPassingMethod OBJECT-TYPE
			SYNTAX INTEGER
				{
				rfc4733(1),
				sipinfo(2)
				}
			MAX-ACCESS read-create
			STATUS current
			DESCRIPTION
				"If zhoneCpeVoipOobDtmfEvents is disabled, dtmp digits are carried along
				the voice path.
				
				If zhoneCpeVoipOobDtmfEvents = enabled, we look at the dtmf-events-passing-method.
				If zhoneCpeVoipDtmfEventsPassingMethod = rfc4733, dtmf digits are carried in the RTP payload.
				If zhoneCpeVoipDtmfEventsPassingMethod = sip-info, dtmf digits are carried along the
				signalling path in the INFO messages."
			DEFVAL { rfc4733 }
			::= { zhoneCpeVoipServerEntry 29 }

		
		-- 1.3.6.1.4.1.5504.5.16.1.2.2.1.30
		zhoneCpeVoipCasEventsPassingMethod OBJECT-TYPE
			SYNTAX INTEGER
				{
				rfc4733(1),
				sipinfo(2)
				}
			MAX-ACCESS read-create
			STATUS current
			DESCRIPTION
				"If zhoneCpeVoipOobCasEvents is disabled, dtmp digits are carried along
				the voice path.
				
				If zhoneCpeVoipOobCasEvents = enabled, we look at the dtmf-events-passing-method.
				If zhoneCpeVoipCasEventsPassingMethod = rfc4733, dtmf digits are carried in the RTP payload.
				If zhoneCpeVoipCasEventsPassingMethod = sip-info, dtmf digits are carried along the
				signalling path in the INFO messages."
			DEFVAL { rfc4733 }
			::= { zhoneCpeVoipServerEntry 30 }

		
		-- 1.3.6.1.4.1.5504.5.16.1.2.2.1.31
		zhoneCpeVoipRtpDscp OBJECT-TYPE
			SYNTAX OCTET STRING (SIZE (1..8))
			MAX-ACCESS read-create
			STATUS current
			DESCRIPTION
				"This parameter indicates DSCP value for cpe voip rtp traffic.
				
				Valid code values:
				
				<0-63>   Differentiated services codepoint value 
				   af11     Mark packets with AF11 dscp (001010) 
				   af12     Mark packets with AF12 dscp (001100) 
				   af13     Mark packets with AF13 dscp (001110) 
				   af21     Mark packets with AF21 dscp (010010) 
				   af22     Mark packets with AF22 dscp (010100) 
				   af23     Mark packets with AF23 dscp (010110) 
				   af31     Mark packets with AF31 dscp (011010) 
				   af32     Mark packets with AF32 dscp (011100) 
				   af33     Mark packets with AF33 dscp (011110) 
				   af41     Mark packets with AF41 dscp (100010) 
				   af42     Mark packets with AF42 dscp (100100) 
				   af43     Mark packets with AF43 dscp (100110) 
				   cs1      Mark packets with CS1(precedence 1) dscp (001000) 
				   cs2      Mark packets with CS2(precedence 2) dscp (010000) 
				   cs3      Mark packets with CS3(precedence 3) dscp (011000) 
				   cs4      Mark packets with CS4(precedence 4) dscp (100000) 
				   cs5      Mark packets with CS5(precedence 5) dscp (101000) 
				   cs6      Mark packets with CS6(precedence 6) dscp (110000) 
				   cs7      Mark packets with CS7(precedence 7) dscp (111000) 
				   default  Mark packets with default dscp (000000) 
				   ef       Mark packets with EF dscp (101110) 
				"
			DEFVAL { "0" }
			::= { zhoneCpeVoipServerEntry 31 }

		
		-- 1.3.6.1.4.1.5504.5.16.1.2.2.1.32
		zhoneCpeVoipSignalingDscp OBJECT-TYPE
			SYNTAX OCTET STRING (SIZE (1..8))
			MAX-ACCESS read-create
			STATUS current
			DESCRIPTION
				"This parameter indicates DSCP value for cpe voip signaling traffic.
				
				Valid code values:
				
				<0-63>   Differentiated services codepoint value 
				   af11     Mark packets with AF11 dscp (001010) 
				   af12     Mark packets with AF12 dscp (001100) 
				   af13     Mark packets with AF13 dscp (001110) 
				   af21     Mark packets with AF21 dscp (010010) 
				   af22     Mark packets with AF22 dscp (010100) 
				   af23     Mark packets with AF23 dscp (010110) 
				   af31     Mark packets with AF31 dscp (011010) 
				   af32     Mark packets with AF32 dscp (011100) 
				   af33     Mark packets with AF33 dscp (011110) 
				   af41     Mark packets with AF41 dscp (100010) 
				   af42     Mark packets with AF42 dscp (100100) 
				   af43     Mark packets with AF43 dscp (100110) 
				   cs1      Mark packets with CS1(precedence 1) dscp (001000) 
				   cs2      Mark packets with CS2(precedence 2) dscp (010000) 
				   cs3      Mark packets with CS3(precedence 3) dscp (011000) 
				   cs4      Mark packets with CS4(precedence 4) dscp (100000) 
				   cs5      Mark packets with CS5(precedence 5) dscp (101000) 
				   cs6      Mark packets with CS6(precedence 6) dscp (110000) 
				   cs7      Mark packets with CS7(precedence 7) dscp (111000) 
				   default  Mark packets with default dscp (000000) 
				   ef       Mark packets with EF dscp (101110) 
				"
			DEFVAL { "0" }
			::= { zhoneCpeVoipServerEntry 32 }

		
		-- 1.3.6.1.4.1.5504.5.16.1.2.2.1.33
		zhoneCpeVoipSipRegRetryTime OBJECT-TYPE
			SYNTAX Unsigned32 (0..2147483647)
			UNITS "seconds"
			MAX-ACCESS read-create
			STATUS current
			DESCRIPTION
				"Sip Reg Retry Time specifies the SIP registration retry time
				in seconds. The default value is 60 seconds."
			DEFVAL { 60 }
			::= { zhoneCpeVoipServerEntry 33 }

		
		-- 1.3.6.1.4.1.5504.5.16.1.2.2.1.34
		zhoneCpeVoipMgcpClientAddressMode OBJECT-TYPE
			SYNTAX INTEGER
				{
				ip(1),
				ipBracketed(2),
				domainName(3)
				}
			MAX-ACCESS read-create
			STATUS current
			DESCRIPTION
				"Ip and IpBracketed will cause the MGCP Client name to be the bound
				voice host IP address. Domain Name will allow the user to input any
				text string, usally a Domain Name."
			DEFVAL { ip }
			::= { zhoneCpeVoipServerEntry 34 }

		
		-- 1.3.6.1.4.1.5504.5.16.1.2.2.1.35
		zhoneCpeVoipMgcpPersistentNotify OBJECT-TYPE
			SYNTAX ZhoneEnabledFlag
			MAX-ACCESS read-create
			STATUS current
			DESCRIPTION
				"When enabled, all switchhook events will be forwarded to the switch
				immediately without regards to what the switch has requested.
				When disabled, the event that the switch has requested will be
				forwarded."
			DEFVAL { disabled }
			::= { zhoneCpeVoipServerEntry 35 }

		
		-- 1.3.6.1.4.1.5504.5.16.1.2.2.1.36
		zhoneCpeVoipPbxNumber OBJECT-TYPE
			SYNTAX OCTET STRING (SIZE (1))
			MAX-ACCESS read-create
			STATUS current
			DESCRIPTION
				"Digit that will be accepted in dialstring and continue to give dial tone - such as dialing 9 for outside number."
			DEFVAL { "9" }
			::= { zhoneCpeVoipServerEntry 36 }

		
		-- 1.3.6.1.4.1.5504.5.16.1.3
		zhoneCpeIpTable OBJECT-TYPE
			SYNTAX SEQUENCE OF ZhoneCpeIpEntry
			MAX-ACCESS not-accessible
			STATUS current
			DESCRIPTION
				"Cpe Ip table for the VoIP feature."
			::= { zhoneCpeObjectID 3 }

		
		-- 1.3.6.1.4.1.5504.5.16.1.3.1
		zhoneCpeIpEntry OBJECT-TYPE
			SYNTAX ZhoneCpeIpEntry
			MAX-ACCESS not-accessible
			STATUS current
			DESCRIPTION
				"Row in the CpeIp table."
			INDEX { zhoneCpeIfIndex, zhoneCpeIpServiceType }
			::= { zhoneCpeIpTable 1 }

		
		ZhoneCpeIpEntry ::=
			SEQUENCE { 
				zhoneCpeIfIndex
					InterfaceIndex,
				zhoneCpeIpServiceType
					INTEGER,
				zhoneCpeIpRowStatus
					ZhoneRowStatus,
				zhoneCpeHostIp
					IpAddress,
				zhoneCpeIpServerProfileIndex
					Integer32
			 }

		-- 1.3.6.1.4.1.5504.5.16.1.3.1.1
		zhoneCpeIfIndex OBJECT-TYPE
			SYNTAX InterfaceIndex
			MAX-ACCESS not-accessible
			STATUS current
			DESCRIPTION
				"This represents the CPE Ip index value."
			::= { zhoneCpeIpEntry 1 }

		
		-- 1.3.6.1.4.1.5504.5.16.1.3.1.2
		zhoneCpeIpServiceType OBJECT-TYPE
			SYNTAX INTEGER
				{
				voip(1),
				pwe(2),
				wifi(3)
				}
			MAX-ACCESS not-accessible
			STATUS current
			DESCRIPTION
				"This represents the CPE Ip service types."
			::= { zhoneCpeIpEntry 2 }

		
		-- 1.3.6.1.4.1.5504.5.16.1.3.1.3
		zhoneCpeIpRowStatus OBJECT-TYPE
			SYNTAX ZhoneRowStatus
			MAX-ACCESS read-create
			STATUS current
			DESCRIPTION
				"Used to create, modify or delete an entry in this table."
			DEFVAL { active }
			::= { zhoneCpeIpEntry 3 }

		
		-- 1.3.6.1.4.1.5504.5.16.1.3.1.4
		zhoneCpeHostIp OBJECT-TYPE
			SYNTAX IpAddress
			MAX-ACCESS read-create
			STATUS current
			DESCRIPTION
				"The address used for IP host services, this attribute has default value 0.0.0.0."
			::= { zhoneCpeIpEntry 4 }

		
		-- 1.3.6.1.4.1.5504.5.16.1.3.1.5
		zhoneCpeIpServerProfileIndex OBJECT-TYPE
			SYNTAX Integer32 (1..2147483647)
			MAX-ACCESS read-create
			STATUS current
			DESCRIPTION
				"This attribute points to the cpe-ip-server profile associated
				with this host IP. When cpe-ip profile is missing, use the default
				cpe-ip-server profile with DHCP enabled."
			DEFVAL { 1 }
			::= { zhoneCpeIpEntry 5 }

		
		-- 1.3.6.1.4.1.5504.5.16.1.4
		zhoneCpeIpServer OBJECT-IDENTITY
			STATUS current
			DESCRIPTION 
				"Cpe Ip Server for the VoIP feature."
			::= { zhoneCpeObjectID 4 }

		
		-- 1.3.6.1.4.1.5504.5.16.1.4.2
		zhoneCpeIpServerIndexNext OBJECT-TYPE
			SYNTAX Integer32
			MAX-ACCESS read-only
			STATUS current
			DESCRIPTION
				"This object contains an appropriate value to be used for the zhoneCpeIpServerIndex
				when creating entries in the zhoneCpeIpServerTable. The value 0 indicates that
				no unassigned entries are available. To obtain the zhoneCpeIpServerIndex value
				for a new entry, the manager issues a management protocol retrieval
				operation to obtain the current value of this object.  After each retrieval,
				the agent should modify the value to the next unassigned index.
				
				After a manager retrieves a value the agent will determine through its local
				policy when this index value will be made available for reuse."
			::= { zhoneCpeIpServer 2 }

		
		-- 1.3.6.1.4.1.5504.5.16.1.4.3
		zhoneCpeIpServerTable OBJECT-TYPE
			SYNTAX SEQUENCE OF ZhoneCpeIpServerEntry
			MAX-ACCESS not-accessible
			STATUS current
			DESCRIPTION
				"Cpe Ip Server table for the VoIP feature."
			::= { zhoneCpeIpServer 3 }

		
		-- 1.3.6.1.4.1.5504.5.16.1.4.3.1
		zhoneCpeIpServerEntry OBJECT-TYPE
			SYNTAX ZhoneCpeIpServerEntry
			MAX-ACCESS not-accessible
			STATUS current
			DESCRIPTION
				"Row in the CpeIpServer table."
			INDEX { zhoneCpeIpServerIndex }
			::= { zhoneCpeIpServerTable 1 }

		
		ZhoneCpeIpServerEntry ::=
			SEQUENCE { 
				zhoneCpeIpServerIndex
					Unsigned32,
				zhoneCpeIpServerRowStatus
					ZhoneRowStatus,
				zhoneCpeIpServerProfileName
					ZhoneAdminString,
				zhoneCpeIpServerHostIpOption
					INTEGER,
				zhoneCpeIpServerNetmask
					IpAddress,
				zhoneCpeIpServerGateway
					IpAddress,
				zhoneCpeIpServerPrimaryDns
					IpAddress,
				zhoneCpeIpServerSecondaryDns
					IpAddress,
				zhoneCpeIpServerFirewallAccess
					BITS,
				zhoneCpeIpServerNat
					INTEGER,
				zhoneCpeIpServerSecureForward
					ZhoneEnabledFlag,
				zhoneCpeIpServerIgmpFunction
					INTEGER,
				zhoneCpeIpServerDefaultIface
					TruthValue,
				zhoneCpeIpServerDnsSrc
					TruthValue,
				zhoneCpeIpServerDnsType
					INTEGER,
				zhoneCpeIpServerMtu
					Unsigned32,
				zhoneCpeIpServerDhcpSnooping
					ZhoneEnabledFlag,
				zhoneCpeIpServerDhcpServer
					IpAddress,
				zhoneCpeIpServerOption82CircuitId
					OCTET STRING,
				zhoneCpeIpServerOption82RemoteId
					OCTET STRING,
				zhoneCpeIpServerIpv6HostIpOption
					INTEGER,
				zhoneCpeIpServerIpv6PrefixLength
					Unsigned32,
				zhoneCpeIpServerIpv6Gateway
					InetAddressIPv6,
				zhoneCpeIpServerIpv6PrimaryDns
					InetAddressIPv6,
				zhoneCpeIpServerIpv6SecondaryDns
					InetAddressIPv6,
				zhoneCpeIpServerIpv6DnsType
					INTEGER,
				zhoneCpeIpServerIgmpv3
					ZhoneEnabledFlag,
				zhoneCpeIpServerIgmpSnoopingQuerier
					ZhoneEnabledFlag
			 }

		-- 1.3.6.1.4.1.5504.5.16.1.4.3.1.1
		zhoneCpeIpServerIndex OBJECT-TYPE
			SYNTAX Unsigned32 (1..2147483647)
			MAX-ACCESS not-accessible
			STATUS current
			DESCRIPTION
				"This represents the CPE Ip server index value."
			::= { zhoneCpeIpServerEntry 1 }

		
		-- 1.3.6.1.4.1.5504.5.16.1.4.3.1.2
		zhoneCpeIpServerRowStatus OBJECT-TYPE
			SYNTAX ZhoneRowStatus
			MAX-ACCESS read-create
			STATUS current
			DESCRIPTION
				"Used to create, modify or delete an entry in this table."
			DEFVAL { active }
			::= { zhoneCpeIpServerEntry 2 }

		
		-- 1.3.6.1.4.1.5504.5.16.1.4.3.1.3
		zhoneCpeIpServerProfileName OBJECT-TYPE
			SYNTAX ZhoneAdminString
			MAX-ACCESS read-create
			STATUS current
			DESCRIPTION
				"CPE Ip server profile for the VoIP services for the dynamic bridging.
				This field is only writable upon creation and must be unique within its
				table."
			::= { zhoneCpeIpServerEntry 3 }

		
		-- 1.3.6.1.4.1.5504.5.16.1.4.3.1.4
		zhoneCpeIpServerHostIpOption OBJECT-TYPE
			SYNTAX INTEGER
				{
				dhcp(1),
				static(2),
				unconfigured(3)
				}
			MAX-ACCESS read-create
			STATUS current
			DESCRIPTION
				"This attribute selects an IP related option."
			DEFVAL { dhcp }
			::= { zhoneCpeIpServerEntry 4 }

		
		-- 1.3.6.1.4.1.5504.5.16.1.4.3.1.5
		zhoneCpeIpServerNetmask OBJECT-TYPE
			SYNTAX IpAddress
			MAX-ACCESS read-create
			STATUS current
			DESCRIPTION
				"The subnet mask for IP host services."
			DEFVAL { 'ffffff00'h }
			::= { zhoneCpeIpServerEntry 5 }

		
		-- 1.3.6.1.4.1.5504.5.16.1.4.3.1.6
		zhoneCpeIpServerGateway OBJECT-TYPE
			SYNTAX IpAddress
			MAX-ACCESS read-create
			STATUS current
			DESCRIPTION
				"The default gateway address used for IP host services, this attribute
				has the default value 0.0.0.0."
			::= { zhoneCpeIpServerEntry 6 }

		
		-- 1.3.6.1.4.1.5504.5.16.1.4.3.1.7
		zhoneCpeIpServerPrimaryDns OBJECT-TYPE
			SYNTAX IpAddress
			MAX-ACCESS read-create
			STATUS current
			DESCRIPTION
				"This attribute specifies the primary DNS IP address. If this value is
				0.0.0.0, no primary SIP DNS is defined. The default value is 0.0.0.0"
			::= { zhoneCpeIpServerEntry 7 }

		
		-- 1.3.6.1.4.1.5504.5.16.1.4.3.1.8
		zhoneCpeIpServerSecondaryDns OBJECT-TYPE
			SYNTAX IpAddress
			MAX-ACCESS read-create
			STATUS current
			DESCRIPTION
				"This attribute specifies the secondary DNS IP address. If this value
				is 0.0.0.0, no secondary SIP DNS is defined. The default value is 0.0.0.0."
			::= { zhoneCpeIpServerEntry 8 }

		
		-- 1.3.6.1.4.1.5504.5.16.1.4.3.1.9
		zhoneCpeIpServerFirewallAccess OBJECT-TYPE
			SYNTAX BITS
				{
				http(0),
				ping(1),
				snmp(2),
				snmptrap(3),
				ssh(4),
				telnet(5)
				}
			MAX-ACCESS read-create
			STATUS current
			DESCRIPTION
				"Lists the protocols allowed on this interface. The firewall option must be enabled before these settings
				will take effect."
			::= { zhoneCpeIpServerEntry 9 }

		
		-- 1.3.6.1.4.1.5504.5.16.1.4.3.1.10
		zhoneCpeIpServerNat OBJECT-TYPE
			SYNTAX INTEGER
				{
				nat(1),
				napt(2),
				disabled(3)
				}
			MAX-ACCESS read-create
			STATUS current
			DESCRIPTION
				"When it is enabled, NAT/NAPT function is performed to translate between the public IP address and the private
				addresses. It is only supported on a WAN interface."
			DEFVAL { nat }
			::= { zhoneCpeIpServerEntry 10 }

		
		-- 1.3.6.1.4.1.5504.5.16.1.4.3.1.11
		zhoneCpeIpServerSecureForward OBJECT-TYPE
			SYNTAX ZhoneEnabledFlag
			MAX-ACCESS read-create
			STATUS current
			DESCRIPTION
				"When this mode is enabled, packets are not flooded to all ports. Instead, all
				packets are forwarded to the port that is designated as the uplink port. In
				this mode, users are prevented from directly communicating with each other,
				and broadcast frames are discarded."
			DEFVAL { disabled }
			::= { zhoneCpeIpServerEntry 11 }

		
		-- 1.3.6.1.4.1.5504.5.16.1.4.3.1.12
		zhoneCpeIpServerIgmpFunction OBJECT-TYPE
			SYNTAX INTEGER
				{
				none(1),
				snooping(2),
				proxy(3),
				snoopingproxy(4)
				}
			MAX-ACCESS read-create
			STATUS current
			DESCRIPTION
				"Enable an Igmp snooping function."
			DEFVAL { none }
			::= { zhoneCpeIpServerEntry 12 }

		
		-- 1.3.6.1.4.1.5504.5.16.1.4.3.1.13
		zhoneCpeIpServerDefaultIface OBJECT-TYPE
			SYNTAX TruthValue
			MAX-ACCESS read-write
			STATUS current
			DESCRIPTION
				"When true, an internally generated packet 
				(e.g., from SNMP trap, SNTP, etc.) is sent out through this 
				interface if the destination IP address is not defined 
				in the route table.
				
				"
			DEFVAL { false }
			::= { zhoneCpeIpServerEntry 13 }

		
		-- 1.3.6.1.4.1.5504.5.16.1.4.3.1.14
		zhoneCpeIpServerDnsSrc OBJECT-TYPE
			SYNTAX TruthValue
			MAX-ACCESS read-write
			STATUS current
			DESCRIPTION
				"When true, the Interface is used by the 
				DHCP Client to obtain DNS information."
			DEFVAL { false }
			::= { zhoneCpeIpServerEntry 14 }

		
		-- 1.3.6.1.4.1.5504.5.16.1.4.3.1.15
		zhoneCpeIpServerDnsType OBJECT-TYPE
			SYNTAX INTEGER
				{
				default(1),
				static(2),
				proxy(3)
				}
			MAX-ACCESS read-write
			STATUS current
			DESCRIPTION
				"Default - Get the DNS information from the WAN interface
				Static - The DNS information is manually provisioned
				Proxy - Enable interface to act as a proxy for DNS requests
				
				                        "
			DEFVAL { default }
			::= { zhoneCpeIpServerEntry 15 }

		
		-- 1.3.6.1.4.1.5504.5.16.1.4.3.1.16
		zhoneCpeIpServerMtu OBJECT-TYPE
			SYNTAX Unsigned32 (0..1540)
			MAX-ACCESS read-write
			STATUS current
			DESCRIPTION
				"The maximum size of IP packet that can be transmitted without
				fragmentation - including IP headers but excluding headers 
				from lower levels in the protocol stack.The default MTU size
				is 1500 bytes."
			DEFVAL { 1500 }
			::= { zhoneCpeIpServerEntry 16 }

		
		-- 1.3.6.1.4.1.5504.5.16.1.4.3.1.17
		zhoneCpeIpServerDhcpSnooping OBJECT-TYPE
			SYNTAX ZhoneEnabledFlag
			MAX-ACCESS read-create
			STATUS current
			DESCRIPTION
				"Enables or disables DHCP Snooping for the LAN device."
			DEFVAL { disabled }
			::= { zhoneCpeIpServerEntry 17 }

		
		-- 1.3.6.1.4.1.5504.5.16.1.4.3.1.18
		zhoneCpeIpServerDhcpServer OBJECT-TYPE
			SYNTAX IpAddress
			MAX-ACCESS read-create
			STATUS current
			DESCRIPTION
				"DHCP Server IP Address."
			DEFVAL { '00000000'h }
			::= { zhoneCpeIpServerEntry 18 }

		
		-- 1.3.6.1.4.1.5504.5.16.1.4.3.1.19
		zhoneCpeIpServerOption82CircuitId OBJECT-TYPE
			SYNTAX OCTET STRING (SIZE (0..128))
			MAX-ACCESS read-create
			STATUS current
			DESCRIPTION
				"This field is used to set DHCP Option82 Circuit Id."
			DEFVAL { "$CoSystemIP$CoSlot$CoPort$CoSubport$CpPortAlias" }
			::= { zhoneCpeIpServerEntry 19 }

		
		-- 1.3.6.1.4.1.5504.5.16.1.4.3.1.20
		zhoneCpeIpServerOption82RemoteId OBJECT-TYPE
			SYNTAX OCTET STRING (SIZE (0..128))
			MAX-ACCESS read-create
			STATUS current
			DESCRIPTION
				"This field is used to set DHCP Option82 Remote Id."
			DEFVAL { "$CpSystemName$CpMAC$CpFSAN" }
			::= { zhoneCpeIpServerEntry 20 }

		
		-- 1.3.6.1.4.1.5504.5.16.1.4.3.1.21
		zhoneCpeIpServerIpv6HostIpOption OBJECT-TYPE
			SYNTAX INTEGER
				{
				unconfigured(2),
				autoconfig(3),
				dhcp(4),
				prefixDelegation(5),
				static(6),
				eui64(7),
				unnumbered(8),
				unnumberedDHCPPD(9)
				}
			MAX-ACCESS read-create
			STATUS current
			DESCRIPTION
				"This attribute represents the method used to assign an ipv6
				address on the WAN-side of the CPE. 
				Enumeration of:
				unconfigured(2)     - The IPv6 address is not configured
				autoconfig(3)       - The Ipv6 address is derived automatically by EUI-64
				                      method using the IPv6 Network Prefix, IPv6 Prefix Length,
				                      default router IPv6 address obtained from network routers 
				                      ( SLACC )
				dhcp(4)             - The IPv6 address is assigned via DHCP server
				                      ( stateful DHCPV6) 
				prefixDelegation(5) - prefixDelegation is only applicable on  LAN Ipv6 interfaces.
				                      When an IPv6 enabled LAN interface is configured for lanPD,
				                      the system will automatically assign it an IPv6 address
				                      from the prefix delegation obtained from the IPv6 
				                      enabled WAN interface.  
				static(6)           - The IPv6 address is assigned manually  
				eui64(7)            - The Ipv6 address is derived by EUI-64 method using the 
				                      specified IPv6 Network Prefix and IPv6 Prefix Length
				unnumbered(8)       - IP unnumbered allows an interface to borrow the IPv6 address
				                      of another interface from the same device.
				unnumberedDHCPPD(9) - unnumberedDHCPPD is only applicable on WAN IPv6 interfaces.
				                      When an IPv6 enabled WAN interface is configured for 
				                      unnumberedDHCPPD, the system uses DHCPv6 to acquire a 
				                      prefix delegation for the IPv6 enabled LAN interface.
				                      The system will not assign the IPv6 enabled WAN interface
				                      an IPv6 address"
			DEFVAL { unconfigured }
			::= { zhoneCpeIpServerEntry 21 }

		
		-- 1.3.6.1.4.1.5504.5.16.1.4.3.1.22
		zhoneCpeIpServerIpv6PrefixLength OBJECT-TYPE
			SYNTAX Unsigned32 (1..128)
			MAX-ACCESS read-create
			STATUS current
			DESCRIPTION
				"This attribute specifies the IPv6 prefix length,
				The default value is 64"
			DEFVAL { 64 }
			::= { zhoneCpeIpServerEntry 22 }

		
		-- 1.3.6.1.4.1.5504.5.16.1.4.3.1.23
		zhoneCpeIpServerIpv6Gateway OBJECT-TYPE
			SYNTAX InetAddressIPv6
			MAX-ACCESS read-create
			STATUS current
			DESCRIPTION
				"This attribute specifies the default gateway IPv6 address,
				The default value is ::/128"
			DEFVAL { "::" }
			::= { zhoneCpeIpServerEntry 23 }

		
		-- 1.3.6.1.4.1.5504.5.16.1.4.3.1.24
		zhoneCpeIpServerIpv6PrimaryDns OBJECT-TYPE
			SYNTAX InetAddressIPv6
			MAX-ACCESS read-create
			STATUS current
			DESCRIPTION
				"This attribute specifies the IPV6 primary DNS IP address, 
				The default value is ::/128"
			DEFVAL { "::" }
			::= { zhoneCpeIpServerEntry 24 }

		
		-- 1.3.6.1.4.1.5504.5.16.1.4.3.1.25
		zhoneCpeIpServerIpv6SecondaryDns OBJECT-TYPE
			SYNTAX InetAddressIPv6
			MAX-ACCESS read-create
			STATUS current
			DESCRIPTION
				"This attribute specifies the IPv6 secondary DNS IP address. 
				The default value is ::/128"
			DEFVAL { "::" }
			::= { zhoneCpeIpServerEntry 25 }

		
		-- 1.3.6.1.4.1.5504.5.16.1.4.3.1.26
		zhoneCpeIpServerIpv6DnsType OBJECT-TYPE
			SYNTAX INTEGER
				{
				default(1),
				static(2),
				proxy(3)
				}
			MAX-ACCESS read-create
			STATUS current
			DESCRIPTION
				"This attribute specifies the DNS mode for this IPv6 interface. 
				Enumeration of:
				default - Get the DNS information from the WAN interface
				static  - The DNS information is manually provisioned
				proxy   - Enable interface to act as a proxy for DNS requests"
			DEFVAL { proxy }
			::= { zhoneCpeIpServerEntry 26 }

		
-- 
-- 
		-- 1.3.6.1.4.1.5504.5.16.1.4.3.1.27
		zhoneCpeIpServerIgmpv3 OBJECT-TYPE
			SYNTAX ZhoneEnabledFlag
			MAX-ACCESS read-create
			STATUS current
			DESCRIPTION
				"This attribute enables or disables IGMPv3.
				 
				IGMPv3 adds support for source filtering, which enables a multicast receiver
				host to signal to a router which groups it wants to receive multicast traffic
				from, and from which source(s) this traffic is expected."
			DEFVAL { disabled }
			::= { zhoneCpeIpServerEntry 27 }

		
-- 
-- 
		-- 1.3.6.1.4.1.5504.5.16.1.4.3.1.28
		zhoneCpeIpServerIgmpSnoopingQuerier OBJECT-TYPE
			SYNTAX ZhoneEnabledFlag
			MAX-ACCESS read-create
			STATUS current
			DESCRIPTION
				"This attribute enables or disables the IGMP snooping querier.
				 
				The IGMP snooping querier sends membership queries when there is no multicast
				router in the VLAN to originate the queries.  When an IGMP snooping querier is
				enabled, it sends out periodic IGMP queries that trigger IGMP report messages
				from hosts that want to receive IP multicast traffic.   IGMP snooping  listens
				to these IGMP reports to establish appropriate forwarding."
			DEFVAL { disabled }
			::= { zhoneCpeIpServerEntry 28 }

		
		-- 1.3.6.1.4.1.5504.5.16.1.5
		zhoneCpeVoipFeatures OBJECT-IDENTITY
			STATUS current
			DESCRIPTION 
				"Cpe Voip Features for the VoIP feature."
			::= { zhoneCpeObjectID 5 }

		
		-- 1.3.6.1.4.1.5504.5.16.1.5.1
		zhoneCpeVoipFeaturesIndexNext OBJECT-TYPE
			SYNTAX Integer32
			MAX-ACCESS read-only
			STATUS current
			DESCRIPTION
				"This object contains an appropriate value to be used for the zhoneCpeVoipFeaturesIndex
				when creating entries in the zhoneCpeVoipFeaturesTable. The value 0 indicates that
				no unassigned entries are available. To obtain the zhoneCpeVoipFeaturesIndex value
				for a new entry, the manager issues a management protocol retrieval
				operation to obtain the current value of this object.  After each retrieval,
				the agent should modify the value to the next unassigned index.
				
				After a manager retrieves a value the agent will determine through its local
				policy when this index value will be made available for reuse."
			::= { zhoneCpeVoipFeatures 1 }

		
		-- 1.3.6.1.4.1.5504.5.16.1.5.2
		zhoneCpeVoipFeaturesTable OBJECT-TYPE
			SYNTAX SEQUENCE OF ZhoneCpeVoipFeaturesEntry
			MAX-ACCESS not-accessible
			STATUS current
			DESCRIPTION
				"Cpe Voip Features table for the VoIP feature."
			::= { zhoneCpeVoipFeatures 2 }

		
		-- 1.3.6.1.4.1.5504.5.16.1.5.2.1
		zhoneCpeVoipFeaturesEntry OBJECT-TYPE
			SYNTAX ZhoneCpeVoipFeaturesEntry
			MAX-ACCESS not-accessible
			STATUS current
			DESCRIPTION
				"Row in the CpeVoipFeatures table."
			INDEX { zhoneCpeVoipFeaturesIndex }
			::= { zhoneCpeVoipFeaturesTable 1 }

		
		ZhoneCpeVoipFeaturesEntry ::=
			SEQUENCE { 
				zhoneCpeVoipFeaturesIndex
					Unsigned32,
				zhoneCpeVoipFeaturesRowStatus
					ZhoneRowStatus,
				zhoneCpeVoipFeaturesProfileName
					ZhoneAdminString,
				zhoneCpeVoipFeaturesAnnouncementType
					INTEGER,
				zhoneCpeVoipCidFeatures
					BITS,
				zhoneCpeVoipCallWaitingFeatures
					BITS,
				zhoneCpeVoipCallProgressOrTransferFeatures
					BITS,
				zhoneCpeVoipCallPresentationFeatures
					BITS,
				zhoneCpeVoipFeaturesHotLine
					INTEGER,
				zhoneCpeVoipFeaturesHotLineNumber
					OCTET STRING,
				zhoneCpeVoipFeaturesWarmLineTimer
					Unsigned32,
				zhoneCpeVoipFeaturesConferenceOptions
					INTEGER,
				zhoneCpeVoipFeaturesConferenceUri
					OCTET STRING
			 }

		-- 1.3.6.1.4.1.5504.5.16.1.5.2.1.1
		zhoneCpeVoipFeaturesIndex OBJECT-TYPE
			SYNTAX Unsigned32 (1..2147483647)
			MAX-ACCESS not-accessible
			STATUS current
			DESCRIPTION
				"This represents the CPE Voip Features index value."
			::= { zhoneCpeVoipFeaturesEntry 1 }

		
		-- 1.3.6.1.4.1.5504.5.16.1.5.2.1.2
		zhoneCpeVoipFeaturesRowStatus OBJECT-TYPE
			SYNTAX ZhoneRowStatus
			MAX-ACCESS read-create
			STATUS current
			DESCRIPTION
				"Used to create, modify or delete an entry in this table."
			DEFVAL { active }
			::= { zhoneCpeVoipFeaturesEntry 2 }

		
		-- 1.3.6.1.4.1.5504.5.16.1.5.2.1.3
		zhoneCpeVoipFeaturesProfileName OBJECT-TYPE
			SYNTAX ZhoneAdminString
			MAX-ACCESS read-create
			STATUS current
			DESCRIPTION
				"CPE Voip Media profile for the dynamic bridging VoIP services.
				This field is only writable upon creation and must be unique within its
				table."
			::= { zhoneCpeVoipFeaturesEntry 3 }

		
		-- 1.3.6.1.4.1.5504.5.16.1.5.2.1.4
		zhoneCpeVoipFeaturesAnnouncementType OBJECT-TYPE
			SYNTAX INTEGER
				{
				silence(1),
				reordertone(2),
				fastbusy(3),
				voice(4),
				notapplicable(5)
				}
			MAX-ACCESS read-create
			STATUS current
			DESCRIPTION
				"This attribute specifies the treatment when a subscriber goes off hook
				but does not attempt a call."
			DEFVAL { reordertone }
			::= { zhoneCpeVoipFeaturesEntry 4 }

		
		-- 1.3.6.1.4.1.5504.5.16.1.5.2.1.5
		zhoneCpeVoipCidFeatures OBJECT-TYPE
			SYNTAX BITS
				{
				callingnumber(0),
				callingname(1),
				cidblocking(2),
				cidnumber(3),
				cidname(4),
				anonymouscidblocking(5)
				}
			MAX-ACCESS read-create
			STATUS current
			DESCRIPTION
				"This attribute contains a bit map of caller ID features. By default all the
				bits are set."
			::= { zhoneCpeVoipFeaturesEntry 5 }

		
		-- 1.3.6.1.4.1.5504.5.16.1.5.2.1.6
		zhoneCpeVoipCallWaitingFeatures OBJECT-TYPE
			SYNTAX BITS
				{
				callwaiting(0),
				cidannouncement(1)
				}
			MAX-ACCESS read-create
			STATUS current
			DESCRIPTION
				"This attribute contains a bit map of call waiting features. By default all the
				bits are set."
			::= { zhoneCpeVoipFeaturesEntry 6 }

		
		-- 1.3.6.1.4.1.5504.5.16.1.5.2.1.7
		zhoneCpeVoipCallProgressOrTransferFeatures OBJECT-TYPE
			SYNTAX BITS
				{
				threeway(0),
				calltransfer(1),
				callhold(2),
				callpark(3),
				donotdisturb(4),
				flashonemergency(5),
				emergencyhold(6),
				sixway(7),
				pbxdialing(8)
				}
			MAX-ACCESS read-create
			STATUS current
			DESCRIPTION
				"This attribute is a bit map of call processing features. By default all the
				bits are set except pbx-dialing feature."
			::= { zhoneCpeVoipFeaturesEntry 7 }

		
		-- 1.3.6.1.4.1.5504.5.16.1.5.2.1.8
		zhoneCpeVoipCallPresentationFeatures OBJECT-TYPE
			SYNTAX BITS
				{
				msgwaitsplashring(0),
				msgwaitspecialdialtone(1),
				msgwaitvisual(2),
				callfwd(3)
				}
			MAX-ACCESS read-create
			STATUS current
			DESCRIPTION
				"This attribute is a bit map of call presentation features. By default all the
				bits are set."
			::= { zhoneCpeVoipFeaturesEntry 8 }

		
		-- 1.3.6.1.4.1.5504.5.16.1.5.2.1.9
		zhoneCpeVoipFeaturesHotLine OBJECT-TYPE
			SYNTAX INTEGER
				{
				disabled(1),
				hot(2),
				warm(3)
				}
			MAX-ACCESS read-create
			STATUS current
			DESCRIPTION
				"When the hotline is hot, the phone will immediately dial the
				Hotline number. When the hotline is warm, the phone wait for
				the period specified in warmline-timer in ms before automatically dial the hotline number. "
			DEFVAL { disabled }
			::= { zhoneCpeVoipFeaturesEntry 9 }

		
		-- 1.3.6.1.4.1.5504.5.16.1.5.2.1.10
		zhoneCpeVoipFeaturesHotLineNumber OBJECT-TYPE
			SYNTAX OCTET STRING (SIZE (0..127))
			MAX-ACCESS read-create
			STATUS current
			DESCRIPTION
				"The number this phone will automatically dial,
				if hotline or warmline feature is enabled."
			::= { zhoneCpeVoipFeaturesEntry 10 }

		
		-- 1.3.6.1.4.1.5504.5.16.1.5.2.1.11
		zhoneCpeVoipFeaturesWarmLineTimer OBJECT-TYPE
			SYNTAX Unsigned32 (200..30000)
			UNITS "ms"
			MAX-ACCESS read-create
			STATUS current
			DESCRIPTION
				"The wait period before a warmline automcatically dial the hotline number."
			DEFVAL { 200 }
			::= { zhoneCpeVoipFeaturesEntry 11 }

		
		-- 1.3.6.1.4.1.5504.5.16.1.5.2.1.12
		zhoneCpeVoipFeaturesConferenceOptions OBJECT-TYPE
			SYNTAX INTEGER
				{
				local(1),
				referServer(2),
				referParticipants(3),
				imsFlashServer(4)
				}
			MAX-ACCESS read-create
			STATUS current
			DESCRIPTION
				"Configure the SIP Client Conference Option of:
				        local(1),
				        referServer(2),
				        referParticipants(3),
				        imsFlashServer(4)"
			DEFVAL { local }
			::= { zhoneCpeVoipFeaturesEntry 12 }

		
		-- 1.3.6.1.4.1.5504.5.16.1.5.2.1.13
		zhoneCpeVoipFeaturesConferenceUri OBJECT-TYPE
			SYNTAX OCTET STRING (SIZE (0..128))
			MAX-ACCESS read-create
			STATUS current
			DESCRIPTION
				"Configure the SIP Client Conference URI"
			DEFVAL { "" }
			::= { zhoneCpeVoipFeaturesEntry 13 }

		
		-- 1.3.6.1.4.1.5504.5.16.1.6
		zhoneCpeVoipMedia OBJECT-IDENTITY
			STATUS current
			DESCRIPTION 
				"Cpe Voip Media for the VoIP feature."
			::= { zhoneCpeObjectID 6 }

		
		-- 1.3.6.1.4.1.5504.5.16.1.6.1
		zhoneCpeVoipMediaIndexNext OBJECT-TYPE
			SYNTAX Integer32
			MAX-ACCESS read-only
			STATUS current
			DESCRIPTION
				"This object contains an appropriate value to be used for the zhoneCpeVoipMediaIndex
				when creating entries in the zhoneCpeVoipMediaTable. The value 0 indicates that
				no unassigned entries are available. To obtain the zhoneCpeVoipMediaIndex value
				for a new entry, the manager issues a management protocol retrieval
				operation to obtain the current value of this object.  After each retrieval,
				the agent should modify the value to the next unassigned index.
				
				After a manager retrieves a value the agent will determine through its local
				policy when this index value will be made available for reuse."
			::= { zhoneCpeVoipMedia 1 }

		
		-- 1.3.6.1.4.1.5504.5.16.1.6.2
		zhoneCpeVoipMediaTable OBJECT-TYPE
			SYNTAX SEQUENCE OF ZhoneCpeVoipMediaEntry
			MAX-ACCESS not-accessible
			STATUS current
			DESCRIPTION
				"Cpe Voip Media table for the VoIP feature."
			::= { zhoneCpeVoipMedia 2 }

		
		-- 1.3.6.1.4.1.5504.5.16.1.6.2.1
		zhoneCpeVoipMediaEntry OBJECT-TYPE
			SYNTAX ZhoneCpeVoipMediaEntry
			MAX-ACCESS not-accessible
			STATUS current
			DESCRIPTION
				"Row in the CpeVoipMedia table."
			INDEX { zhoneCpeVoipMediaIndex }
			::= { zhoneCpeVoipMediaTable 1 }

		
		ZhoneCpeVoipMediaEntry ::=
			SEQUENCE { 
				zhoneCpeVoipMediaIndex
					Unsigned32,
				zhoneCpeVoipMediaRowStatus
					ZhoneRowStatus,
				zhoneCpeVoipMediaProfileName
					ZhoneAdminString,
				zhoneCpeVoipMediaEchoCancel
					ZhoneEnabledFlag,
				zhoneCpeVoipFaxMode
					INTEGER,
				zhoneCpeVoipCodecSelectionFirstOrder
					INTEGER,
				zhoneCpeVoipPacketPeriodSelectionFirstOrder
					Integer32,
				zhoneCpeVoipSilenceSuppressionFirstOrder
					ZhoneEnabledFlag,
				zhoneCpeVoipCodecSelectionSecondOrder
					INTEGER,
				zhoneCpeVoipPacketPeriodSelectionSecondOrder
					Integer32,
				zhoneCpeVoipSilenceSuppressionSecondOrder
					ZhoneEnabledFlag,
				zhoneCpeVoipCodecSelectionThirdOrder
					INTEGER,
				zhoneCpeVoipPacketPeriodSelectionThirdOrder
					Integer32,
				zhoneCpeVoipSilenceSuppressionThirdOrder
					ZhoneEnabledFlag,
				zhoneCpeVoipCodecSelectionFourthOrder
					INTEGER,
				zhoneCpeVoipPacketPeriodSelectionFourthOrder
					Integer32,
				zhoneCpeVoipSilenceSuppressionFourthOrder
					ZhoneEnabledFlag,
				zhoneCpeVoipMediaHookFlashTimerMin
					Integer32,
				zhoneCpeVoipMediaHookFlashTimerMax
					Integer32
			 }

		-- 1.3.6.1.4.1.5504.5.16.1.6.2.1.1
		zhoneCpeVoipMediaIndex OBJECT-TYPE
			SYNTAX Unsigned32 (1..2147483647)
			MAX-ACCESS not-accessible
			STATUS current
			DESCRIPTION
				"This represents the CPE Voip Media index value."
			::= { zhoneCpeVoipMediaEntry 1 }

		
		-- 1.3.6.1.4.1.5504.5.16.1.6.2.1.2
		zhoneCpeVoipMediaRowStatus OBJECT-TYPE
			SYNTAX ZhoneRowStatus
			MAX-ACCESS read-create
			STATUS current
			DESCRIPTION
				"Used to create, modify or delete an entry in this table."
			DEFVAL { active }
			::= { zhoneCpeVoipMediaEntry 2 }

		
		-- 1.3.6.1.4.1.5504.5.16.1.6.2.1.3
		zhoneCpeVoipMediaProfileName OBJECT-TYPE
			SYNTAX ZhoneAdminString
			MAX-ACCESS read-create
			STATUS current
			DESCRIPTION
				"CPE Voip Media profile for the dynamic bridging VoIP services.
				This field is only writable upon creation and must be unique within its
				table."
			::= { zhoneCpeVoipMediaEntry 3 }

		
		-- 1.3.6.1.4.1.5504.5.16.1.6.2.1.4
		zhoneCpeVoipMediaEchoCancel OBJECT-TYPE
			SYNTAX ZhoneEnabledFlag
			MAX-ACCESS read-create
			STATUS current
			DESCRIPTION
				"This attribute turns on and off echo cancellation."
			DEFVAL { enabled }
			::= { zhoneCpeVoipMediaEntry 4 }

		
		-- 1.3.6.1.4.1.5504.5.16.1.6.2.1.5
		zhoneCpeVoipFaxMode OBJECT-TYPE
			SYNTAX INTEGER
				{
				passthrough(1),
				t38(2)
				}
			MAX-ACCESS read-create
			STATUS current
			DESCRIPTION
				"This attribute selects the fax mode."
			DEFVAL { passthrough }
			::= { zhoneCpeVoipMediaEntry 5 }

		
		-- 1.3.6.1.4.1.5504.5.16.1.6.2.1.6
		zhoneCpeVoipCodecSelectionFirstOrder OBJECT-TYPE
			SYNTAX INTEGER
				{
				pcmu(1),
				gsm(2),
				g723(3),
				dvi4eightKHz(4),
				dvi4sixteenKHz(5),
				lpc(6),
				pcma(7),
				g722(8),
				l16twochannels(9),
				l16onechannel(10),
				qcelp(11),
				cn(12),
				mpa(13),
				g728(14),
				dvi411(15),
				dvi422(16),
				g729(17)
				}
			MAX-ACCESS read-create
			STATUS current
			DESCRIPTION
				"This attribute specifies codec selection as defined by RFC 3551."
			DEFVAL { pcmu }
			::= { zhoneCpeVoipMediaEntry 6 }

		
		-- 1.3.6.1.4.1.5504.5.16.1.6.2.1.7
		zhoneCpeVoipPacketPeriodSelectionFirstOrder OBJECT-TYPE
			SYNTAX Integer32 (10..30)
			UNITS "milli seconds"
			MAX-ACCESS read-create
			STATUS current
			DESCRIPTION
				"This attribute specifies the packet period selection interval in
				milliseconds. The default value is 20. Valid values are 10..30 ms."
			DEFVAL { 20 }
			::= { zhoneCpeVoipMediaEntry 7 }

		
		-- 1.3.6.1.4.1.5504.5.16.1.6.2.1.8
		zhoneCpeVoipSilenceSuppressionFirstOrder OBJECT-TYPE
			SYNTAX ZhoneEnabledFlag
			MAX-ACCESS read-create
			STATUS current
			DESCRIPTION
				"This attribute specifies whether silence suppression is on or off."
			DEFVAL { disabled }
			::= { zhoneCpeVoipMediaEntry 8 }

		
		-- 1.3.6.1.4.1.5504.5.16.1.6.2.1.9
		zhoneCpeVoipCodecSelectionSecondOrder OBJECT-TYPE
			SYNTAX INTEGER
				{
				pcmu(1),
				gsm(2),
				g723(3),
				dvi4eightKHz(4),
				dvi4sixteenKHz(5),
				lpc(6),
				pcma(7),
				g722(8),
				l16twochannels(9),
				l16onechannel(10),
				qcelp(11),
				cn(12),
				mpa(13),
				g728(14),
				dvi411(15),
				dvi422(16),
				g729(17)
				}
			MAX-ACCESS read-create
			STATUS current
			DESCRIPTION
				"This attribute specifies codec selection as defined by RFC 3551."
			DEFVAL { pcmu }
			::= { zhoneCpeVoipMediaEntry 9 }

		
		-- 1.3.6.1.4.1.5504.5.16.1.6.2.1.10
		zhoneCpeVoipPacketPeriodSelectionSecondOrder OBJECT-TYPE
			SYNTAX Integer32 (10..30)
			UNITS "milli seconds"
			MAX-ACCESS read-create
			STATUS current
			DESCRIPTION
				"This attribute specifies the packet period selection interval in
				milliseconds. The default value is 20. Valid values are 10..30 ms."
			DEFVAL { 20 }
			::= { zhoneCpeVoipMediaEntry 10 }

		
		-- 1.3.6.1.4.1.5504.5.16.1.6.2.1.11
		zhoneCpeVoipSilenceSuppressionSecondOrder OBJECT-TYPE
			SYNTAX ZhoneEnabledFlag
			MAX-ACCESS read-create
			STATUS current
			DESCRIPTION
				"This attribute specifies whether silence suppression is on or off."
			DEFVAL { disabled }
			::= { zhoneCpeVoipMediaEntry 11 }

		
		-- 1.3.6.1.4.1.5504.5.16.1.6.2.1.12
		zhoneCpeVoipCodecSelectionThirdOrder OBJECT-TYPE
			SYNTAX INTEGER
				{
				pcmu(1),
				gsm(2),
				g723(3),
				dvi4eightKHz(4),
				dvi4sixteenKHz(5),
				lpc(6),
				pcma(7),
				g722(8),
				l16twochannels(9),
				l16onechannel(10),
				qcelp(11),
				cn(12),
				mpa(13),
				g728(14),
				dvi411(15),
				dvi422(16),
				g729(17)
				}
			MAX-ACCESS read-create
			STATUS current
			DESCRIPTION
				"This attribute specifies codec selection as defined by RFC 3551."
			DEFVAL { pcmu }
			::= { zhoneCpeVoipMediaEntry 12 }

		
		-- 1.3.6.1.4.1.5504.5.16.1.6.2.1.13
		zhoneCpeVoipPacketPeriodSelectionThirdOrder OBJECT-TYPE
			SYNTAX Integer32 (10..30)
			UNITS "milli seconds"
			MAX-ACCESS read-create
			STATUS current
			DESCRIPTION
				"This attribute specifies the packet period selection interval in
				milliseconds. The default value is 20. Valid values are 10..30 ms."
			DEFVAL { 20 }
			::= { zhoneCpeVoipMediaEntry 13 }

		
		-- 1.3.6.1.4.1.5504.5.16.1.6.2.1.14
		zhoneCpeVoipSilenceSuppressionThirdOrder OBJECT-TYPE
			SYNTAX ZhoneEnabledFlag
			MAX-ACCESS read-create
			STATUS current
			DESCRIPTION
				"This attribute specifies whether silence suppression is on or off."
			DEFVAL { disabled }
			::= { zhoneCpeVoipMediaEntry 14 }

		
		-- 1.3.6.1.4.1.5504.5.16.1.6.2.1.15
		zhoneCpeVoipCodecSelectionFourthOrder OBJECT-TYPE
			SYNTAX INTEGER
				{
				pcmu(1),
				gsm(2),
				g723(3),
				dvi4eightKHz(4),
				dvi4sixteenKHz(5),
				lpc(6),
				pcma(7),
				g722(8),
				l16twochannels(9),
				l16onechannel(10),
				qcelp(11),
				cn(12),
				mpa(13),
				g728(14),
				dvi411(15),
				dvi422(16),
				g729(17)
				}
			MAX-ACCESS read-create
			STATUS current
			DESCRIPTION
				"This attribute specifies codec selection as defined by RFC 3551."
			DEFVAL { pcmu }
			::= { zhoneCpeVoipMediaEntry 15 }

		
		-- 1.3.6.1.4.1.5504.5.16.1.6.2.1.16
		zhoneCpeVoipPacketPeriodSelectionFourthOrder OBJECT-TYPE
			SYNTAX Integer32 (10..30)
			UNITS "milli seconds"
			MAX-ACCESS read-create
			STATUS current
			DESCRIPTION
				"This attribute specifies the packet period selection interval in
				milliseconds. The default value is 20. Valid values are 10..30 ms."
			DEFVAL { 20 }
			::= { zhoneCpeVoipMediaEntry 16 }

		
		-- 1.3.6.1.4.1.5504.5.16.1.6.2.1.17
		zhoneCpeVoipSilenceSuppressionFourthOrder OBJECT-TYPE
			SYNTAX ZhoneEnabledFlag
			MAX-ACCESS read-create
			STATUS current
			DESCRIPTION
				"This attribute specifies whether silence suppression is on or off."
			DEFVAL { disabled }
			::= { zhoneCpeVoipMediaEntry 17 }

		
		-- 1.3.6.1.4.1.5504.5.16.1.6.2.1.18
		zhoneCpeVoipMediaHookFlashTimerMin OBJECT-TYPE
			SYNTAX Integer32
			MAX-ACCESS read-write
			STATUS current
			DESCRIPTION
				"The Hookflash specifies the minimum timer that qualifies for a
				hookflash.  Any loopopen below this time will be ignored as a
				glitch."
			DEFVAL { 100 }
			::= { zhoneCpeVoipMediaEntry 18 }

		
		-- 1.3.6.1.4.1.5504.5.16.1.6.2.1.19
		zhoneCpeVoipMediaHookFlashTimerMax OBJECT-TYPE
			SYNTAX Integer32
			MAX-ACCESS read-write
			STATUS current
			DESCRIPTION
				"The Hookflash specifies the maximum timer that qualifies for a
				hookflash.  Any loopopen more than this timer will be considered
				as a onhook."
			DEFVAL { 1550 }
			::= { zhoneCpeVoipMediaEntry 19 }

		
		-- 1.3.6.1.4.1.5504.5.16.1.7
		zhoneCpeVoipSubscriberTable OBJECT-TYPE
			SYNTAX SEQUENCE OF ZhoneCpeVoipSubscriberEntry
			MAX-ACCESS not-accessible
			STATUS current
			DESCRIPTION
				"Cpe Voip Subscriber table for the VoIP feature."
			::= { zhoneCpeObjectID 7 }

		
		-- 1.3.6.1.4.1.5504.5.16.1.7.1
		zhoneCpeVoipSubscriberEntry OBJECT-TYPE
			SYNTAX ZhoneCpeVoipSubscriberEntry
			MAX-ACCESS not-accessible
			STATUS current
			DESCRIPTION
				"Row in the CpeVoipSubscriber table."
			INDEX { zhoneCpeIfIndex, zhoneCpeVoipSubscriberPortNumber }
			::= { zhoneCpeVoipSubscriberTable 1 }

		
		ZhoneCpeVoipSubscriberEntry ::=
			SEQUENCE { 
				zhoneCpeVoipSubscriberPortNumber
					Unsigned32,
				zhoneCpeVoipSubscriberRowStatus
					ZhoneRowStatus,
				zhoneCpeVoipSubscriberAdminState
					ZhoneAdminState,
				zhoneCpeVoipSubscriberDialNumber
					ZhoneAdminString,
				zhoneCpeVoipSubscriberDisplayName
					OCTET STRING,
				zhoneCpeVoipSubscriberUserName
					OCTET STRING,
				zhoneCpeVoipSubscriberPassword
					OCTET STRING,
				zhoneCpeVoipSubscriberImpedance
					INTEGER,
				zhoneCpeVoipSubscriberRxGain
					Integer32,
				zhoneCpeVoipSubscriberTxGain
					Integer32,
				zhoneCpeVoipSubscriberTransmissionPath
					INTEGER,
				zhoneCpeVoipSubscriberSignallingCode
					INTEGER,
				zhoneCpeVoipServerProfileIndex
					Unsigned32,
				zhoneCpeVoipFeaturesProfileIndex
					Unsigned32,
				zhoneCpeVoipMediaProfileIndex
					Unsigned32,
				zhoneCpeVoipSubscriberPhoneFollowsWan
					ZhoneEnabledFlag,
				zhoneCpeVoipSubscriberDescription
					OCTET STRING
			 }

		-- 1.3.6.1.4.1.5504.5.16.1.7.1.1
		zhoneCpeVoipSubscriberPortNumber OBJECT-TYPE
			SYNTAX Unsigned32 (1..2147483647)
			MAX-ACCESS not-accessible
			STATUS current
			DESCRIPTION
				"This represents the CPE Voip Subscriber Port Number."
			::= { zhoneCpeVoipSubscriberEntry 1 }

		
		-- 1.3.6.1.4.1.5504.5.16.1.7.1.2
		zhoneCpeVoipSubscriberRowStatus OBJECT-TYPE
			SYNTAX ZhoneRowStatus
			MAX-ACCESS read-create
			STATUS current
			DESCRIPTION
				"Used to create, modify or delete an entry in this table."
			DEFVAL { active }
			::= { zhoneCpeVoipSubscriberEntry 2 }

		
		-- 1.3.6.1.4.1.5504.5.16.1.7.1.3
		zhoneCpeVoipSubscriberAdminState OBJECT-TYPE
			SYNTAX ZhoneAdminState
			MAX-ACCESS read-create
			STATUS current
			DESCRIPTION
				"This shows the admin state for the CpeVoipSubscriber."
			DEFVAL { 1 }
			::= { zhoneCpeVoipSubscriberEntry 3 }

		
		-- 1.3.6.1.4.1.5504.5.16.1.7.1.4
		zhoneCpeVoipSubscriberDialNumber OBJECT-TYPE
			SYNTAX ZhoneAdminString
			MAX-ACCESS read-create
			STATUS current
			DESCRIPTION
				"This attribute contains the dialing number to make the call."
			::= { zhoneCpeVoipSubscriberEntry 4 }

		
		-- 1.3.6.1.4.1.5504.5.16.1.7.1.5
		zhoneCpeVoipSubscriberDisplayName OBJECT-TYPE
			SYNTAX OCTET STRING (SIZE (0..25))
			MAX-ACCESS read-create
			STATUS current
			DESCRIPTION
				"This ASCII string attribute defines the customer id used for the display
				attribute in outgoing SIP messages."
			::= { zhoneCpeVoipSubscriberEntry 5 }

		
		-- 1.3.6.1.4.1.5504.5.16.1.7.1.6
		zhoneCpeVoipSubscriberUserName OBJECT-TYPE
			SYNTAX OCTET STRING (SIZE (1..50))
			MAX-ACCESS read-create
			STATUS current
			DESCRIPTION
				"This attribute contains the SIP user identification used for authentication."
			::= { zhoneCpeVoipSubscriberEntry 6 }

		
		-- 1.3.6.1.4.1.5504.5.16.1.7.1.7
		zhoneCpeVoipSubscriberPassword OBJECT-TYPE
			SYNTAX OCTET STRING (SIZE (1..32))
			MAX-ACCESS read-create
			STATUS current
			DESCRIPTION
				"This attribute contains the SIP password used for authentication."
			::= { zhoneCpeVoipSubscriberEntry 7 }

		
		-- 1.3.6.1.4.1.5504.5.16.1.7.1.8
		zhoneCpeVoipSubscriberImpedance OBJECT-TYPE
			SYNTAX INTEGER
				{
				ohm600(1),
				ohm900(2),
				complex1(3),
				complex2(4),
				complex3(5)
				}
			UNITS "ohm"
			MAX-ACCESS read-create
			STATUS current
			DESCRIPTION
				"This attribute specifies the impedance for the POTS UNI."
			DEFVAL { ohm600 }
			::= { zhoneCpeVoipSubscriberEntry 8 }

		
		-- 1.3.6.1.4.1.5504.5.16.1.7.1.9
		zhoneCpeVoipSubscriberRxGain OBJECT-TYPE
			SYNTAX Integer32 (-12..6)
			UNITS "dB"
			MAX-ACCESS read-create
			STATUS current
			DESCRIPTION
				"This attribute specifies a gain value for the received signal in the
				form of a 2s complement number. Valid values are -120 (-12.0 dB) to
				60 (+6.0 dB)."
			DEFVAL { 0 }
			::= { zhoneCpeVoipSubscriberEntry 9 }

		
		-- 1.3.6.1.4.1.5504.5.16.1.7.1.10
		zhoneCpeVoipSubscriberTxGain OBJECT-TYPE
			SYNTAX Integer32 (-12..6)
			UNITS "dB"
			MAX-ACCESS read-create
			STATUS current
			DESCRIPTION
				"This attribute specifies a gain value for the transmit signal in the
				form of a 2s complement number. Valid values are -120 (-12.0 dB) to
				60 (+6.0 dB)."
			DEFVAL { 0 }
			::= { zhoneCpeVoipSubscriberEntry 10 }

		
		-- 1.3.6.1.4.1.5504.5.16.1.7.1.11
		zhoneCpeVoipSubscriberTransmissionPath OBJECT-TYPE
			SYNTAX INTEGER
				{
				fulltimeonhookxmit(1),
				parttimeonhookxmit(2)
				}
			MAX-ACCESS read-create
			STATUS current
			DESCRIPTION
				"This attribute allows setting the POTS UNI either to full-time on-hook
				transmission or part-time on-hook transmission."
			DEFVAL { fulltimeonhookxmit }
			::= { zhoneCpeVoipSubscriberEntry 11 }

		
		-- 1.3.6.1.4.1.5504.5.16.1.7.1.12
		zhoneCpeVoipSubscriberSignallingCode OBJECT-TYPE
			SYNTAX INTEGER
				{
				loopstart(1),
				groundstart(2),
				loopreversebattery(3),
				coinfirst(4),
				dialtonefirst(5),
				multiparty(6)
				}
			MAX-ACCESS read-create
			STATUS current
			DESCRIPTION
				"This attribute specifies the POTS-side signaling."
			DEFVAL { loopstart }
			::= { zhoneCpeVoipSubscriberEntry 12 }

		
		-- 1.3.6.1.4.1.5504.5.16.1.7.1.13
		zhoneCpeVoipServerProfileIndex OBJECT-TYPE
			SYNTAX Unsigned32 (1..2147483647)
			MAX-ACCESS read-create
			STATUS current
			DESCRIPTION
				"This attribute points to the associated cpe-voip-server profile."
			::= { zhoneCpeVoipSubscriberEntry 13 }

		
		-- 1.3.6.1.4.1.5504.5.16.1.7.1.14
		zhoneCpeVoipFeaturesProfileIndex OBJECT-TYPE
			SYNTAX Unsigned32 (1..2147483647)
			MAX-ACCESS read-create
			STATUS current
			DESCRIPTION
				"This attribute points to the associated cpe-voip-feature profile."
			DEFVAL { 1 }
			::= { zhoneCpeVoipSubscriberEntry 14 }

		
		-- 1.3.6.1.4.1.5504.5.16.1.7.1.15
		zhoneCpeVoipMediaProfileIndex OBJECT-TYPE
			SYNTAX Unsigned32 (1..2147483647)
			MAX-ACCESS read-create
			STATUS current
			DESCRIPTION
				"This attribute points to the associated cpe-voip-media profile."
			DEFVAL { 1 }
			::= { zhoneCpeVoipSubscriberEntry 15 }

		
		-- 1.3.6.1.4.1.5504.5.16.1.7.1.16
		zhoneCpeVoipSubscriberPhoneFollowsWan OBJECT-TYPE
			SYNTAX ZhoneEnabledFlag
			MAX-ACCESS read-create
			STATUS current
			DESCRIPTION
				"When enabled the phone will lose power any time the WAN is operation
				status of down.This will allow line monitoring equipment to detect
				loss of service."
			DEFVAL { disabled }
			::= { zhoneCpeVoipSubscriberEntry 16 }

		
		-- 1.3.6.1.4.1.5504.5.16.1.7.1.17
		zhoneCpeVoipSubscriberDescription OBJECT-TYPE
			SYNTAX OCTET STRING (SIZE (0..32))
			MAX-ACCESS read-create
			STATUS current
			DESCRIPTION
				"Describes the CPE Voip subscriber profile instance"
			DEFVAL { "" }
			::= { zhoneCpeVoipSubscriberEntry 17 }

		
		-- 1.3.6.1.4.1.5504.5.16.1.8
		zhoneCpeEthSubscriberTable OBJECT-TYPE
			SYNTAX SEQUENCE OF ZhoneCpeEthSubscriberEntry
			MAX-ACCESS not-accessible
			STATUS current
			DESCRIPTION
				"Cpe Eth Subscriber table."
			::= { zhoneCpeObjectID 8 }

		
		-- 1.3.6.1.4.1.5504.5.16.1.8.1
		zhoneCpeEthSubscriberEntry OBJECT-TYPE
			SYNTAX ZhoneCpeEthSubscriberEntry
			MAX-ACCESS not-accessible
			STATUS current
			DESCRIPTION
				"Row in the CpeEthSubscriber table."
			INDEX { zhoneCpeIfIndex, zhoneCpeEthSubscriberPortNumber }
			::= { zhoneCpeEthSubscriberTable 1 }

		
		ZhoneCpeEthSubscriberEntry ::=
			SEQUENCE { 
				zhoneCpeEthSubscriberPortNumber
					Unsigned32,
				zhoneCpeEthSubscriberRowStatus
					ZhoneRowStatus,
				zhoneCpeEthSubscriberAdminState
					ZhoneAdminState,
				zhoneCpeEthSubscriberLoopback
					ZhoneEnabledFlag,
				zhoneCpeEthSubscriberRate
					INTEGER,
				zhoneCpeEthSubscriberDuplex
					INTEGER,
				zhoneCpeEthSubscriberMtu
					Unsigned32,
				zhoneCpeEthSubscriberPortType
					INTEGER,
				zhoneCpeEthSubscriberPauseTime
					Unsigned32,
				zhoneCpeEthSubscriberMode
					INTEGER,
				zhoneCpeEthSubscriberPowerFeed
					ZhoneEnabledFlag,
				zhoneCpeVideoProfileIndex
					Unsigned32,
				zhoneCpeTrafficManagementProfileIndex
					Unsigned32,
				zhoneCpeEthSubscriberLineStatusAlarm
					ZhoneEnabledFlag,
				zhoneCpeEthSubscriberAlarmSeverity
					ZhoneAlarmSeverity,
				zhoneCpeEthSubscriberPowerShed
					ZhoneEnabledFlag,
				zhoneCpeEthSubscriberPowerRange
					INTEGER,
				zhoneCpeEthSubscriberLldpMedList
					Unsigned32,
				zhoneCpeEthSubscriberCustomPowerRange
					Unsigned32,
				zhoneCpeEthSubscriberDescription
					OCTET STRING,
				zhoneCpeEthSubscriberVlanFilterList
					Unsigned32,
				zhoneCpeEthSubscriberAuthenticationMode
					INTEGER,
				zhoneCpeEthSubscriberAccessControlListProfileIndex
					Integer32
			 }

		-- 1.3.6.1.4.1.5504.5.16.1.8.1.1
		zhoneCpeEthSubscriberPortNumber OBJECT-TYPE
			SYNTAX Unsigned32 (1..2147483647)
			MAX-ACCESS not-accessible
			STATUS current
			DESCRIPTION
				"This represents the CPE Eth Subscriber Port Number."
			::= { zhoneCpeEthSubscriberEntry 1 }

		
		-- 1.3.6.1.4.1.5504.5.16.1.8.1.2
		zhoneCpeEthSubscriberRowStatus OBJECT-TYPE
			SYNTAX ZhoneRowStatus
			MAX-ACCESS read-create
			STATUS current
			DESCRIPTION
				"Used to create, modify or delete an entry in this table."
			DEFVAL { active }
			::= { zhoneCpeEthSubscriberEntry 2 }

		
		-- 1.3.6.1.4.1.5504.5.16.1.8.1.3
		zhoneCpeEthSubscriberAdminState OBJECT-TYPE
			SYNTAX ZhoneAdminState
			MAX-ACCESS read-create
			STATUS current
			DESCRIPTION
				"This attribute activates or deactivates the functions performed by
				the Ethernet port for this subscriber or put the port in test mode."
			DEFVAL { 1 }
			::= { zhoneCpeEthSubscriberEntry 3 }

		
		-- 1.3.6.1.4.1.5504.5.16.1.8.1.4
		zhoneCpeEthSubscriberLoopback OBJECT-TYPE
			SYNTAX ZhoneEnabledFlag
			MAX-ACCESS read-create
			STATUS current
			DESCRIPTION
				"This enables or disables Ethernet loopback."
			DEFVAL { disabled }
			::= { zhoneCpeEthSubscriberEntry 4 }

		
		-- 1.3.6.1.4.1.5504.5.16.1.8.1.5
		zhoneCpeEthSubscriberRate OBJECT-TYPE
			SYNTAX INTEGER
				{
				auto(1),
				tenMbps(2),
				oneHundredMbps(3),
				oneThousandMbps(4)
				}
			UNITS "Mbps"
			MAX-ACCESS read-create
			STATUS current
			DESCRIPTION
				"This attribute sets the Ethernet port rate."
			DEFVAL { auto }
			::= { zhoneCpeEthSubscriberEntry 5 }

		
		-- 1.3.6.1.4.1.5504.5.16.1.8.1.6
		zhoneCpeEthSubscriberDuplex OBJECT-TYPE
			SYNTAX INTEGER
				{
				auto(1),
				full(2),
				half(3)
				}
			MAX-ACCESS read-create
			STATUS current
			DESCRIPTION
				"This attribute sets the Ethernet port duplex."
			DEFVAL { auto }
			::= { zhoneCpeEthSubscriberEntry 6 }

		
		-- 1.3.6.1.4.1.5504.5.16.1.8.1.7
		zhoneCpeEthSubscriberMtu OBJECT-TYPE
			SYNTAX Unsigned32 (0..65535)
			MAX-ACCESS read-create
			STATUS current
			DESCRIPTION
				"This attribute denotes the maximum frame size allowed across this interface."
			DEFVAL { 1518 }
			::= { zhoneCpeEthSubscriberEntry 7 }

		
		-- 1.3.6.1.4.1.5504.5.16.1.8.1.8
		zhoneCpeEthSubscriberPortType OBJECT-TYPE
			SYNTAX INTEGER
				{
				dce(1),
				dte(2)
				}
			MAX-ACCESS read-create
			STATUS current
			DESCRIPTION
				"This attribute specifies the Ethernet interface wiring."
			DEFVAL { dce }
			::= { zhoneCpeEthSubscriberEntry 8 }

		
		-- 1.3.6.1.4.1.5504.5.16.1.8.1.9
		zhoneCpeEthSubscriberPauseTime OBJECT-TYPE
			SYNTAX Unsigned32 (0..65535)
			UNITS "quanta"
			MAX-ACCESS read-create
			STATUS current
			DESCRIPTION
				"This attribute allows the interface to ask the subscriber terminal to
				temporarily suspend sending data. Units are in pause quanta
				(1 pause quantum is 512 bit times of the particular implementation)."
			DEFVAL { 0 }
			::= { zhoneCpeEthSubscriberEntry 9 }

		
		-- 1.3.6.1.4.1.5504.5.16.1.8.1.10
		zhoneCpeEthSubscriberMode OBJECT-TYPE
			SYNTAX INTEGER
				{
				bridged(1),
				routed(2)
				}
			MAX-ACCESS read-create
			STATUS current
			DESCRIPTION
				"This attribute specifies whether the Ethernet interface is bridged or
				derived from an IP router function."
			DEFVAL { bridged }
			::= { zhoneCpeEthSubscriberEntry 10 }

		
		-- 1.3.6.1.4.1.5504.5.16.1.8.1.11
		zhoneCpeEthSubscriberPowerFeed OBJECT-TYPE
			SYNTAX ZhoneEnabledFlag
			MAX-ACCESS read-create
			STATUS current
			DESCRIPTION
				"This attribute controls whether power is provided to an external equipment
				over the Ethernet interface."
			DEFVAL { disabled }
			::= { zhoneCpeEthSubscriberEntry 11 }

		
		-- 1.3.6.1.4.1.5504.5.16.1.8.1.12
		zhoneCpeVideoProfileIndex OBJECT-TYPE
			SYNTAX Unsigned32 (0..2147483647)
			MAX-ACCESS read-create
			STATUS current
			DESCRIPTION
				"This object points to the associated video profile."
			DEFVAL { 0 }
			::= { zhoneCpeEthSubscriberEntry 12 }

		
		-- 1.3.6.1.4.1.5504.5.16.1.8.1.13
		zhoneCpeTrafficManagementProfileIndex OBJECT-TYPE
			SYNTAX Unsigned32 (0..2147483647)
			MAX-ACCESS read-create
			STATUS current
			DESCRIPTION
				"This object points to the associated Traffic Management profile. If there is
				no traffic control for the UNI, set it to 0."
			DEFVAL { 0 }
			::= { zhoneCpeEthSubscriberEntry 13 }

		
		-- 1.3.6.1.4.1.5504.5.16.1.8.1.14
		zhoneCpeEthSubscriberLineStatusAlarm OBJECT-TYPE
			SYNTAX ZhoneEnabledFlag
			MAX-ACCESS read-create
			STATUS current
			DESCRIPTION
				"This field is for enabling/disabling alarm reporting from this CPE UNI."
			DEFVAL { disabled }
			::= { zhoneCpeEthSubscriberEntry 14 }

		
		-- 1.3.6.1.4.1.5504.5.16.1.8.1.15
		zhoneCpeEthSubscriberAlarmSeverity OBJECT-TYPE
			SYNTAX ZhoneAlarmSeverity
			MAX-ACCESS read-create
			STATUS current
			DESCRIPTION
				"This field is for specifying the severity level of all the alarms from this CPE UNI."
			DEFVAL { major }
			::= { zhoneCpeEthSubscriberEntry 15 }

		
		-- 1.3.6.1.4.1.5504.5.16.1.8.1.16
		zhoneCpeEthSubscriberPowerShed OBJECT-TYPE
			SYNTAX ZhoneEnabledFlag
			MAX-ACCESS read-create
			STATUS current
			DESCRIPTION
				"When zhoneCpeSystemCommonPowerShutdownDelay is non-zero and the unit is operating on Battery
				Power during an AC power outage, this option controls the Enable/Disable state of each
				Ethernet port. Ports with Power Shedding State as Enabled will remain operational on Battery
				Power, while Disabled ports will be shut down to conserve battery power. "
			DEFVAL { enabled }
			::= { zhoneCpeEthSubscriberEntry 16 }

		
		-- 1.3.6.1.4.1.5504.5.16.1.8.1.17
		zhoneCpeEthSubscriberPowerRange OBJECT-TYPE
			SYNTAX INTEGER
				{
				disabled(1),
				low(2),
				medium(3),
				high(4),
				custom(5)
				}
			MAX-ACCESS read-create
			STATUS current
			DESCRIPTION
				"Maximum PoE ( Power over ethernet ) Power allowed per port. When disabled,
				no PoE Power will be provided."
			DEFVAL { disabled }
			::= { zhoneCpeEthSubscriberEntry 17 }

		
		-- 1.3.6.1.4.1.5504.5.16.1.8.1.18
		zhoneCpeEthSubscriberLldpMedList OBJECT-TYPE
			SYNTAX Unsigned32
			MAX-ACCESS read-create
			STATUS current
			DESCRIPTION
				"A list of cpe-lldp-med-policy profiles."
			::= { zhoneCpeEthSubscriberEntry 18 }

		
		-- 1.3.6.1.4.1.5504.5.16.1.8.1.19
		zhoneCpeEthSubscriberCustomPowerRange OBJECT-TYPE
			SYNTAX Unsigned32 (0..320)
			MAX-ACCESS read-create
			STATUS current
			DESCRIPTION
				"Maximum Power supplied on this PoE port in units of 0.1 Watts."
			::= { zhoneCpeEthSubscriberEntry 19 }

		
		-- 1.3.6.1.4.1.5504.5.16.1.8.1.20
		zhoneCpeEthSubscriberDescription OBJECT-TYPE
			SYNTAX OCTET STRING (SIZE (0..32))
			MAX-ACCESS read-create
			STATUS current
			DESCRIPTION
				"Describes the CPE Eth subscriber profile instance"
			DEFVAL { "" }
			::= { zhoneCpeEthSubscriberEntry 20 }

		
		-- 1.3.6.1.4.1.5504.5.16.1.8.1.21
		zhoneCpeEthSubscriberVlanFilterList OBJECT-TYPE
			SYNTAX Unsigned32
			MAX-ACCESS read-create
			STATUS current
			DESCRIPTION
				"DThis attribute points to a list of VLAN filter rules.  The default 
				value 0 indicates no list is used."
			DEFVAL { 0 }
			::= { zhoneCpeEthSubscriberEntry 21 }

		
		-- 1.3.6.1.4.1.5504.5.16.1.8.1.22
		zhoneCpeEthSubscriberAuthenticationMode OBJECT-TYPE
			SYNTAX INTEGER
				{
				enable(1),
				disable(2),
				auto(3)
				}
			MAX-ACCESS read-create
			STATUS current
			DESCRIPTION
				"This field specifies the Authentication Mode for the LAN port
				enable   -- Enables the Port Access Entity control
				disable  -- Disables the Port Access Entity control
				auto     -- Enables PAE control with Guest VLAN Tagging"
			DEFVAL { disable }
			::= { zhoneCpeEthSubscriberEntry 22 }

		
		-- 1.3.6.1.4.1.5504.5.16.1.8.1.23
		zhoneCpeEthSubscriberAccessControlListProfileIndex OBJECT-TYPE
			SYNTAX Integer32
			MAX-ACCESS read-create
			STATUS current
			DESCRIPTION
				"specifies the cpe-access-ctrl-list applicable to this eth subscriber"
			::= { zhoneCpeEthSubscriberEntry 23 }

		
		-- 1.3.6.1.4.1.5504.5.16.1.9
		zhoneCpeVideo OBJECT-IDENTITY
			STATUS current
			DESCRIPTION 
				"Cpe Video objects."
			::= { zhoneCpeObjectID 9 }

		
		-- 1.3.6.1.4.1.5504.5.16.1.9.1
		zhoneCpeVideoIndexNext OBJECT-TYPE
			SYNTAX Integer32
			MAX-ACCESS read-only
			STATUS current
			DESCRIPTION
				"This object contains an appropriate value to be used for the zhoneCpeVideoIndex
				when creating entries in the zhoneCpeVideoTable. The value 0 indicates that
				no unassigned entries are available. To obtain the zhoneCpeVideoIndex value
				for a new entry, the manager issues a management protocol retrieval
				operation to obtain the current value of this object.  After each retrieval,
				the agent should modify the value to the next unassigned index.
				
				After a manager retrieves a value the agent will determine through its local
				policy when this index value will be made available for reuse."
			::= { zhoneCpeVideo 1 }

		
		-- 1.3.6.1.4.1.5504.5.16.1.9.2
		zhoneCpeVideoTable OBJECT-TYPE
			SYNTAX SEQUENCE OF ZhoneCpeVideoEntry
			MAX-ACCESS not-accessible
			STATUS current
			DESCRIPTION
				"Cpe Video table."
			::= { zhoneCpeVideo 2 }

		
		-- 1.3.6.1.4.1.5504.5.16.1.9.2.1
		zhoneCpeVideoEntry OBJECT-TYPE
			SYNTAX ZhoneCpeVideoEntry
			MAX-ACCESS not-accessible
			STATUS current
			DESCRIPTION
				"Row in the Cpe Video table."
			INDEX { zhoneCpeVideoIndex, zhoneCpeGemPort, zhoneCpeVlan }
			::= { zhoneCpeVideoTable 1 }

		
		ZhoneCpeVideoEntry ::=
			SEQUENCE { 
				zhoneCpeVideoIndex
					Unsigned32,
				zhoneCpeGemPort
					Unsigned32,
				zhoneCpeVlan
					Unsigned32,
				zhoneCpeVideoRowStatus
					ZhoneRowStatus,
				zhoneCpeVideoProfileName
					ZhoneAdminString,
				zhoneCpeVideoMaxSimultaneousGroups
					Unsigned32,
				zhoneCpeVideoMaxMulticastBandwidth
					Unsigned32,
				zhoneCpeVideoBandwidthEnforce
					TruthValue,
				zhoneCpeVideoIgmpVersion
					INTEGER,
				zhoneCpeVideoIgmpFunction
					INTEGER,
				zhoneCpeVideoImmediateLeave
					ZhoneEnabledFlag,
				zhoneCpeVideoUpstreamIgmpRate
					Unsigned32,
				zhoneCpeVideoRobustness
					Unsigned32,
				zhoneCpeVideoAccessControlList
					Unsigned32
			 }

		-- 1.3.6.1.4.1.5504.5.16.1.9.2.1.1
		zhoneCpeVideoIndex OBJECT-TYPE
			SYNTAX Unsigned32 (1..2147483647)
			MAX-ACCESS not-accessible
			STATUS current
			DESCRIPTION
				"This represents the CPE Video Index."
			::= { zhoneCpeVideoEntry 1 }

		
		-- 1.3.6.1.4.1.5504.5.16.1.9.2.1.2
		zhoneCpeGemPort OBJECT-TYPE
			SYNTAX Unsigned32 (0..4095)
			MAX-ACCESS not-accessible
			STATUS current
			DESCRIPTION
				"This represents the CPE GEM Port Index."
			::= { zhoneCpeVideoEntry 2 }

		
		-- 1.3.6.1.4.1.5504.5.16.1.9.2.1.3
		zhoneCpeVlan OBJECT-TYPE
			SYNTAX Unsigned32 (0..4095)
			MAX-ACCESS not-accessible
			STATUS current
			DESCRIPTION
				"This represents the CPE Vlan Id."
			::= { zhoneCpeVideoEntry 3 }

		
		-- 1.3.6.1.4.1.5504.5.16.1.9.2.1.4
		zhoneCpeVideoRowStatus OBJECT-TYPE
			SYNTAX ZhoneRowStatus
			MAX-ACCESS read-create
			STATUS current
			DESCRIPTION
				"Used to create, modify or delete an entry in this table."
			DEFVAL { active }
			::= { zhoneCpeVideoEntry 4 }

		
		-- 1.3.6.1.4.1.5504.5.16.1.9.2.1.5
		zhoneCpeVideoProfileName OBJECT-TYPE
			SYNTAX ZhoneAdminString
			MAX-ACCESS read-create
			STATUS current
			DESCRIPTION
				"CPE Video profile for the dynamic bridging. This field is only writable
				upon creation and must be unique within its table."
			::= { zhoneCpeVideoEntry 5 }

		
		-- 1.3.6.1.4.1.5504.5.16.1.9.2.1.6
		zhoneCpeVideoMaxSimultaneousGroups OBJECT-TYPE
			SYNTAX Unsigned32 (0..65535)
			MAX-ACCESS read-create
			STATUS current
			DESCRIPTION
				"This attribute specifies the maximum number of dynamic multicast groups
				that may be replicated to the client port at any one time. The default
				value 0 specifies that no administrative limit is to be imposed."
			DEFVAL { 0 }
			::= { zhoneCpeVideoEntry 6 }

		
		-- 1.3.6.1.4.1.5504.5.16.1.9.2.1.7
		zhoneCpeVideoMaxMulticastBandwidth OBJECT-TYPE
			SYNTAX Unsigned32 (0..2147483647)
			UNITS "bytes/second"
			MAX-ACCESS read-create
			STATUS current
			DESCRIPTION
				"This attribute specifies the maximum imputed dynamic bandwidth, in
				bytes per second, that may be delivered to the client port at anyone time.
				The default value 0 specifies that no administrative limit is to be imposed."
			DEFVAL { 0 }
			::= { zhoneCpeVideoEntry 7 }

		
		-- 1.3.6.1.4.1.5504.5.16.1.9.2.1.8
		zhoneCpeVideoBandwidthEnforce OBJECT-TYPE
			SYNTAX TruthValue
			MAX-ACCESS read-create
			STATUS current
			DESCRIPTION
				"The default value of this boolean attribute is false, and specifies that
				attempts to exceed the max multicast bandwidth be counted but honored.
				The value true specifies that such attempts be counted and denied.
				The imputed bandwidth value is taken from the dynamic access control list
				table, both for a new join request and for pre-existing groups."
			DEFVAL { false }
			::= { zhoneCpeVideoEntry 8 }

		
		-- 1.3.6.1.4.1.5504.5.16.1.9.2.1.9
		zhoneCpeVideoIgmpVersion OBJECT-TYPE
			SYNTAX INTEGER
				{
				version1(1),
				version2(2),
				version3(3)
				}
			MAX-ACCESS read-create
			STATUS current
			DESCRIPTION
				"This attribute specifies the version of the IGMP to be supported."
			DEFVAL { version2 }
			::= { zhoneCpeVideoEntry 9 }

		
		-- 1.3.6.1.4.1.5504.5.16.1.9.2.1.10
		zhoneCpeVideoIgmpFunction OBJECT-TYPE
			SYNTAX INTEGER
				{
				transparentsnooping(1),
				snoopwithproxy(2),
				proxy(3)
				}
			MAX-ACCESS read-create
			STATUS current
			DESCRIPTION
				"This attribute enables an IGMP function - transparent IGMP snooping only,
				snooping with proxy reporting (SPR) and IGMP proxy. The function must be
				consistent with the capabilities specified by the other IGMP configuration
				attributes."
			DEFVAL { transparentsnooping }
			::= { zhoneCpeVideoEntry 10 }

		
		-- 1.3.6.1.4.1.5504.5.16.1.9.2.1.11
		zhoneCpeVideoImmediateLeave OBJECT-TYPE
			SYNTAX ZhoneEnabledFlag
			MAX-ACCESS read-create
			STATUS current
			DESCRIPTION
				"This attribute enables or disables the immediate leave function."
			DEFVAL { disabled }
			::= { zhoneCpeVideoEntry 11 }

		
		-- 1.3.6.1.4.1.5504.5.16.1.9.2.1.12
		zhoneCpeVideoUpstreamIgmpRate OBJECT-TYPE
			SYNTAX Unsigned32 (0..2147483647)
			UNITS "messages/second"
			MAX-ACCESS read-create
			STATUS current
			DESCRIPTION
				"This attribute limits the maximum rate of upstream IGMP traffic.
				Traffic in excess of this limit is silently discarded. The attribute
				value is specified in messages/second. The default value 0 imposes no rate
				limit on this traffic."
			DEFVAL { 0 }
			::= { zhoneCpeVideoEntry 12 }

		
		-- 1.3.6.1.4.1.5504.5.16.1.9.2.1.13
		zhoneCpeVideoRobustness OBJECT-TYPE
			SYNTAX Unsigned32 (0..255)
			MAX-ACCESS read-create
			STATUS current
			DESCRIPTION
				"This attribute allows tuning for possible packet loss in the network.
				The default value 0 causes the ONT to follow the IETF recommendation
				to copy the robustness value from query messages originating further
				upstream."
			DEFVAL { 0 }
			::= { zhoneCpeVideoEntry 13 }

		
		-- 1.3.6.1.4.1.5504.5.16.1.9.2.1.14
		zhoneCpeVideoAccessControlList OBJECT-TYPE
			SYNTAX Unsigned32 (0..2147483647)
			MAX-ACCESS read-create
			STATUS current
			DESCRIPTION
				"This attribute points to a access control group list. The default value 0
				indicates no control list is used."
			DEFVAL { 0 }
			::= { zhoneCpeVideoEntry 14 }

		
		-- 1.3.6.1.4.1.5504.5.16.1.10
		zhoneCpeVideoAccessControl OBJECT-IDENTITY
			STATUS current
			DESCRIPTION 
				"Cpe Video Access Control objects."
			::= { zhoneCpeObjectID 10 }

		
		-- 1.3.6.1.4.1.5504.5.16.1.10.1
		zhoneCpeVideoAccessControlIndexTable OBJECT-TYPE
			SYNTAX SEQUENCE OF ZhoneCpeVideoAccessControlIndexEntry
			MAX-ACCESS not-accessible
			STATUS current
			DESCRIPTION
				"Table of next available index values for CPE video access control profile."
			::= { zhoneCpeVideoAccessControl 1 }

		
		-- 1.3.6.1.4.1.5504.5.16.1.10.1.1
		zhoneCpeVideoAccessControlIndexEntry OBJECT-TYPE
			SYNTAX ZhoneCpeVideoAccessControlIndexEntry
			MAX-ACCESS not-accessible
			STATUS current
			DESCRIPTION
				"Row in the zhoneCpeVideoAccessControlIndexTable."
			INDEX { zhoneCpeVideoAccessControlListIndex }
			::= { zhoneCpeVideoAccessControlIndexTable 1 }

		
		ZhoneCpeVideoAccessControlIndexEntry ::=
			SEQUENCE { 
				zhoneCpeVideoAccessControlIndexNext
					Unsigned32
			 }

		-- 1.3.6.1.4.1.5504.5.16.1.10.1.1.1
		zhoneCpeVideoAccessControlIndexNext OBJECT-TYPE
			SYNTAX Unsigned32 (1..2147483647)
			MAX-ACCESS read-only
			STATUS current
			DESCRIPTION
				"This represents the next available index value for video access control profile.
				When 30 cpe-video-access-control profiles are configured this field wil give 
				zero as next available index."
			::= { zhoneCpeVideoAccessControlIndexEntry 1 }

		
		-- 1.3.6.1.4.1.5504.5.16.1.10.2
		zhoneCpeVideoAccessControlTable OBJECT-TYPE
			SYNTAX SEQUENCE OF ZhoneCpeVideoAccessControlEntry
			MAX-ACCESS not-accessible
			STATUS current
			DESCRIPTION
				"Cpe Video Access Control table."
			::= { zhoneCpeVideoAccessControl 2 }

		
		-- 1.3.6.1.4.1.5504.5.16.1.10.2.1
		zhoneCpeVideoAccessControlEntry OBJECT-TYPE
			SYNTAX ZhoneCpeVideoAccessControlEntry
			MAX-ACCESS not-accessible
			STATUS current
			DESCRIPTION
				"Row in the Cpe Video Access Control table."
			INDEX { zhoneCpeVideoAccessControlListIndex, zhoneCpeVideoAccessControlEntryIndex }
			::= { zhoneCpeVideoAccessControlTable 1 }

		
		ZhoneCpeVideoAccessControlEntry ::=
			SEQUENCE { 
				zhoneCpeVideoAccessControlListIndex
					Unsigned32,
				zhoneCpeVideoAccessControlEntryIndex
					Unsigned32,
				zhoneCpeVideoAccessControlRowStatus
					ZhoneRowStatus,
				zhoneCpeVideoAccessControlProfileName
					ZhoneAdminString,
				zhoneCpeVideoAccessControlType
					INTEGER,
				zhoneCpeVideoAccessControlSrcIp
					IpAddress,
				zhoneCpeVideoAccessControlDstIpStart
					IpAddress,
				zhoneCpeVideoAccessControlDstIpEnd
					IpAddress,
				zhoneCpeVideoAccessControlImputedGroupBw
					Unsigned32
			 }

		-- 1.3.6.1.4.1.5504.5.16.1.10.2.1.1
		zhoneCpeVideoAccessControlListIndex OBJECT-TYPE
			SYNTAX Unsigned32 (1..2147483647)
			MAX-ACCESS not-accessible
			STATUS current
			DESCRIPTION
				"This represents the CPE Video Access Control List Index."
			::= { zhoneCpeVideoAccessControlEntry 1 }

		
		-- 1.3.6.1.4.1.5504.5.16.1.10.2.1.2
		zhoneCpeVideoAccessControlEntryIndex OBJECT-TYPE
			SYNTAX Unsigned32 (1..2147483647)
			MAX-ACCESS not-accessible
			STATUS current
			DESCRIPTION
				"This represents the CPE Video Access Control Entry Index."
			::= { zhoneCpeVideoAccessControlEntry 2 }

		
		-- 1.3.6.1.4.1.5504.5.16.1.10.2.1.3
		zhoneCpeVideoAccessControlRowStatus OBJECT-TYPE
			SYNTAX ZhoneRowStatus
			MAX-ACCESS read-create
			STATUS current
			DESCRIPTION
				"Used to create, modify or delete an entry in this table."
			DEFVAL { active }
			::= { zhoneCpeVideoAccessControlEntry 3 }

		
		-- 1.3.6.1.4.1.5504.5.16.1.10.2.1.4
		zhoneCpeVideoAccessControlProfileName OBJECT-TYPE
			SYNTAX ZhoneAdminString
			MAX-ACCESS read-create
			STATUS current
			DESCRIPTION
				"CPE Video profile for the dynamic bridging. This field is only writable
				upon creation and must be unique within its table."
			::= { zhoneCpeVideoAccessControlEntry 4 }

		
		-- 1.3.6.1.4.1.5504.5.16.1.10.2.1.5
		zhoneCpeVideoAccessControlType OBJECT-TYPE
			SYNTAX INTEGER
				{
				normal(1),
				alwayson(2),
				periodic(3)
				}
			MAX-ACCESS read-create
			STATUS current
			DESCRIPTION
				"This attribute defines the video stream type."
			DEFVAL { normal }
			::= { zhoneCpeVideoAccessControlEntry 5 }

		
		-- 1.3.6.1.4.1.5504.5.16.1.10.2.1.6
		zhoneCpeVideoAccessControlSrcIp OBJECT-TYPE
			SYNTAX IpAddress
			MAX-ACCESS read-create
			STATUS current
			DESCRIPTION
				"This is the source IP address. Default value is 0.0.0.0, it specifies that
				the source IP address is to be ignored."
			::= { zhoneCpeVideoAccessControlEntry 6 }

		
		-- 1.3.6.1.4.1.5504.5.16.1.10.2.1.7
		zhoneCpeVideoAccessControlDstIpStart OBJECT-TYPE
			SYNTAX IpAddress
			MAX-ACCESS read-create
			STATUS current
			DESCRIPTION
				"Destination IP address of the start of the multicast range. Default value
				is 0.0.0.0."
			::= { zhoneCpeVideoAccessControlEntry 7 }

		
		-- 1.3.6.1.4.1.5504.5.16.1.10.2.1.8
		zhoneCpeVideoAccessControlDstIpEnd OBJECT-TYPE
			SYNTAX IpAddress
			MAX-ACCESS read-create
			STATUS current
			DESCRIPTION
				"Destination IP address of the end of the multicast range. Default value is 
				0.0.0.0."
			::= { zhoneCpeVideoAccessControlEntry 8 }

		
		-- 1.3.6.1.4.1.5504.5.16.1.10.2.1.9
		zhoneCpeVideoAccessControlImputedGroupBw OBJECT-TYPE
			SYNTAX Unsigned32 (0..2147483647)
			UNITS "bytes/second"
			MAX-ACCESS read-create
			STATUS current
			DESCRIPTION
				"Expressed in bytes/sec, the imputed group bandwidth is used to decide
				whether or not to honor a join request in the presence of a max multicast
				bandwidth limit. The default value 0 effectively allows this table entry
				to avoid max bandwidth limitations."
			DEFVAL { 0 }
			::= { zhoneCpeVideoAccessControlEntry 9 }

		
		-- 1.3.6.1.4.1.5504.5.16.1.11
		zhoneCpePweSubscriberTable OBJECT-TYPE
			SYNTAX SEQUENCE OF ZhoneCpePweSubscriberEntry
			MAX-ACCESS not-accessible
			STATUS current
			DESCRIPTION
				"Cpe Pwe Subscriber table."
			::= { zhoneCpeObjectID 11 }

		
		-- 1.3.6.1.4.1.5504.5.16.1.11.1
		zhoneCpePweSubscriberEntry OBJECT-TYPE
			SYNTAX ZhoneCpePweSubscriberEntry
			MAX-ACCESS not-accessible
			STATUS current
			DESCRIPTION
				"Row in the CpePweSubscriber table."
			INDEX { zhoneCpeIfIndex, zhoneCpePweSubscriberPortNumber }
			::= { zhoneCpePweSubscriberTable 1 }

		
		ZhoneCpePweSubscriberEntry ::=
			SEQUENCE { 
				zhoneCpePweSubscriberPortNumber
					Unsigned32,
				zhoneCpePweSubscriberRowStatus
					ZhoneRowStatus,
				zhoneCpePweSubscriberAdminState
					ZhoneAdminState,
				zhoneCpePweSubscriberLoopback
					INTEGER,
				zhoneCpePweSubscriberNearEndPort
					Unsigned32,
				zhoneCpePweSubscriberFarEndIp
					IpAddress,
				zhoneCpePweSubscriberFarEndPort
					Unsigned32,
				zhoneCpePweSubscriberLineLength
					Unsigned32,
				zhoneCpePweProfileIndex
					Unsigned32,
				zhoneCpePweSubscriberLineStatusAlarm
					ZhoneEnabledFlag,
				zhoneCpePweSubscriberAlarmSeverity
					ZhoneAlarmSeverity,
				zhoneCpePweSubscriberDescription
					OCTET STRING,
				zhoneCpePweSubscriberDestMac
					MacAddress,
				zhoneCpePweSubscriberOuterMplsLabel
					Unsigned32,
				zhoneCpePweSubscriberInnerMplsLabel
					Unsigned32,
				zhoneCpePweSubscriberEcid
					Unsigned32
			 }

		-- 1.3.6.1.4.1.5504.5.16.1.11.1.1
		zhoneCpePweSubscriberPortNumber OBJECT-TYPE
			SYNTAX Unsigned32 (1..2147483647)
			MAX-ACCESS not-accessible
			STATUS current
			DESCRIPTION
				"This represents the CPE Pwe Subscriber Port Number."
			::= { zhoneCpePweSubscriberEntry 1 }

		
		-- 1.3.6.1.4.1.5504.5.16.1.11.1.2
		zhoneCpePweSubscriberRowStatus OBJECT-TYPE
			SYNTAX ZhoneRowStatus
			MAX-ACCESS read-create
			STATUS current
			DESCRIPTION
				"Used to create, modify or delete an entry in this table."
			DEFVAL { active }
			::= { zhoneCpePweSubscriberEntry 2 }

		
		-- 1.3.6.1.4.1.5504.5.16.1.11.1.3
		zhoneCpePweSubscriberAdminState OBJECT-TYPE
			SYNTAX ZhoneAdminState
			MAX-ACCESS read-create
			STATUS current
			DESCRIPTION
				"This attribute activates or deactivates the functions performed by the
				CES port for this subscriber or puts the port in test mode."
			DEFVAL { 1 }
			::= { zhoneCpePweSubscriberEntry 3 }

		
		-- 1.3.6.1.4.1.5504.5.16.1.11.1.4
		zhoneCpePweSubscriberLoopback OBJECT-TYPE
			SYNTAX INTEGER
				{
				noloop(1),
				payload(2),
				line(3),
				ponside(4),
				cesside(5)
				}
			MAX-ACCESS read-create
			STATUS current
			DESCRIPTION
				"This attribute specifies and reports the loopback configuration of the
				physical interface."
			DEFVAL { noloop }
			::= { zhoneCpePweSubscriberEntry 4 }

		
		-- 1.3.6.1.4.1.5504.5.16.1.11.1.5
		zhoneCpePweSubscriberNearEndPort OBJECT-TYPE
			SYNTAX Unsigned32 (0..65535)
			MAX-ACCESS read-create
			STATUS current
			DESCRIPTION
				"When the pseudowire service is transported via IP, this attribute specifies
				the port number of the near-end TCP/UDP service. The default value is
				57000 + port number."
			DEFVAL { 57000 }
			::= { zhoneCpePweSubscriberEntry 5 }

		
		-- 1.3.6.1.4.1.5504.5.16.1.11.1.6
		zhoneCpePweSubscriberFarEndIp OBJECT-TYPE
			SYNTAX IpAddress
			MAX-ACCESS read-create
			STATUS current
			DESCRIPTION
				"When the pseudowire service is transported via IP, this attribute specifies
				the IP or resolved name of the far-end termination point."
			::= { zhoneCpePweSubscriberEntry 6 }

		
		-- 1.3.6.1.4.1.5504.5.16.1.11.1.7
		zhoneCpePweSubscriberFarEndPort OBJECT-TYPE
			SYNTAX Unsigned32 (0..65535)
			MAX-ACCESS read-create
			STATUS current
			DESCRIPTION
				"When the pseudowire service is transported via IP, this attribute specifies
				the port number of the far-end TCP/UDP service. The default value is
				57000 + port number."
			DEFVAL { 57000 }
			::= { zhoneCpePweSubscriberEntry 7 }

		
		-- 1.3.6.1.4.1.5504.5.16.1.11.1.8
		zhoneCpePweSubscriberLineLength OBJECT-TYPE
			SYNTAX Unsigned32 (0..65535)
			UNITS "feet"
			MAX-ACCESS read-create
			STATUS current
			DESCRIPTION
				"This attribute specifies the length of the twisted pair cable from a DS1
				physical UNI to the DSX-1 cross-connect point."
			DEFVAL { 0 }
			::= { zhoneCpePweSubscriberEntry 8 }

		
		-- 1.3.6.1.4.1.5504.5.16.1.11.1.9
		zhoneCpePweProfileIndex OBJECT-TYPE
			SYNTAX Unsigned32 (1..2147483647)
			MAX-ACCESS read-create
			STATUS current
			DESCRIPTION
				"This attribute points to the associated PWE profile. 1 indicates a
				default profile is used."
			DEFVAL { 1 }
			::= { zhoneCpePweSubscriberEntry 9 }

		
		-- 1.3.6.1.4.1.5504.5.16.1.11.1.10
		zhoneCpePweSubscriberLineStatusAlarm OBJECT-TYPE
			SYNTAX ZhoneEnabledFlag
			MAX-ACCESS read-create
			STATUS current
			DESCRIPTION
				"This field is for enabling/disabling alarm reporting from this CPE UNI."
			DEFVAL { enabled }
			::= { zhoneCpePweSubscriberEntry 10 }

		
		-- 1.3.6.1.4.1.5504.5.16.1.11.1.11
		zhoneCpePweSubscriberAlarmSeverity OBJECT-TYPE
			SYNTAX ZhoneAlarmSeverity
			MAX-ACCESS read-create
			STATUS current
			DESCRIPTION
				"This field is for specifying the severity level of all the alarms from this CPE UNI."
			DEFVAL { major }
			::= { zhoneCpePweSubscriberEntry 11 }

		
		-- 1.3.6.1.4.1.5504.5.16.1.11.1.12
		zhoneCpePweSubscriberDescription OBJECT-TYPE
			SYNTAX OCTET STRING (SIZE (0..32))
			MAX-ACCESS read-create
			STATUS current
			DESCRIPTION
				"Describes the CPE pwe subscriber profile instance"
			DEFVAL { "" }
			::= { zhoneCpePweSubscriberEntry 12 }

		
		-- 1.3.6.1.4.1.5504.5.16.1.11.1.13
		zhoneCpePweSubscriberDestMac OBJECT-TYPE
			SYNTAX MacAddress
			MAX-ACCESS read-create
			STATUS current
			DESCRIPTION
				"Each connection requires the configuration of the MAC Address of the peer Ethernet bridged device. If the destination MAC address is incorrectly configured, all PWE packets will be discarded by the remote PWE device. If the field is empty, MAC address Mode is dynamic. The destination MAC address is determined from ARP."
			DEFVAL { '000147000000'h }
			::= { zhoneCpePweSubscriberEntry 13 }

		
		-- 1.3.6.1.4.1.5504.5.16.1.11.1.14
		zhoneCpePweSubscriberOuterMplsLabel OBJECT-TYPE
			SYNTAX Unsigned32
			MAX-ACCESS read-create
			STATUS current
			DESCRIPTION
				"The outer MPLS label identifies the MPLS LSP, used to tunnel the TDMoMPLS packets through the MPLS network. It is also known as the tunnel label or the transport label."
			DEFVAL { '0'b }
			::= { zhoneCpePweSubscriberEntry 14 }

		
		-- 1.3.6.1.4.1.5504.5.16.1.11.1.15
		zhoneCpePweSubscriberInnerMplsLabel OBJECT-TYPE
			SYNTAX Unsigned32
			MAX-ACCESS read-create
			STATUS current
			DESCRIPTION
				"Inner MPLS label is also known as the PW label or the interworking label, which contains the bundle identifier used to multiplex multiple bundles within the same tunnel. It is used for all packets transmitted to and received from the remote PWE device."
			DEFVAL { '0'b }
			::= { zhoneCpePweSubscriberEntry 15 }

		
		-- 1.3.6.1.4.1.5504.5.16.1.11.1.16
		zhoneCpePweSubscriberEcid OBJECT-TYPE
			SYNTAX Unsigned32
			MAX-ACCESS read-create
			STATUS current
			DESCRIPTION
				"Emulated Circuit ID (ECID) defines the destination that will be used for all packets transmitted to and received from the remote PWE device."
			DEFVAL { '0'b }
			::= { zhoneCpePweSubscriberEntry 16 }

		
		-- 1.3.6.1.4.1.5504.5.16.1.12
		zhoneCpePwe OBJECT-IDENTITY
			STATUS current
			DESCRIPTION 
				"Cpe Pwe objects."
			::= { zhoneCpeObjectID 12 }

		
		-- 1.3.6.1.4.1.5504.5.16.1.12.1
		zhoneCpePweIndexNext OBJECT-TYPE
			SYNTAX Integer32
			MAX-ACCESS read-only
			STATUS current
			DESCRIPTION
				"This object contains an appropriate value to be used for the zhoneCpePweIndex
				when creating entries in the zhoneCpePweTable. The value 0 indicates that
				no unassigned entries are available. To obtain the zhoneCpePweIndex value
				for a new entry, the manager issues a management protocol retrieval
				operation to obtain the current value of this object.  After each retrieval,
				the agent should modify the value to the next unassigned index.
				
				After a manager retrieves a value the agent will determine through its local
				policy when this index value will be made available for reuse."
			::= { zhoneCpePwe 1 }

		
		-- 1.3.6.1.4.1.5504.5.16.1.12.2
		zhoneCpePweTable OBJECT-TYPE
			SYNTAX SEQUENCE OF ZhoneCpePweEntry
			MAX-ACCESS not-accessible
			STATUS current
			DESCRIPTION
				"Cpe Pwe table."
			::= { zhoneCpePwe 2 }

		
		-- 1.3.6.1.4.1.5504.5.16.1.12.2.1
		zhoneCpePweEntry OBJECT-TYPE
			SYNTAX ZhoneCpePweEntry
			MAX-ACCESS not-accessible
			STATUS current
			DESCRIPTION
				"Row in the CpePwe table."
			INDEX { zhoneCpePweIndex }
			::= { zhoneCpePweTable 1 }

		
		ZhoneCpePweEntry ::=
			SEQUENCE { 
				zhoneCpePweIndex
					Unsigned32,
				zhoneCpePweRowStatus
					ZhoneRowStatus,
				zhoneCpePweProfileName
					ZhoneAdminString,
				zhoneCpePweLineType
					INTEGER,
				zhoneCpePweEncoding
					INTEGER,
				zhoneCpePweDs1Mode
					INTEGER,
				zhoneCpePweDs1Framing
					INTEGER,
				zhoneCpePweTransport
					INTEGER,
				zhoneCpePweServiceType
					INTEGER,
				zhoneCpePweSignalling
					INTEGER,
				zhoneCpePwePayloadSize
					Unsigned32,
				zhoneCpePwePayloadEncapsulationDelay
					INTEGER,
				zhoneCpePweTimingMode
					INTEGER,
				zhoneCpePweChannelAssign
					BITS,
				zhoneCpePweClockReference
					Unsigned32,
				zhoneCpePweRtpTimeStampMode
					INTEGER,
				zhoneCpePwePtypePayload
					Unsigned32,
				zhoneCpePwePtypeSignalling
					Unsigned32,
				zhoneCpePweSSrcPayload
					Unsigned32,
				zhoneCpePweSSrcSignalling
					Unsigned32,
				zhoneCpePweExpectedPTypePayload
					Unsigned32,
				zhoneCpePweExpectedPTypeSignalling
					Unsigned32,
				zhoneCpePweExpectedSSrcPayload
					Unsigned32,
				zhoneCpePweExpectedSSrcSignalling
					Unsigned32,
				zhoneCpePweJitterBufMax
					Unsigned32,
				zhoneCpePweJitterBufDesired
					Unsigned32,
				zhoneCpePweFillPolicy
					INTEGER,
				zhoneCpePweMisconnectedDeclarePolicy
					Unsigned32,
				zhoneCpePweMisconnectedClearPolicy
					Unsigned32,
				zhoneCpePweLossPacketDeclarePolicy
					Unsigned32,
				zhoneCpePweLossPacketClearPolicy
					Unsigned32,
				zhoneCpePweOverrunUnderrunDeclarePolicy
					Unsigned32,
				zhoneCpePweOverrunUnderrunClearPolicy
					Unsigned32,
				zhoneCpePweMalformedDeclarePolicy
					Unsigned32,
				zhoneCpePweMalformedClearPolicy
					Unsigned32,
				zhoneCpePweRBitTransmitSetPolicy
					Unsigned32,
				zhoneCpePweRBitTransmitClearPolicy
					Unsigned32,
				zhoneCpePweRBitReceivePolicy
					INTEGER,
				zhoneCpePweLBitReceivePolicy
					INTEGER,
				zhoneCpePweSesThreshold
					Unsigned32,
				zhoneCpePweCdvTolerance
					Unsigned32,
				zhoneCpePweChannelAssociatedSignalling
					INTEGER,
				zhoneCpePweMplsTpType
					INTEGER,
				zhoneCpePweDscp
					OCTET STRING
			 }

		-- 1.3.6.1.4.1.5504.5.16.1.12.2.1.1
		zhoneCpePweIndex OBJECT-TYPE
			SYNTAX Unsigned32 (1..2147483647)
			MAX-ACCESS not-accessible
			STATUS current
			DESCRIPTION
				"This represents the CPE Pwe Index."
			::= { zhoneCpePweEntry 1 }

		
		-- 1.3.6.1.4.1.5504.5.16.1.12.2.1.2
		zhoneCpePweRowStatus OBJECT-TYPE
			SYNTAX ZhoneRowStatus
			MAX-ACCESS read-create
			STATUS current
			DESCRIPTION
				"Used to create, modify or delete an entry in this table."
			DEFVAL { active }
			::= { zhoneCpePweEntry 2 }

		
		-- 1.3.6.1.4.1.5504.5.16.1.12.2.1.3
		zhoneCpePweProfileName OBJECT-TYPE
			SYNTAX ZhoneAdminString
			MAX-ACCESS read-create
			STATUS current
			DESCRIPTION
				"CPE Pwe profile for the dynamic bridging. This field is only writable
				upon creation and must be unique within its table."
			::= { zhoneCpePweEntry 3 }

		
		-- 1.3.6.1.4.1.5504.5.16.1.12.2.1.4
		zhoneCpePweLineType OBJECT-TYPE
			SYNTAX INTEGER
				{
				ds1(1),
				e1(2),
				other(3)
				}
			MAX-ACCESS read-create
			STATUS current
			DESCRIPTION
				"This attribute specifies the line type (T1, E1 or other) used."
			DEFVAL { e1 }
			::= { zhoneCpePweEntry 4 }

		
		-- 1.3.6.1.4.1.5504.5.16.1.12.2.1.5
		zhoneCpePweEncoding OBJECT-TYPE
			SYNTAX INTEGER
				{
				b8zs(1),
				ami(2),
				hdb3(3),
				b3zs(4)
				}
			MAX-ACCESS read-create
			STATUS current
			DESCRIPTION
				"This attribute specifies the line coding scheme."
			DEFVAL { hdb3 }
			::= { zhoneCpePweEntry 5 }

		
		-- 1.3.6.1.4.1.5504.5.16.1.12.2.1.6
		zhoneCpePweDs1Mode OBJECT-TYPE
			SYNTAX INTEGER
				{
				shorthaulnopwr(1),
				longhaulnopwr(2),
				niulonghaulnopwr(3),
				niulonghaulpwr(4)
				}
			MAX-ACCESS read-create
			STATUS current
			DESCRIPTION
				"This attribute specifies the mode of a DS1."
			DEFVAL { shorthaulnopwr }
			::= { zhoneCpePweEntry 6 }

		
		-- 1.3.6.1.4.1.5504.5.16.1.12.2.1.7
		zhoneCpePweDs1Framing OBJECT-TYPE
			SYNTAX INTEGER
				{
				extsuperframe(1),
				superframe(2),
				unframed(3),
				g704(4),
				jtg704(5)
				}
			MAX-ACCESS read-create
			STATUS current
			DESCRIPTION
				"This attribute specifies the DS1 framing structure."
			DEFVAL { unframed }
			::= { zhoneCpePweEntry 7 }

		
		-- 1.3.6.1.4.1.5504.5.16.1.12.2.1.8
		zhoneCpePweTransport OBJECT-TYPE
			SYNTAX INTEGER
				{
				ethernet(1),
				udp(2),
				mpls(3)
				}
			MAX-ACCESS read-create
			STATUS current
			DESCRIPTION
				"The underlying transport for the Pseudowire service."
			DEFVAL { udp }
			::= { zhoneCpePweEntry 8 }

		
		-- 1.3.6.1.4.1.5504.5.16.1.12.2.1.9
		zhoneCpePweServiceType OBJECT-TYPE
			SYNTAX INTEGER
				{
				unstructured(1),
				octetalignedunstruct(2),
				structured(3)
				}
			MAX-ACCESS read-create
			STATUS current
			DESCRIPTION
				"This attribute specifies the basic service type, either a transparent bit
				pipe or an encapsulation that recognizes the underlying structure of the
				payload."
			DEFVAL { unstructured }
			::= { zhoneCpePweEntry 9 }

		
		-- 1.3.6.1.4.1.5504.5.16.1.12.2.1.10
		zhoneCpePweSignalling OBJECT-TYPE
			SYNTAX INTEGER
				{
				nosignalling(1),
				inbandcas(2),
				outofbandcas(3)
				}
			MAX-ACCESS read-create
			STATUS current
			DESCRIPTION
				"This attribute specifies how CAS signalling is carried."
			DEFVAL { nosignalling }
			::= { zhoneCpePweEntry 10 }

		
		-- 1.3.6.1.4.1.5504.5.16.1.12.2.1.11
		zhoneCpePwePayloadSize OBJECT-TYPE
			SYNTAX Unsigned32 (0..65535)
			MAX-ACCESS read-create
			STATUS current
			DESCRIPTION
				"Number of payload bytes per packet. Valid only if service type =
				unstructured or unstructured octet-aligned. Valid choices depend on the
				TDM service, but must include the following. Other choices are at the
				vendor's discretion.
				DS1	192
				DS1	200, required only if unstructured octet aligned service is
				        supported
				E1	256
				DS3	1024
				E3	1024"
			DEFVAL { 250 }
			::= { zhoneCpePweEntry 11 }

		
		-- 1.3.6.1.4.1.5504.5.16.1.12.2.1.12
		zhoneCpePwePayloadEncapsulationDelay OBJECT-TYPE
			SYNTAX INTEGER
				{
				nosignallingandNvalueis1(1),
				nosignallingandNvalueis2to4(2),
				nosignallingandNvalueisgreaterthan4(3),
				ds1cas(4),
				e1cas(5)
				}
			UNITS "number of frames"
			MAX-ACCESS read-create
			STATUS current
			DESCRIPTION
				"This represents number of 125 microsecond frames to be encapsulated in
				each pseudowire packet. Valid only if service type = structured. The
				minimum set of choices for various TDM services is listed below, and is
				affected by the possible presence of in-band signalling. Other choices are at
				the vendor discretion.
				NxDS0, no signalling, N = 1 64 (8 ms) required,
				                            40 (5 ms) desired
				NxDS0, no signalling, N = 2..4 32 (4 ms)
				NxDS0, no signalling, N > 4 8 (1 ms)
				NxDS0 with DS1 CAS 24 (3 ms)
				NxDS0 with E1 CAS 16 (2 ms)"
			DEFVAL { nosignallingandNvalueis1 }
			::= { zhoneCpePweEntry 12 }

		
		-- 1.3.6.1.4.1.5504.5.16.1.12.2.1.13
		zhoneCpePweTimingMode OBJECT-TYPE
			SYNTAX INTEGER
				{
				network(1),
				differential(2),
				adaptive(3),
				loop(4)
				}
			MAX-ACCESS read-create
			STATUS current
			DESCRIPTION
				"This attribute selects the timing mode of the TDM service. If RTP is used,
				this attribute must be set to be consistent with the value of the RTP time
				stamp mode attribute in the RTP parameters managed entity at the far end.
				1 Network timing 
				2 Differential timing
				3 Adaptive timing (default)
				4 Loop timing: local TDM transmit clock derived from local TDM
				               receive stream"
			DEFVAL { adaptive }
			::= { zhoneCpePweEntry 13 }

		
		-- 1.3.6.1.4.1.5504.5.16.1.12.2.1.14
		zhoneCpePweChannelAssign OBJECT-TYPE
			SYNTAX BITS
				{
				channel0(0),
				channel1(1),
				channel2(2),
				channel3(3),
				channel4(4),
				channel5(5),
				channel6(6),
				channel7(7),
				channel8(8),
				channel9(9),
				channel10(10),
				channel11(11),
				channel12(12),
				channel13(13),
				channel14(14),
				channel15(15),
				channel16(16),
				channel17(17),
				channel18(18),
				channel19(19),
				channel20(20),
				channel21(21),
				channel22(22),
				channel23(23),
				channel24(24),
				channel25(25),
				channel26(26),
				channel27(27),
				channel28(28),
				channel29(29),
				channel30(30),
				channel31(31)
				}
			MAX-ACCESS read-create
			STATUS current
			DESCRIPTION
				"If service type is structured, this attribute is a bit field indicating
				the 64kbps sub channels are used. This is not supported currently. The default
				value is channel0, but it might change later."
			::= { zhoneCpePweEntry 14 }

		
		-- 1.3.6.1.4.1.5504.5.16.1.12.2.1.15
		zhoneCpePweClockReference OBJECT-TYPE
			SYNTAX Unsigned32 (1..65535)
			UNITS "kHz"
			MAX-ACCESS read-create
			STATUS current
			DESCRIPTION
				"This attribute specifies the frequency of the common timing reference,
				in multiples of 8 kHz. The default value is 1 (8 kHz)."
			DEFVAL { 1 }
			::= { zhoneCpePweEntry 15 }

		
		-- 1.3.6.1.4.1.5504.5.16.1.12.2.1.16
		zhoneCpePweRtpTimeStampMode OBJECT-TYPE
			SYNTAX INTEGER
				{
				unknown(1),
				absolute(2),
				differential(3)
				}
			MAX-ACCESS read-create
			STATUS current
			DESCRIPTION
				"This attribute determines the mode in which RTP timestamps are generated
				in the TDM to PSN direction."
			DEFVAL { unknown }
			::= { zhoneCpePweEntry 16 }

		
		-- 1.3.6.1.4.1.5504.5.16.1.12.2.1.17
		zhoneCpePwePtypePayload OBJECT-TYPE
			SYNTAX Unsigned32 (96..127)
			MAX-ACCESS read-create
			STATUS current
			DESCRIPTION
				"This attribute specifies the RTP payload type for the payload channel
				in the TDM to PSN direction. Assignable PTYPEs lie in the dynamic range
				96..127."
			DEFVAL { 96 }
			::= { zhoneCpePweEntry 17 }

		
		-- 1.3.6.1.4.1.5504.5.16.1.12.2.1.18
		zhoneCpePwePtypeSignalling OBJECT-TYPE
			SYNTAX Unsigned32 (0..127)
			MAX-ACCESS read-create
			STATUS current
			DESCRIPTION
				"This attribute specifies the RTP payload type direction for the signaling
				channel in the TDM to PSN. Assignable PTYPEs lie in the dynamic range
				96..127. If signalling is not transported in its own channel, the value
				should be set to 0. So the valid values used are 0, 96-127."
			DEFVAL { 0 }
			::= { zhoneCpePweEntry 18 }

		
		-- 1.3.6.1.4.1.5504.5.16.1.12.2.1.19
		zhoneCpePweSSrcPayload OBJECT-TYPE
			SYNTAX Unsigned32 (0..2147483647)
			MAX-ACCESS read-create
			STATUS current
			DESCRIPTION
				"This attribute specifies the RTP synchronization source for the payload
				channel in the TDM to PSN direction."
			DEFVAL { 0 }
			::= { zhoneCpePweEntry 19 }

		
		-- 1.3.6.1.4.1.5504.5.16.1.12.2.1.20
		zhoneCpePweSSrcSignalling OBJECT-TYPE
			SYNTAX Unsigned32 (0..2147483647)
			MAX-ACCESS read-create
			STATUS current
			DESCRIPTION
				"This attribute specifies the RTP synchronization source for the signaling
				channel in the TDM to PSN direction. If signalling is not transported in
				its own channel, this value should be set to 0."
			DEFVAL { 0 }
			::= { zhoneCpePweEntry 20 }

		
		-- 1.3.6.1.4.1.5504.5.16.1.12.2.1.21
		zhoneCpePweExpectedPTypePayload OBJECT-TYPE
			SYNTAX Unsigned32 (0..255)
			MAX-ACCESS read-create
			STATUS current
			DESCRIPTION
				"This attribute specifies the RTP payload type for the payload channel in
				the PSN to TDM direction. The received payload type may be used to detect
				malformed packets. To disable the check functions, set the value to its
				default value 0."
			DEFVAL { 0 }
			::= { zhoneCpePweEntry 21 }

		
		-- 1.3.6.1.4.1.5504.5.16.1.12.2.1.22
		zhoneCpePweExpectedPTypeSignalling OBJECT-TYPE
			SYNTAX Unsigned32 (0..255)
			MAX-ACCESS read-create
			STATUS current
			DESCRIPTION
				"This attribute specifies the RTP payload type for the signaling channel
				in the PSN to TDM direction. The received payload type may be used to
				detect malformed packets. To disable the check functions, set the value
				to its default value 0."
			DEFVAL { 0 }
			::= { zhoneCpePweEntry 22 }

		
		-- 1.3.6.1.4.1.5504.5.16.1.12.2.1.23
		zhoneCpePweExpectedSSrcPayload OBJECT-TYPE
			SYNTAX Unsigned32 (0..2147483647)
			MAX-ACCESS read-create
			STATUS current
			DESCRIPTION
				"This attribute specifies the RTP synchronization source in the PSN to TDM
				direction. The received SSRC may be used to detect misconnection
				(stray packets). To disable the check functions, set the value to its
				default value 0."
			DEFVAL { 0 }
			::= { zhoneCpePweEntry 23 }

		
		-- 1.3.6.1.4.1.5504.5.16.1.12.2.1.24
		zhoneCpePweExpectedSSrcSignalling OBJECT-TYPE
			SYNTAX Unsigned32 (0..2147483647)
			MAX-ACCESS read-create
			STATUS current
			DESCRIPTION
				"This attribute specifies the RTP synchronization source for the signalling
				channel in the PSN to TDM direction. The received SSRC may be used to detect
				misconnection (stray packets). To disable the check functions, set the value
				to its default value 0."
			DEFVAL { 0 }
			::= { zhoneCpePweEntry 24 }

		
		-- 1.3.6.1.4.1.5504.5.16.1.12.2.1.25
		zhoneCpePweJitterBufMax OBJECT-TYPE
			SYNTAX Unsigned32 (0..65535)
			UNITS "micro seconds"
			MAX-ACCESS read-create
			STATUS current
			DESCRIPTION
				"This attribute specifies the desired maximum depth of the playout buffer
				in the PSN to TDM direction. The value is expressed as a multiple of the
				125 micro second frame rate. The value 0 selects the ONT's internal policy."
			DEFVAL { 128 }
			::= { zhoneCpePweEntry 25 }

		
		-- 1.3.6.1.4.1.5504.5.16.1.12.2.1.26
		zhoneCpePweJitterBufDesired OBJECT-TYPE
			SYNTAX Unsigned32 (0..65535)
			UNITS "micro seconds"
			MAX-ACCESS read-create
			STATUS current
			DESCRIPTION
				"This attribute specifies the desired nominal fill depth of the playout
				buffer in the PSN to TDM direction. The value is expressed as a multiple
				of the 125 micro second frame rate. The value 0 selects the ONT's internal
				policy."
			DEFVAL { 64 }
			::= { zhoneCpePweEntry 26 }

		
		-- 1.3.6.1.4.1.5504.5.16.1.12.2.1.27
		zhoneCpePweFillPolicy OBJECT-TYPE
			SYNTAX INTEGER
				{
				vendorspecific(1),
				ais(2),
				allones(3),
				allzeros(4),
				repeatprevdata(5),
				ds1idle(6)
				}
			MAX-ACCESS read-create
			STATUS current
			DESCRIPTION
				"This attribute defines the payload bit pattern to be applied toward the
				TDM service if no payload packet is available to play out. The default
				value 1 specifies that the ONT apply its internal policy, ie vendor-specific."
			DEFVAL { vendorspecific }
			::= { zhoneCpePweEntry 27 }

		
		-- 1.3.6.1.4.1.5504.5.16.1.12.2.1.28
		zhoneCpePweMisconnectedDeclarePolicy OBJECT-TYPE
			SYNTAX Unsigned32 (0..100)
			MAX-ACCESS read-create
			STATUS current
			DESCRIPTION
				"The alarm declaration policy attribute defines the anomaly rate that causes
				the corresponding alarm to be declared. It is an integer percentage between
				1..100. If this density of anomalies occurs during the alarm onset soak
				interval, the alarm is declared. The default value 0 selects the ONT's
				internal policy."
			DEFVAL { 0 }
			::= { zhoneCpePweEntry 28 }

		
		-- 1.3.6.1.4.1.5504.5.16.1.12.2.1.29
		zhoneCpePweMisconnectedClearPolicy OBJECT-TYPE
			SYNTAX Unsigned32 (0..255)
			MAX-ACCESS read-create
			STATUS current
			DESCRIPTION
				"The alarm clear policy attribute defines the anomaly rate that causes the
				correcponding alarm to be cleared. It is an integer percentage between
				0..99. If no more than this density of anomalies occurs during the alarm
				clear soak interval, the alarm is cleared. The default value 255 selects
				the ONT's internal policy."
			DEFVAL { 255 }
			::= { zhoneCpePweEntry 29 }

		
		-- 1.3.6.1.4.1.5504.5.16.1.12.2.1.30
		zhoneCpePweLossPacketDeclarePolicy OBJECT-TYPE
			SYNTAX Unsigned32 (0..100)
			MAX-ACCESS read-create
			STATUS current
			DESCRIPTION
				"The alarm declaration policy attribute defines the anomaly rate that causes
				the corresponding alarm to be declared. It is an integer percentage between
				1..100. If this density of anomalies occurs during the alarm onset soak
				interval, the alarm is declared. The default value 0 selects the ONT's
				internal policy."
			DEFVAL { 0 }
			::= { zhoneCpePweEntry 30 }

		
		-- 1.3.6.1.4.1.5504.5.16.1.12.2.1.31
		zhoneCpePweLossPacketClearPolicy OBJECT-TYPE
			SYNTAX Unsigned32 (0..255)
			MAX-ACCESS read-create
			STATUS current
			DESCRIPTION
				"The alarm clear policy attribute defines the anomaly rate that causes the
				correcponding alarm to be cleared. It is an integer percentage between
				0..99. If no more than this density of anomalies occurs during the alarm
				clear soak interval, the alarm is cleared. The default value 255 selects
				the ONT's internal policy."
			DEFVAL { 255 }
			::= { zhoneCpePweEntry 31 }

		
		-- 1.3.6.1.4.1.5504.5.16.1.12.2.1.32
		zhoneCpePweOverrunUnderrunDeclarePolicy OBJECT-TYPE
			SYNTAX Unsigned32 (0..100)
			MAX-ACCESS read-create
			STATUS current
			DESCRIPTION
				"The alarm declaration policy attribute defines the anomaly rate that causes
				the corresponding alarm to be declared. It is an integer percentage between
				1..100. If this density of anomalies occurs during the alarm onset soak
				interval, the alarm is declared. The default value 0 selects the ONT's
				internal policy."
			DEFVAL { 0 }
			::= { zhoneCpePweEntry 32 }

		
		-- 1.3.6.1.4.1.5504.5.16.1.12.2.1.33
		zhoneCpePweOverrunUnderrunClearPolicy OBJECT-TYPE
			SYNTAX Unsigned32 (0..255)
			MAX-ACCESS read-create
			STATUS current
			DESCRIPTION
				"The alarm clear policy attribute defines the anomaly rate that causes the
				correcponding alarm to be cleared. It is an integer percentage between
				0..99. If no more than this density of anomalies occurs during the alarm
				clear soak interval, the alarm is cleared. The default value 255 selects
				the ONT's internal policy."
			DEFVAL { 255 }
			::= { zhoneCpePweEntry 33 }

		
		-- 1.3.6.1.4.1.5504.5.16.1.12.2.1.34
		zhoneCpePweMalformedDeclarePolicy OBJECT-TYPE
			SYNTAX Unsigned32 (0..100)
			MAX-ACCESS read-create
			STATUS current
			DESCRIPTION
				"The alarm declaration policy attribute defines the anomaly rate that causes
				the corresponding alarm to be declared. It is an integer percentage between
				1..100. If this density of anomalies occurs during the alarm onset soak
				interval, the alarm is declared. The default value 0 selects the ONT's
				internal policy."
			DEFVAL { 0 }
			::= { zhoneCpePweEntry 34 }

		
		-- 1.3.6.1.4.1.5504.5.16.1.12.2.1.35
		zhoneCpePweMalformedClearPolicy OBJECT-TYPE
			SYNTAX Unsigned32 (0..255)
			MAX-ACCESS read-create
			STATUS current
			DESCRIPTION
				"The alarm clear policy attribute defines the anomaly rate that causes the
				correcponding alarm to be cleared. It is an integer percentage between
				0..99. If no more than this density of anomalies occurs during the alarm
				clear soak interval, the alarm is cleared. The default value 255 selects
				the ONT's internal policy."
			DEFVAL { 255 }
			::= { zhoneCpePweEntry 35 }

		
		-- 1.3.6.1.4.1.5504.5.16.1.12.2.1.36
		zhoneCpePweRBitTransmitSetPolicy OBJECT-TYPE
			SYNTAX Unsigned32 (0..255)
			MAX-ACCESS read-create
			STATUS current
			DESCRIPTION
				"This attribute defines the number of consecutive lost packets that
				causes the transmitted R bit to be set in the TDM to PSN direction, indicating
				lost packets to the far end. The default value 0 selects the ONT internal
				policy."
			DEFVAL { 0 }
			::= { zhoneCpePweEntry 36 }

		
		-- 1.3.6.1.4.1.5504.5.16.1.12.2.1.37
		zhoneCpePweRBitTransmitClearPolicy OBJECT-TYPE
			SYNTAX Unsigned32 (0..255)
			MAX-ACCESS read-create
			STATUS current
			DESCRIPTION
				"This attribute defines the number of consecutive valid packets
				that causes the transmitted R bit to be cleared in the TDM to PSN direction,
				removing the remote failure indication to the far end. The default value 0
				selects the ONT internal policy."
			DEFVAL { 0 }
			::= { zhoneCpePweEntry 37 }

		
		-- 1.3.6.1.4.1.5504.5.16.1.12.2.1.38
		zhoneCpePweRBitReceivePolicy OBJECT-TYPE
			SYNTAX INTEGER
				{
				nothing(1),
				alarm(2),
				idlechannel(3)
				}
			MAX-ACCESS read-create
			STATUS current
			DESCRIPTION
				"This attribute defines the action toward the Nx64 TDM interface when
				remote failure is indicated on packets received from the PSN."
			DEFVAL { nothing }
			::= { zhoneCpePweEntry 38 }

		
		-- 1.3.6.1.4.1.5504.5.16.1.12.2.1.39
		zhoneCpePweLBitReceivePolicy OBJECT-TYPE
			SYNTAX INTEGER
				{
				ais(1),
				repeatlastpkt(2),
				idlechannel(3)
				}
			MAX-ACCESS read-create
			STATUS current
			DESCRIPTION
				"This attribute defines the action toward the TDM interface when far end TDM
				failure is indicated on packets received from the PSN."
			DEFVAL { ais }
			::= { zhoneCpePweEntry 39 }

		
		-- 1.3.6.1.4.1.5504.5.16.1.12.2.1.40
		zhoneCpePweSesThreshold OBJECT-TYPE
			SYNTAX Unsigned32 (0..65535)
			MAX-ACCESS read-create
			STATUS current
			DESCRIPTION
				"Number of lost, malformed or otherwise unusable packets expected in the
				PSN to TDM direction within a one-second interval that causes a severely
				errored second to be counted. Stray packets do not count toward a severely
				errored second, nor do packets whose L bit is set at the far end. The
				default value is 3."
			DEFVAL { 3 }
			::= { zhoneCpePweEntry 40 }

		
		-- 1.3.6.1.4.1.5504.5.16.1.12.2.1.41
		zhoneCpePweCdvTolerance OBJECT-TYPE
			SYNTAX Unsigned32 (0..65535)
			UNITS "microseconds"
			MAX-ACCESS read-create
			STATUS current
			DESCRIPTION
				"This attribute represents the duration of user data that must be buffered
				by the CES interworking entity to offset packet delay variation. It is
				expressed in 10 microsecond increments. The default value for DS1 CES is
				750 micro seconds; for DS3 CES, it is 1000 micro seconds."
			DEFVAL { 750 }
			::= { zhoneCpePweEntry 41 }

		
		-- 1.3.6.1.4.1.5504.5.16.1.12.2.1.42
		zhoneCpePweChannelAssociatedSignalling OBJECT-TYPE
			SYNTAX INTEGER
				{
				base(1),
				e1cas(2),
				sfcas(3),
				ds1esfcas(4),
				j2cas(5)
				}
			MAX-ACCESS read-create
			STATUS current
			DESCRIPTION
				"This attribute selects the signalling format. It applies to structured
				interfaces only."
			DEFVAL { base }
			::= { zhoneCpePweEntry 42 }

		
		-- 1.3.6.1.4.1.5504.5.16.1.12.2.1.43
		zhoneCpePweMplsTpType OBJECT-TYPE
			SYNTAX INTEGER
				{
				ethernet(1),
				gem(2)
				}
			MAX-ACCESS read-create
			STATUS current
			DESCRIPTION
				"This attribute specifies the type of ANI-side termination for the MPLS
				Pseudowire."
			DEFVAL { ethernet }
			::= { zhoneCpePweEntry 43 }

		
		-- 1.3.6.1.4.1.5504.5.16.1.12.2.1.44
		zhoneCpePweDscp OBJECT-TYPE
			SYNTAX OCTET STRING (SIZE (1..8))
			MAX-ACCESS read-create
			STATUS current
			DESCRIPTION
				"This parameter indicates DSCP value for cpe pwe traffic.
				
				Valid code values:
				
				<0-63>   Differentiated services codepoint value 
				   af11     Mark packets with AF11 dscp (001010) 
				   af12     Mark packets with AF12 dscp (001100) 
				   af13     Mark packets with AF13 dscp (001110) 
				   af21     Mark packets with AF21 dscp (010010) 
				   af22     Mark packets with AF22 dscp (010100) 
				   af23     Mark packets with AF23 dscp (010110) 
				   af31     Mark packets with AF31 dscp (011010) 
				   af32     Mark packets with AF32 dscp (011100) 
				   af33     Mark packets with AF33 dscp (011110) 
				   af41     Mark packets with AF41 dscp (100010) 
				   af42     Mark packets with AF42 dscp (100100) 
				   af43     Mark packets with AF43 dscp (100110) 
				   cs1      Mark packets with CS1(precedence 1) dscp (001000) 
				   cs2      Mark packets with CS2(precedence 2) dscp (010000) 
				   cs3      Mark packets with CS3(precedence 3) dscp (011000) 
				   cs4      Mark packets with CS4(precedence 4) dscp (100000) 
				   cs5      Mark packets with CS5(precedence 5) dscp (101000) 
				   cs6      Mark packets with CS6(precedence 6) dscp (110000) 
				   cs7      Mark packets with CS7(precedence 7) dscp (111000) 
				   default  Mark packets with default dscp (000000) 
				   ef       Mark packets with EF dscp (101110) 
				"
			DEFVAL { "0" }
			::= { zhoneCpePweEntry 44 }

		
		-- 1.3.6.1.4.1.5504.5.16.1.13
		zhoneCpeOnuModelInfoTable OBJECT-TYPE
			SYNTAX SEQUENCE OF ZhoneCpeOnuModelInfoEntry
			MAX-ACCESS not-accessible
			STATUS current
			DESCRIPTION
				"Cpe Onu Model Info table."
			::= { zhoneCpeObjectID 13 }

		
		-- 1.3.6.1.4.1.5504.5.16.1.13.1
		zhoneCpeOnuModelInfoEntry OBJECT-TYPE
			SYNTAX ZhoneCpeOnuModelInfoEntry
			MAX-ACCESS not-accessible
			STATUS current
			DESCRIPTION
				"Row in the CpeOnuModelInfo table."
			INDEX { zhoneCpeOnuModelInfoIndex }
			::= { zhoneCpeOnuModelInfoTable 1 }

		
		ZhoneCpeOnuModelInfoEntry ::=
			SEQUENCE { 
				zhoneCpeOnuModelInfoIndex
					Unsigned32,
				zhoneCpeOnuModelName
					ZhoneAdminString,
				zhoneCpeOnuBatteryBackup
					TruthValue,
				zhoneCpeOnuSipPlarSupported
					TruthValue,
				zhoneCpeOnuEthSlotNumber
					Unsigned32,
				zhoneCpeOnuNumberOfEthPorts
					Unsigned32,
				zhoneCpeOnuPotsSlotNumber
					Unsigned32,
				zhoneCpeOnuNumberOfPotsPorts
					Unsigned32,
				zhoneCpeOnuRfVideoSlotNumber
					Unsigned32,
				zhoneCpeOnuNumberOfRfVideoPorts
					Unsigned32,
				zhoneCpeOnuCesSlotNumber
					Unsigned32,
				zhoneCpeOnuNumberOfCesPorts
					Unsigned32,
				zhoneCpeOnuModelInfoRGBridged
					TruthValue,
				zhoneCpeOnuNumberOfWlanPorts
					Unsigned32,
				zhoneCpeOnuModelInfoRg
					TruthValue,
				zhoneCpeOnuModelInfoRgVoip
					TruthValue,
				zhoneCpeOnuModelInfoRgPwe
					TruthValue,
				zhoneCpeOnuModelInfoTftpDnld
					TruthValue,
				zhoneCpeOnuSipSupported
					TruthValue,
				zhoneCpeOnuH248Supported
					TruthValue,
				zhoneCpeOnuMgcpSupported
					TruthValue,
				zhoneCpeOnuT1Supported
					TruthValue,
				zhoneCpeOnuE1Supported
					TruthValue,
				zhoneCpeOnuNumberOfPoEPorts
					Unsigned32,
				zhoneCpeOnuModelSpecificInfo
					BITS
			 }

		-- 1.3.6.1.4.1.5504.5.16.1.13.1.1
		zhoneCpeOnuModelInfoIndex OBJECT-TYPE
			SYNTAX Unsigned32 (1..2147483647)
			MAX-ACCESS not-accessible
			STATUS current
			DESCRIPTION
				"This represents the CpeOnuModelInfo Index."
			::= { zhoneCpeOnuModelInfoEntry 1 }

		
		-- 1.3.6.1.4.1.5504.5.16.1.13.1.2
		zhoneCpeOnuModelName OBJECT-TYPE
			SYNTAX ZhoneAdminString
			MAX-ACCESS read-only
			STATUS current
			DESCRIPTION
				"This repesents the Onu Model name."
			::= { zhoneCpeOnuModelInfoEntry 2 }

		
		-- 1.3.6.1.4.1.5504.5.16.1.13.1.3
		zhoneCpeOnuBatteryBackup OBJECT-TYPE
			SYNTAX TruthValue
			MAX-ACCESS read-only
			STATUS current
			DESCRIPTION
				"This represents the Onu battery backup."
			::= { zhoneCpeOnuModelInfoEntry 3 }

		
		-- 1.3.6.1.4.1.5504.5.16.1.13.1.4
		zhoneCpeOnuSipPlarSupported OBJECT-TYPE
			SYNTAX TruthValue
			MAX-ACCESS read-only
			STATUS current
			DESCRIPTION
				"This represents whether SipPlar is supported on this ONU."
			::= { zhoneCpeOnuModelInfoEntry 4 }

		
		-- 1.3.6.1.4.1.5504.5.16.1.13.1.5
		zhoneCpeOnuEthSlotNumber OBJECT-TYPE
			SYNTAX Unsigned32 (0..2147483647)
			MAX-ACCESS read-only
			STATUS current
			DESCRIPTION
				"This represents the Onu ethernet slot number."
			::= { zhoneCpeOnuModelInfoEntry 5 }

		
		-- 1.3.6.1.4.1.5504.5.16.1.13.1.6
		zhoneCpeOnuNumberOfEthPorts OBJECT-TYPE
			SYNTAX Unsigned32 (0..2147483647)
			MAX-ACCESS read-only
			STATUS current
			DESCRIPTION
				"This represents the number of ethernet ports on an ONU."
			::= { zhoneCpeOnuModelInfoEntry 6 }

		
		-- 1.3.6.1.4.1.5504.5.16.1.13.1.7
		zhoneCpeOnuPotsSlotNumber OBJECT-TYPE
			SYNTAX Unsigned32 (0..2147483647)
			MAX-ACCESS read-only
			STATUS current
			DESCRIPTION
				"This represents the Onu Pots Slot Number."
			::= { zhoneCpeOnuModelInfoEntry 7 }

		
		-- 1.3.6.1.4.1.5504.5.16.1.13.1.8
		zhoneCpeOnuNumberOfPotsPorts OBJECT-TYPE
			SYNTAX Unsigned32 (0..2147483647)
			MAX-ACCESS read-only
			STATUS current
			DESCRIPTION
				"This represents the number of Pots ports on an ONU."
			::= { zhoneCpeOnuModelInfoEntry 8 }

		
		-- 1.3.6.1.4.1.5504.5.16.1.13.1.9
		zhoneCpeOnuRfVideoSlotNumber OBJECT-TYPE
			SYNTAX Unsigned32 (0..2147483647)
			MAX-ACCESS read-only
			STATUS current
			DESCRIPTION
				"This represents the Onu RfVideo slot number."
			::= { zhoneCpeOnuModelInfoEntry 9 }

		
		-- 1.3.6.1.4.1.5504.5.16.1.13.1.10
		zhoneCpeOnuNumberOfRfVideoPorts OBJECT-TYPE
			SYNTAX Unsigned32 (0..2147483647)
			MAX-ACCESS read-only
			STATUS current
			DESCRIPTION
				"This represents the number of RfVideo ports."
			::= { zhoneCpeOnuModelInfoEntry 10 }

		
		-- 1.3.6.1.4.1.5504.5.16.1.13.1.11
		zhoneCpeOnuCesSlotNumber OBJECT-TYPE
			SYNTAX Unsigned32 (0..2147483647)
			MAX-ACCESS read-only
			STATUS current
			DESCRIPTION
				"This represents the Onu Ces slot number."
			::= { zhoneCpeOnuModelInfoEntry 11 }

		
		-- 1.3.6.1.4.1.5504.5.16.1.13.1.12
		zhoneCpeOnuNumberOfCesPorts OBJECT-TYPE
			SYNTAX Unsigned32 (0..2147483647)
			MAX-ACCESS read-only
			STATUS current
			DESCRIPTION
				"This represents the number of Ces ports on an ONU."
			::= { zhoneCpeOnuModelInfoEntry 12 }

		
		-- 1.3.6.1.4.1.5504.5.16.1.13.1.13
		zhoneCpeOnuModelInfoRGBridged OBJECT-TYPE
			SYNTAX TruthValue
			MAX-ACCESS read-only
			STATUS current
			DESCRIPTION
				"If TRUE, layer 2 bridging can only be configured via a RG management
				interface such as SNMP, TR-69, CLI or Web UI. Otherwise, VoIP can be
				configured via OMCI as well."
			::= { zhoneCpeOnuModelInfoEntry 13 }

		
		-- 1.3.6.1.4.1.5504.5.16.1.13.1.14
		zhoneCpeOnuNumberOfWlanPorts OBJECT-TYPE
			SYNTAX Unsigned32
			MAX-ACCESS read-only
			STATUS current
			DESCRIPTION
				"This represents the number of Wlan ports on an ONU."
			::= { zhoneCpeOnuModelInfoEntry 14 }

		
		-- 1.3.6.1.4.1.5504.5.16.1.13.1.15
		zhoneCpeOnuModelInfoRg OBJECT-TYPE
			SYNTAX TruthValue
			MAX-ACCESS read-only
			STATUS current
			DESCRIPTION
				"If TRUE, CPE is capable of providing RG (residential gateway)
				services."
			::= { zhoneCpeOnuModelInfoEntry 15 }

		
		-- 1.3.6.1.4.1.5504.5.16.1.13.1.16
		zhoneCpeOnuModelInfoRgVoip OBJECT-TYPE
			SYNTAX TruthValue
			MAX-ACCESS read-only
			STATUS current
			DESCRIPTION
				"If TRUE, VoIP can only be configured via a RG management interface
				such as SNMP, TR-69, CLI or Web UI. Otherwise, VoIP can be
				configured via OMCI as well."
			::= { zhoneCpeOnuModelInfoEntry 16 }

		
		-- 1.3.6.1.4.1.5504.5.16.1.13.1.17
		zhoneCpeOnuModelInfoRgPwe OBJECT-TYPE
			SYNTAX TruthValue
			MAX-ACCESS read-only
			STATUS current
			DESCRIPTION
				"If TRUE, PWE can only be configured via a RG management interface
				such as SNMP, TR-69, CLI or Web UI. Otherwise, PWE can be configured
				via OMCI as well."
			::= { zhoneCpeOnuModelInfoEntry 17 }

		
		-- 1.3.6.1.4.1.5504.5.16.1.13.1.18
		zhoneCpeOnuModelInfoTftpDnld OBJECT-TYPE
			SYNTAX TruthValue
			MAX-ACCESS read-only
			STATUS current
			DESCRIPTION
				"If TRUE, then this model support software image download via
				TFTP. Otherwise, only OMCI downloads are supported."
			::= { zhoneCpeOnuModelInfoEntry 18 }

		
		-- 1.3.6.1.4.1.5504.5.16.1.13.1.19
		zhoneCpeOnuSipSupported OBJECT-TYPE
			SYNTAX TruthValue
			MAX-ACCESS read-only
			STATUS current
			DESCRIPTION
				"This represents whether Sip is supported on this ONU."
			::= { zhoneCpeOnuModelInfoEntry 19 }

		
		-- 1.3.6.1.4.1.5504.5.16.1.13.1.20
		zhoneCpeOnuH248Supported OBJECT-TYPE
			SYNTAX TruthValue
			MAX-ACCESS read-only
			STATUS current
			DESCRIPTION
				"This represents whether H248 is supported on this ONU."
			::= { zhoneCpeOnuModelInfoEntry 20 }

		
		-- 1.3.6.1.4.1.5504.5.16.1.13.1.21
		zhoneCpeOnuMgcpSupported OBJECT-TYPE
			SYNTAX TruthValue
			MAX-ACCESS read-only
			STATUS current
			DESCRIPTION
				"This represents whether MGCP is supported on this ONU."
			::= { zhoneCpeOnuModelInfoEntry 21 }

		
		-- 1.3.6.1.4.1.5504.5.16.1.13.1.22
		zhoneCpeOnuT1Supported OBJECT-TYPE
			SYNTAX TruthValue
			MAX-ACCESS read-only
			STATUS current
			DESCRIPTION
				"This represents whether T1 is supported on this ONU."
			::= { zhoneCpeOnuModelInfoEntry 22 }

		
		-- 1.3.6.1.4.1.5504.5.16.1.13.1.23
		zhoneCpeOnuE1Supported OBJECT-TYPE
			SYNTAX TruthValue
			MAX-ACCESS read-only
			STATUS current
			DESCRIPTION
				"This represents whether E1 is supported on this ONU."
			::= { zhoneCpeOnuModelInfoEntry 23 }

		
		-- 1.3.6.1.4.1.5504.5.16.1.13.1.24
		zhoneCpeOnuNumberOfPoEPorts OBJECT-TYPE
			SYNTAX Unsigned32 (0..2147483647)
			MAX-ACCESS read-only
			STATUS current
			DESCRIPTION
				"This represents the number of Power over Ethernet ports on an ONU."
			::= { zhoneCpeOnuModelInfoEntry 24 }

		
		-- 1.3.6.1.4.1.5504.5.16.1.13.1.25
		zhoneCpeOnuModelSpecificInfo OBJECT-TYPE
			SYNTAX BITS
				{
				ethernet(0),
				wlan(1)
				}
			MAX-ACCESS read-only
			STATUS current
			DESCRIPTION
				"This represents the model specific information for a CPE based on
				interface type.  Each bit represents presence of model specific
				information for a specific interface type."
			::= { zhoneCpeOnuModelInfoEntry 25 }

		
		-- 1.3.6.1.4.1.5504.5.16.1.14
		zhoneCpeConnectionTable OBJECT-TYPE
			SYNTAX SEQUENCE OF ZhoneCpeConnectionEntry
			MAX-ACCESS not-accessible
			STATUS current
			DESCRIPTION
				"This table stores information about the connection
				between a logical or physical interface on the managing 
				device and a port on the CPE."
			::= { zhoneCpeObjectID 14 }

		
		-- 1.3.6.1.4.1.5504.5.16.1.14.1
		zhoneCpeConnectionEntry OBJECT-TYPE
			SYNTAX ZhoneCpeConnectionEntry
			MAX-ACCESS not-accessible
			STATUS current
			DESCRIPTION
				"Row in the CPE Connection table."
			INDEX { zhoneCpePortIfIndex, zhoneCpeTpType, zhoneCpeTpIndex, zhoneCpeVlanId, zhoneCpeSlanId
				 }
			::= { zhoneCpeConnectionTable 1 }

		
		ZhoneCpeConnectionEntry ::=
			SEQUENCE { 
				zhoneCpePortIfIndex
					InterfaceIndex,
				zhoneCpeTpType
					TpType,
				zhoneCpeTpIndex
					Unsigned32,
				zhoneCpeVlanId
					Unsigned32,
				zhoneCpeSlanId
					Unsigned32,
				zhoneCpeConnectionRowStatus
					ZhoneRowStatus,
				zhoneCpeConnectionVlanCos
					Unsigned32,
				zhoneCpeConnectionVlanTpId
					Unsigned32,
				zhoneCpeConnectionSlanCos
					Unsigned32,
				zhoneCpeConnectionSlanTpId
					Unsigned32,
				zhoneCpeConnectionTranslateVlanId
					Unsigned32,
				zhoneCpeConnectionTranslateVlanCos
					Unsigned32,
				zhoneCpeConnectionTranslateVlanTpId
					Unsigned32,
				zhoneCpeConnectionTranslateSlanId
					Unsigned32,
				zhoneCpeConnectionTranslateSlanCos
					Unsigned32,
				zhoneCpeConnectionTranslateSlanTpId
					Unsigned32,
				zhoneCpeConnectionFloodingGport
					Unsigned32,
				zhoneCpeConnectionVideoGport
					Unsigned32,
				zhoneCpeConnectionDscpToCosProfileIndex
					Unsigned32,
				zhoneCpeConnectionRgMode
					INTEGER,
				zhoneCpeConnectionGuidedVlanId
					Unsigned32,
				zhoneCpeConnectionGuidedCos
					Unsigned32,
				zhoneCpeConnectionMacBridgePortInfo
					Unsigned32
			 }

		-- 1.3.6.1.4.1.5504.5.16.1.14.1.1
		zhoneCpePortIfIndex OBJECT-TYPE
			SYNTAX InterfaceIndex
			MAX-ACCESS not-accessible
			STATUS current
			DESCRIPTION
				"ifIndex of the port on which this connection is based.
				For a GPON connection, this is the GEM port ifIndex."
			::= { zhoneCpeConnectionEntry 1 }

		
		-- 1.3.6.1.4.1.5504.5.16.1.14.1.2
		zhoneCpeTpType OBJECT-TYPE
			SYNTAX TpType
			MAX-ACCESS not-accessible
			STATUS current
			DESCRIPTION
				"TpType identifies the type of termination point 
				associated with this MAC bridge port.
				"
			::= { zhoneCpeConnectionEntry 2 }

		
		-- 1.3.6.1.4.1.5504.5.16.1.14.1.3
		zhoneCpeTpIndex OBJECT-TYPE
			SYNTAX Unsigned32 (0..255)
			MAX-ACCESS not-accessible
			STATUS current
			DESCRIPTION
				"TpIndex identifies the Index of termination point
				associated with this MAC bridge port."
			::= { zhoneCpeConnectionEntry 3 }

		
		-- 1.3.6.1.4.1.5504.5.16.1.14.1.4
		zhoneCpeVlanId OBJECT-TYPE
			SYNTAX Unsigned32 (0..4096)
			MAX-ACCESS not-accessible
			STATUS current
			DESCRIPTION
				"The Virtual LAN Id for VLAN Tag Insertion."
			::= { zhoneCpeConnectionEntry 4 }

		
		-- 1.3.6.1.4.1.5504.5.16.1.14.1.5
		zhoneCpeSlanId OBJECT-TYPE
			SYNTAX Unsigned32 (0..4096)
			MAX-ACCESS not-accessible
			STATUS current
			DESCRIPTION
				"The Secure LAN Id for SLAN Tag Insertion."
			::= { zhoneCpeConnectionEntry 5 }

		
		-- 1.3.6.1.4.1.5504.5.16.1.14.1.6
		zhoneCpeConnectionRowStatus OBJECT-TYPE
			SYNTAX ZhoneRowStatus
			MAX-ACCESS read-create
			STATUS current
			DESCRIPTION
				"Used to create, modify or delete an entry in this table."
			::= { zhoneCpeConnectionEntry 6 }

		
-- 
		-- 1.3.6.1.4.1.5504.5.16.1.14.1.7
		zhoneCpeConnectionVlanCos OBJECT-TYPE
			SYNTAX Unsigned32 (0..8)
			MAX-ACCESS read-create
			STATUS current
			DESCRIPTION
				"The Class-Of-Service (COS) value used for VLAN Tag Insertion."
			DEFVAL { 0 }
			::= { zhoneCpeConnectionEntry 7 }

		
-- 
		-- 1.3.6.1.4.1.5504.5.16.1.14.1.8
		zhoneCpeConnectionVlanTpId OBJECT-TYPE
			SYNTAX Unsigned32 (33024 | 34984 | 37120 | 37376)
			MAX-ACCESS read-create
			STATUS current
			DESCRIPTION
				"The value of the tag protocol identifier that is being
				used for QinQ packets. (0x8100 is default.).
				
				Valid values are :
				
				1. 33024 ( 0x8100 )
				2. 34984 ( 0x88A8 )
				3. 37120 ( 0x9100 )
				4. 37376 ( 0x9200 )
				
				"
			DEFVAL { 33024 }
			::= { zhoneCpeConnectionEntry 8 }

		
-- 
		-- 1.3.6.1.4.1.5504.5.16.1.14.1.9
		zhoneCpeConnectionSlanCos OBJECT-TYPE
			SYNTAX Unsigned32 (0..8)
			MAX-ACCESS read-create
			STATUS current
			DESCRIPTION
				"The Class-Of-Service (COS) value used for SLAN Tag Insertion."
			DEFVAL { 0 }
			::= { zhoneCpeConnectionEntry 9 }

		
-- 
		-- 1.3.6.1.4.1.5504.5.16.1.14.1.10
		zhoneCpeConnectionSlanTpId OBJECT-TYPE
			SYNTAX Unsigned32 (33024 | 34984 | 37120 | 37376)
			MAX-ACCESS read-create
			STATUS current
			DESCRIPTION
				"The value of the tag protocol identifier that is being
				used for QinQ packets. (0x8100 is default.).
				
				Valid values are:
				
				1. 33024 ( 0x8100 )
				2. 34984 ( 0x88A8 )
				3. 37120 ( 0x9100 )
				4. 37376 ( 0x9200 )"
			DEFVAL { 33024 }
			::= { zhoneCpeConnectionEntry 10 }

		
		-- 1.3.6.1.4.1.5504.5.16.1.14.1.11
		zhoneCpeConnectionTranslateVlanId OBJECT-TYPE
			SYNTAX Unsigned32 (0..4096)
			MAX-ACCESS read-create
			STATUS current
			DESCRIPTION
				"The Virtual LAN Id for VLAN Tag Insertion."
			DEFVAL { 0 }
			::= { zhoneCpeConnectionEntry 11 }

		
-- 
		-- 1.3.6.1.4.1.5504.5.16.1.14.1.12
		zhoneCpeConnectionTranslateVlanCos OBJECT-TYPE
			SYNTAX Unsigned32 (0..8)
			MAX-ACCESS read-create
			STATUS current
			DESCRIPTION
				"The Class-Of-Service (COS) value used for VLAN Tag Insertion."
			DEFVAL { 0 }
			::= { zhoneCpeConnectionEntry 12 }

		
-- 
		-- 1.3.6.1.4.1.5504.5.16.1.14.1.13
		zhoneCpeConnectionTranslateVlanTpId OBJECT-TYPE
			SYNTAX Unsigned32 (33024 | 34984 | 37120 | 37376)
			MAX-ACCESS read-create
			STATUS current
			DESCRIPTION
				"The value of the tag protocol identifier that is being
				used for QinQ packets. (0x8100 is default.).
				
				Valid values are:
				
				1. 33024 ( 0x8100 )
				2. 34984 ( 0x88A8 )
				3. 37120 ( 0x9100 )
				4. 37376 ( 0x9200 )"
			DEFVAL { 33024 }
			::= { zhoneCpeConnectionEntry 13 }

		
		-- 1.3.6.1.4.1.5504.5.16.1.14.1.14
		zhoneCpeConnectionTranslateSlanId OBJECT-TYPE
			SYNTAX Unsigned32 (0..4096)
			MAX-ACCESS read-create
			STATUS current
			DESCRIPTION
				"The Secure LAN Id for SLAN Tag Insertion."
			DEFVAL { 0 }
			::= { zhoneCpeConnectionEntry 14 }

		
-- 
		-- 1.3.6.1.4.1.5504.5.16.1.14.1.15
		zhoneCpeConnectionTranslateSlanCos OBJECT-TYPE
			SYNTAX Unsigned32 (0..8)
			MAX-ACCESS read-create
			STATUS current
			DESCRIPTION
				"The Class-Of-Service (COS) value used for SLAN Tag Insertion."
			DEFVAL { 0 }
			::= { zhoneCpeConnectionEntry 15 }

		
-- 
		-- 1.3.6.1.4.1.5504.5.16.1.14.1.16
		zhoneCpeConnectionTranslateSlanTpId OBJECT-TYPE
			SYNTAX Unsigned32 (33024 | 34984 | 37120 | 37376)
			MAX-ACCESS read-create
			STATUS current
			DESCRIPTION
				"The value of the tag protocol identifier that is being
				used for QinQ packets. (0x8100 is default.).
				
				Valid values are:
				
				1. 33024 ( 0x8100 )
				2. 34984 ( 0x88A8 )
				3. 37120 ( 0x9100 )
				4. 37376 ( 0x9200 )"
			DEFVAL { 33024 }
			::= { zhoneCpeConnectionEntry 16 }

		
-- 
		-- 1.3.6.1.4.1.5504.5.16.1.14.1.17
		zhoneCpeConnectionFloodingGport OBJECT-TYPE
			SYNTAX Unsigned32 (0..4095)
			MAX-ACCESS read-create
			STATUS current
			DESCRIPTION
				"This is the downstream only GEM port for broadcast 
				unknown MAC address packets."
			DEFVAL { 0 }
			::= { zhoneCpeConnectionEntry 17 }

		
-- 
		-- 1.3.6.1.4.1.5504.5.16.1.14.1.18
		zhoneCpeConnectionVideoGport OBJECT-TYPE
			SYNTAX Unsigned32 (0..4095)
			MAX-ACCESS read-create
			STATUS current
			DESCRIPTION
				"This is the downstream only multicast GEM port for IPTV 
				content streams."
			DEFVAL { 0 }
			::= { zhoneCpeConnectionEntry 18 }

		
		-- 1.3.6.1.4.1.5504.5.16.1.14.1.19
		zhoneCpeConnectionDscpToCosProfileIndex OBJECT-TYPE
			SYNTAX Unsigned32 (0..2147483647)
			MAX-ACCESS read-create
			STATUS current
			DESCRIPTION
				"Index of dscp-to-cos profile."
			DEFVAL { 0 }
			::= { zhoneCpeConnectionEntry 19 }

		
		-- 1.3.6.1.4.1.5504.5.16.1.14.1.20
		zhoneCpeConnectionRgMode OBJECT-TYPE
			SYNTAX INTEGER
				{
				routed(1),
				brouted(2),
				rpppoe(3),
				bpppoe(4),
				bridged(5),
				notApplicable(6)
				}
			MAX-ACCESS read-create
			STATUS current
			DESCRIPTION
				"Use to specify the RG service for a CPE.
								
				When creating or deleting a CPE connection, if the CPE does not
				support RG service then this object should not be provided. If a CPE
				does support RG service then this object must be provided.
								
				When reading this object, the value returned will be 'notApplicable'.
							
				This data is not preserved in the CPE connection profile."
			::= { zhoneCpeConnectionEntry 20 }

		
		-- 1.3.6.1.4.1.5504.5.16.1.14.1.21
		zhoneCpeConnectionGuidedVlanId OBJECT-TYPE
			SYNTAX Unsigned32 (0..4096)
			MAX-ACCESS read-create
			STATUS current
			DESCRIPTION
				"The Guided VLAN Id for RG Services.   A zero value means
				a guided vlan does not exist.
				
				If a guided vlan is used then uni-vlan and uni-slan values
				must be zero.
				"
			DEFVAL { 0 }
			::= { zhoneCpeConnectionEntry 21 }

		
		-- 1.3.6.1.4.1.5504.5.16.1.14.1.22
		zhoneCpeConnectionGuidedCos OBJECT-TYPE
			SYNTAX Unsigned32 (0..8)
			MAX-ACCESS read-create
			STATUS current
			DESCRIPTION
				"The Guided Class-Of-Service (COS) value used for RG SERVICES.
				
				A zero means a guided cos does not exist."
			DEFVAL { 0 }
			::= { zhoneCpeConnectionEntry 22 }

		
		-- 1.3.6.1.4.1.5504.5.16.1.14.1.23
		zhoneCpeConnectionMacBridgePortInfo OBJECT-TYPE
			SYNTAX Unsigned32
			MAX-ACCESS read-only
			STATUS current
			DESCRIPTION
				"MAC bridge port ID/num for ONUs.
				Saved here so we don't have to dynamically generate it and reconfigure the ONU on each system reboot."
			DEFVAL { 0 }
			::= { zhoneCpeConnectionEntry 23 }

		
		-- 1.3.6.1.4.1.5504.5.16.1.15
		zhoneCpeRfSubscriberTable OBJECT-TYPE
			SYNTAX SEQUENCE OF ZhoneCpeRfSubscriberEntry
			MAX-ACCESS not-accessible
			STATUS current
			DESCRIPTION
				"Cpe Rf Subscriber table."
			::= { zhoneCpeObjectID 15 }

		
		-- 1.3.6.1.4.1.5504.5.16.1.15.1
		zhoneCpeRfSubscriberEntry OBJECT-TYPE
			SYNTAX ZhoneCpeRfSubscriberEntry
			MAX-ACCESS not-accessible
			STATUS current
			DESCRIPTION
				"Row in the Cpe Rf Subscriber table."
			INDEX { zhoneCpeIfIndex, zhoneCpeRfSubscriberPortNumber }
			::= { zhoneCpeRfSubscriberTable 1 }

		
		ZhoneCpeRfSubscriberEntry ::=
			SEQUENCE { 
				zhoneCpeRfSubscriberPortNumber
					Unsigned32,
				zhoneCpeRfSubscriberRowStatus
					ZhoneRowStatus,
				zhoneCpeRfSubscriberAdminState
					ZhoneAdminState,
				zhoneCpeRfSubscriberLineStatusAlarm
					ZhoneEnabledFlag,
				zhoneCpeRfSubscriberAlarmSeverity
					ZhoneAlarmSeverity,
				zhoneCpeRfSubscriberDescription
					OCTET STRING
			 }

		-- 1.3.6.1.4.1.5504.5.16.1.15.1.1
		zhoneCpeRfSubscriberPortNumber OBJECT-TYPE
			SYNTAX Unsigned32 (1..2147483647)
			MAX-ACCESS not-accessible
			STATUS current
			DESCRIPTION
				"This represents the CPE Rf Subscriber port number."
			::= { zhoneCpeRfSubscriberEntry 1 }

		
		-- 1.3.6.1.4.1.5504.5.16.1.15.1.2
		zhoneCpeRfSubscriberRowStatus OBJECT-TYPE
			SYNTAX ZhoneRowStatus
			MAX-ACCESS read-create
			STATUS current
			DESCRIPTION
				"Used to create, modify or delete an entry in this table."
			DEFVAL { active }
			::= { zhoneCpeRfSubscriberEntry 2 }

		
		-- 1.3.6.1.4.1.5504.5.16.1.15.1.3
		zhoneCpeRfSubscriberAdminState OBJECT-TYPE
			SYNTAX ZhoneAdminState
			MAX-ACCESS read-create
			STATUS current
			DESCRIPTION
				"This attribute activates or deactivates the functions performed by
				the RF port for this subscriber or put the port in test mode."
			DEFVAL { 1 }
			::= { zhoneCpeRfSubscriberEntry 3 }

		
		-- 1.3.6.1.4.1.5504.5.16.1.15.1.4
		zhoneCpeRfSubscriberLineStatusAlarm OBJECT-TYPE
			SYNTAX ZhoneEnabledFlag
			MAX-ACCESS read-create
			STATUS current
			DESCRIPTION
				"This field is for enabling/disabling alarm reporting from this CPE UNI."
			DEFVAL { disabled }
			::= { zhoneCpeRfSubscriberEntry 4 }

		
		-- 1.3.6.1.4.1.5504.5.16.1.15.1.5
		zhoneCpeRfSubscriberAlarmSeverity OBJECT-TYPE
			SYNTAX ZhoneAlarmSeverity
			MAX-ACCESS read-create
			STATUS current
			DESCRIPTION
				"This field is for specifying the severity level of all the alarms from this CPE UNI."
			DEFVAL { major }
			::= { zhoneCpeRfSubscriberEntry 5 }

		
		-- 1.3.6.1.4.1.5504.5.16.1.15.1.6
		zhoneCpeRfSubscriberDescription OBJECT-TYPE
			SYNTAX OCTET STRING (SIZE (0..32))
			MAX-ACCESS read-create
			STATUS current
			DESCRIPTION
				"Describes the CPE RF subscriber profile instance"
			DEFVAL { "" }
			::= { zhoneCpeRfSubscriberEntry 6 }

		
		-- 1.3.6.1.4.1.5504.5.16.1.16
		zhoneCpeTrafficManagement OBJECT-IDENTITY
			STATUS current
			DESCRIPTION 
				"Cpe Traffic Management objects."
			::= { zhoneCpeObjectID 16 }

		
		-- 1.3.6.1.4.1.5504.5.16.1.16.1
		zhoneCpeTrafficManagementIndexNext OBJECT-TYPE
			SYNTAX Integer32
			MAX-ACCESS read-only
			STATUS current
			DESCRIPTION
				"This object contains an appropriate value to be used for the
				zhoneCpeTrafficManagementIndex when creating entries in the
				zhoneCpeTrafficManagementTable. The value 0 indicates that
				no unassigned entries are available. To obtain the zhoneCpeTrafficManagementIndex
				value for a new entry, the manager issues a management protocol retrieval
				operation to obtain the current value of this object.  After each retrieval,
				the agent should modify the value to the next unassigned index.
				
				After a manager retrieves a value the agent will determine through its local
				policy when this index value will be made available for reuse."
			::= { zhoneCpeTrafficManagement 1 }

		
		-- 1.3.6.1.4.1.5504.5.16.1.16.2
		zhoneCpeTrafficManagementTable OBJECT-TYPE
			SYNTAX SEQUENCE OF ZhoneCpeTrafficManagementEntry
			MAX-ACCESS not-accessible
			STATUS current
			DESCRIPTION
				"Cpe Traffic Management table."
			::= { zhoneCpeTrafficManagement 2 }

		
		-- 1.3.6.1.4.1.5504.5.16.1.16.2.1
		zhoneCpeTrafficManagementEntry OBJECT-TYPE
			SYNTAX ZhoneCpeTrafficManagementEntry
			MAX-ACCESS not-accessible
			STATUS current
			DESCRIPTION
				"Row in the Cpe Traffic Management table."
			INDEX { zhoneCpeTrafficManagementIndex }
			::= { zhoneCpeTrafficManagementTable 1 }

		
		ZhoneCpeTrafficManagementEntry ::=
			SEQUENCE { 
				zhoneCpeTrafficManagementIndex
					Unsigned32,
				zhoneCpeTrafficManagementRowStatus
					ZhoneRowStatus,
				zhoneCpeTrafficManagementProfileName
					ZhoneAdminString,
				zhoneCpeTrafficManagementUpstreamSIR
					Unsigned32,
				zhoneCpeTrafficManagementUpstreamPIR
					Unsigned32,
				zhoneCpeTrafficManagementUpstreamPriority
					Unsigned32,
				zhoneCpeTrafficManagementUpstreamWeight
					Unsigned32,
				zhoneCpeTrafficManagementDownstreamSIR
					Unsigned32,
				zhoneCpeTrafficManagementDownstreamPIR
					Unsigned32,
				zhoneCpeTrafficManagementDownstreamPriority
					Unsigned32,
				zhoneCpeTrafficManagementDownstreamWeight
					Unsigned32,
				zhoneCpeTrafficManagementPeakBurstSize
					Unsigned32
			 }

		-- 1.3.6.1.4.1.5504.5.16.1.16.2.1.1
		zhoneCpeTrafficManagementIndex OBJECT-TYPE
			SYNTAX Unsigned32 (1..2147483647)
			MAX-ACCESS not-accessible
			STATUS current
			DESCRIPTION
				"This represents the CPE Traffic Management Index, values are from the range
				1 to n."
			::= { zhoneCpeTrafficManagementEntry 1 }

		
		-- 1.3.6.1.4.1.5504.5.16.1.16.2.1.2
		zhoneCpeTrafficManagementRowStatus OBJECT-TYPE
			SYNTAX ZhoneRowStatus
			MAX-ACCESS read-create
			STATUS current
			DESCRIPTION
				"Used to create, modify or delete an entry in this table."
			DEFVAL { active }
			::= { zhoneCpeTrafficManagementEntry 2 }

		
		-- 1.3.6.1.4.1.5504.5.16.1.16.2.1.3
		zhoneCpeTrafficManagementProfileName OBJECT-TYPE
			SYNTAX ZhoneAdminString
			MAX-ACCESS read-create
			STATUS current
			DESCRIPTION
				"CPE Traffic Management profile for the dynamic bridging. This field is only
				writable upon creation and must be unique within its table."
			::= { zhoneCpeTrafficManagementEntry 3 }

		
		-- 1.3.6.1.4.1.5504.5.16.1.16.2.1.4
		zhoneCpeTrafficManagementUpstreamSIR OBJECT-TYPE
			SYNTAX Unsigned32 (0..1310720)
			UNITS "kbps"
			MAX-ACCESS read-create
			STATUS current
			DESCRIPTION
				"This attribute specifies the upstream sustained information rate.
				Unit is kbps."
			DEFVAL { 0 }
			::= { zhoneCpeTrafficManagementEntry 4 }

		
		-- 1.3.6.1.4.1.5504.5.16.1.16.2.1.5
		zhoneCpeTrafficManagementUpstreamPIR OBJECT-TYPE
			SYNTAX Unsigned32 (0..1310720)
			UNITS "kbps"
			MAX-ACCESS read-create
			STATUS current
			DESCRIPTION
				"This attribute specifies the upstream peak information rate. Unit is kbps."
			DEFVAL { 0 }
			::= { zhoneCpeTrafficManagementEntry 5 }

		
		-- 1.3.6.1.4.1.5504.5.16.1.16.2.1.6
		zhoneCpeTrafficManagementUpstreamPriority OBJECT-TYPE
			SYNTAX Unsigned32 (0..65535)
			MAX-ACCESS read-create
			STATUS current
			DESCRIPTION
				"Upstream Priority, currently the only used value range is 0-7."
			DEFVAL { 0 }
			::= { zhoneCpeTrafficManagementEntry 6 }

		
		-- 1.3.6.1.4.1.5504.5.16.1.16.2.1.7
		zhoneCpeTrafficManagementUpstreamWeight OBJECT-TYPE
			SYNTAX Unsigned32 (0..255)
			MAX-ACCESS read-create
			STATUS current
			DESCRIPTION
				"Upstream Weight for weighted round robin scheduling, variable size
				is 1 byte, default 0."
			DEFVAL { 0 }
			::= { zhoneCpeTrafficManagementEntry 7 }

		
		-- 1.3.6.1.4.1.5504.5.16.1.16.2.1.8
		zhoneCpeTrafficManagementDownstreamSIR OBJECT-TYPE
			SYNTAX Unsigned32 (0..1310720)
			UNITS "kbps"
			MAX-ACCESS read-create
			STATUS current
			DESCRIPTION
				"This attribute specifies the downstream sustained information rate.
				Unit is kbps."
			DEFVAL { 0 }
			::= { zhoneCpeTrafficManagementEntry 8 }

		
		-- 1.3.6.1.4.1.5504.5.16.1.16.2.1.9
		zhoneCpeTrafficManagementDownstreamPIR OBJECT-TYPE
			SYNTAX Unsigned32 (0..1310720)
			UNITS "kbps"
			MAX-ACCESS read-create
			STATUS current
			DESCRIPTION
				"This attribute specifies the downstream peak information rate.
				Unit is kbps."
			DEFVAL { 0 }
			::= { zhoneCpeTrafficManagementEntry 9 }

		
		-- 1.3.6.1.4.1.5504.5.16.1.16.2.1.10
		zhoneCpeTrafficManagementDownstreamPriority OBJECT-TYPE
			SYNTAX Unsigned32 (0..65535)
			MAX-ACCESS read-create
			STATUS current
			DESCRIPTION
				"Downstream Priority, currently the only used value range is 0-7."
			DEFVAL { 0 }
			::= { zhoneCpeTrafficManagementEntry 10 }

		
		-- 1.3.6.1.4.1.5504.5.16.1.16.2.1.11
		zhoneCpeTrafficManagementDownstreamWeight OBJECT-TYPE
			SYNTAX Unsigned32 (0..255)
			MAX-ACCESS read-create
			STATUS current
			DESCRIPTION
				"Downstream Weight for weighted round robin scheduling, variable size
				is 1 byte, default 0.
				"
			DEFVAL { 0 }
			::= { zhoneCpeTrafficManagementEntry 11 }

		
		-- 1.3.6.1.4.1.5504.5.16.1.16.2.1.12
		zhoneCpeTrafficManagementPeakBurstSize OBJECT-TYPE
			SYNTAX Unsigned32 (0..512000)
			UNITS "bytes"
			MAX-ACCESS read-write
			STATUS current
			DESCRIPTION
				"Peak burst/block size, in bytes. Default value 0 means use CPE system default."
			DEFVAL { 0 }
			::= { zhoneCpeTrafficManagementEntry 12 }

		
		-- 1.3.6.1.4.1.5504.5.16.1.17
		zhoneCpeSystemTable OBJECT-TYPE
			SYNTAX SEQUENCE OF ZhoneCpeSystemEntry
			MAX-ACCESS not-accessible
			STATUS current
			DESCRIPTION
				"Cpe System table."
			::= { zhoneCpeObjectID 17 }

		
		-- 1.3.6.1.4.1.5504.5.16.1.17.1
		zhoneCpeSystemEntry OBJECT-TYPE
			SYNTAX ZhoneCpeSystemEntry
			MAX-ACCESS not-accessible
			STATUS current
			DESCRIPTION
				"Row in the Cpe System table."
			INDEX { zhoneCpeIfIndex }
			::= { zhoneCpeSystemTable 1 }

		
		ZhoneCpeSystemEntry ::=
			SEQUENCE { 
				zhoneCpeSystemRowStatus
					ZhoneRowStatus,
				zhoneCpeSystemCommonProfileIndex
					Unsigned32,
				zhoneCpeSystemMgcpClientName
					OCTET STRING,
				zhoneCpeSystemRadiusNasIdentifier
					OCTET STRING,
				zhoneCpeSystemTr69ServerConnReqUsername
					OCTET STRING,
				zhoneCpeSystemTr69ServerConnReqPassword
					OCTET STRING
			 }

		-- 1.3.6.1.4.1.5504.5.16.1.17.1.1
		zhoneCpeSystemRowStatus OBJECT-TYPE
			SYNTAX ZhoneRowStatus
			MAX-ACCESS read-create
			STATUS current
			DESCRIPTION
				"Used to create, modify or delete an entry in this table."
			DEFVAL { active }
			::= { zhoneCpeSystemEntry 1 }

		
		-- 1.3.6.1.4.1.5504.5.16.1.17.1.2
		zhoneCpeSystemCommonProfileIndex OBJECT-TYPE
			SYNTAX Unsigned32 (0..2147483647)
			MAX-ACCESS read-create
			STATUS current
			DESCRIPTION
				"This object points to the associated System Common profile."
			DEFVAL { 0 }
			::= { zhoneCpeSystemEntry 2 }

		
		-- 1.3.6.1.4.1.5504.5.16.1.17.1.3
		zhoneCpeSystemMgcpClientName OBJECT-TYPE
			SYNTAX OCTET STRING (SIZE (1..64))
			MAX-ACCESS read-create
			STATUS current
			DESCRIPTION
				"User string used in accessing the call agent. This is a unique value.
				This is not a mandatory field, users can leave it empty as well."
			::= { zhoneCpeSystemEntry 3 }

		
		-- 1.3.6.1.4.1.5504.5.16.1.17.1.4
		zhoneCpeSystemRadiusNasIdentifier OBJECT-TYPE
			SYNTAX OCTET STRING (SIZE (1..255))
			MAX-ACCESS read-create
			STATUS current
			DESCRIPTION
				"The NAS identifier used by the CPE for
				RADIUS access requests"
			::= { zhoneCpeSystemEntry 4 }

		
		-- 1.3.6.1.4.1.5504.5.16.1.17.1.5
		zhoneCpeSystemTr69ServerConnReqUsername OBJECT-TYPE
			SYNTAX OCTET STRING (SIZE (0..256))
			MAX-ACCESS read-create
			STATUS current
			DESCRIPTION
				"CPE Username used to authenticate an ACS making a
				Connection Request to the CPE."
			DEFVAL { "" }
			::= { zhoneCpeSystemEntry 5 }

		
		-- 1.3.6.1.4.1.5504.5.16.1.17.1.6
		zhoneCpeSystemTr69ServerConnReqPassword OBJECT-TYPE
			SYNTAX OCTET STRING (SIZE (0..256))
			MAX-ACCESS read-create
			STATUS current
			DESCRIPTION
				"CPE Password used to authenticate an ACS making a
				Connection Request to the CPE. When read by an ACS
				this parameter returns an empty string, regardless
				of the actual value"
			DEFVAL { "" }
			::= { zhoneCpeSystemEntry 6 }

		
		-- 1.3.6.1.4.1.5504.5.16.1.18
		zhoneCpeSystemCommon OBJECT-IDENTITY
			STATUS current
			DESCRIPTION 
				"Cpe System Common objects."
			::= { zhoneCpeObjectID 18 }

		
		-- 1.3.6.1.4.1.5504.5.16.1.18.1
		zhoneCpeSystemCommonIndexNext OBJECT-TYPE
			SYNTAX Unsigned32
			MAX-ACCESS read-only
			STATUS current
			DESCRIPTION
				"This object contains an appropriate value to be used for the
				zhoneCpeSystemCommonIndex when creating entries in the zhoneCpeSystemCommonTable.
				The value 0 indicates that no unassigned entries are available. To obtain the
				zhoneCpeSystemCommonIndex value for a new entry, the manager issues a management
				protocol retrieval operation to obtain the current value of this object.  After each
				retrieval, the agent should modify the value to the next unassigned index.
				
				After a manager retrieves a value the agent will determine through its local
				policy when this index value will be made available for reuse."
			::= { zhoneCpeSystemCommon 1 }

		
		-- 1.3.6.1.4.1.5504.5.16.1.18.2
		zhoneCpeSystemCommonTable OBJECT-TYPE
			SYNTAX SEQUENCE OF ZhoneCpeSystemCommonEntry
			MAX-ACCESS not-accessible
			STATUS current
			DESCRIPTION
				"Cpe System Common table."
			::= { zhoneCpeSystemCommon 2 }

		
		-- 1.3.6.1.4.1.5504.5.16.1.18.2.1
		zhoneCpeSystemCommonEntry OBJECT-TYPE
			SYNTAX ZhoneCpeSystemCommonEntry
			MAX-ACCESS not-accessible
			STATUS current
			DESCRIPTION
				"Row in the Cpe System Common table."
			INDEX { zhoneCpeSystemCommonIndex }
			::= { zhoneCpeSystemCommonTable 1 }

		
		ZhoneCpeSystemCommonEntry ::=
			SEQUENCE { 
				zhoneCpeSystemCommonIndex
					Unsigned32,
				zhoneCpeSystemCommonRowStatus
					ZhoneRowStatus,
				zhoneCpeSystemCommonProfileName
					ZhoneAdminString,
				zhoneCpeSystemCommonFirewall
					ZhoneEnabledFlag,
				zhoneCpeSystemCommonSyncCookieProtection
					ZhoneEnabledFlag,
				zhoneCpeSystemCommonCrossVlanRouting
					ZhoneEnabledFlag,
				zhoneCpeStaticRouteListProfileIndex
					Unsigned32,
				zhoneCpeDnsHostListProfile
					Unsigned32,
				zhoneCpeSystemCommonTr69Inform
					ZhoneEnabledFlag,
				zhoneCpeSystemCommonInformInterval
					Unsigned32,
				zhoneCpeSystemCommonAcsUrl
					OCTET STRING,
				zhoneCpeSystemCommonAcsUsername
					OCTET STRING,
				zhoneCpeSystemCommonAcsPassword
					OCTET STRING,
				zhoneCpeSystemCommonAdminPassword
					OCTET STRING,
				zhoneCpeSystemCommonSupportPassword
					OCTET STRING,
				zhoneCpeSystemCommonUserPassword
					OCTET STRING,
				zhoneCpeSystemCommonPowerSupply
					Unsigned32,
				zhoneCpeSystemCommonPowerShutdownDelay
					Unsigned32,
				zhoneCpeSystemCommonPowerRestoreDelay
					Unsigned32,
				zhoneCpeSystemCommonLanServiceMode
					INTEGER,
				zhoneCpeSystemCommonStagTpid
					INTEGER,
				zhoneCpeSystemCommonBridgeLoopDetect
					ZhoneEnabledFlag,
				zhoneCpeSystemCommonBlockUpstreamDhcpOffer
					ZhoneEnabledFlag,
				zhoneCpeSystemCommonBlockDownstreamDnsQuery
					ZhoneEnabledFlag,
				zhoneCpeSystemCommonCrossVlanMulticast
					ZhoneEnabledFlag,
				zhoneCpeSystemCommonPrioritizationMethod
					INTEGER,
				zhoneCpeSystemCommonSchedulingMethod
					INTEGER,
				zhoneCpeSystemCommonAuthServerPrimaryAddr
					IpAddress,
				zhoneCpeSystemCommonAuthServerPrimaryPortNum
					Integer32,
				zhoneCpeSystemCommonAuthPrimarySharedSecret
					SnmpAdminString,
				zhoneCpeSystemCommonAuthServerSecondaryAddr
					IpAddress,
				zhoneCpeSystemCommonAuthServerSecondaryPortNum
					Integer32,
				zhoneCpeSystemCommonAuthSecondarySharedSecret
					SnmpAdminString,
				zhoneCpeSystemCommonAccServerPrimaryAddr
					IpAddress,
				zhoneCpeSystemCommonAccServerPrimaryPortNum
					Integer32,
				zhoneCpeSystemCommonAccPrimarySharedSecret
					SnmpAdminString,
				zhoneCpeSystemCommonAccServerSecondaryAddr
					IpAddress,
				zhoneCpeSystemCommonAccServerSecondaryPortNum
					Integer32,
				zhoneCpeSystemCommonAccSecondarySharedSecret
					SnmpAdminString,
				zhoneCpeSystemCommonMaxSupplicantsPerVLAN
					Unsigned32,
				zhoneCpeSystemCommonGuestVlan
					Unsigned32,
				zhoneCpeSystemCommonGroupId1Name
					OCTET STRING,
				zhoneCpeSystemCommonGroupId1Vlan
					Unsigned32,
				zhoneCpeSystemCommonGroupId2Name
					OCTET STRING,
				zhoneCpeSystemCommonGroupId2Vlan
					Unsigned32,
				zhoneCpeSystemCommonGroupId3Name
					OCTET STRING,
				zhoneCpeSystemCommonGroupId3Vlan
					Unsigned32,
				zhoneCpeSystemCommonReAuthEnabled
					ZhoneEnabledFlag,
				zhoneCpeSystemCommonReAuthPeriod
					Unsigned32,
				zhoneCpeSystemCommonAuthQuietPeriod
					Unsigned32,
				zhoneCpeSystemCommonAuthServerTimeout
					Unsigned32,
				zhoneCpeSystemCommonAuthKeyTxEnabled
					ZhoneEnabledFlag,
				zhoneCpeSystemCommonTr69CfgConnReqAuth
					ZhoneEnabledFlag
			 }

		-- 1.3.6.1.4.1.5504.5.16.1.18.2.1.1
		zhoneCpeSystemCommonIndex OBJECT-TYPE
			SYNTAX Unsigned32 (1..2147483647)
			MAX-ACCESS not-accessible
			STATUS current
			DESCRIPTION
				"This represents the CPE System Common index value."
			::= { zhoneCpeSystemCommonEntry 1 }

		
		-- 1.3.6.1.4.1.5504.5.16.1.18.2.1.2
		zhoneCpeSystemCommonRowStatus OBJECT-TYPE
			SYNTAX ZhoneRowStatus
			MAX-ACCESS read-create
			STATUS current
			DESCRIPTION
				"Used to create, modify or delete an entry in this table."
			DEFVAL { active }
			::= { zhoneCpeSystemCommonEntry 2 }

		
		-- 1.3.6.1.4.1.5504.5.16.1.18.2.1.3
		zhoneCpeSystemCommonProfileName OBJECT-TYPE
			SYNTAX ZhoneAdminString
			MAX-ACCESS read-create
			STATUS current
			DESCRIPTION
				"CPE System Common profile. This field is only writable upon creation and must be
				unique within its table."
			::= { zhoneCpeSystemCommonEntry 3 }

		
		-- 1.3.6.1.4.1.5504.5.16.1.18.2.1.4
		zhoneCpeSystemCommonFirewall OBJECT-TYPE
			SYNTAX ZhoneEnabledFlag
			MAX-ACCESS read-create
			STATUS current
			DESCRIPTION
				"Enable/disable firewall. Enabling firewall can protect the CPE from unwanted
				instruction. When firewall is enabled, incoming connections can be selectively
				allowed through firewall access and port forwarding settings."
			DEFVAL { enabled }
			::= { zhoneCpeSystemCommonEntry 4 }

		
		-- 1.3.6.1.4.1.5504.5.16.1.18.2.1.5
		zhoneCpeSystemCommonSyncCookieProtection OBJECT-TYPE
			SYNTAX ZhoneEnabledFlag
			MAX-ACCESS read-create
			STATUS current
			DESCRIPTION
				"Protects against malicious attackers attempting to exploit TCP handshaking."
			DEFVAL { enabled }
			::= { zhoneCpeSystemCommonEntry 5 }

		
		-- 1.3.6.1.4.1.5504.5.16.1.18.2.1.6
		zhoneCpeSystemCommonCrossVlanRouting OBJECT-TYPE
			SYNTAX ZhoneEnabledFlag
			MAX-ACCESS read-create
			STATUS current
			DESCRIPTION
				"If enabled is selected, routing between VLANs is allowed.
				
				Enabled
				
				Route table lookups ignore the VLAN ID of the ingress and egress ports. If there is
				a match, the packet is routed out the interface specified in the Route table,
				regardless of which VLAN it is a member of. Cross VLAN Routing enabled is the
				default behavior.
				
				Disabled
				
				Packets will be forwarded to the configured Default Route for the VLAN that they
				arrived on, unless there is a Route Table match within that same VLAN. Routing of
				packets across VLANs is prevented, providing traffic isolation.
				
				"
			DEFVAL { disabled }
			::= { zhoneCpeSystemCommonEntry 6 }

		
		-- 1.3.6.1.4.1.5504.5.16.1.18.2.1.7
		zhoneCpeStaticRouteListProfileIndex OBJECT-TYPE
			SYNTAX Unsigned32 (0..2147483647)
			MAX-ACCESS read-create
			STATUS current
			DESCRIPTION
				"Address of the static-route-list profile associated with this CPE."
			DEFVAL { 0 }
			::= { zhoneCpeSystemCommonEntry 7 }

		
		-- 1.3.6.1.4.1.5504.5.16.1.18.2.1.8
		zhoneCpeDnsHostListProfile OBJECT-TYPE
			SYNTAX Unsigned32
			MAX-ACCESS read-create
			STATUS current
			DESCRIPTION
				"Index of the dns-host profile associated with this entry, or
				0 if none."
			DEFVAL { 0 }
			::= { zhoneCpeSystemCommonEntry 8 }

		
		-- 1.3.6.1.4.1.5504.5.16.1.18.2.1.9
		zhoneCpeSystemCommonTr69Inform OBJECT-TYPE
			SYNTAX ZhoneEnabledFlag
			MAX-ACCESS read-create
			STATUS current
			DESCRIPTION
				"Enable or Disable the generation of Inform messages to the ACS
				(Auto Configuration Server)."
			DEFVAL { enabled }
			::= { zhoneCpeSystemCommonEntry 9 }

		
		-- 1.3.6.1.4.1.5504.5.16.1.18.2.1.10
		zhoneCpeSystemCommonInformInterval OBJECT-TYPE
			SYNTAX Unsigned32
			UNITS "seconds"
			MAX-ACCESS read-create
			STATUS current
			DESCRIPTION
				"Periodic interval (in seconds) at which Inform messages will be generated."
			::= { zhoneCpeSystemCommonEntry 10 }

		
		-- 1.3.6.1.4.1.5504.5.16.1.18.2.1.11
		zhoneCpeSystemCommonAcsUrl OBJECT-TYPE
			SYNTAX OCTET STRING (SIZE (0..256))
			MAX-ACCESS read-create
			STATUS current
			DESCRIPTION
				"URL for the CPE to connect to the ACS
				"
			::= { zhoneCpeSystemCommonEntry 11 }

		
		-- 1.3.6.1.4.1.5504.5.16.1.18.2.1.12
		zhoneCpeSystemCommonAcsUsername OBJECT-TYPE
			SYNTAX OCTET STRING (SIZE (0..64))
			MAX-ACCESS read-create
			STATUS current
			DESCRIPTION
				"User name required for access to the ACS"
			DEFVAL { "" }
			::= { zhoneCpeSystemCommonEntry 12 }

		
		-- 1.3.6.1.4.1.5504.5.16.1.18.2.1.13
		zhoneCpeSystemCommonAcsPassword OBJECT-TYPE
			SYNTAX OCTET STRING (SIZE (0..64))
			MAX-ACCESS read-create
			STATUS current
			DESCRIPTION
				"User password required for access to the ACS."
			DEFVAL { "" }
			::= { zhoneCpeSystemCommonEntry 13 }

		
		-- 1.3.6.1.4.1.5504.5.16.1.18.2.1.14
		zhoneCpeSystemCommonAdminPassword OBJECT-TYPE
			SYNTAX OCTET STRING (SIZE (0..16))
			MAX-ACCESS read-create
			STATUS current
			DESCRIPTION
				"Log-in password for user account admin."
			::= { zhoneCpeSystemCommonEntry 14 }

		
		-- 1.3.6.1.4.1.5504.5.16.1.18.2.1.15
		zhoneCpeSystemCommonSupportPassword OBJECT-TYPE
			SYNTAX OCTET STRING (SIZE (0..16))
			MAX-ACCESS read-create
			STATUS current
			DESCRIPTION
				"Log-in password for user account support."
			::= { zhoneCpeSystemCommonEntry 15 }

		
		-- 1.3.6.1.4.1.5504.5.16.1.18.2.1.16
		zhoneCpeSystemCommonUserPassword OBJECT-TYPE
			SYNTAX OCTET STRING (SIZE (0..16))
			MAX-ACCESS read-create
			STATUS current
			DESCRIPTION
				"Log-in password for user account."
			::= { zhoneCpeSystemCommonEntry 16 }

		
		-- 1.3.6.1.4.1.5504.5.16.1.18.2.1.17
		zhoneCpeSystemCommonPowerSupply OBJECT-TYPE
			SYNTAX Unsigned32 (0..2147483647)
			MAX-ACCESS read-create
			STATUS current
			DESCRIPTION
				"The total watts the power supply plugged into the device can provide. Default value 0
				means not specified."
			DEFVAL { 0 }
			::= { zhoneCpeSystemCommonEntry 17 }

		
		-- 1.3.6.1.4.1.5504.5.16.1.18.2.1.18
		zhoneCpeSystemCommonPowerShutdownDelay OBJECT-TYPE
			SYNTAX Unsigned32 (0..60)
			MAX-ACCESS read-create
			STATUS current
			DESCRIPTION
				"Power shedding control. Shutdown delay in minutes. When the unit detects that it
				is running on battery power, it has the option to shut down all support but the voice
				over IP telephone service. Default value 0 means not specified."
			DEFVAL { 0 }
			::= { zhoneCpeSystemCommonEntry 18 }

		
		-- 1.3.6.1.4.1.5504.5.16.1.18.2.1.19
		zhoneCpeSystemCommonPowerRestoreDelay OBJECT-TYPE
			SYNTAX Unsigned32 (0..10)
			MAX-ACCESS read-create
			STATUS current
			DESCRIPTION
				"Power shedding control. Restore delay in minutes. When the unit detects that it is running
				on battery power, it has the option to shut down all support but the voice over IP
				telephone service. Default value 0 means not specified."
			DEFVAL { 0 }
			::= { zhoneCpeSystemCommonEntry 19 }

		
		-- 1.3.6.1.4.1.5504.5.16.1.18.2.1.20
		zhoneCpeSystemCommonLanServiceMode OBJECT-TYPE
			SYNTAX INTEGER
				{
				stag(1),
				normal(2)
				}
			MAX-ACCESS read-create
			STATUS current
			DESCRIPTION
				"LAN service Mode. Enumuration of:
				stag    - In stag mode, Service Provider tag implements transparent LAN service (TLS) 
				          to tunnel the customer traffic over a service provider network.
				normal  - In normal mode, CPE device operates according to the IEEE 
				          802.1Q or 802.1D specifications."
			DEFVAL { normal }
			::= { zhoneCpeSystemCommonEntry 20 }

		
		-- 1.3.6.1.4.1.5504.5.16.1.18.2.1.21
		zhoneCpeSystemCommonStagTpid OBJECT-TYPE
			SYNTAX INTEGER
				{
				tpid8100(1),
				tpid88a8(2),
				tpid9100(3),
				tpid9200(4),
				tpid9300(5)
				}
			MAX-ACCESS read-create
			STATUS current
			DESCRIPTION
				"This specifies the TPID (Tag Protocol ID) of the S-Tag. It is only 
				used when the device's VlanMode is set to S-Tag."
			DEFVAL { tpid8100 }
			::= { zhoneCpeSystemCommonEntry 21 }

		
		-- 1.3.6.1.4.1.5504.5.16.1.18.2.1.22
		zhoneCpeSystemCommonBridgeLoopDetect OBJECT-TYPE
			SYNTAX ZhoneEnabledFlag
			MAX-ACCESS read-create
			STATUS current
			DESCRIPTION
				"This object defines the VLAN router operation. If this object is set 
				to enabled, the router will route between IP subnets across VLANs. Route 
				table lookups will ignore the VLAN ID of the ingress and egress ports.
				If there is a match, the packet is routed out the interface specified
				in the Route Table, regardless of the VLAN with which it is a member.
				
				If set to disabled, the router will only route between IP subnets that
				are on the same VLAN. Packets will be forwarded to the configured Default
				Route for the VLAN that they arrived on, unless there is a Route Table
				match within that same VLAN. Routing of packets across VLANs is
				prevented, providing traffic isolation."
			DEFVAL { enabled }
			::= { zhoneCpeSystemCommonEntry 22 }

		
		-- 1.3.6.1.4.1.5504.5.16.1.18.2.1.23
		zhoneCpeSystemCommonBlockUpstreamDhcpOffer OBJECT-TYPE
			SYNTAX ZhoneEnabledFlag
			MAX-ACCESS read-create
			STATUS current
			DESCRIPTION
				"Set as Enabled, filter all DHCP offers going to the network.
				Set as Disabled, allow unit to forward DHCP offers."
			DEFVAL { enabled }
			::= { zhoneCpeSystemCommonEntry 23 }

		
		-- 1.3.6.1.4.1.5504.5.16.1.18.2.1.24
		zhoneCpeSystemCommonBlockDownstreamDnsQuery OBJECT-TYPE
			SYNTAX ZhoneEnabledFlag
			MAX-ACCESS read-create
			STATUS current
			DESCRIPTION
				"Set as Enabled, ignore DNS queries. Set as Disabled,
				Respond to any DNS queries"
			DEFVAL { enabled }
			::= { zhoneCpeSystemCommonEntry 24 }

		
		-- 1.3.6.1.4.1.5504.5.16.1.18.2.1.25
		zhoneCpeSystemCommonCrossVlanMulticast OBJECT-TYPE
			SYNTAX ZhoneEnabledFlag
			MAX-ACCESS read-create
			STATUS current
			DESCRIPTION
				"This object defines the VLAN router operation. If this object is set 
				to enabled, the router will route between IP subnets across VLANs. Route 
				table lookups will ignore the VLAN ID of the ingress and egress ports.
				If there is a match, the packet is routed out the interface specified
				in the Route Table, regardless of the VLAN with which it is a member.	      
				
				If set to disabled, the router will only route between IP subnets that
				are on the same VLAN. Packets will be forwarded to the configured Default
				Route for the VLAN that they arrived on, unless there is a Route Table
				match within that same VLAN. Routing of packets across VLANs is
				prevented, providing traffic isolation."
			DEFVAL { disabled }
			::= { zhoneCpeSystemCommonEntry 25 }

		
		-- 1.3.6.1.4.1.5504.5.16.1.18.2.1.26
		zhoneCpeSystemCommonPrioritizationMethod OBJECT-TYPE
			SYNTAX INTEGER
				{
				vlancos(1),
				ipdscp(2)
				}
			MAX-ACCESS read-create
			STATUS current
			DESCRIPTION
				"Quality of Service Method. Enumeration of:
				vlancos     - Layer 2 VLAN COS method will check the COS bits in 
				              the Ethernet Packet to define the QOS.
				ipdscp      - Layer 3 IP Precedence method will check the DSCP field
				              in the IP header to determine priority of the packet."
			DEFVAL { vlancos }
			::= { zhoneCpeSystemCommonEntry 26 }

		
		-- 1.3.6.1.4.1.5504.5.16.1.18.2.1.27
		zhoneCpeSystemCommonSchedulingMethod OBJECT-TYPE
			SYNTAX INTEGER
				{
				strict(1),
				wrr(2)
				}
			MAX-ACCESS read-create
			STATUS current
			DESCRIPTION
				"Quality of Service Scheduling Method. Enumeration of:
				strict     - Strict Scheduling
				wrr        - Strict with Weighted Round Robin Scheduling"
			DEFVAL { wrr }
			::= { zhoneCpeSystemCommonEntry 27 }

		
		-- 1.3.6.1.4.1.5504.5.16.1.18.2.1.28
		zhoneCpeSystemCommonAuthServerPrimaryAddr OBJECT-TYPE
			SYNTAX IpAddress
			MAX-ACCESS read-create
			STATUS current
			DESCRIPTION
				"This field specifies the IP address of the Primary 
				RADIUS authentication server."
			DEFVAL { '7F000001'h }
			::= { zhoneCpeSystemCommonEntry 28 }

		
		-- 1.3.6.1.4.1.5504.5.16.1.18.2.1.29
		zhoneCpeSystemCommonAuthServerPrimaryPortNum OBJECT-TYPE
			SYNTAX Integer32 (0..65535)
			MAX-ACCESS read-create
			STATUS current
			DESCRIPTION
				"This field specifies the UDP port number used by client
				to send requests to the Primary RADIUS authentication server."
			DEFVAL { 1812 }
			::= { zhoneCpeSystemCommonEntry 29 }

		
		-- 1.3.6.1.4.1.5504.5.16.1.18.2.1.30
		zhoneCpeSystemCommonAuthPrimarySharedSecret OBJECT-TYPE
			SYNTAX SnmpAdminString
			MAX-ACCESS read-create
			STATUS current
			DESCRIPTION
				"This field specifies the Shared secret to access 
				Primary Radius Server's authentication services."
			DEFVAL { "zhone" }
			::= { zhoneCpeSystemCommonEntry 30 }

		
		-- 1.3.6.1.4.1.5504.5.16.1.18.2.1.31
		zhoneCpeSystemCommonAuthServerSecondaryAddr OBJECT-TYPE
			SYNTAX IpAddress
			MAX-ACCESS read-create
			STATUS current
			DESCRIPTION
				"This field specifies the IP address of the Secondary 
				RADIUS authentication server."
			DEFVAL { '00000000'h }
			::= { zhoneCpeSystemCommonEntry 31 }

		
		-- 1.3.6.1.4.1.5504.5.16.1.18.2.1.32
		zhoneCpeSystemCommonAuthServerSecondaryPortNum OBJECT-TYPE
			SYNTAX Integer32 (0..65535)
			MAX-ACCESS read-create
			STATUS current
			DESCRIPTION
				"This field specifies the UDP port number used by client to 
				send requests to the Secondary RADIUS authentication server."
			DEFVAL { 1812 }
			::= { zhoneCpeSystemCommonEntry 32 }

		
		-- 1.3.6.1.4.1.5504.5.16.1.18.2.1.33
		zhoneCpeSystemCommonAuthSecondarySharedSecret OBJECT-TYPE
			SYNTAX SnmpAdminString
			MAX-ACCESS read-create
			STATUS current
			DESCRIPTION
				"This field specifies the shared secret to access Secondary
				 Radius Server's authentication services."
			DEFVAL { "zhone" }
			::= { zhoneCpeSystemCommonEntry 33 }

		
		-- 1.3.6.1.4.1.5504.5.16.1.18.2.1.34
		zhoneCpeSystemCommonAccServerPrimaryAddr OBJECT-TYPE
			SYNTAX IpAddress
			MAX-ACCESS read-create
			STATUS current
			DESCRIPTION
				"This field specifies the IP address of the Primary 
				RADIUS accounting server."
			DEFVAL { '7F000001'h }
			::= { zhoneCpeSystemCommonEntry 34 }

		
		-- 1.3.6.1.4.1.5504.5.16.1.18.2.1.35
		zhoneCpeSystemCommonAccServerPrimaryPortNum OBJECT-TYPE
			SYNTAX Integer32 (0..65535)
			MAX-ACCESS read-create
			STATUS current
			DESCRIPTION
				"This field specifies the UDP port number used by client 
				to send requests to the Primary RADIUS accounting server."
			DEFVAL { 1813 }
			::= { zhoneCpeSystemCommonEntry 35 }

		
		-- 1.3.6.1.4.1.5504.5.16.1.18.2.1.36
		zhoneCpeSystemCommonAccPrimarySharedSecret OBJECT-TYPE
			SYNTAX SnmpAdminString
			MAX-ACCESS read-create
			STATUS current
			DESCRIPTION
				"This field specifies the Shared secret to access Secondary
				Radius Server's accounting services."
			DEFVAL { "zhone" }
			::= { zhoneCpeSystemCommonEntry 36 }

		
		-- 1.3.6.1.4.1.5504.5.16.1.18.2.1.37
		zhoneCpeSystemCommonAccServerSecondaryAddr OBJECT-TYPE
			SYNTAX IpAddress
			MAX-ACCESS read-create
			STATUS current
			DESCRIPTION
				"This field specifies the IP address of the Secondary 
				RADIUS accounting server"
			DEFVAL { '00000000'h }
			::= { zhoneCpeSystemCommonEntry 37 }

		
		-- 1.3.6.1.4.1.5504.5.16.1.18.2.1.38
		zhoneCpeSystemCommonAccServerSecondaryPortNum OBJECT-TYPE
			SYNTAX Integer32 (0..65535)
			MAX-ACCESS read-create
			STATUS current
			DESCRIPTION
				"This field specifies the UDP port number used by client to send requests
				to the Secondary RADIUS accounting server."
			DEFVAL { 1813 }
			::= { zhoneCpeSystemCommonEntry 38 }

		
		-- 1.3.6.1.4.1.5504.5.16.1.18.2.1.39
		zhoneCpeSystemCommonAccSecondarySharedSecret OBJECT-TYPE
			SYNTAX SnmpAdminString
			MAX-ACCESS read-create
			STATUS current
			DESCRIPTION
				"This field specifies the Shared secret to access Secondary 
				Radius Server's accounting services."
			DEFVAL { "zhone" }
			::= { zhoneCpeSystemCommonEntry 39 }

		
		-- 1.3.6.1.4.1.5504.5.16.1.18.2.1.40
		zhoneCpeSystemCommonMaxSupplicantsPerVLAN OBJECT-TYPE
			SYNTAX Unsigned32 (1..10)
			MAX-ACCESS read-create
			STATUS current
			DESCRIPTION
				"This field specifies the maximum number of Supplicants for
				the LAN port,The Range of maximun number of supplicants 
				can be 1 to 10."
			DEFVAL { 1 }
			::= { zhoneCpeSystemCommonEntry 40 }

		
		-- 1.3.6.1.4.1.5504.5.16.1.18.2.1.41
		zhoneCpeSystemCommonGuestVlan OBJECT-TYPE
			SYNTAX Unsigned32 (0..4095)
			MAX-ACCESS read-create
			STATUS current
			DESCRIPTION
				"This field specifies the VLAN ID to be used for attached 
				devices that do not successfully authenticate using 802.1X
				when the Port Authentication Mode is AUTO."
			DEFVAL { 0 }
			::= { zhoneCpeSystemCommonEntry 41 }

		
		-- 1.3.6.1.4.1.5504.5.16.1.18.2.1.42
		zhoneCpeSystemCommonGroupId1Name OBJECT-TYPE
			SYNTAX OCTET STRING (SIZE (0..32))
			MAX-ACCESS read-create
			STATUS current
			DESCRIPTION
				"This field specifies the name of Vlan group ID 1 for a 
				particular service."
			DEFVAL { "data" }
			::= { zhoneCpeSystemCommonEntry 42 }

		
		-- 1.3.6.1.4.1.5504.5.16.1.18.2.1.43
		zhoneCpeSystemCommonGroupId1Vlan OBJECT-TYPE
			SYNTAX Unsigned32 (0..4095)
			MAX-ACCESS read-create
			STATUS current
			DESCRIPTION
				"This field specifies the Vlan group ID 1 for a 
				particular service."
			DEFVAL { 0 }
			::= { zhoneCpeSystemCommonEntry 43 }

		
		-- 1.3.6.1.4.1.5504.5.16.1.18.2.1.44
		zhoneCpeSystemCommonGroupId2Name OBJECT-TYPE
			SYNTAX OCTET STRING (SIZE (0..32))
			MAX-ACCESS read-create
			STATUS current
			DESCRIPTION
				"This field specifies the name of Vlan group ID 2 for a 
				particular service."
			DEFVAL { "voice" }
			::= { zhoneCpeSystemCommonEntry 44 }

		
		-- 1.3.6.1.4.1.5504.5.16.1.18.2.1.45
		zhoneCpeSystemCommonGroupId2Vlan OBJECT-TYPE
			SYNTAX Unsigned32 (0..4095)
			MAX-ACCESS read-create
			STATUS current
			DESCRIPTION
				"This field specifies the Vlan group ID 2 for a 
				particular service."
			DEFVAL { 0 }
			::= { zhoneCpeSystemCommonEntry 45 }

		
		-- 1.3.6.1.4.1.5504.5.16.1.18.2.1.46
		zhoneCpeSystemCommonGroupId3Name OBJECT-TYPE
			SYNTAX OCTET STRING (SIZE (0..32))
			MAX-ACCESS read-create
			STATUS current
			DESCRIPTION
				"This field specifies the name of Vlan group ID 3 for a 
				particular service."
			DEFVAL { "port" }
			::= { zhoneCpeSystemCommonEntry 46 }

		
		-- 1.3.6.1.4.1.5504.5.16.1.18.2.1.47
		zhoneCpeSystemCommonGroupId3Vlan OBJECT-TYPE
			SYNTAX Unsigned32 (0..4095)
			MAX-ACCESS read-create
			STATUS current
			DESCRIPTION
				"This field specifies the Vlan group ID 3 for a
				particular service."
			DEFVAL { 0 }
			::= { zhoneCpeSystemCommonEntry 47 }

		
		-- 1.3.6.1.4.1.5504.5.16.1.18.2.1.48
		zhoneCpeSystemCommonReAuthEnabled OBJECT-TYPE
			SYNTAX ZhoneEnabledFlag
			MAX-ACCESS read-create
			STATUS current
			DESCRIPTION
				"This field specifies whether the Re-authentication is 
				enabled or disabled."
			DEFVAL { enabled }
			::= { zhoneCpeSystemCommonEntry 48 }

		
		-- 1.3.6.1.4.1.5504.5.16.1.18.2.1.49
		zhoneCpeSystemCommonReAuthPeriod OBJECT-TYPE
			SYNTAX Unsigned32
			UNITS "seconds"
			MAX-ACCESS read-create
			STATUS current
			DESCRIPTION
				"This field specifies the Re-authentication Period value 
				in seconds."
			DEFVAL { 3600 }
			::= { zhoneCpeSystemCommonEntry 49 }

		
		-- 1.3.6.1.4.1.5504.5.16.1.18.2.1.50
		zhoneCpeSystemCommonAuthQuietPeriod OBJECT-TYPE
			SYNTAX Unsigned32
			UNITS "seconds"
			MAX-ACCESS read-only
			STATUS current
			DESCRIPTION
				"This field specifies the number of seconds the supplicant 
				wait before reattempting authentication  after the failed
				authentication attempt"
			DEFVAL { 60 }
			::= { zhoneCpeSystemCommonEntry 50 }

		
		-- 1.3.6.1.4.1.5504.5.16.1.18.2.1.51
		zhoneCpeSystemCommonAuthServerTimeout OBJECT-TYPE
			SYNTAX Unsigned32
			UNITS "seconds"
			MAX-ACCESS read-create
			STATUS current
			DESCRIPTION
				"This field specifies the authentication server timeout
				value in seconds."
			DEFVAL { 30 }
			::= { zhoneCpeSystemCommonEntry 51 }

		
		-- 1.3.6.1.4.1.5504.5.16.1.18.2.1.52
		zhoneCpeSystemCommonAuthKeyTxEnabled OBJECT-TYPE
			SYNTAX ZhoneEnabledFlag
			MAX-ACCESS read-only
			STATUS current
			DESCRIPTION
				"This field specifies whether the shared secret key
				transmission is enabled or disabled."
			DEFVAL { disabled }
			::= { zhoneCpeSystemCommonEntry 52 }

		
		-- 1.3.6.1.4.1.5504.5.16.1.18.2.1.53
		zhoneCpeSystemCommonTr69CfgConnReqAuth OBJECT-TYPE
			SYNTAX ZhoneEnabledFlag
			MAX-ACCESS read-create
			STATUS current
			DESCRIPTION
				"Enable or disable connection request authentication"
			DEFVAL { disabled }
			::= { zhoneCpeSystemCommonEntry 53 }

		
		-- 1.3.6.1.4.1.5504.5.16.1.19
		zhoneCpeInterfaceVlanTable OBJECT-TYPE
			SYNTAX SEQUENCE OF ZhoneCpeInterfaceVlanEntry
			MAX-ACCESS not-accessible
			STATUS current
			DESCRIPTION
				"Cpe Interface Vlan table."
			::= { zhoneCpeObjectID 19 }

		
		-- 1.3.6.1.4.1.5504.5.16.1.19.1
		zhoneCpeInterfaceVlanEntry OBJECT-TYPE
			SYNTAX ZhoneCpeInterfaceVlanEntry
			MAX-ACCESS not-accessible
			STATUS current
			DESCRIPTION
				"Row in the Cpe Interface Vlan table."
			INDEX { zhoneCpeIfIndex, zhoneCpeTpType, zhoneCpeTpIndex, zhoneCpeVlanId, zhoneCpeSlanId
				 }
			::= { zhoneCpeInterfaceVlanTable 1 }

		
		ZhoneCpeInterfaceVlanEntry ::=
			SEQUENCE { 
				zhoneCpeInterfaceVlanRowStatus
					ZhoneRowStatus,
				zhoneCpeInterfaceVlanRgMode
					INTEGER,
				zhoneCpeInterfaceVlanTranslateVlanId
					Unsigned32,
				zhoneCpeInterfaceVlanTranslateVlanCos
					Unsigned32,
				zhoneCpeInterfaceVlanTranslateSlanId
					Unsigned32,
				zhoneCpeInterfaceVlanTranslateSlanCos
					Unsigned32,
				zhoneCpeInterfaceVlanTranslateSlanTpId
					Unsigned32,
				zhoneCpeInterfaceVlanIpAddress
					IpAddress,
				zhoneCpeIpServerProfile
					Unsigned32,
				zhoneCpeDhcpServerProfileIndex
					Unsigned32,
				zhoneCpePortFwdListProfileIndex
					Unsigned32,
				zhoneCpeInterfaceVlanIpv6Address
					InetAddressIPv6
			 }

		-- 1.3.6.1.4.1.5504.5.16.1.19.1.1
		zhoneCpeInterfaceVlanRowStatus OBJECT-TYPE
			SYNTAX ZhoneRowStatus
			MAX-ACCESS read-create
			STATUS current
			DESCRIPTION
				"Used to create, modify or delete an entry in this table."
			DEFVAL { active }
			::= { zhoneCpeInterfaceVlanEntry 1 }

		
		-- 1.3.6.1.4.1.5504.5.16.1.19.1.2
		zhoneCpeInterfaceVlanRgMode OBJECT-TYPE
			SYNTAX INTEGER
				{
				routed(1),
				brouted(2),
				routedpppoe(3),
				bridgedpppoe(4),
				bridged(5)
				}
			MAX-ACCESS read-create
			STATUS current
			DESCRIPTION
				"Specifies the VLAN connection type of the interface."
			DEFVAL { brouted }
			::= { zhoneCpeInterfaceVlanEntry 2 }

		
		-- 1.3.6.1.4.1.5504.5.16.1.19.1.3
		zhoneCpeInterfaceVlanTranslateVlanId OBJECT-TYPE
			SYNTAX Unsigned32 (0..4096)
			MAX-ACCESS read-create
			STATUS current
			DESCRIPTION
				"The Virtual LAN Id for VLAN Tag Insertion."
			DEFVAL { 0 }
			::= { zhoneCpeInterfaceVlanEntry 3 }

		
		-- 1.3.6.1.4.1.5504.5.16.1.19.1.4
		zhoneCpeInterfaceVlanTranslateVlanCos OBJECT-TYPE
			SYNTAX Unsigned32 (0..8)
			MAX-ACCESS read-create
			STATUS current
			DESCRIPTION
				"The Class-Of-Service (COS) value used for VLAN Tag Insertion."
			DEFVAL { 0 }
			::= { zhoneCpeInterfaceVlanEntry 4 }

		
		-- 1.3.6.1.4.1.5504.5.16.1.19.1.5
		zhoneCpeInterfaceVlanTranslateSlanId OBJECT-TYPE
			SYNTAX Unsigned32 (0..4096)
			MAX-ACCESS read-create
			STATUS current
			DESCRIPTION
				"The Secure LAN Id for SLAN Tag Insertion."
			DEFVAL { 0 }
			::= { zhoneCpeInterfaceVlanEntry 5 }

		
		-- 1.3.6.1.4.1.5504.5.16.1.19.1.6
		zhoneCpeInterfaceVlanTranslateSlanCos OBJECT-TYPE
			SYNTAX Unsigned32 (0..8)
			MAX-ACCESS read-create
			STATUS current
			DESCRIPTION
				"The Class-Of-Service (COS) value used for SLAN Tag Insertion."
			DEFVAL { 0 }
			::= { zhoneCpeInterfaceVlanEntry 6 }

		
		-- 1.3.6.1.4.1.5504.5.16.1.19.1.7
		zhoneCpeInterfaceVlanTranslateSlanTpId OBJECT-TYPE
			SYNTAX Unsigned32 (33024 | 34984 | 37120 | 37376)
			MAX-ACCESS read-create
			STATUS current
			DESCRIPTION
				"The value of the tag protocol identifier that is being used for QinQ packets.
				(0x8100 is default).
				
				
				Valid values are:
				
				1. 33024 ( 0x8100 )
				2. 34984 ( 0x88A8 )
				3. 37120 ( 0x9100 )
				4. 37376 ( 0x9200 )"
			DEFVAL { 33024 }
			::= { zhoneCpeInterfaceVlanEntry 7 }

		
		-- 1.3.6.1.4.1.5504.5.16.1.19.1.8
		zhoneCpeInterfaceVlanIpAddress OBJECT-TYPE
			SYNTAX IpAddress
			MAX-ACCESS read-create
			STATUS current
			DESCRIPTION
				"The address used for IP host services. Default is 0.0.0.0."
			DEFVAL { '00000000'h }
			::= { zhoneCpeInterfaceVlanEntry 8 }

		
		-- 1.3.6.1.4.1.5504.5.16.1.19.1.9
		zhoneCpeIpServerProfile OBJECT-TYPE
			SYNTAX Unsigned32 (0..2147483647)
			MAX-ACCESS read-create
			STATUS current
			DESCRIPTION
				"The address of the cpe-ip-server profile associated with this host IP address.
				The value 0 indicates no associated cpe-ip-server profile."
			DEFVAL { 0 }
			::= { zhoneCpeInterfaceVlanEntry 9 }

		
		-- 1.3.6.1.4.1.5504.5.16.1.19.1.10
		zhoneCpeDhcpServerProfileIndex OBJECT-TYPE
			SYNTAX Unsigned32 (0..2147483647)
			MAX-ACCESS read-create
			STATUS current
			DESCRIPTION
				"The address of the DHCP server profile associated with this interface.
				The value 0 indicates no associated cpe-dhcp-server profile."
			DEFVAL { 0 }
			::= { zhoneCpeInterfaceVlanEntry 10 }

		
		-- 1.3.6.1.4.1.5504.5.16.1.19.1.11
		zhoneCpePortFwdListProfileIndex OBJECT-TYPE
			SYNTAX Unsigned32 (0..2147483647)
			MAX-ACCESS read-create
			STATUS current
			DESCRIPTION
				"The address of the port fwd list profile associated with this
				interface. It is only supported on a WAN interface. The value 0 indicates
				no associated cpe-port-fwding profile."
			DEFVAL { 0 }
			::= { zhoneCpeInterfaceVlanEntry 11 }

		
		-- 1.3.6.1.4.1.5504.5.16.1.19.1.12
		zhoneCpeInterfaceVlanIpv6Address OBJECT-TYPE
			SYNTAX InetAddressIPv6
			MAX-ACCESS read-create
			STATUS current
			DESCRIPTION
				"This attribute specifies the IPV6 address,
				The default value is ::/128"
			DEFVAL { "::" }
			::= { zhoneCpeInterfaceVlanEntry 12 }

		
		-- 1.3.6.1.4.1.5504.5.16.1.20
		zhoneCpeDhcpServer OBJECT-IDENTITY
			STATUS current
			DESCRIPTION 
				"Cpe Dhcp Server objects."
			::= { zhoneCpeObjectID 20 }

		
		-- 1.3.6.1.4.1.5504.5.16.1.20.1
		zhoneCpeDhcpServerIndexNext OBJECT-TYPE
			SYNTAX Integer32
			MAX-ACCESS read-only
			STATUS current
			DESCRIPTION
				"This object contains an appropriate value to be used for the
				zhoneCpeDhcpServerIndex when creating entries in the zhoneCpeDhcpServerTable.
				The value 0 indicates that no unassigned entries are available. To obtain the
				zhoneCpeDhcpServerIndex value for a new entry, the manager issues a management
				protocol retrieval operation to obtain the current value of this object.  After each
				retrieval, the agent should modify the value to the next unassigned index.
				
				After a manager retrieves a value the agent will determine through its local
				policy when this index value will be made available for reuse."
			::= { zhoneCpeDhcpServer 1 }

		
		-- 1.3.6.1.4.1.5504.5.16.1.20.2
		zhoneCpeDhcpServerTable OBJECT-TYPE
			SYNTAX SEQUENCE OF ZhoneCpeDhcpServerEntry
			MAX-ACCESS not-accessible
			STATUS current
			DESCRIPTION
				"Cpe Dhcp Server table."
			::= { zhoneCpeDhcpServer 2 }

		
		-- 1.3.6.1.4.1.5504.5.16.1.20.2.1
		zhoneCpeDhcpServerEntry OBJECT-TYPE
			SYNTAX ZhoneCpeDhcpServerEntry
			MAX-ACCESS not-accessible
			STATUS current
			DESCRIPTION
				"Row in the Cpe Dhcp Server table."
			INDEX { zhoneCpeDhcpServerIndex }
			::= { zhoneCpeDhcpServerTable 1 }

		
		ZhoneCpeDhcpServerEntry ::=
			SEQUENCE { 
				zhoneCpeDhcpServerIndex
					Unsigned32,
				zhoneCpeDhcpServerRowStatus
					ZhoneRowStatus,
				zhoneCpeDhcpServerProfileName
					ZhoneAdminString,
				zhoneCpeDhcpServerStartAddress
					IpAddress,
				zhoneCpeDhcpServerEndAddress
					IpAddress,
				zhoneCpeDhcpServerLeaseTime
					Integer32,
				zhoneCpeDhcpServerConditionalServerListProfile
					Unsigned32,
				zhoneCpeDhcpServerIpv6DhcpServer
					ZhoneEnabledFlag,
				zhoneCpeDhcpServerIpv6DhcpMode
					INTEGER,
				zhoneCpeDhcpServerIpv6RouterAdvertise
					ZhoneEnabledFlag,
				zhoneCpeDhcpServerIpv6LeaseTime 
					Integer32,
				zhoneCpeDhcpServerIpv6StartAddress
					InetAddressIPv6,
				zhoneCpeDhcpServerIpv6EndAddress
					InetAddressIPv6
			 }

		-- 1.3.6.1.4.1.5504.5.16.1.20.2.1.1
		zhoneCpeDhcpServerIndex OBJECT-TYPE
			SYNTAX Unsigned32 (1..2147483647)
			MAX-ACCESS not-accessible
			STATUS current
			DESCRIPTION
				"This represents the CPE DHCP server index value."
			::= { zhoneCpeDhcpServerEntry 1 }

		
		-- 1.3.6.1.4.1.5504.5.16.1.20.2.1.2
		zhoneCpeDhcpServerRowStatus OBJECT-TYPE
			SYNTAX ZhoneRowStatus
			MAX-ACCESS read-create
			STATUS current
			DESCRIPTION
				"Used to create, modify or delete an entry in this table."
			DEFVAL { active }
			::= { zhoneCpeDhcpServerEntry 2 }

		
		-- 1.3.6.1.4.1.5504.5.16.1.20.2.1.3
		zhoneCpeDhcpServerProfileName OBJECT-TYPE
			SYNTAX ZhoneAdminString
			MAX-ACCESS read-create
			STATUS current
			DESCRIPTION
				"CPE DHCP Server profile. This field is only writable upon creation and must be
				unique within its table."
			::= { zhoneCpeDhcpServerEntry 3 }

		
		-- 1.3.6.1.4.1.5504.5.16.1.20.2.1.4
		zhoneCpeDhcpServerStartAddress OBJECT-TYPE
			SYNTAX IpAddress
			MAX-ACCESS read-create
			STATUS current
			DESCRIPTION
				"First address in the pool to be assigned by the DHCP server. Default value is 0.0.0.0."
			DEFVAL { '00000000'h }
			::= { zhoneCpeDhcpServerEntry 4 }

		
		-- 1.3.6.1.4.1.5504.5.16.1.20.2.1.5
		zhoneCpeDhcpServerEndAddress OBJECT-TYPE
			SYNTAX IpAddress
			MAX-ACCESS read-create
			STATUS current
			DESCRIPTION
				"Last address in the pool to be assigned by the DHCP server. Default value is 0.0.0.0."
			DEFVAL { '00000000'h }
			::= { zhoneCpeDhcpServerEntry 5 }

		
		-- 1.3.6.1.4.1.5504.5.16.1.20.2.1.6
		zhoneCpeDhcpServerLeaseTime OBJECT-TYPE
			SYNTAX Integer32 (-1..2147483647)
			UNITS "seconds"
			MAX-ACCESS read-create
			STATUS current
			DESCRIPTION
				"Lease time in seconds of client assigned addresses. A value of -1 indicates an
				infinite lease."
			DEFVAL { -1 }
			::= { zhoneCpeDhcpServerEntry 6 }

		
		-- 1.3.6.1.4.1.5504.5.16.1.20.2.1.7
		zhoneCpeDhcpServerConditionalServerListProfile OBJECT-TYPE
			SYNTAX Unsigned32
			MAX-ACCESS read-create
			STATUS current
			DESCRIPTION
				"Index of the dhcp-conditional-server-list profile associated 
				with this entry, or 0 if none."
			DEFVAL { 0 }
			::= { zhoneCpeDhcpServerEntry 7 }

		
		-- 1.3.6.1.4.1.5504.5.16.1.20.2.1.8
		zhoneCpeDhcpServerIpv6DhcpServer OBJECT-TYPE
			SYNTAX ZhoneEnabledFlag
			MAX-ACCESS read-create
			STATUS current
			DESCRIPTION
				"Enables or disables the IPv6 DHCP server
				on the LAN interface"
			DEFVAL { enabled }
			::= { zhoneCpeDhcpServerEntry 8 }

		
		-- 1.3.6.1.4.1.5504.5.16.1.20.2.1.9
		zhoneCpeDhcpServerIpv6DhcpMode OBJECT-TYPE
			SYNTAX INTEGER
				{
				stateful(1),
				stateless(2)
				}
			MAX-ACCESS read-create
			STATUS current
			DESCRIPTION
				"This attribute specifies the DHCP Mode of the 
				DHCPV6 server as stateful or stateless"
			DEFVAL { stateless }
			::= { zhoneCpeDhcpServerEntry 9 }

		
		-- 1.3.6.1.4.1.5504.5.16.1.20.2.1.10
		zhoneCpeDhcpServerIpv6RouterAdvertise OBJECT-TYPE
			SYNTAX ZhoneEnabledFlag
			MAX-ACCESS read-create
			STATUS current
			DESCRIPTION
				"Enable or disable Router Advertisement service,
				where router announces periodically its IPv6 address"
			DEFVAL { enabled }
			::= { zhoneCpeDhcpServerEntry 10 }

		
		-- 1.3.6.1.4.1.5504.5.16.1.20.2.1.11
		zhoneCpeDhcpServerIpv6LeaseTime  OBJECT-TYPE
			SYNTAX Integer32 (-1..2147483647)
			UNITS "seconds"
			MAX-ACCESS read-create
			STATUS current
			DESCRIPTION
				"Specifies the lease time in seconds of client assigned addresses.
				A value of -1 indicates an infinite lease."
			DEFVAL { 86400 }
			::= { zhoneCpeDhcpServerEntry 11 }

		
		-- 1.3.6.1.4.1.5504.5.16.1.20.2.1.12
		zhoneCpeDhcpServerIpv6StartAddress OBJECT-TYPE
			SYNTAX InetAddressIPv6
			MAX-ACCESS read-create
			STATUS current
			DESCRIPTION
				"This parameter is for assigning IPv6 address by stateful DHCPV6 
				server. The value indicates the beginning of the interface ID pool
				to be assigned by the DHCPV6 server"
			DEFVAL { "::2" }
			::= { zhoneCpeDhcpServerEntry 12 }

		
		-- 1.3.6.1.4.1.5504.5.16.1.20.2.1.13
		zhoneCpeDhcpServerIpv6EndAddress OBJECT-TYPE
			SYNTAX InetAddressIPv6
			MAX-ACCESS read-create
			STATUS current
			DESCRIPTION
				"This parameter is for assigning IPv6 address by stateful DHCPv6 
				server. The value indicates the end of the interface ID pool
				to be assigned by the DHCPV6 server"
			DEFVAL { "::254" }
			::= { zhoneCpeDhcpServerEntry 13 }

		
		-- 1.3.6.1.4.1.5504.5.16.1.21
		zhoneCpePppoeTable OBJECT-TYPE
			SYNTAX SEQUENCE OF ZhoneCpePppoeEntry
			MAX-ACCESS not-accessible
			STATUS current
			DESCRIPTION
				"Cpe PPPOE table."
			::= { zhoneCpeObjectID 21 }

		
		-- 1.3.6.1.4.1.5504.5.16.1.21.1
		zhoneCpePppoeEntry OBJECT-TYPE
			SYNTAX ZhoneCpePppoeEntry
			MAX-ACCESS not-accessible
			STATUS current
			DESCRIPTION
				"Row in the Cpe PPPOE table."
			INDEX { zhoneCpeIfIndex, zhoneCpeTpType, zhoneCpeTpIndex, zhoneCpeVlanId, zhoneCpeSlanId
				 }
			::= { zhoneCpePppoeTable 1 }

		
		ZhoneCpePppoeEntry ::=
			SEQUENCE { 
				zhoneCpePppoeRowStatus
					ZhoneRowStatus,
				zhoneCpePppoeUsername
					OCTET STRING,
				zhoneCpePppoePassword
					OCTET STRING,
				zhoneCpePppoeAuthentication
					INTEGER,
				zhoneCpePppoeRetryInterval
					Unsigned32,
				zhoneCpePppoeIdleDisconnectTime
					Unsigned32
			 }

		-- 1.3.6.1.4.1.5504.5.16.1.21.1.1
		zhoneCpePppoeRowStatus OBJECT-TYPE
			SYNTAX ZhoneRowStatus
			MAX-ACCESS read-create
			STATUS current
			DESCRIPTION
				"Used to create, modify or delete an entry in this table."
			DEFVAL { active }
			::= { zhoneCpePppoeEntry 1 }

		
		-- 1.3.6.1.4.1.5504.5.16.1.21.1.2
		zhoneCpePppoeUsername OBJECT-TYPE
			SYNTAX OCTET STRING (SIZE (1..64))
			MAX-ACCESS read-create
			STATUS current
			DESCRIPTION
				"The login user name to be used for PPP authentication."
			::= { zhoneCpePppoeEntry 2 }

		
		-- 1.3.6.1.4.1.5504.5.16.1.21.1.3
		zhoneCpePppoePassword OBJECT-TYPE
			SYNTAX OCTET STRING (SIZE (1..25))
			MAX-ACCESS read-create
			STATUS current
			DESCRIPTION
				"The login password to be used for PPP authentication."
			::= { zhoneCpePppoeEntry 3 }

		
		-- 1.3.6.1.4.1.5504.5.16.1.21.1.4
		zhoneCpePppoeAuthentication OBJECT-TYPE
			SYNTAX INTEGER
				{
				auto(1),
				pap(2),
				chap(3),
				mschap(4)
				}
			MAX-ACCESS read-create
			STATUS current
			DESCRIPTION
				"The PPP authentication protocol to be used for PPP authentication."
			DEFVAL { auto }
			::= { zhoneCpePppoeEntry 4 }

		
		-- 1.3.6.1.4.1.5504.5.16.1.21.1.5
		zhoneCpePppoeRetryInterval OBJECT-TYPE
			SYNTAX Unsigned32 (1..2147483647)
			UNITS "seconds"
			MAX-ACCESS read-create
			STATUS current
			DESCRIPTION
				"Time in seconds before retrying connection."
			DEFVAL { 3 }
			::= { zhoneCpePppoeEntry 5 }

		
		-- 1.3.6.1.4.1.5504.5.16.1.21.1.6
		zhoneCpePppoeIdleDisconnectTime OBJECT-TYPE
			SYNTAX Unsigned32 (0..2147483647)
			UNITS "seconds"
			MAX-ACCESS read-create
			STATUS current
			DESCRIPTION
				"The time in seconds where the connection remains idle
				and the CPE automatically terminates the connection.
				A value of 0 (zero) indicates that the connection is 
				not to be shutdown automatically
				"
			DEFVAL { 0 }
			::= { zhoneCpePppoeEntry 6 }

		
		-- 1.3.6.1.4.1.5504.5.16.1.22
		zhoneCpeWlanSubscriberTable OBJECT-TYPE
			SYNTAX SEQUENCE OF ZhoneCpeWlanSubscriberEntry
			MAX-ACCESS not-accessible
			STATUS current
			DESCRIPTION
				"Cpe Wlan Subscriber table."
			::= { zhoneCpeObjectID 22 }

		
		-- 1.3.6.1.4.1.5504.5.16.1.22.1
		zhoneCpeWlanSubscriberEntry OBJECT-TYPE
			SYNTAX ZhoneCpeWlanSubscriberEntry
			MAX-ACCESS not-accessible
			STATUS current
			DESCRIPTION
				"Row in the Cpe Wlan Subscriber table."
			INDEX { zhoneCpeIfIndex, zhoneCpeWlanSubscriberIndex }
			::= { zhoneCpeWlanSubscriberTable 1 }

		
		ZhoneCpeWlanSubscriberEntry ::=
			SEQUENCE { 
				zhoneCpeWlanSubscriberIndex
					Unsigned32,
				zhoneCpeWlanSubscriberRowStatus
					ZhoneRowStatus,
				zhoneCpeWlanSubscriberAdminState
					ZhoneAdminState,
				zhoneCpeWlanSubscriberSsid
					OCTET STRING,
				zhoneCpeWlanSubscriberEncryptKey
					OCTET STRING,
				zhoneCpeWlanSubscriberDevicePin
					OCTET STRING,
				zhoneCpeWlanSubscriberRadiusKey
					OCTET STRING,
				zhoneCpeWlanProfileIndex
					Unsigned32,
				zhoneCpeAccessControlListProfileIndex
					Unsigned32,
				zhoneCpeWdsMacListProfileIndex
					Unsigned32,
				zhoneCpeWlanAdvProfileIndex
					Unsigned32,
				zhoneCpeWlanSubscriberDescription
					OCTET STRING
			 }

		-- 1.3.6.1.4.1.5504.5.16.1.22.1.1
		zhoneCpeWlanSubscriberIndex OBJECT-TYPE
			SYNTAX Unsigned32 (1..2147483647)
			MAX-ACCESS not-accessible
			STATUS current
			DESCRIPTION
				"This represents the CPE WLAN subscriber index value."
			::= { zhoneCpeWlanSubscriberEntry 1 }

		
		-- 1.3.6.1.4.1.5504.5.16.1.22.1.2
		zhoneCpeWlanSubscriberRowStatus OBJECT-TYPE
			SYNTAX ZhoneRowStatus
			MAX-ACCESS read-create
			STATUS current
			DESCRIPTION
				"Used to create, modify or delete an entry in this table."
			DEFVAL { active }
			::= { zhoneCpeWlanSubscriberEntry 2 }

		
		-- 1.3.6.1.4.1.5504.5.16.1.22.1.3
		zhoneCpeWlanSubscriberAdminState OBJECT-TYPE
			SYNTAX ZhoneAdminState
			MAX-ACCESS read-create
			STATUS current
			DESCRIPTION
				"This attribute activates or deactivates the functions performed by
				the wireless LAN interface for this subscriber or put the interface
				in test mode. Values are Up, Down, Test."
			DEFVAL { 1 }
			::= { zhoneCpeWlanSubscriberEntry 3 }

		
		-- 1.3.6.1.4.1.5504.5.16.1.22.1.4
		zhoneCpeWlanSubscriberSsid OBJECT-TYPE
			SYNTAX OCTET STRING (SIZE (1..32))
			MAX-ACCESS read-create
			STATUS current
			DESCRIPTION
				"The SSID assigned to the wireless LAN interface."
			::= { zhoneCpeWlanSubscriberEntry 4 }

		
		-- 1.3.6.1.4.1.5504.5.16.1.22.1.5
		zhoneCpeWlanSubscriberEncryptKey OBJECT-TYPE
			SYNTAX OCTET STRING (SIZE (1..64))
			MAX-ACCESS read-create
			STATUS current
			DESCRIPTION
				"WEP 64-bit encryption key: 5 ASCII characters or 10 hexadecimal digits
				WEP 128-bit encryption key: 13 ASCII charactess or 26 hexadecimal digits
				WPA Passphrase: 64 characters."
			::= { zhoneCpeWlanSubscriberEntry 5 }

		
		-- 1.3.6.1.4.1.5504.5.16.1.22.1.6
		zhoneCpeWlanSubscriberDevicePin OBJECT-TYPE
			SYNTAX OCTET STRING (SIZE (1..8))
			MAX-ACCESS read-create
			STATUS current
			DESCRIPTION
				"Device pin is only applicable when WPS security method is enabled."
			::= { zhoneCpeWlanSubscriberEntry 6 }

		
		-- 1.3.6.1.4.1.5504.5.16.1.22.1.7
		zhoneCpeWlanSubscriberRadiusKey OBJECT-TYPE
			SYNTAX OCTET STRING (SIZE (1..13))
			MAX-ACCESS read-create
			STATUS current
			DESCRIPTION
				"Remote Authentication Dial In User Server (RADIUS) authentication key.
				This field cannot contain a SPACE and is returned as a string of asterisks."
			::= { zhoneCpeWlanSubscriberEntry 7 }

		
		-- 1.3.6.1.4.1.5504.5.16.1.22.1.8
		zhoneCpeWlanProfileIndex OBJECT-TYPE
			SYNTAX Unsigned32 (0..2147483647)
			MAX-ACCESS read-create
			STATUS current
			DESCRIPTION
				"The address of cpe-wlan profile associated with this CPE."
			DEFVAL { 1 }
			::= { zhoneCpeWlanSubscriberEntry 8 }

		
		-- 1.3.6.1.4.1.5504.5.16.1.22.1.9
		zhoneCpeAccessControlListProfileIndex OBJECT-TYPE
			SYNTAX Unsigned32 (0..2147483647)
			MAX-ACCESS read-create
			STATUS current
			DESCRIPTION
				"The address of cpe-access-ctrl-list profile associated with this CPE."
			DEFVAL { 0 }
			::= { zhoneCpeWlanSubscriberEntry 9 }

		
		-- 1.3.6.1.4.1.5504.5.16.1.22.1.10
		zhoneCpeWdsMacListProfileIndex OBJECT-TYPE
			SYNTAX Unsigned32 (0..2147483647)
			MAX-ACCESS read-create
			STATUS current
			DESCRIPTION
				"The address of cpe-wds-mac-ctrl-list profile associated with this CPE."
			DEFVAL { 0 }
			::= { zhoneCpeWlanSubscriberEntry 10 }

		
		-- 1.3.6.1.4.1.5504.5.16.1.22.1.11
		zhoneCpeWlanAdvProfileIndex OBJECT-TYPE
			SYNTAX Unsigned32 (0..2147483647)
			MAX-ACCESS read-create
			STATUS current
			DESCRIPTION
				"The address of cpe-wlan-advanced profile associated with this CPE."
			DEFVAL { 1 }
			::= { zhoneCpeWlanSubscriberEntry 11 }

		
		-- 1.3.6.1.4.1.5504.5.16.1.22.1.12
		zhoneCpeWlanSubscriberDescription OBJECT-TYPE
			SYNTAX OCTET STRING (SIZE (0..32))
			MAX-ACCESS read-create
			STATUS current
			DESCRIPTION
				"Describes the CPE WLAN subscriber profile instance"
			DEFVAL { "" }
			::= { zhoneCpeWlanSubscriberEntry 12 }

		
		-- 1.3.6.1.4.1.5504.5.16.1.23
		zhoneCpeWlan OBJECT-IDENTITY
			STATUS current
			DESCRIPTION 
				"Cpe Wlan objects."
			::= { zhoneCpeObjectID 23 }

		
		-- 1.3.6.1.4.1.5504.5.16.1.23.1
		zhoneCpeWlanIndexNext OBJECT-TYPE
			SYNTAX Integer32
			MAX-ACCESS read-only
			STATUS current
			DESCRIPTION
				"This object contains an appropriate value to be used for the
				zhoneCpeWlanIndex when creating entries in the zhoneCpeWlanTable.
				The value 0 indicates that no unassigned entries are available. To obtain the
				zhoneCpeWlanIndex value for a new entry, the manager issues a management
				protocol retrieval operation to obtain the current value of this object.  After each
				retrieval, the agent should modify the value to the next unassigned index.
				
				After a manager retrieves a value the agent will determine through its local
				policy when this index value will be made available for reuse."
			::= { zhoneCpeWlan 1 }

		
		-- 1.3.6.1.4.1.5504.5.16.1.23.2
		zhoneCpeWlanTable OBJECT-TYPE
			SYNTAX SEQUENCE OF ZhoneCpeWlanEntry
			MAX-ACCESS not-accessible
			STATUS current
			DESCRIPTION
				"Cpe Wlan table."
			::= { zhoneCpeWlan 2 }

		
		-- 1.3.6.1.4.1.5504.5.16.1.23.2.1
		zhoneCpeWlanEntry OBJECT-TYPE
			SYNTAX ZhoneCpeWlanEntry
			MAX-ACCESS not-accessible
			STATUS current
			DESCRIPTION
				"Row in the Cpe Wlan table."
			INDEX { zhoneCpeWlanIndex }
			::= { zhoneCpeWlanTable 1 }

		
		ZhoneCpeWlanEntry ::=
			SEQUENCE { 
				zhoneCpeWlanIndex
					Unsigned32,
				zhoneCpeWlanRowStatus
					ZhoneRowStatus,
				zhoneCpeWlanProfileName
					ZhoneAdminString,
				zhoneCpeWlanHideAccessPoint
					ZhoneEnabledFlag,
				zhoneCpeWlanIsolateClients
					ZhoneEnabledFlag,
				zhoneCpeWlanWmmAdvertise
					ZhoneEnabledFlag,
				zhoneCpeWlanMcastFwd
					ZhoneEnabledFlag,
				zhoneCpeWlanMaxClients
					Unsigned32,
				zhoneCpeWlanNetAuthentication
					INTEGER,
				zhoneCpeWlanWpaGroupRekeyInterval
					Unsigned32,
				zhoneCpeWlanWpaEncryption
					INTEGER,
				zhoneCpeWlanWepEncryption
					ZhoneEnabledFlag,
				zhoneCpeWlanWepStrength
					INTEGER,
				zhoneCpeWlanRadiusServerIp
					IpAddress,
				zhoneCpeWlanRadiusPort
					Unsigned32,
				zhoneCpeWlanWpa2PreAuthentication
					ZhoneEnabledFlag,
				zhoneCpeWlanNetReAuthenticationInterval
					Unsigned32
			 }

		-- 1.3.6.1.4.1.5504.5.16.1.23.2.1.1
		zhoneCpeWlanIndex OBJECT-TYPE
			SYNTAX Unsigned32 (1..2147483647)
			MAX-ACCESS not-accessible
			STATUS current
			DESCRIPTION
				"This represents the CPE WLAN index value."
			::= { zhoneCpeWlanEntry 1 }

		
		-- 1.3.6.1.4.1.5504.5.16.1.23.2.1.2
		zhoneCpeWlanRowStatus OBJECT-TYPE
			SYNTAX ZhoneRowStatus
			MAX-ACCESS read-create
			STATUS current
			DESCRIPTION
				"Used to create, modify or delete an entry in this table."
			DEFVAL { active }
			::= { zhoneCpeWlanEntry 2 }

		
		-- 1.3.6.1.4.1.5504.5.16.1.23.2.1.3
		zhoneCpeWlanProfileName OBJECT-TYPE
			SYNTAX ZhoneAdminString
			MAX-ACCESS read-create
			STATUS current
			DESCRIPTION
				"This field is only writable upon creation and must be unique within
				its table."
			::= { zhoneCpeWlanEntry 3 }

		
		-- 1.3.6.1.4.1.5504.5.16.1.23.2.1.4
		zhoneCpeWlanHideAccessPoint OBJECT-TYPE
			SYNTAX ZhoneEnabledFlag
			MAX-ACCESS read-create
			STATUS current
			DESCRIPTION
				"Enable or disable the suppression of the advertising of the access point's
				SSID. If enabled, clients will need to configure the SSID to associate."
			DEFVAL { disabled }
			::= { zhoneCpeWlanEntry 4 }

		
		-- 1.3.6.1.4.1.5504.5.16.1.23.2.1.5
		zhoneCpeWlanIsolateClients OBJECT-TYPE
			SYNTAX ZhoneEnabledFlag
			MAX-ACCESS read-create
			STATUS current
			DESCRIPTION
				"Isolate clients within the wireless network from communicating directly
				with each other."
			DEFVAL { disabled }
			::= { zhoneCpeWlanEntry 5 }

		
		-- 1.3.6.1.4.1.5504.5.16.1.23.2.1.6
		zhoneCpeWlanWmmAdvertise OBJECT-TYPE
			SYNTAX ZhoneEnabledFlag
			MAX-ACCESS read-create
			STATUS current
			DESCRIPTION
				"WMM (Wireless Multi Media) provides a subset of the IEEE 802.11e QoS
				standard, which adds prioritization to wireless to optimize their
				performance. When multiple concurrent applications are on the wireless
				network each application may have different latency and throughput needs.
				WMM provides for this optimization, however WMM may provide slower."
			DEFVAL { enabled }
			::= { zhoneCpeWlanEntry 6 }

		
		-- 1.3.6.1.4.1.5504.5.16.1.23.2.1.7
		zhoneCpeWlanMcastFwd OBJECT-TYPE
			SYNTAX ZhoneEnabledFlag
			MAX-ACCESS read-create
			STATUS current
			DESCRIPTION
				"Wireless Multicast Forwarding enables the ability to send wireless
				packets to be intercepted by all nodes in the transmission range of
				the sender."
			DEFVAL { disabled }
			::= { zhoneCpeWlanEntry 7 }

		
		-- 1.3.6.1.4.1.5504.5.16.1.23.2.1.8
		zhoneCpeWlanMaxClients OBJECT-TYPE
			SYNTAX Unsigned32 (1..50)
			MAX-ACCESS read-create
			STATUS current
			DESCRIPTION
				"The maximum number of wireless client devices that may be simultaneously
				connected to the wireless network."
			DEFVAL { 16 }
			::= { zhoneCpeWlanEntry 8 }

		
		-- 1.3.6.1.4.1.5504.5.16.1.23.2.1.9
		zhoneCpeWlanNetAuthentication OBJECT-TYPE
			SYNTAX INTEGER
				{
				open(1),
				shared(2),
				dot1x(3),
				wpa(4),
				wpapsk(5),
				wpa2(6),
				wpa2psk(7),
				mixedwpa2wpa(8),
				mixedwpa2wpapsk(9)
				}
			MAX-ACCESS read-create
			STATUS current
			DESCRIPTION
				"Configure the network authentication method."
			DEFVAL { open }
			::= { zhoneCpeWlanEntry 9 }

		
		-- 1.3.6.1.4.1.5504.5.16.1.23.2.1.10
		zhoneCpeWlanWpaGroupRekeyInterval OBJECT-TYPE
			SYNTAX Unsigned32 (0..2147483647)
			MAX-ACCESS read-create
			STATUS current
			DESCRIPTION
				"Wpa Group Rekey Interval."
			DEFVAL { 0 }
			::= { zhoneCpeWlanEntry 10 }

		
		-- 1.3.6.1.4.1.5504.5.16.1.23.2.1.11
		zhoneCpeWlanWpaEncryption OBJECT-TYPE
			SYNTAX INTEGER
				{
				aes(1),
				tkipaes(2)
				}
			MAX-ACCESS read-create
			STATUS current
			DESCRIPTION
				"WPA encryption mode."
			DEFVAL { aes }
			::= { zhoneCpeWlanEntry 11 }

		
		-- 1.3.6.1.4.1.5504.5.16.1.23.2.1.12
		zhoneCpeWlanWepEncryption OBJECT-TYPE
			SYNTAX ZhoneEnabledFlag
			MAX-ACCESS read-create
			STATUS current
			DESCRIPTION
				"WEP encryption mode."
			DEFVAL { disabled }
			::= { zhoneCpeWlanEntry 12 }

		
		-- 1.3.6.1.4.1.5504.5.16.1.23.2.1.13
		zhoneCpeWlanWepStrength OBJECT-TYPE
			SYNTAX INTEGER
				{
				bit64(1),
				bit128(2)
				}
			MAX-ACCESS read-create
			STATUS current
			DESCRIPTION
				"WEP encryption strength."
			DEFVAL { bit128 }
			::= { zhoneCpeWlanEntry 13 }

		
		-- 1.3.6.1.4.1.5504.5.16.1.23.2.1.14
		zhoneCpeWlanRadiusServerIp OBJECT-TYPE
			SYNTAX IpAddress
			MAX-ACCESS read-create
			STATUS current
			DESCRIPTION
				"IP address of the Remote Authentication Dial In User Server (RADIUS) used
				for 802.1x authentication. Default is 0.0.0.0."
			DEFVAL { '00000000'h }
			::= { zhoneCpeWlanEntry 14 }

		
		-- 1.3.6.1.4.1.5504.5.16.1.23.2.1.15
		zhoneCpeWlanRadiusPort OBJECT-TYPE
			SYNTAX Unsigned32 (0..99999)
			MAX-ACCESS read-create
			STATUS current
			DESCRIPTION
				"UDP port to use for accessing the Remote Authentication Dial In User
				Server (RADIUS)."
			DEFVAL { 1812 }
			::= { zhoneCpeWlanEntry 15 }

		
		-- 1.3.6.1.4.1.5504.5.16.1.23.2.1.16
		zhoneCpeWlanWpa2PreAuthentication OBJECT-TYPE
			SYNTAX ZhoneEnabledFlag
			MAX-ACCESS read-create
			STATUS current
			DESCRIPTION
				"Enable or disable WPA2 pre-authentication."
			DEFVAL { disabled }
			::= { zhoneCpeWlanEntry 16 }

		
		-- 1.3.6.1.4.1.5504.5.16.1.23.2.1.17
		zhoneCpeWlanNetReAuthenticationInterval OBJECT-TYPE
			SYNTAX Unsigned32 (0..2147483647)
			UNITS "seconds"
			MAX-ACCESS read-create
			STATUS current
			DESCRIPTION
				"Configure the WPA2 network re-authentication time, in seconds."
			DEFVAL { 36000 }
			::= { zhoneCpeWlanEntry 17 }

		
		-- 1.3.6.1.4.1.5504.5.16.1.24
		zhoneCpeStaticRouteList OBJECT-IDENTITY
			STATUS current
			DESCRIPTION 
				"Cpe Static Route List objects."
			::= { zhoneCpeObjectID 24 }

		
		-- 1.3.6.1.4.1.5504.5.16.1.24.1
		zhoneCpeStaticRouteListIndexNext OBJECT-TYPE
			SYNTAX Integer32
			MAX-ACCESS read-only
			STATUS current
			DESCRIPTION
				"This object contains an appropriate value to be used for the
				zhoneCpeStaticRouteListIndex when creating entries in the zhoneCpeStaticRouteListTable.
				The value 0 indicates that no unassigned entries are available. To obtain the
				zhoneCpeStaticRouteListIndex value for a new entry, the manager issues a management
				protocol retrieval operation to obtain the current value of this object.  After each
				retrieval, the agent should modify the value to the next unassigned index.
				
				After a manager retrieves a value the agent will determine through its local
				policy when this index value will be made available for reuse."
			::= { zhoneCpeStaticRouteList 1 }

		
		-- 1.3.6.1.4.1.5504.5.16.1.24.2
		zhoneCpeStaticRouteListTable OBJECT-TYPE
			SYNTAX SEQUENCE OF ZhoneCpeStaticRouteListEntry
			MAX-ACCESS not-accessible
			STATUS current
			DESCRIPTION
				"Cpe Static Route List table."
			::= { zhoneCpeStaticRouteList 2 }

		
		-- 1.3.6.1.4.1.5504.5.16.1.24.2.1
		zhoneCpeStaticRouteListEntry OBJECT-TYPE
			SYNTAX ZhoneCpeStaticRouteListEntry
			MAX-ACCESS not-accessible
			STATUS current
			DESCRIPTION
				"Row in the Cpe Static Route List table."
			INDEX { zhoneCpeStaticRouteListIndex }
			::= { zhoneCpeStaticRouteListTable 1 }

		
		ZhoneCpeStaticRouteListEntry ::=
			SEQUENCE { 
				zhoneCpeStaticRouteListIndex
					Unsigned32,
				zhoneCpeStaticRouteListRowStatus
					ZhoneRowStatus,
				zhoneCpeStaticRouteListProfileName
					ZhoneAdminString
			 }

		-- 1.3.6.1.4.1.5504.5.16.1.24.2.1.1
		zhoneCpeStaticRouteListIndex OBJECT-TYPE
			SYNTAX Unsigned32 (1..2147483647)
			MAX-ACCESS not-accessible
			STATUS current
			DESCRIPTION
				"This represents the CPE Static Route List index value."
			::= { zhoneCpeStaticRouteListEntry 1 }

		
		-- 1.3.6.1.4.1.5504.5.16.1.24.2.1.2
		zhoneCpeStaticRouteListRowStatus OBJECT-TYPE
			SYNTAX ZhoneRowStatus
			MAX-ACCESS read-create
			STATUS current
			DESCRIPTION
				"Used to create, modify or delete an entry in this table."
			DEFVAL { active }
			::= { zhoneCpeStaticRouteListEntry 2 }

		
		-- 1.3.6.1.4.1.5504.5.16.1.24.2.1.3
		zhoneCpeStaticRouteListProfileName OBJECT-TYPE
			SYNTAX ZhoneAdminString
			MAX-ACCESS read-create
			STATUS current
			DESCRIPTION
				"CPE Static Route List profile. This field is only writable upon creation
				and must be unique within its table."
			::= { zhoneCpeStaticRouteListEntry 3 }

		
		-- 1.3.6.1.4.1.5504.5.16.1.25
		zhoneCpeStaticRoute OBJECT-IDENTITY
			STATUS current
			DESCRIPTION 
				"Cpe Static Route Entry objects."
			::= { zhoneCpeObjectID 25 }

		
		-- 1.3.6.1.4.1.5504.5.16.1.25.1
		zhoneCpeStaticRouteIndexTable OBJECT-TYPE
			SYNTAX SEQUENCE OF ZhoneCpeStaticRouteIndexEntry
			MAX-ACCESS not-accessible
			STATUS current
			DESCRIPTION
				"Table of next available index values for CPE static route entry profile."
			::= { zhoneCpeStaticRoute 1 }

		
		-- 1.3.6.1.4.1.5504.5.16.1.25.1.1
		zhoneCpeStaticRouteIndexEntry OBJECT-TYPE
			SYNTAX ZhoneCpeStaticRouteIndexEntry
			MAX-ACCESS not-accessible
			STATUS current
			DESCRIPTION
				"Row in the zhoneCpeStaticRouteEntryIndexTable."
			INDEX { zhoneCpeStaticRouteListIndex }
			::= { zhoneCpeStaticRouteIndexTable 1 }

		
		ZhoneCpeStaticRouteIndexEntry ::=
			SEQUENCE { 
				zhoneCpeStaticRouteEntryIndexNext
					Unsigned32
			 }

		-- 1.3.6.1.4.1.5504.5.16.1.25.1.1.1
		zhoneCpeStaticRouteEntryIndexNext OBJECT-TYPE
			SYNTAX Unsigned32
			MAX-ACCESS read-only
			STATUS current
			DESCRIPTION
				"This represents the next available index value for the cpe static route entry
				profile."
			::= { zhoneCpeStaticRouteIndexEntry 1 }

		
		-- 1.3.6.1.4.1.5504.5.16.1.25.2
		zhoneCpeStaticRouteTable OBJECT-TYPE
			SYNTAX SEQUENCE OF ZhoneCpeStaticRouteEntry
			MAX-ACCESS not-accessible
			STATUS current
			DESCRIPTION
				"Cpe Static Route Entry table."
			::= { zhoneCpeStaticRoute 2 }

		
		-- 1.3.6.1.4.1.5504.5.16.1.25.2.1
		zhoneCpeStaticRouteEntry OBJECT-TYPE
			SYNTAX ZhoneCpeStaticRouteEntry
			MAX-ACCESS not-accessible
			STATUS current
			DESCRIPTION
				"Row in the Cpe Static Route Entry table."
			INDEX { zhoneCpeStaticRouteListIndex, zhoneCpeStaticRouteEntryIndex }
			::= { zhoneCpeStaticRouteTable 1 }

		
		ZhoneCpeStaticRouteEntry ::=
			SEQUENCE { 
				zhoneCpeStaticRouteEntryIndex
					Unsigned32,
				zhoneCpeStaticRouteRowStatus
					ZhoneRowStatus,
				zhoneCpeStaticRouteDestinationIp
					IpAddress,
				zhoneCpeStaticRouteNetmask
					IpAddress,
				zhoneCpeStaticRouteGateway
					IpAddress,
				zhoneCpeStaticRouteMetric
					Integer32
			 }

		-- 1.3.6.1.4.1.5504.5.16.1.25.2.1.1
		zhoneCpeStaticRouteEntryIndex OBJECT-TYPE
			SYNTAX Unsigned32 (1..2147483647)
			MAX-ACCESS not-accessible
			STATUS current
			DESCRIPTION
				"This represents the CPE Static Route Entry Entry Index."
			::= { zhoneCpeStaticRouteEntry 1 }

		
		-- 1.3.6.1.4.1.5504.5.16.1.25.2.1.2
		zhoneCpeStaticRouteRowStatus OBJECT-TYPE
			SYNTAX ZhoneRowStatus
			MAX-ACCESS read-create
			STATUS current
			DESCRIPTION
				"Used to create, modify or delete an entry in this table."
			DEFVAL { active }
			::= { zhoneCpeStaticRouteEntry 2 }

		
		-- 1.3.6.1.4.1.5504.5.16.1.25.2.1.3
		zhoneCpeStaticRouteDestinationIp OBJECT-TYPE
			SYNTAX IpAddress
			MAX-ACCESS read-create
			STATUS current
			DESCRIPTION
				"The IP address of the destination network or host.
				Default is 0.0.0.0.
				"
			DEFVAL { '00000000'h }
			::= { zhoneCpeStaticRouteEntry 3 }

		
		-- 1.3.6.1.4.1.5504.5.16.1.25.2.1.4
		zhoneCpeStaticRouteNetmask OBJECT-TYPE
			SYNTAX IpAddress
			MAX-ACCESS read-create
			STATUS current
			DESCRIPTION
				"Destination subnet mask. A value of 0.0.0.0 indicates no destination subnet mask is
				specified. Default is 255.255.255.0."
			DEFVAL { 'ffffff00'h }
			::= { zhoneCpeStaticRouteEntry 4 }

		
		-- 1.3.6.1.4.1.5504.5.16.1.25.2.1.5
		zhoneCpeStaticRouteGateway OBJECT-TYPE
			SYNTAX IpAddress
			MAX-ACCESS read-create
			STATUS current
			DESCRIPTION
				"Next hop IpAddress. Default value is 0.0.0.0."
			DEFVAL { '00000000'h }
			::= { zhoneCpeStaticRouteEntry 5 }

		
		-- 1.3.6.1.4.1.5504.5.16.1.25.2.1.6
		zhoneCpeStaticRouteMetric OBJECT-TYPE
			SYNTAX Integer32 (0..2147483647)
			MAX-ACCESS read-create
			STATUS current
			DESCRIPTION
				"Number of hops to reach the destination. A value of 0 indicates this metric is not used."
			DEFVAL { 1 }
			::= { zhoneCpeStaticRouteEntry 6 }

		
		-- 1.3.6.1.4.1.5504.5.16.1.26
		zhoneCpePortFwdList OBJECT-IDENTITY
			STATUS current
			DESCRIPTION 
				"Cpe Port Fwd List objects."
			::= { zhoneCpeObjectID 26 }

		
		-- 1.3.6.1.4.1.5504.5.16.1.26.1
		zhoneCpePortFwdListIndexNext OBJECT-TYPE
			SYNTAX Integer32
			MAX-ACCESS read-only
			STATUS current
			DESCRIPTION
				"This object contains an appropriate value to be used for the
				zhoneCpePortFwdListIndex when creating entries in the zhoneCpePortFwdListTable.
				The value 0 indicates that no unassigned entries are available. To obtain the
				zhoneCpePortFwdListIndex value for a new entry, the manager issues a management
				protocol retrieval operation to obtain the current value of this object.  After each
				retrieval, the agent should modify the value to the next unassigned index.
				
				After a manager retrieves a value the agent will determine through its local
				policy when this index value will be made available for reuse."
			::= { zhoneCpePortFwdList 1 }

		
		-- 1.3.6.1.4.1.5504.5.16.1.26.2
		zhoneCpePortFwdListTable OBJECT-TYPE
			SYNTAX SEQUENCE OF ZhoneCpePortFwdListEntry
			MAX-ACCESS not-accessible
			STATUS current
			DESCRIPTION
				"Cpe Port Fwd List table."
			::= { zhoneCpePortFwdList 2 }

		
		-- 1.3.6.1.4.1.5504.5.16.1.26.2.1
		zhoneCpePortFwdListEntry OBJECT-TYPE
			SYNTAX ZhoneCpePortFwdListEntry
			MAX-ACCESS not-accessible
			STATUS current
			DESCRIPTION
				"Row in the Cpe Port Fwd List table."
			INDEX { zhoneCpePortFwdListIndex }
			::= { zhoneCpePortFwdListTable 1 }

		
		ZhoneCpePortFwdListEntry ::=
			SEQUENCE { 
				zhoneCpePortFwdListIndex
					Unsigned32,
				zhoneCpePortFwdListRowStatus
					ZhoneRowStatus,
				zhoneCpePortFwdListProfileName
					ZhoneAdminString
			 }

		-- 1.3.6.1.4.1.5504.5.16.1.26.2.1.1
		zhoneCpePortFwdListIndex OBJECT-TYPE
			SYNTAX Unsigned32 (1..2147483647)
			MAX-ACCESS not-accessible
			STATUS current
			DESCRIPTION
				"This represents the CPE Port Fwd List index value."
			::= { zhoneCpePortFwdListEntry 1 }

		
		-- 1.3.6.1.4.1.5504.5.16.1.26.2.1.2
		zhoneCpePortFwdListRowStatus OBJECT-TYPE
			SYNTAX ZhoneRowStatus
			MAX-ACCESS read-create
			STATUS current
			DESCRIPTION
				"Used to create, modify or delete an entry in this table."
			DEFVAL { active }
			::= { zhoneCpePortFwdListEntry 2 }

		
		-- 1.3.6.1.4.1.5504.5.16.1.26.2.1.3
		zhoneCpePortFwdListProfileName OBJECT-TYPE
			SYNTAX ZhoneAdminString
			MAX-ACCESS read-create
			STATUS current
			DESCRIPTION
				"CPE Port Fwd List profile. This field is only writable upon creation
				and must be unique within its table."
			::= { zhoneCpePortFwdListEntry 3 }

		
		-- 1.3.6.1.4.1.5504.5.16.1.27
		zhoneCpePortFwd OBJECT-IDENTITY
			STATUS current
			DESCRIPTION 
				"Cpe Port Fwd Entry objects."
			::= { zhoneCpeObjectID 27 }

		
		-- 1.3.6.1.4.1.5504.5.16.1.27.1
		zhoneCpePortFwdIndexTable OBJECT-TYPE
			SYNTAX SEQUENCE OF ZhoneCpePortFwdIndexEntry
			MAX-ACCESS not-accessible
			STATUS current
			DESCRIPTION
				"Table of next available index values for CPE port fwd entry profile."
			::= { zhoneCpePortFwd 1 }

		
		-- 1.3.6.1.4.1.5504.5.16.1.27.1.1
		zhoneCpePortFwdIndexEntry OBJECT-TYPE
			SYNTAX ZhoneCpePortFwdIndexEntry
			MAX-ACCESS not-accessible
			STATUS current
			DESCRIPTION
				"Row in the zhoneCpePortFwdEntryIndexTable."
			INDEX { zhoneCpePortFwdListIndex }
			::= { zhoneCpePortFwdIndexTable 1 }

		
		ZhoneCpePortFwdIndexEntry ::=
			SEQUENCE { 
				zhoneCpePortFwdEntryIndexNext
					Unsigned32
			 }

		-- 1.3.6.1.4.1.5504.5.16.1.27.1.1.1
		zhoneCpePortFwdEntryIndexNext OBJECT-TYPE
			SYNTAX Unsigned32
			MAX-ACCESS read-only
			STATUS current
			DESCRIPTION
				"This represents the next available index value for the cpe port fwd entry
				profile."
			::= { zhoneCpePortFwdIndexEntry 1 }

		
		-- 1.3.6.1.4.1.5504.5.16.1.27.2
		zhoneCpePortFwdTable OBJECT-TYPE
			SYNTAX SEQUENCE OF ZhoneCpePortFwdEntry
			MAX-ACCESS not-accessible
			STATUS current
			DESCRIPTION
				"Description."
			::= { zhoneCpePortFwd 2 }

		
		-- 1.3.6.1.4.1.5504.5.16.1.27.2.1
		zhoneCpePortFwdEntry OBJECT-TYPE
			SYNTAX ZhoneCpePortFwdEntry
			MAX-ACCESS not-accessible
			STATUS current
			DESCRIPTION
				"Description."
			INDEX { zhoneCpePortFwdListIndex, zhoneCpePortFwdEntryIndex }
			::= { zhoneCpePortFwdTable 1 }

		
		ZhoneCpePortFwdEntry ::=
			SEQUENCE { 
				zhoneCpePortFwdEntryIndex
					Unsigned32,
				zhoneCpePortFwdRowStatus
					ZhoneRowStatus,
				zhoneCpePortFwdType
					INTEGER,
				zhoneCpePortFwdPortStart
					Unsigned32,
				zhoneCpePortFwdPortEnd
					Unsigned32,
				zhoneCpePortFwdProtocol
					INTEGER,
				zhoneCpePortFwdPrivatePort
					Unsigned32,
				zhoneCpePortFwdPrivateIp
					IpAddress
			 }

		-- 1.3.6.1.4.1.5504.5.16.1.27.2.1.1
		zhoneCpePortFwdEntryIndex OBJECT-TYPE
			SYNTAX Unsigned32 (1..2147483647)
			MAX-ACCESS not-accessible
			STATUS current
			DESCRIPTION
				"This represents the CPE Port Fwd Entry Entry Index."
			::= { zhoneCpePortFwdEntry 1 }

		
		-- 1.3.6.1.4.1.5504.5.16.1.27.2.1.2
		zhoneCpePortFwdRowStatus OBJECT-TYPE
			SYNTAX ZhoneRowStatus
			MAX-ACCESS read-create
			STATUS current
			DESCRIPTION
				"Used to create, modify or delete an entry in this table."
			DEFVAL { active }
			::= { zhoneCpePortFwdEntry 2 }

		
		-- 1.3.6.1.4.1.5504.5.16.1.27.2.1.3
		zhoneCpePortFwdType OBJECT-TYPE
			SYNTAX INTEGER
				{
				dmz(1),
				portrange(2),
				portremap(3)
				}
			MAX-ACCESS read-create
			STATUS current
			DESCRIPTION
				"portRange - Range indicates that any traffic on those ports will be sent to the private IP address. 
				portRemap - Remap indicates that any traffic on those ports will be sent to the private IP address at the private port.
				dmz       - When DMZ is chosen it is the only rule allowed on that interface. A DMZ rule is effectively the same as a rule with
				            all ports included. Range rules are more secure than setting
				            a DMZ rule, because Range rules allow ports or groups of
				            ports to be opened up.
				"
			DEFVAL { dmz }
			::= { zhoneCpePortFwdEntry 3 }

		
		-- 1.3.6.1.4.1.5504.5.16.1.27.2.1.4
		zhoneCpePortFwdPortStart OBJECT-TYPE
			SYNTAX Unsigned32 (0..65535)
			MAX-ACCESS read-create
			STATUS current
			DESCRIPTION
				"Lowest value port number for the range."
			DEFVAL { 0 }
			::= { zhoneCpePortFwdEntry 4 }

		
		-- 1.3.6.1.4.1.5504.5.16.1.27.2.1.5
		zhoneCpePortFwdPortEnd OBJECT-TYPE
			SYNTAX Unsigned32 (0..65535)
			MAX-ACCESS read-create
			STATUS current
			DESCRIPTION
				"Highest value port number for the range. This can be equal to port-start
				if there is only one port."
			DEFVAL { 0 }
			::= { zhoneCpePortFwdEntry 5 }

		
		-- 1.3.6.1.4.1.5504.5.16.1.27.2.1.6
		zhoneCpePortFwdProtocol OBJECT-TYPE
			SYNTAX INTEGER
				{
				none(1),
				tcp(2),
				udp(3),
				tcpudp(4),
				icmp(5),
				icmpv4(6)
				}
			MAX-ACCESS read-create
			STATUS current
			DESCRIPTION
				"Indicate which protocols to monitor for the port numbers."
			DEFVAL { none }
			::= { zhoneCpePortFwdEntry 6 }

		
		-- 1.3.6.1.4.1.5504.5.16.1.27.2.1.7
		zhoneCpePortFwdPrivatePort OBJECT-TYPE
			SYNTAX Unsigned32 (0..65535)
			MAX-ACCESS read-create
			STATUS current
			DESCRIPTION
				"The port number with which to send the traffic."
			DEFVAL { 0 }
			::= { zhoneCpePortFwdEntry 7 }

		
		-- 1.3.6.1.4.1.5504.5.16.1.27.2.1.8
		zhoneCpePortFwdPrivateIp OBJECT-TYPE
			SYNTAX IpAddress
			MAX-ACCESS read-create
			STATUS current
			DESCRIPTION
				"The port IP Address with which to send the traffic. The default
				value is 0.0.0.0."
			DEFVAL { '00000000'h }
			::= { zhoneCpePortFwdEntry 8 }

		
		-- 1.3.6.1.4.1.5504.5.16.1.28
		zhoneCpeServiceApplication OBJECT-IDENTITY
			STATUS current
			DESCRIPTION 
				"CPE Service Application for CPEs."
			::= { zhoneCpeObjectID 28 }

		
		-- 1.3.6.1.4.1.5504.5.16.1.28.1
		zhoneCpeServiceApplicationTable OBJECT-TYPE
			SYNTAX SEQUENCE OF ZhoneCpeServiceApplicationEntry
			MAX-ACCESS not-accessible
			STATUS current
			DESCRIPTION
				"Cpe Service Application table for CPEs."
			::= { zhoneCpeServiceApplication 1 }

		
		-- 1.3.6.1.4.1.5504.5.16.1.28.2.1
		zhoneCpeServiceApplicationEntry OBJECT-TYPE
			SYNTAX ZhoneCpeServiceApplicationEntry
			MAX-ACCESS not-accessible
			STATUS current
			DESCRIPTION
				"Row in the CpeServiceApplication table."
			INDEX { zhoneCpeServiceApplicationTemplateType, zhoneCpeServiceApplicationTemplateId, zhoneCpeIfIndex, zhoneCpeServiceApplicationVirtualConnection, zhoneCpeServiceApplicationTpType, 
				zhoneCpeServiceApplicationTpIndex, zhoneCpeServiceApplicationVlan, zhoneCpeServiceApplicationSlan }
			::= { zhoneCpeServiceApplicationTable 1 }

		
		ZhoneCpeServiceApplicationEntry ::=
			SEQUENCE { 
				zhoneCpeServiceApplicationTemplateType
					ZhoneCpeTemplateType,
				zhoneCpeServiceApplicationTemplateId
					Unsigned32,
				zhoneCpeServiceApplicationVirtualConnection
					Unsigned32,
				zhoneCpeServiceApplicationTpType
					TpType,
				zhoneCpeServiceApplicationTpIndex
					Unsigned32,
				zhoneCpeServiceApplicationRowStatus
					ZhoneRowStatus,
				zhoneCpeServiceApplicationVlan
					Unsigned32,
				zhoneCpeServiceApplicationSlan
					Unsigned32
			 }

		-- 1.3.6.1.4.1.5504.5.16.1.28.2.1.1
		zhoneCpeServiceApplicationTemplateType OBJECT-TYPE
			SYNTAX ZhoneCpeTemplateType
			MAX-ACCESS accessible-for-notify
			STATUS current
			DESCRIPTION
				"This represents the Template type associated with the service.
				For example, VOIP, Data, Video, PWE etc. The template type
				is 'internal' for services generated on the device."
			::= { zhoneCpeServiceApplicationEntry 1 }

		
		-- 1.3.6.1.4.1.5504.5.16.1.28.2.1.2
		zhoneCpeServiceApplicationTemplateId OBJECT-TYPE
			SYNTAX Unsigned32 (1..2147483647)
			MAX-ACCESS accessible-for-notify
			STATUS current
			DESCRIPTION
				"This represents the Template id of the cpe service application.
				Template ID is maitntained by the device manager.  Template ID is asigned
				based on the service application configured on the CPE."
			::= { zhoneCpeServiceApplicationEntry 2 }

		
		-- 1.3.6.1.4.1.5504.5.16.1.28.2.1.3
		zhoneCpeServiceApplicationVirtualConnection OBJECT-TYPE
			SYNTAX Unsigned32 (1..2147483647)
			MAX-ACCESS accessible-for-notify
			STATUS current
			DESCRIPTION
				"This represents the Virtual connection of the cpe service application.
				For example, in case of GPON CPE, GEM port is the virtual connection."
			::= { zhoneCpeServiceApplicationEntry 3 }

		
		-- 1.3.6.1.4.1.5504.5.16.1.28.2.1.4
		zhoneCpeServiceApplicationTpType OBJECT-TYPE
			SYNTAX TpType
			MAX-ACCESS accessible-for-notify
			STATUS current
			DESCRIPTION
				"This represents the Transport point (TP) in the CPE.  For example, ethernet, pots etc."
			::= { zhoneCpeServiceApplicationEntry 4 }

		
		-- 1.3.6.1.4.1.5504.5.16.1.28.2.1.5
		zhoneCpeServiceApplicationTpIndex OBJECT-TYPE
			SYNTAX Unsigned32 (1..2147483647)
			MAX-ACCESS accessible-for-notify
			STATUS current
			DESCRIPTION
				"This represents the Transport point (TP) Number associated with the transport point type."
			::= { zhoneCpeServiceApplicationEntry 5 }

		
		-- 1.3.6.1.4.1.5504.5.16.1.28.2.1.6
		zhoneCpeServiceApplicationRowStatus OBJECT-TYPE
			SYNTAX ZhoneRowStatus
			MAX-ACCESS read-create
			STATUS current
			DESCRIPTION
				"Used to create, modify or delete an entry in this table."
			DEFVAL { active }
			::= { zhoneCpeServiceApplicationEntry 6 }

		
		-- 1.3.6.1.4.1.5504.5.16.1.28.2.1.7
		zhoneCpeServiceApplicationVlan OBJECT-TYPE
			SYNTAX Unsigned32
			MAX-ACCESS accessible-for-notify
			STATUS current
			DESCRIPTION
				"This field consists of vlan-cos (high-order 2 bytes) and 
				vlan-id (low-order 2 bytes)."
			::= { zhoneCpeServiceApplicationEntry 7 }

		
		-- 1.3.6.1.4.1.5504.5.16.1.28.2.1.8
		zhoneCpeServiceApplicationSlan OBJECT-TYPE
			SYNTAX Unsigned32
			MAX-ACCESS accessible-for-notify
			STATUS current
			DESCRIPTION
				"This field consists of vlan-cos (high-order 2 bytes) and 
				vlan-id (low-order 2 bytes)."
			::= { zhoneCpeServiceApplicationEntry 8 }

		
		-- 1.3.6.1.4.1.5504.5.16.1.29
		zhoneCpeDnsHostList OBJECT-IDENTITY
			STATUS current
			DESCRIPTION 
				"Dns Host List Objects."
			::= { zhoneCpeObjectID 29 }

		
		-- 1.3.6.1.4.1.5504.5.16.1.29.1
		zhoneCpeDnsHostListIndexNext OBJECT-TYPE
			SYNTAX Integer32
			MAX-ACCESS read-only
			STATUS current
			DESCRIPTION
				"This object contains an appropriate value to be used for the
				zhoneCpeDnsHostListIndex when creating entries in the zhoneCpeDnsHostListTable.
				The value 0 indicates that no unassigned entries are available. To obtain the
				zhoneCpeDnsHostListIndex value for a new entry, the manager issues a management
				protocol retrieval operation to obtain the current value of this object.  After each
				retrieval, the agent should modify the value to the next unassigned index.
				
				After a manager retrieves a value the agent will determine through its local
				policy when this index value will be made available for reuse."
			::= { zhoneCpeDnsHostList 1 }

		
		-- 1.3.6.1.4.1.5504.5.16.1.29.2
		zhoneCpeDnsHostListTable OBJECT-TYPE
			SYNTAX SEQUENCE OF ZhoneCpeDnsHostListEntry
			MAX-ACCESS not-accessible
			STATUS current
			DESCRIPTION
				"The table of DNS host lists."
			::= { zhoneCpeDnsHostList 2 }

		
		-- 1.3.6.1.4.1.5504.5.16.1.29.2.1
		zhoneCpeDnsHostListEntry OBJECT-TYPE
			SYNTAX ZhoneCpeDnsHostListEntry
			MAX-ACCESS not-accessible
			STATUS current
			DESCRIPTION
				"Row in the zhoneCpeDnsHostList table."
			INDEX { zhoneCpeDnsHostListIndex }
			::= { zhoneCpeDnsHostListTable 1 }

		
		ZhoneCpeDnsHostListEntry ::=
			SEQUENCE { 
				zhoneCpeDnsHostListIndex
					Unsigned32,
				zhoneCpeDnsHostListRowStatus
					RowStatus,
				zhoneCpeDnsHostListProfileName
					ZhoneAdminString
			 }

		-- 1.3.6.1.4.1.5504.5.16.1.29.2.1.2
		zhoneCpeDnsHostListIndex OBJECT-TYPE
			SYNTAX Unsigned32
			MAX-ACCESS not-accessible
			STATUS current
			DESCRIPTION
				"Index number for the zhoneCpeDnsHostList table entry."
			::= { zhoneCpeDnsHostListEntry 2 }

		
		-- 1.3.6.1.4.1.5504.5.16.1.29.2.1.3
		zhoneCpeDnsHostListRowStatus OBJECT-TYPE
			SYNTAX RowStatus
			MAX-ACCESS read-create
			STATUS current
			DESCRIPTION
				"Used to create, modify or delete an entry in this table."
			DEFVAL { active }
			::= { zhoneCpeDnsHostListEntry 3 }

		
		-- 1.3.6.1.4.1.5504.5.16.1.29.2.1.4
		zhoneCpeDnsHostListProfileName OBJECT-TYPE
			SYNTAX ZhoneAdminString
			MAX-ACCESS read-create
			STATUS current
			DESCRIPTION
				"Profile name for this cpe-dns-host profile. This must be 
				unique, and is writable only on creation."
			::= { zhoneCpeDnsHostListEntry 4 }

		
		-- 1.3.6.1.4.1.5504.5.16.1.30
		zhoneCpeDnsHost OBJECT-IDENTITY
			STATUS current
			DESCRIPTION 
				"Cpe Dns host objects."
			::= { zhoneCpeObjectID 30 }

		
		-- 1.3.6.1.4.1.5504.5.16.1.30.1
		zhoneCpeDnsHostIndexTable OBJECT-TYPE
			SYNTAX SEQUENCE OF ZhoneCpeDnsHostIndexEntry
			MAX-ACCESS not-accessible
			STATUS current
			DESCRIPTION
				"Table of next available values for Dns Host Entry index."
			::= { zhoneCpeDnsHost 1 }

		
		-- 1.3.6.1.4.1.5504.5.16.1.30.1.1
		zhoneCpeDnsHostIndexEntry OBJECT-TYPE
			SYNTAX ZhoneCpeDnsHostIndexEntry
			MAX-ACCESS not-accessible
			STATUS current
			DESCRIPTION
				"Row in the zhoneCpeDnsHostIndex table."
			INDEX { zhoneCpeDnsHostListIndex }
			::= { zhoneCpeDnsHostIndexTable 1 }

		
		ZhoneCpeDnsHostIndexEntry ::=
			SEQUENCE { 
				zhoneCpeDnsHostIndexEntryIndexNext
					Integer32
			 }

		-- 1.3.6.1.4.1.5504.5.16.1.30.1.1.1
		zhoneCpeDnsHostIndexEntryIndexNext OBJECT-TYPE
			SYNTAX Integer32
			MAX-ACCESS read-only
			STATUS current
			DESCRIPTION
				"Next available entry index for row in zhoneCpeDnsHostTable."
			::= { zhoneCpeDnsHostIndexEntry 1 }

		
		-- 1.3.6.1.4.1.5504.5.16.1.30.2
		zhoneCpeDnsHostTable OBJECT-TYPE
			SYNTAX SEQUENCE OF ZhoneCpeDnsHostEntry
			MAX-ACCESS not-accessible
			STATUS current
			DESCRIPTION
				"The table of Cpe Dns Host entries."
			::= { zhoneCpeDnsHost 2 }

		
		-- 1.3.6.1.4.1.5504.5.16.1.30.2.1
		zhoneCpeDnsHostEntry OBJECT-TYPE
			SYNTAX ZhoneCpeDnsHostEntry
			MAX-ACCESS not-accessible
			STATUS current
			DESCRIPTION
				"A row in the Cpe Dns Host table."
			INDEX { zhoneCpeDnsHostListIndex, zhoneCpeDnsHostEntryIndex }
			::= { zhoneCpeDnsHostTable 1 }

		
		ZhoneCpeDnsHostEntry ::=
			SEQUENCE { 
				zhoneCpeDnsHostEntryIndex
					Unsigned32,
				zhoneCpeDnsHostRowStatus
					RowStatus,
				zhoneCpeDnsHostDomainName
					OCTET STRING,
				zhoneCpeDnsHostIpAddress
					IpAddress
			 }

		-- 1.3.6.1.4.1.5504.5.16.1.30.2.1.1
		zhoneCpeDnsHostEntryIndex OBJECT-TYPE
			SYNTAX Unsigned32
			MAX-ACCESS not-accessible
			STATUS current
			DESCRIPTION
				"Index for this entry within the CpeDnsHost list."
			::= { zhoneCpeDnsHostEntry 1 }

		
		-- 1.3.6.1.4.1.5504.5.16.1.30.2.1.2
		zhoneCpeDnsHostRowStatus OBJECT-TYPE
			SYNTAX RowStatus
			MAX-ACCESS read-create
			STATUS current
			DESCRIPTION
				"Used to create, modify or delete an entry in this table."
			DEFVAL { active }
			::= { zhoneCpeDnsHostEntry 2 }

		
		-- 1.3.6.1.4.1.5504.5.16.1.30.2.1.3
		zhoneCpeDnsHostDomainName OBJECT-TYPE
			SYNTAX OCTET STRING (SIZE (0..256))
			MAX-ACCESS read-create
			STATUS current
			DESCRIPTION
				"The domain name assigned to the host IP address.
				
				 
				
				"
			::= { zhoneCpeDnsHostEntry 3 }

		
		-- 1.3.6.1.4.1.5504.5.16.1.30.2.1.4
		zhoneCpeDnsHostIpAddress OBJECT-TYPE
			SYNTAX IpAddress
			MAX-ACCESS read-create
			STATUS current
			DESCRIPTION
				"Host IP address."
			::= { zhoneCpeDnsHostEntry 4 }

		
		-- 1.3.6.1.4.1.5504.5.16.1.31
		zhoneCpeWlanAdvanced OBJECT-IDENTITY
			STATUS current
			DESCRIPTION 
				"Cpe Wlan Advanced objects."
			::= { zhoneCpeObjectID 31 }

		
		-- 1.3.6.1.4.1.5504.5.16.1.31.1
		zhoneCpeWlanAdvIndexNext OBJECT-TYPE
			SYNTAX Integer32
			MAX-ACCESS read-only
			STATUS current
			DESCRIPTION
				"This object contains an appropriate value to be used for the
				zhoneCpeWlanIndex when creating entries in the zhoneCpeWlanTable.
				The value 0 indicates that no unassigned entries are available. To obtain the
				zhoneCpeWlanIndex value for a new entry, the manager issues a management
				protocol retrieval operation to obtain the current value of this object.  After each
				retrieval, the agent should modify the value to the next unassigned index.
				
				After a manager retrieves a value the agent will determine through its local
				policy when this index value will be made available for reuse."
			::= { zhoneCpeWlanAdvanced 1 }

		
		-- 1.3.6.1.4.1.5504.5.16.1.31.2
		zhoneCpeWlanAdvancedTable OBJECT-TYPE
			SYNTAX SEQUENCE OF ZhoneCpeWlanAdvancedEntry
			MAX-ACCESS not-accessible
			STATUS current
			DESCRIPTION
				"Cpe Wlan Advanced table."
			::= { zhoneCpeWlanAdvanced 2 }

		
		-- 1.3.6.1.4.1.5504.5.16.1.31.2.1
		zhoneCpeWlanAdvancedEntry OBJECT-TYPE
			SYNTAX ZhoneCpeWlanAdvancedEntry
			MAX-ACCESS not-accessible
			STATUS current
			DESCRIPTION
				"Row in the Cpe Wlan Advanced table."
			INDEX { zhoneCpeWlanAdvIndex }
			::= { zhoneCpeWlanAdvancedTable 1 }

		
		ZhoneCpeWlanAdvancedEntry ::=
			SEQUENCE { 
				zhoneCpeWlanAdvIndex
					Unsigned32,
				zhoneCpeWlanAdvRowStatus
					ZhoneRowStatus,
				zhoneCpeWlanAdvProfileName
					ZhoneAdminString,
				zhoneCpeWlanAdvChannel
					INTEGER,
				zhoneCpeWlanAdvAutoChanTimer
					Unsigned32,
				zhoneCpeWlanAdvDot11nMode
					INTEGER,
				zhoneCpeWlanAdvDot11nRate
					INTEGER,
				zhoneCpeWlanAdvDot1nProtection
					INTEGER,
				zhoneCpeWlanAdvDot1nClientOnly
					ZhoneEnabledFlag,
				zhoneCpeWlanAdvRate54G
					INTEGER,
				zhoneCpeWlanAdvMcastRate
					INTEGER,
				zhoneCpeWlanAdvBasicRate
					INTEGER,
				zhoneCpeWlanAdvFragmentationThreshold
					Unsigned32,
				zhoneCpeWlanAdvRtsThreshold
					Unsigned32,
				zhoneCpeWlanAdvDtimInterval
					Unsigned32,
				zhoneCpeWlanAdvBeaconInterval
					Unsigned32,
				zhoneCpeWlanAdvGlobalMaxClients
					Unsigned32,
				zhoneCpeWlanAdvXpressTechnology
					ZhoneEnabledFlag,
				zhoneCpeWlanAdvTxPower
					Unsigned32,
				zhoneCpeWlanAdvWmm
					ZhoneEnabledFlag,
				zhoneCpeWlanAdvWmmNoAck
					ZhoneEnabledFlag,
				zhoneCpeWlanAdvWmmApsd
					ZhoneEnabledFlag,
				zhoneCpeWlanAdvApMode
					INTEGER,
				zhoneCpeWlanAdvBridgeRestrict
					INTEGER,
				zhoneCpeWlanAdvWps
					ZhoneEnabledFlag,
				zhoneCpeWlanAdvWpsAddClientMethod
					INTEGER,
				zhoneCpeWlanAdvWpsApMode
					INTEGER,
				zhoneCpeWlanAdvDualBandCfgBands
					WlDualBandCfgBands,
				zhoneCpeWlanAdvDualBandCfgRegModes
					WlDualBandCfgRegModes,
				zhoneCpeWlanAdvDualBandPreNetworkRadarCheck
					INTEGER,
				zhoneCpeWlanAdvDualBandInNetworkRadarCheck
					INTEGER,
				zhoneCpeWlanAdvDualBandCfgTpcMitigationModes
					WlDualBandCfgTpcMitigationLevels,
				zhoneCpeWlanAdvCfgBandwidth
					INTEGER,
				zhoneCpeWlanAdvBeamformingTx
					TruthValue,
				zhoneCpeWlanAdvBeamformingRx
					TruthValue,
				zhoneCpeWlanAdvPhysicalRadioInterface
					ZhoneEnabledFlag
			 }

		-- 1.3.6.1.4.1.5504.5.16.1.31.2.1.1
		zhoneCpeWlanAdvIndex OBJECT-TYPE
			SYNTAX Unsigned32 (1..2147483647)
			MAX-ACCESS not-accessible
			STATUS current
			DESCRIPTION
				"This represents the CPE WLAN Advanced index value."
			::= { zhoneCpeWlanAdvancedEntry 1 }

		
		-- 1.3.6.1.4.1.5504.5.16.1.31.2.1.2
		zhoneCpeWlanAdvRowStatus OBJECT-TYPE
			SYNTAX ZhoneRowStatus
			MAX-ACCESS read-create
			STATUS current
			DESCRIPTION
				"Used to create, modify or delete an entry in this table."
			DEFVAL { active }
			::= { zhoneCpeWlanAdvancedEntry 2 }

		
		-- 1.3.6.1.4.1.5504.5.16.1.31.2.1.3
		zhoneCpeWlanAdvProfileName OBJECT-TYPE
			SYNTAX ZhoneAdminString
			MAX-ACCESS read-create
			STATUS current
			DESCRIPTION
				"This field is only writable upon creation and must be unique within
				its table."
			::= { zhoneCpeWlanAdvancedEntry 3 }

		
		-- 1.3.6.1.4.1.5504.5.16.1.31.2.1.4
		zhoneCpeWlanAdvChannel OBJECT-TYPE
			SYNTAX INTEGER
				{
				auto(1),
				c1(2),
				c2(3),
				c3(4),
				c4(5),
				c5(6),
				c6(7),
				c7(8),
				c8(9),
				c9(10),
				c10(11),
				c11(12),
				c12(13),
				c13(14)
				}
			MAX-ACCESS read-create
			STATUS current
			DESCRIPTION
				"Defines which channel to use, or 'auto' for automatic selection of a
				channel with low interference. 802.11b and 802.11g use channels to limit
				interference from other devices. "
			DEFVAL { auto }
			::= { zhoneCpeWlanAdvancedEntry 4 }

		
		-- 1.3.6.1.4.1.5504.5.16.1.31.2.1.5
		zhoneCpeWlanAdvAutoChanTimer OBJECT-TYPE
			SYNTAX Unsigned32 (0..2147483647)
			MAX-ACCESS read-create
			STATUS current
			DESCRIPTION
				"When configured for auto mode, this timer value specifies how often
				(in minutes) to re-analyze the spectrum to select a low interference
				channel. Note: auto channel rescan will only occur when there are no
				actively connected devices."
			DEFVAL { 15 }
			::= { zhoneCpeWlanAdvancedEntry 5 }

		
		-- 1.3.6.1.4.1.5504.5.16.1.31.2.1.6
		zhoneCpeWlanAdvDot11nMode OBJECT-TYPE
			SYNTAX INTEGER
				{
				auto(1),
				disabled(2)
				}
			MAX-ACCESS read-create
			STATUS current
			DESCRIPTION
				"802.11n MIMO EWC modes of operation. 802.11n improves data rates via MIMO
				(multiple-input, multiple-output) using spatial streams which each have a
				channel width of 40 MHz or 20 MHz. Usage of 802.11n in the 2.4 and 5GHz
				modes should depend on interference with other 802.11 or bluetooth systems
				on the same frequency. Enhanced Wireless Consortium (EWC) provides extra
				enhancements (adding the ability to define 20 MHz channels)."
			DEFVAL { auto }
			::= { zhoneCpeWlanAdvancedEntry 6 }

		
		-- 1.3.6.1.4.1.5504.5.16.1.31.2.1.7
		zhoneCpeWlanAdvDot11nRate OBJECT-TYPE
			SYNTAX INTEGER
				{
				auto(1),
				use54g(2),
				rate6dot5m(3),
				rate13m(4),
				rate19dot5m(5),
				rate26m(6),
				rate39m(7),
				rate58dot5m(9),
				rate65m(10),
				rate78m(11),
				rate104m(12),
				rate117m(13),
				rate130m(14)
				}
			MAX-ACCESS read-create
			STATUS current
			DESCRIPTION
				"Supported 802.11n MIMO rates, in Mbps."
			DEFVAL { auto }
			::= { zhoneCpeWlanAdvancedEntry 7 }

		
		-- 1.3.6.1.4.1.5504.5.16.1.31.2.1.8
		zhoneCpeWlanAdvDot1nProtection OBJECT-TYPE
			SYNTAX INTEGER
				{
				auto(1),
				disabled(2)
				}
			MAX-ACCESS read-create
			STATUS current
			DESCRIPTION
				"802.11n MIMO protection modes."
			DEFVAL { auto }
			::= { zhoneCpeWlanAdvancedEntry 8 }

		
		-- 1.3.6.1.4.1.5504.5.16.1.31.2.1.9
		zhoneCpeWlanAdvDot1nClientOnly OBJECT-TYPE
			SYNTAX ZhoneEnabledFlag
			MAX-ACCESS read-create
			STATUS current
			DESCRIPTION
				"Enable or disable the restriction of access to 802.11n clients, only.
				When enabled, prevent 802.11b/g clients from connecting."
			DEFVAL { disabled }
			::= { zhoneCpeWlanAdvancedEntry 9 }

		
		-- 1.3.6.1.4.1.5504.5.16.1.31.2.1.10
		zhoneCpeWlanAdvRate54G OBJECT-TYPE
			SYNTAX INTEGER
				{
				auto(1),
				rate1m(2),
				rate2m(3),
				rate5dot5m(4),
				rate6m(5),
				rate9m(6),
				rate11m(7),
				rate12m(8),
				rate18m(9),
				rate24m(10),
				rate36m(11),
				rate48m(12),
				rate54m(13)
				}
			MAX-ACCESS read-create
			STATUS current
			DESCRIPTION
				"The rate when the radio is operating in 802.11g mode. This object only
				applies when the Multiple Input Multiple Output (MIMO) 802.11n Rate is
				set to use 54g."
			DEFVAL { auto }
			::= { zhoneCpeWlanAdvancedEntry 10 }

		
		-- 1.3.6.1.4.1.5504.5.16.1.31.2.1.11
		zhoneCpeWlanAdvMcastRate OBJECT-TYPE
			SYNTAX INTEGER
				{
				auto(1),
				rate1m(2),
				rate2m(3),
				rate5dot5m(4),
				rate6m(5),
				rate9m(6),
				rate11m(7),
				rate12m(8),
				rate18m(9),
				rate24m(10),
				rate36m(11),
				rate48m(12),
				rate54m(13)
				}
			MAX-ACCESS read-create
			STATUS current
			DESCRIPTION
				"The rate for the multicast traffic."
			DEFVAL { auto }
			::= { zhoneCpeWlanAdvancedEntry 11 }

		
		-- 1.3.6.1.4.1.5504.5.16.1.31.2.1.12
		zhoneCpeWlanAdvBasicRate OBJECT-TYPE
			SYNTAX INTEGER
				{
				default(1),
				all(2),
				rate1n2(3),
				stdrates(4)
				}
			MAX-ACCESS read-create
			STATUS current
			DESCRIPTION
				"The rate when the radio is operating in basic 802.11b/g mode."
			DEFVAL { default }
			::= { zhoneCpeWlanAdvancedEntry 12 }

		
		-- 1.3.6.1.4.1.5504.5.16.1.31.2.1.13
		zhoneCpeWlanAdvFragmentationThreshold OBJECT-TYPE
			SYNTAX Unsigned32 (256..2346)
			MAX-ACCESS read-create
			STATUS current
			DESCRIPTION
				"The threshold at which the packets are fragmented."
			DEFVAL { 2346 }
			::= { zhoneCpeWlanAdvancedEntry 13 }

		
		-- 1.3.6.1.4.1.5504.5.16.1.31.2.1.14
		zhoneCpeWlanAdvRtsThreshold OBJECT-TYPE
			SYNTAX Unsigned32 (0..2347)
			MAX-ACCESS read-create
			STATUS current
			DESCRIPTION
				"The packet size of a request-to-send (RTS) transmission. A low threshold
				implies RTS packets are sent more frequently, thus requiring more
				bandwidth but ensuring packet transmission on a busy network."
			DEFVAL { 2347 }
			::= { zhoneCpeWlanAdvancedEntry 14 }

		
		-- 1.3.6.1.4.1.5504.5.16.1.31.2.1.15
		zhoneCpeWlanAdvDtimInterval OBJECT-TYPE
			SYNTAX Unsigned32 (1..255)
			MAX-ACCESS read-create
			STATUS current
			DESCRIPTION
				"The interval at which Delivery Traffic Indication Messages (DTIM) are
				generated. A DTIM message notifies a wireless client that a packet is
				waiting for transmission."
			DEFVAL { 1 }
			::= { zhoneCpeWlanAdvancedEntry 15 }

		
		-- 1.3.6.1.4.1.5504.5.16.1.31.2.1.16
		zhoneCpeWlanAdvBeaconInterval OBJECT-TYPE
			SYNTAX Unsigned32 (1..65535)
			MAX-ACCESS read-create
			STATUS current
			DESCRIPTION
				"The interval at which Beacons are generated."
			DEFVAL { 100 }
			::= { zhoneCpeWlanAdvancedEntry 16 }

		
		-- 1.3.6.1.4.1.5504.5.16.1.31.2.1.17
		zhoneCpeWlanAdvGlobalMaxClients OBJECT-TYPE
			SYNTAX Unsigned32 (1..128)
			MAX-ACCESS read-create
			STATUS current
			DESCRIPTION
				"The maximum number of wireless client devices that may be simultaneously
				connected to the radio. This value should include the sum total of all
				active SSIDs."
			DEFVAL { 50 }
			::= { zhoneCpeWlanAdvancedEntry 17 }

		
		-- 1.3.6.1.4.1.5504.5.16.1.31.2.1.18
		zhoneCpeWlanAdvXpressTechnology OBJECT-TYPE
			SYNTAX ZhoneEnabledFlag
			MAX-ACCESS read-create
			STATUS current
			DESCRIPTION
				"Enable or disable the XPress(TM) Technology."
			DEFVAL { disabled }
			::= { zhoneCpeWlanAdvancedEntry 18 }

		
		-- 1.3.6.1.4.1.5504.5.16.1.31.2.1.19
		zhoneCpeWlanAdvTxPower OBJECT-TYPE
			SYNTAX Unsigned32 (1..100)
			MAX-ACCESS read-create
			STATUS current
			DESCRIPTION
				"The percentage of total power that should be used for data transmissions."
			DEFVAL { 100 }
			::= { zhoneCpeWlanAdvancedEntry 19 }

		
		-- 1.3.6.1.4.1.5504.5.16.1.31.2.1.20
		zhoneCpeWlanAdvWmm OBJECT-TYPE
			SYNTAX ZhoneEnabledFlag
			MAX-ACCESS read-create
			STATUS current
			DESCRIPTION
				"Enable or disable Wifi Multimedia. When set to TRUE, audio, video and
				voice application data is prioritized over other network traffic."
			DEFVAL { enabled }
			::= { zhoneCpeWlanAdvancedEntry 20 }

		
		-- 1.3.6.1.4.1.5504.5.16.1.31.2.1.21
		zhoneCpeWlanAdvWmmNoAck OBJECT-TYPE
			SYNTAX ZhoneEnabledFlag
			MAX-ACCESS read-create
			STATUS current
			DESCRIPTION
				"Enable or disable the suppression of acknowledgements for frames that do
				not require a QOS Acknowledgement. This avoids the unnecessary
				transmission of acknowledgements for highly time-critical data."
			DEFVAL { disabled }
			::= { zhoneCpeWlanAdvancedEntry 21 }

		
		-- 1.3.6.1.4.1.5504.5.16.1.31.2.1.22
		zhoneCpeWlanAdvWmmApsd OBJECT-TYPE
			SYNTAX ZhoneEnabledFlag
			MAX-ACCESS read-create
			STATUS current
			DESCRIPTION
				"Enable or disable the Automatic Power Save Delivery (APSD) power
				management method. This feature is useful for bi-directional applications,
				such as VoIp phones."
			DEFVAL { enabled }
			::= { zhoneCpeWlanAdvancedEntry 22 }

		
		-- 1.3.6.1.4.1.5504.5.16.1.31.2.1.23
		zhoneCpeWlanAdvApMode OBJECT-TYPE
			SYNTAX INTEGER
				{
				accesspoint(1),
				wirelessbridge(2)
				}
			MAX-ACCESS read-create
			STATUS current
			DESCRIPTION
				"Wireless bridge modes of operation."
			DEFVAL { accesspoint }
			::= { zhoneCpeWlanAdvancedEntry 23 }

		
		-- 1.3.6.1.4.1.5504.5.16.1.31.2.1.24
		zhoneCpeWlanAdvBridgeRestrict OBJECT-TYPE
			SYNTAX INTEGER
				{
				enabled(1),
				enabledscan(2),
				disabled(3)
				}
			MAX-ACCESS read-create
			STATUS current
			DESCRIPTION
				"Wireless Bridge Restriction Modes of operation."
			DEFVAL { disabled }
			::= { zhoneCpeWlanAdvancedEntry 24 }

		
		-- 1.3.6.1.4.1.5504.5.16.1.31.2.1.25
		zhoneCpeWlanAdvWps OBJECT-TYPE
			SYNTAX ZhoneEnabledFlag
			MAX-ACCESS read-create
			STATUS current
			DESCRIPTION
				"Enable or disable WiFi Protected Setup (WPS) security method. If WPS is
				enabled, the network authentication method, the data encryption, and
				network key should also be configured in order to authenticate to this
				wireless network. It is available for WPA-PSK, WPA2-PSK,
				Mixed WPA2/WPA-PSK and Open Network Authentication methods."
			DEFVAL { disabled }
			::= { zhoneCpeWlanAdvancedEntry 25 }

		
		-- 1.3.6.1.4.1.5504.5.16.1.31.2.1.26
		zhoneCpeWlanAdvWpsAddClientMethod OBJECT-TYPE
			SYNTAX INTEGER
				{
				pushbutton(1),
				stapin(2),
				appin(3)
				}
			MAX-ACCESS read-create
			STATUS current
			DESCRIPTION
				"A client can be added via three different methods."
			DEFVAL { pushbutton }
			::= { zhoneCpeWlanAdvancedEntry 26 }

		
		-- 1.3.6.1.4.1.5504.5.16.1.31.2.1.27
		zhoneCpeWlanAdvWpsApMode OBJECT-TYPE
			SYNTAX INTEGER
				{
				configured(1),
				unconfigured(2)
				}
			MAX-ACCESS read-create
			STATUS current
			DESCRIPTION
				"If the provider is using an external registrar for security, select
				configured. The PIN for AP mode is specified by the registrar. Provide
				this PIN to the client. Issue Config AP to begin the registration process
				with the client."
			DEFVAL { configured }
			::= { zhoneCpeWlanAdvancedEntry 27 }

		
		-- 1.3.6.1.4.1.5504.5.16.1.31.2.1.28
		zhoneCpeWlanAdvDualBandCfgBands OBJECT-TYPE
			SYNTAX WlDualBandCfgBands
			MAX-ACCESS read-create
			STATUS current
			DESCRIPTION
				"Broadcast Operational Bands supported by a dual-band radio:
				    bandUndefined(1)
				    band2Dot4GHz(2)   
				    band5GHz(3)"
			DEFVAL { band2Dot4GHz }
			::= { zhoneCpeWlanAdvancedEntry 28 }

		
		-- 1.3.6.1.4.1.5504.5.16.1.31.2.1.29
		zhoneCpeWlanAdvDualBandCfgRegModes OBJECT-TYPE
			SYNTAX WlDualBandCfgRegModes
			MAX-ACCESS read-create
			STATUS current
			DESCRIPTION
				"Regulatory modes supported by a dual-band radio:
				    regModeDisabled(1)
				    regMode802Dot11h(2)
				    regMode802Dot11d(3)"
			DEFVAL { regModeDisabled }
			::= { zhoneCpeWlanAdvancedEntry 29 }

		
		-- 1.3.6.1.4.1.5504.5.16.1.31.2.1.30
		zhoneCpeWlanAdvDualBandPreNetworkRadarCheck OBJECT-TYPE
			SYNTAX INTEGER (-1..99)
			MAX-ACCESS read-create
			STATUS current
			DESCRIPTION
				"802.11h Pre-Network Radar Check. A value of (-1) disables 
				pre-network checks."
			DEFVAL { -1 }
			::= { zhoneCpeWlanAdvancedEntry 30 }

		
		-- 1.3.6.1.4.1.5504.5.16.1.31.2.1.31
		zhoneCpeWlanAdvDualBandInNetworkRadarCheck OBJECT-TYPE
			SYNTAX INTEGER (-1..99)
			MAX-ACCESS read-create
			STATUS current
			DESCRIPTION
				"802.11h In-Network Radar Check. A value of (-1) disables 
				in-network checks."
			DEFVAL { -1 }
			::= { zhoneCpeWlanAdvancedEntry 31 }

		
		-- 1.3.6.1.4.1.5504.5.16.1.31.2.1.32
		zhoneCpeWlanAdvDualBandCfgTpcMitigationModes OBJECT-TYPE
			SYNTAX WlDualBandCfgTpcMitigationLevels
			MAX-ACCESS read-create
			STATUS current
			DESCRIPTION
				"802.11h Transmission Power Control (TPC) is used to automatically
				adjust the transmission power level on 5.0-GHz radios to avoid
				interfering with radar and satellites. TPC mitigation levels 
				supported:
				    tpcOff(1)
				    tpc2dB(2)
				    tpc3dB(3)
				    tpc4dB(4)"
			DEFVAL { tpcOff }
			::= { zhoneCpeWlanAdvancedEntry 32 }

		
		-- 1.3.6.1.4.1.5504.5.16.1.31.2.1.33
		zhoneCpeWlanAdvCfgBandwidth OBJECT-TYPE
			SYNTAX INTEGER
				{
				bandwidth20MHz(1),
				bandwidth40MHz(2),
				bandwidth20In2GAnd40In5G(3),
				bandwidth80MHz(4)
				}
			MAX-ACCESS read-create
			STATUS current
			DESCRIPTION
				"Aggregate radio bandwidth setting as 20MHz/40MHz/20In2GAnd40In5G/80MHz"
			DEFVAL { bandwidth20MHz }
			::= { zhoneCpeWlanAdvancedEntry 33 }

		
		-- 1.3.6.1.4.1.5504.5.16.1.31.2.1.34
		zhoneCpeWlanAdvBeamformingTx OBJECT-TYPE
			SYNTAX TruthValue
			MAX-ACCESS read-create
			STATUS current
			DESCRIPTION
				"Beamforming Transmission (BFR): Enable Beamformer on the 5GHz radio.Beamforming 
				or spatial filtering is a signal processing technique used in sensor arrays for 
				directional signal transmission or reception."
			DEFVAL { false }
			::= { zhoneCpeWlanAdvancedEntry 34 }

		
		-- 1.3.6.1.4.1.5504.5.16.1.31.2.1.35
		zhoneCpeWlanAdvBeamformingRx OBJECT-TYPE
			SYNTAX TruthValue
			MAX-ACCESS read-create
			STATUS current
			DESCRIPTION
				"Beamforming Reception (BFE): Enable Beamformee on the 5GHz radio.Beamforming 
				or spatial filtering is a signal processing technique used in sensor arrays 
				for directional signal transmission or reception."
			DEFVAL { false }
			::= { zhoneCpeWlanAdvancedEntry 35 }

		
-- 
-- 
		-- 1.3.6.1.4.1.5504.5.16.1.31.2.1.36
		zhoneCpeWlanAdvPhysicalRadioInterface OBJECT-TYPE
			SYNTAX ZhoneEnabledFlag
			MAX-ACCESS read-create
			STATUS current
			DESCRIPTION
				"This attribute enables or disables the physical radio of the CPE.When enabled,
				the primary Wireless LAN interface and all Wireless Virtual LAN interfaces associated
				with the radio are enabled. When disabled, the radio transmitter is disabled and
				all Wireless LAN interfaces associated with the radio are disabled."
			DEFVAL { enabled }
			::= { zhoneCpeWlanAdvancedEntry 36 }

		
		-- 1.3.6.1.4.1.5504.5.16.1.32
		zhoneCpeCondDhcpSrvList OBJECT-IDENTITY
			STATUS current
			DESCRIPTION 
				"Conditional DHCP server list objects"
			::= { zhoneCpeObjectID 32 }

		
		-- 1.3.6.1.4.1.5504.5.16.1.32.1
		zhoneCpeCondiDhcpSrvListIndexNext OBJECT-TYPE
			SYNTAX Integer32
			MAX-ACCESS read-only
			STATUS current
			DESCRIPTION
				"This object contains an appropriate value to be used for the
				zhoneCpeCondDhcpSrvListIndex when creating entries in the zhoneCpeCondDhcpSrvListTable.
				The value 0 indicates that no unassigned entries are available. To obtain the
				zhoneCpeCondDhcpSrvListIndex value for a new entry, the manager issues a management
				protocol retrieval operation to obtain the current value of this object.  After each
				retrieval, the agent should modify the value to the next unassigned index.
				
				After a manager retrieves a value the agent will determine through its local
				policy when this index value will be made available for reuse."
			::= { zhoneCpeCondDhcpSrvList 1 }

		
		-- 1.3.6.1.4.1.5504.5.16.1.32.2
		zhoneCpeCondDhcpSrvListTable OBJECT-TYPE
			SYNTAX SEQUENCE OF ZhoneCpeCondDhcpSrvListEntry
			MAX-ACCESS not-accessible
			STATUS current
			DESCRIPTION
				"Table in which each entry is a list of conditional dhcp server rules."
			::= { zhoneCpeCondDhcpSrvList 2 }

		
		-- 1.3.6.1.4.1.5504.5.16.1.32.2.1
		zhoneCpeCondDhcpSrvListEntry OBJECT-TYPE
			SYNTAX ZhoneCpeCondDhcpSrvListEntry
			MAX-ACCESS not-accessible
			STATUS current
			DESCRIPTION
				"Row in conditional DHCP server list table"
			INDEX { zhoneCpeCondDhcpSrvListIndex }
			::= { zhoneCpeCondDhcpSrvListTable 1 }

		
		ZhoneCpeCondDhcpSrvListEntry ::=
			SEQUENCE { 
				zhoneCpeCondDhcpSrvListIndex
					Unsigned32,
				zhoneCpeCondDhcpSrvListRowStatus
					RowStatus,
				zhoneCpeCondDhcpSrvListProfileName
					ZhoneAdminString
			 }

		-- 1.3.6.1.4.1.5504.5.16.1.32.2.1.1
		zhoneCpeCondDhcpSrvListIndex OBJECT-TYPE
			SYNTAX Unsigned32
			MAX-ACCESS not-accessible
			STATUS current
			DESCRIPTION
				"Index number for this cpe conditional dhcp server list.
				This is the number that goes into the cpe-dhcp-server record."
			::= { zhoneCpeCondDhcpSrvListEntry 1 }

		
		-- 1.3.6.1.4.1.5504.5.16.1.32.2.1.2
		zhoneCpeCondDhcpSrvListRowStatus OBJECT-TYPE
			SYNTAX RowStatus
			MAX-ACCESS read-create
			STATUS current
			DESCRIPTION
				"Used to create, modify or delete an entry in this table."
			::= { zhoneCpeCondDhcpSrvListEntry 2 }

		
		-- 1.3.6.1.4.1.5504.5.16.1.32.2.1.3
		zhoneCpeCondDhcpSrvListProfileName OBJECT-TYPE
			SYNTAX ZhoneAdminString
			MAX-ACCESS read-create
			STATUS current
			DESCRIPTION
				"Profile name for this cpe-cond-dhcp-srv-list profile. This must be 
				unique, and is writable only on creation."
			::= { zhoneCpeCondDhcpSrvListEntry 3 }

		
		-- 1.3.6.1.4.1.5504.5.16.1.33
		zhoneCpeCondDhcpSrv OBJECT-IDENTITY
			STATUS current
			DESCRIPTION 
				"Conditional DHCP server objects"
			::= { zhoneCpeObjectID 33 }

		
		-- 1.3.6.1.4.1.5504.5.16.1.33.1
		zhoneCpeCondDhcpSrvIndexTable OBJECT-TYPE
			SYNTAX SEQUENCE OF ZhoneCpeCondDhcpSrvIndexEntry
			MAX-ACCESS not-accessible
			STATUS current
			DESCRIPTION
				"Table of next available indexes for each conditional DHCP server list."
			::= { zhoneCpeCondDhcpSrv 1 }

		
		-- 1.3.6.1.4.1.5504.5.16.1.33.1.1
		zhoneCpeCondDhcpSrvIndexEntry OBJECT-TYPE
			SYNTAX ZhoneCpeCondDhcpSrvIndexEntry
			MAX-ACCESS not-accessible
			STATUS current
			DESCRIPTION
				"Row in the conditional DHCP server index table."
			INDEX { zhoneCpeCondDhcpSrvListIndex }
			::= { zhoneCpeCondDhcpSrvIndexTable 1 }

		
		ZhoneCpeCondDhcpSrvIndexEntry ::=
			SEQUENCE { 
				zhoneCpeCondDhcpSrvIndexEntryIndexNext
					Integer32
			 }

		-- 1.3.6.1.4.1.5504.5.16.1.33.1.1.1
		zhoneCpeCondDhcpSrvIndexEntryIndexNext OBJECT-TYPE
			SYNTAX Integer32
			MAX-ACCESS read-only
			STATUS current
			DESCRIPTION
				"Next available index for a conditional DHCP server list."
			::= { zhoneCpeCondDhcpSrvIndexEntry 1 }

		
		-- 1.3.6.1.4.1.5504.5.16.1.33.2
		zhoneCpeCondDhcpSrvTable OBJECT-TYPE
			SYNTAX SEQUENCE OF ZhoneCpeCondDhcpSrvEntry
			MAX-ACCESS not-accessible
			STATUS current
			DESCRIPTION
				"Table of conditional DHCP server data."
			::= { zhoneCpeCondDhcpSrv 2 }

		
		-- 1.3.6.1.4.1.5504.5.16.1.33.2.1
		zhoneCpeCondDhcpSrvEntry OBJECT-TYPE
			SYNTAX ZhoneCpeCondDhcpSrvEntry
			MAX-ACCESS not-accessible
			STATUS current
			DESCRIPTION
				"Row inf the conditional DHCP server table"
			INDEX { zhoneCpeCondDhcpSrvListIndex, zhoneCpeCondDhcpSrvEntryIndex }
			::= { zhoneCpeCondDhcpSrvTable 1 }

		
		ZhoneCpeCondDhcpSrvEntry ::=
			SEQUENCE { 
				zhoneCpeCondDhcpSrvEntryIndex
					Unsigned32,
				zhoneCpeCondDhcpSrvRowStatus
					RowStatus,
				zhoneCpeCondDhcpSrvAdminState
					ZhoneEnabledFlag,
				zhoneCpeCondDhcpSrvPriorityOrder
					Integer32,
				zhoneCpeCondDhcpVciOui
					ZhoneAdminString,
				zhoneCpeCondDhcpSrvVciMatch
					INTEGER,
				zhoneCpeCondDhcpSrvStartAddr
					IpAddress,
				zhoneCpeCondDhcpSrvEndAddr
					IpAddress,
				zhoneCpeCondDhcpSrvWanVlan
					Unsigned32,
				zhoneCpeCondDhcpSrvPortFwdRule
					ZhoneEnabledFlag,
				zhoneCpeCondDhcpSrvStartPort
					Unsigned32,
				zhoneCpeCondDhcpSrvPrivatePort
					Unsigned32,
				zhoneCpeCondDhcpSrvProtocol
					INTEGER,
				zhoneCpeCondDhcpSrvPriDns
					IpAddress,
				zhoneCpeCondDhcpSrvSecDns
					IpAddress,
				zhoneCpeCondDhcpSrvPriNpt
					IpAddress,
				zhoneCpeCondDhcpSrvSecNpt
					IpAddress,
				zhoneCpeCondDhcpSrvVsi
					OCTET STRING,
				zhoneCpeCondDhcpSrvPermanent
					ZhoneEnabledFlag
			 }

		-- 1.3.6.1.4.1.5504.5.16.1.33.2.1.1
		zhoneCpeCondDhcpSrvEntryIndex OBJECT-TYPE
			SYNTAX Unsigned32
			MAX-ACCESS not-accessible
			STATUS current
			DESCRIPTION
				"The entry index within the conditional DHCP server list"
			::= { zhoneCpeCondDhcpSrvEntry 1 }

		
		-- 1.3.6.1.4.1.5504.5.16.1.33.2.1.2
		zhoneCpeCondDhcpSrvRowStatus OBJECT-TYPE
			SYNTAX RowStatus
			MAX-ACCESS read-create
			STATUS current
			DESCRIPTION
				"The row status for adding and deleting rows."
			::= { zhoneCpeCondDhcpSrvEntry 2 }

		
		-- 1.3.6.1.4.1.5504.5.16.1.33.2.1.3
		zhoneCpeCondDhcpSrvAdminState OBJECT-TYPE
			SYNTAX ZhoneEnabledFlag
			MAX-ACCESS read-create
			STATUS current
			DESCRIPTION
				"Enable/disable this rule. Disabling allows rule to be temporarily 
				unavailable for testing or debug purposes."
			DEFVAL { enabled }
			::= { zhoneCpeCondDhcpSrvEntry 3 }

		
		-- 1.3.6.1.4.1.5504.5.16.1.33.2.1.4
		zhoneCpeCondDhcpSrvPriorityOrder OBJECT-TYPE
			SYNTAX Integer32
			MAX-ACCESS read-create
			STATUS current
			DESCRIPTION
				"When multiple Conditional DHCP Rules are applied to the same 
				physical port and an ingress packet matches more than one rule, 
				the rule with the highest Priority will be applied.
				
				The default priority is for rules to be applied in the order created."
			::= { zhoneCpeCondDhcpSrvEntry 4 }

		
		-- 1.3.6.1.4.1.5504.5.16.1.33.2.1.5
		zhoneCpeCondDhcpVciOui OBJECT-TYPE
			SYNTAX ZhoneAdminString
			MAX-ACCESS read-create
			STATUS current
			DESCRIPTION
				"This field is for Vendor Class Identifier (Option 60) or 
				Organizationally Unique Identifier. Conditional DHCP Rules 
				classify ingress packets based on a matching OUI, or based on 
				a matching DHCP Option 60 string value.
				
				OUI is the first 3 bytes of a MAC, separated by colons 
				(e.g. 00:02:71). 
				
				VCI is the text string included in the Option 60. When an 
				attached device sends a DHCP Discover packet to request a 
				dynamically assigned IP Address, it may include this Option 60 
				string to identify what type of device it is.
				"
			DEFVAL { "" }
			::= { zhoneCpeCondDhcpSrvEntry 5 }

		
		-- 1.3.6.1.4.1.5504.5.16.1.33.2.1.6
		zhoneCpeCondDhcpSrvVciMatch OBJECT-TYPE
			SYNTAX INTEGER
				{
				prefix(1),
				suffix(2),
				substring(3)
				}
			MAX-ACCESS read-create
			STATUS current
			DESCRIPTION
				"VCI, the Option 60 String included in the DHCP Discover packet, 
				may be up to 255 characters long, while the vci-oui field supports 
				a maximum of 32 characters. This configuration option specifies 
				where to look in the entire Option 60 string for a match. 
				Choices are at the beginning (Prefix), at the end (Suffix), 
				or anywhere in the string (Substring).
				"
			DEFVAL { prefix }
			::= { zhoneCpeCondDhcpSrvEntry 6 }

		
		-- 1.3.6.1.4.1.5504.5.16.1.33.2.1.7
		zhoneCpeCondDhcpSrvStartAddr OBJECT-TYPE
			SYNTAX IpAddress
			MAX-ACCESS read-create
			STATUS current
			DESCRIPTION
				"Starting IP Address for the subnet range associated with this rule. 
				Must be in the same subnet as the LAN IP Interface for this VLAN. 
				Every Conditional DHCP Rule should have a unique range of IP 
				Addresses within the LAN Subnet (non-overlapping).
				"
			::= { zhoneCpeCondDhcpSrvEntry 7 }

		
		-- 1.3.6.1.4.1.5504.5.16.1.33.2.1.8
		zhoneCpeCondDhcpSrvEndAddr OBJECT-TYPE
			SYNTAX IpAddress
			MAX-ACCESS read-create
			STATUS current
			DESCRIPTION
				"Last ip address associated with this rule."
			::= { zhoneCpeCondDhcpSrvEntry 8 }

		
		-- 1.3.6.1.4.1.5504.5.16.1.33.2.1.9
		zhoneCpeCondDhcpSrvWanVlan OBJECT-TYPE
			SYNTAX Unsigned32 (0..4096)
			MAX-ACCESS read-create
			STATUS current
			DESCRIPTION
				"VLAN ID of the WAN interface that shall be used as the default 
				forwarding path for all packets received with an IP address in 
				this subnet. This feature enables automatic forwarding of packets 
				sourced by a Conditional DHCP Client device to a different 
				Default Gateway (based on the VLAN ID).
				"
			DEFVAL { '0'b }
			::= { zhoneCpeCondDhcpSrvEntry 9 }

		
		-- 1.3.6.1.4.1.5504.5.16.1.33.2.1.10
		zhoneCpeCondDhcpSrvPortFwdRule OBJECT-TYPE
			SYNTAX ZhoneEnabledFlag
			MAX-ACCESS read-create
			STATUS current
			DESCRIPTION
				"When enabled, a Static Port Forwarding Firewall Rule will 
				automatically be created for each client device assigned an 
				IP Address based on this rule.
				"
			DEFVAL { disabled }
			::= { zhoneCpeCondDhcpSrvEntry 10 }

		
		-- 1.3.6.1.4.1.5504.5.16.1.33.2.1.11
		zhoneCpeCondDhcpSrvStartPort OBJECT-TYPE
			SYNTAX Unsigned32 (0..65535)
			MAX-ACCESS read-create
			STATUS current
			DESCRIPTION
				"WAN-side Port Number of the Port Forwarding Rule that will be 
				automatically created for the Conditional DHCP client assigned 
				the Starting IP Address defined for this rule. The WAN-side Port 
				Number will increment by 1 for each new client device.
				"
			DEFVAL { 65501 }
			::= { zhoneCpeCondDhcpSrvEntry 11 }

		
		-- 1.3.6.1.4.1.5504.5.16.1.33.2.1.12
		zhoneCpeCondDhcpSrvPrivatePort OBJECT-TYPE
			SYNTAX Unsigned32 (0..65535)
			MAX-ACCESS read-create
			STATUS current
			DESCRIPTION
				"The LAN-side Port Number of the Port Forwarding Rule that will 
				be bound to the private IP Address assigned to each client. 
				This Port Number is typically assigned based on the application 
				that the Port Forwarding Rule will be used for. For example, 
				if the Rule will be used to enable on-demand SSH connections 
				to client devices with conditional IP Addresses, then the 
				Private Port will be 22.
				"
			DEFVAL { 0 }
			::= { zhoneCpeCondDhcpSrvEntry 12 }

		
		-- 1.3.6.1.4.1.5504.5.16.1.33.2.1.13
		zhoneCpeCondDhcpSrvProtocol OBJECT-TYPE
			SYNTAX INTEGER
				{
				tcp(1),
				udp(2),
				both(3)
				}
			MAX-ACCESS read-create
			STATUS current
			DESCRIPTION
				"Defines what type of packets will be allowed through the 
				Static Port Forwarding Rule.
				"
			DEFVAL { tcp }
			::= { zhoneCpeCondDhcpSrvEntry 13 }

		
		-- 1.3.6.1.4.1.5504.5.16.1.33.2.1.14
		zhoneCpeCondDhcpSrvPriDns OBJECT-TYPE
			SYNTAX IpAddress
			MAX-ACCESS read-create
			STATUS current
			DESCRIPTION
				"Defines the Option 6 Primary DNS IP Addresses that will be 
				included in the DHCP Offer to Conditional DHCP client devices 
				matching this rule.
				"
			DEFVAL { '00000000'h }
			::= { zhoneCpeCondDhcpSrvEntry 14 }

		
		-- 1.3.6.1.4.1.5504.5.16.1.33.2.1.15
		zhoneCpeCondDhcpSrvSecDns OBJECT-TYPE
			SYNTAX IpAddress
			MAX-ACCESS read-create
			STATUS current
			DESCRIPTION
				"Defines the Option 6 Secondary DNS IP Addresses that will be 
				included in the DHCP Offer to Conditional DHCP client devices 
				matching this rule.
				"
			DEFVAL { '00000000'h }
			::= { zhoneCpeCondDhcpSrvEntry 15 }

		
		-- 1.3.6.1.4.1.5504.5.16.1.33.2.1.16
		zhoneCpeCondDhcpSrvPriNpt OBJECT-TYPE
			SYNTAX IpAddress
			MAX-ACCESS read-create
			STATUS current
			DESCRIPTION
				"Defines the Option 42 Primary NTP IP Addresses that will be 
				included in the DHCP Offer to Conditional DHCP client devices 
				matching this rule. NOTE that Option 2 (Timezone Offset) will 
				also be included in the DHCP Offer. The Option 2 value will be 
				automatically populated by the ONT, based on what it was assigned 
				on an uplink interface with DHCP client enabled.
				"
			DEFVAL { '00000000'h }
			::= { zhoneCpeCondDhcpSrvEntry 16 }

		
		-- 1.3.6.1.4.1.5504.5.16.1.33.2.1.17
		zhoneCpeCondDhcpSrvSecNpt OBJECT-TYPE
			SYNTAX IpAddress
			MAX-ACCESS read-create
			STATUS current
			DESCRIPTION
				"Defines the Option 42 Secondary NTP IP Addresses that will be 
				included in the DHCP Offer to Conditional DHCP client devices 
				matching this rule.
				"
			DEFVAL { '00000000'h }
			::= { zhoneCpeCondDhcpSrvEntry 17 }

		
		-- 1.3.6.1.4.1.5504.5.16.1.33.2.1.18
		zhoneCpeCondDhcpSrvVsi OBJECT-TYPE
			SYNTAX OCTET STRING (SIZE (0..255))
			MAX-ACCESS read-create
			STATUS current
			DESCRIPTION
				"Vendor Specific Information (Option 43) is a user-configured text 
				string of up to 32 characters with no restrictions on format or 
				content. Required by some DHCP client devices for specific 
				applications and/or boot up procedures.
				"
			::= { zhoneCpeCondDhcpSrvEntry 18 }

		
		-- 1.3.6.1.4.1.5504.5.16.1.33.2.1.19
		zhoneCpeCondDhcpSrvPermanent OBJECT-TYPE
			SYNTAX ZhoneEnabledFlag
			MAX-ACCESS read-create
			STATUS current
			DESCRIPTION
				"When enabled, IP Addresses are permanently bound to the MAC address
				of the device they are assigned to. DHCP Lease table will show
				permanent entries for each host."
			DEFVAL { enabled }
			::= { zhoneCpeCondDhcpSrvEntry 19 }

		
		-- 1.3.6.1.4.1.5504.5.16.1.34
		zhoneCpeCmd OBJECT IDENTIFIER ::= { zhoneCpeObjectID 34 }
-- The CPE Command objects expose the MXK clone/delete/copy
-- operations to SNMP.
		
		-- 1.3.6.1.4.1.5504.5.16.1.34.1
		zhoneCpeCmdOperation OBJECT-TYPE
			SYNTAX INTEGER
				{
				deleteSlot(1),
				deletePort(2),
				deleteCpe(3),
				deleteUni(4),
				deleteService(5),
				moveSlotToSlot(10),
				movePortToPort(11),
				moveCpeToCpe(12),
				moveUniToUni(13),
				moveServiceToService(15),
				cloneSlotToSlot(20),
				clonePortToPort(21),
				cloneCpeToCpe(22),
				cloneUniToUni(23),
				cloneServiceToService(24),
				cloneCpeToSlot(25),
				cloneCpeToPort(26),
				applyCpeToSlot(40),
				applyCpeToPort(41),
				applyCpeToCpe(42),
				createVirtualCpe(60),
				deleteVirtualCpe(61),
				applySvcToCpe(70),
				removeSvcFromCpe(80),
				decoupleCpe(81)
				}
			MAX-ACCESS read-write
			STATUS current
			DESCRIPTION
				"The Command operation to be performed.  The command operation
				will determine which of the other zhoneCpeCmd objects 
				will be used.
				
				The DELETE commands delete configuration.
				
				The MOVE commands copy configuration from source to
				destination.  Source configuration is deleted.
				
				The CLONE commands copy configuration from source to
				destination.  Source configuration is perserved.
				Destination configuration befor clone operation is
				deleted.
				
				The APPLY commands copy configuration from source to
				destination.  Source configuration is perserved.
				Destination configuration prior to appy operation
				is preserved.
				
				"
			::= { zhoneCpeCmd 1 }

		
		-- 1.3.6.1.4.1.5504.5.16.1.34.2
		zhoneCpeCmdSrcIfIndex OBJECT-TYPE
			SYNTAX Unsigned32
			MAX-ACCESS read-write
			STATUS current
			DESCRIPTION
				"Command SOURCE ifIndex.
				
				Using this object overwrites source shelf/slot/port/subPort objects.
				
				This object must be used for virtual CPEs."
			::= { zhoneCpeCmd 2 }

		
		-- 1.3.6.1.4.1.5504.5.16.1.34.3
		zhoneCpeCmdSrcShelf OBJECT-TYPE
			SYNTAX Unsigned32
			MAX-ACCESS read-write
			STATUS current
			DESCRIPTION
				"Command SOURCE shelf"
			::= { zhoneCpeCmd 3 }

		
		-- 1.3.6.1.4.1.5504.5.16.1.34.4
		zhoneCpeCmdSrcSlot OBJECT-TYPE
			SYNTAX Unsigned32
			MAX-ACCESS read-write
			STATUS current
			DESCRIPTION
				"Command SOURCE slot"
			::= { zhoneCpeCmd 4 }

		
		-- 1.3.6.1.4.1.5504.5.16.1.34.5
		zhoneCpeCmdSrcPort OBJECT-TYPE
			SYNTAX Unsigned32
			MAX-ACCESS read-write
			STATUS current
			DESCRIPTION
				"Command SOURCE port."
			::= { zhoneCpeCmd 5 }

		
		-- 1.3.6.1.4.1.5504.5.16.1.34.6
		zhoneCpeCmdSrcSubport OBJECT-TYPE
			SYNTAX Unsigned32
			MAX-ACCESS read-write
			STATUS current
			DESCRIPTION
				"Command SOURCE subPort."
			::= { zhoneCpeCmd 6 }

		
		-- 1.3.6.1.4.1.5504.5.16.1.34.7
		zhoneCpeCmdSrcTpType OBJECT-TYPE
			SYNTAX TpType
			MAX-ACCESS read-write
			STATUS current
			DESCRIPTION
				"Command SOURCE tpType."
			::= { zhoneCpeCmd 7 }

		
		-- 1.3.6.1.4.1.5504.5.16.1.34.8
		zhoneCpeCmdSrcTpIndex OBJECT-TYPE
			SYNTAX Unsigned32
			MAX-ACCESS read-write
			STATUS current
			DESCRIPTION
				"Command SOURCE tpIndex"
			::= { zhoneCpeCmd 8 }

		
		-- 1.3.6.1.4.1.5504.5.16.1.34.9
		zhoneCpeCmdDstIfIndex OBJECT-TYPE
			SYNTAX Unsigned32
			MAX-ACCESS read-write
			STATUS current
			DESCRIPTION
				"Command DESTINATION ifIndex.
				
				Using this object overwrites destination shelf/slot/port/subPort objects.
				
				This object must be used for virtual CPEs."
			::= { zhoneCpeCmd 9 }

		
		-- 1.3.6.1.4.1.5504.5.16.1.34.10
		zhoneCpeCmdDstShelf OBJECT-TYPE
			SYNTAX Unsigned32
			MAX-ACCESS read-write
			STATUS current
			DESCRIPTION
				"Command DESTINATION shelf"
			::= { zhoneCpeCmd 10 }

		
		-- 1.3.6.1.4.1.5504.5.16.1.34.11
		zhoneCpeCmdDstSlot OBJECT-TYPE
			SYNTAX Unsigned32
			MAX-ACCESS read-write
			STATUS current
			DESCRIPTION
				"Command DESTINATION slot"
			::= { zhoneCpeCmd 11 }

		
		-- 1.3.6.1.4.1.5504.5.16.1.34.12
		zhoneCpeCmdDstPort OBJECT-TYPE
			SYNTAX Unsigned32
			MAX-ACCESS read-write
			STATUS current
			DESCRIPTION
				"Command DESTINATION port."
			::= { zhoneCpeCmd 12 }

		
		-- 1.3.6.1.4.1.5504.5.16.1.34.13
		zhoneCpeCmdDstSubport OBJECT-TYPE
			SYNTAX Unsigned32
			MAX-ACCESS read-write
			STATUS current
			DESCRIPTION
				"Command DESTINATION subPort."
			::= { zhoneCpeCmd 13 }

		
		-- 1.3.6.1.4.1.5504.5.16.1.34.14
		zhoneCpeCmdDstTpType OBJECT-TYPE
			SYNTAX TpType
			MAX-ACCESS read-write
			STATUS current
			DESCRIPTION
				"Command DESTINATION tpType."
			::= { zhoneCpeCmd 14 }

		
		-- 1.3.6.1.4.1.5504.5.16.1.34.15
		zhoneCpeCmdDstTpIndex OBJECT-TYPE
			SYNTAX Unsigned32
			MAX-ACCESS read-write
			STATUS current
			DESCRIPTION
				"Command DESTINATION tpIndex"
			::= { zhoneCpeCmd 15 }

		
		-- 1.3.6.1.4.1.5504.5.16.1.34.16
		zhoneCpeCmdString OBJECT-TYPE
			SYNTAX ZhoneAdminString
			MAX-ACCESS read-write
			STATUS current
			DESCRIPTION
				"General purpose string parameter.  Used to specify
				names or other string values."
			::= { zhoneCpeCmd 16 }

		
		-- 1.3.6.1.4.1.5504.5.16.1.34.17
		zhoneCpeCmdSvcTemplateType OBJECT-TYPE
			SYNTAX ZhoneCpeTemplateType
			MAX-ACCESS read-write
			STATUS current
			DESCRIPTION
				"Command cpe service template type."
			::= { zhoneCpeCmd 17 }

		
		-- 1.3.6.1.4.1.5504.5.16.1.34.18
		zhoneCpeCmdSvcTemplateId OBJECT-TYPE
			SYNTAX Unsigned32
			MAX-ACCESS read-write
			STATUS current
			DESCRIPTION
				"Command cpe service template indentification."
			::= { zhoneCpeCmd 18 }

		
		-- 1.3.6.1.4.1.5504.5.16.1.34.19
		zhoneCpeCmdSvcTemplateIfIndex OBJECT-TYPE
			SYNTAX Unsigned32
			MAX-ACCESS read-write
			STATUS current
			DESCRIPTION
				"Command cpe service template destintation CPE ifIndex."
			::= { zhoneCpeCmd 19 }

		
		-- 1.3.6.1.4.1.5504.5.16.1.34.20
		zhoneCpeCmdSvcTemplateVirtualConn OBJECT-TYPE
			SYNTAX Unsigned32
			MAX-ACCESS read-write
			STATUS current
			DESCRIPTION
				"Command cpe service template source CPE ifIndex.
				Also known as the virutal CPE ifIndex."
			::= { zhoneCpeCmd 20 }

		
		-- 1.3.6.1.4.1.5504.5.16.1.34.21
		zhoneCpeCmdSvcTemplateTpType OBJECT-TYPE
			SYNTAX TpType
			MAX-ACCESS read-write
			STATUS current
			DESCRIPTION
				"Command cpe service tpType.   A zero value means all TpTypes
				on the destination CPE."
			::= { zhoneCpeCmd 21 }

		
		-- 1.3.6.1.4.1.5504.5.16.1.34.22
		zhoneCpeCmdSvcTemplateTpIndex OBJECT-TYPE
			SYNTAX Unsigned32
			MAX-ACCESS read-write
			STATUS current
			DESCRIPTION
				"Command cpe service DESTINATION tpIndex.  A zero value 
				means all UNI ports of the destination CPE."
			::= { zhoneCpeCmd 22 }

		
		-- 1.3.6.1.4.1.5504.5.16.1.34.23
		zhoneCpeCmdSvcTemplateVlan OBJECT-TYPE
			SYNTAX Unsigned32
			MAX-ACCESS read-write
			STATUS current
			DESCRIPTION
				"Command cpe service VLAN, consisting of vlan cos (high 
				order 16 bits) and vlan ID (low order 16 bits)."
			::= { zhoneCpeCmd 23 }

		
		-- 1.3.6.1.4.1.5504.5.16.1.34.24
		zhoneCpeCmdSvcTemplateSlan OBJECT-TYPE
			SYNTAX Unsigned32
			MAX-ACCESS read-write
			STATUS current
			DESCRIPTION
				"Command cpe service SLAN, consisting of slan cos (high 
				order 16 bits) and slan ID (low order 16 bits)."
			::= { zhoneCpeCmd 24 }

		
		-- 1.3.6.1.4.1.5504.5.16.1.34.25
		zhoneCpeCmdOverrideTpIndex OBJECT-TYPE
			SYNTAX Unsigned32
			MAX-ACCESS read-write
			STATUS current
			DESCRIPTION
				"If set, use this as the uni number to which the service
				on the target CPE is applied."
			::= { zhoneCpeCmd 25 }

		
		-- 1.3.6.1.4.1.5504.5.16.1.34.26
		zhoneCpeCmdOverrideVlanId OBJECT-TYPE
			SYNTAX Unsigned32
			MAX-ACCESS read-write
			STATUS current
			DESCRIPTION
				"If set, use this vlanId on the destination CPE."
			::= { zhoneCpeCmd 26 }

		
		-- 1.3.6.1.4.1.5504.5.16.1.34.27
		zhoneCpeCmdOverrideVlanCos OBJECT-TYPE
			SYNTAX Unsigned32
			MAX-ACCESS read-write
			STATUS current
			DESCRIPTION
				"If set, use this value as the vlan cos on the destination CPE."
			::= { zhoneCpeCmd 27 }

		
		-- 1.3.6.1.4.1.5504.5.16.1.34.28
		zhoneCpeCmdOverrideSlanId OBJECT-TYPE
			SYNTAX Unsigned32
			MAX-ACCESS read-write
			STATUS current
			DESCRIPTION
				"If set, use this slanId on the destination CPE."
			::= { zhoneCpeCmd 28 }

		
		-- 1.3.6.1.4.1.5504.5.16.1.34.29
		zhoneCpeCmdOverrideSlanCos OBJECT-TYPE
			SYNTAX Unsigned32
			MAX-ACCESS read-write
			STATUS current
			DESCRIPTION
				"If set, use this slan cos on the destination CPE."
			::= { zhoneCpeCmd 29 }

		
		-- 1.3.6.1.4.1.5504.5.16.1.34.30
		zhoneCpeCmdStatus OBJECT-TYPE
			SYNTAX INTEGER
				{
				none(0),
				submitted(1),
				inprogress(2),
				done(3),
				error(4)
				}
			MAX-ACCESS read-only
			STATUS current
			DESCRIPTION
				"Status of the most recent command submitted."
			::= { zhoneCpeCmd 30 }

		
		-- 1.3.6.1.4.1.5504.5.16.1.34.31
		zoneCpeCmdErrorCode OBJECT-TYPE
			SYNTAX Integer32
			MAX-ACCESS read-only
			STATUS current
			DESCRIPTION
				"If zhoneCpeCmdState has value 'error', then this is the 
				Zhone_Enhanced_Status code that describes the error.
				"
			::= { zhoneCpeCmd 31 }

		
		-- 1.3.6.1.4.1.5504.5.16.1.35
		zhoneCpeLldpMedPolicyList OBJECT-IDENTITY
			STATUS current
			DESCRIPTION 
				"Link Layer Discovery Protocol MED network policy list objects"
			::= { zhoneCpeObjectID 35 }

		
		-- 1.3.6.1.4.1.5504.5.16.1.35.1
		zhoneCpeLldpMedPolicyListIndexNext OBJECT-TYPE
			SYNTAX Integer32
			MAX-ACCESS read-only
			STATUS current
			DESCRIPTION
				"This object contains an appropriate value to be used for the
				zhoneCpeLldpMedPolicyListIndex when creating entries in the zhoneCpeLldpMedPolicyListTable.
				The value 0 indicates that no unassigned entries are available. To obtain the
				zhoneCpeLldpMedPolicyListIndex value for a new entry, the manager issues a management
				protocol retrieval operation to obtain the current value of this object.  After each
				retrieval, the agent should modify the value to the next unassigned index.
				
				After a manager retrieves a value the agent will determine through its local
				policy when this index value will be made available for reuse."
			::= { zhoneCpeLldpMedPolicyList 1 }

		
		-- 1.3.6.1.4.1.5504.5.16.1.35.2
		zhoneCpeLldpMedPolicyListTable OBJECT-TYPE
			SYNTAX SEQUENCE OF ZhoneCpeLldpMedPolicyListEntry
			MAX-ACCESS not-accessible
			STATUS current
			DESCRIPTION
				"Table in which each entry is a list of LLDP-MED network policy rules."
			::= { zhoneCpeLldpMedPolicyList 2 }

		
		-- 1.3.6.1.4.1.5504.5.16.1.35.2.1
		zhoneCpeLldpMedPolicyListEntry OBJECT-TYPE
			SYNTAX ZhoneCpeLldpMedPolicyListEntry
			MAX-ACCESS not-accessible
			STATUS current
			DESCRIPTION
				"Row in LLDP-MED network policy list table"
			INDEX { zhoneCpeLldpMedPolicyListIndex }
			::= { zhoneCpeLldpMedPolicyListTable 1 }

		
		ZhoneCpeLldpMedPolicyListEntry ::=
			SEQUENCE { 
				zhoneCpeLldpMedPolicyListIndex
					Unsigned32,
				zhoneCpeLldpMedPolicyListRowStatus
					RowStatus,
				zhoneCpeLldpMedPolicyListProfileName
					ZhoneAdminString,
				zhoneCpeLldpMedPolicyListDeviceDiscoveryNotify
					ZhoneEnabledFlag,
				zhoneCpeLldpMedPolicyListNotificationInterval
					Unsigned32
			 }

		-- 1.3.6.1.4.1.5504.5.16.1.35.2.1.1
		zhoneCpeLldpMedPolicyListIndex OBJECT-TYPE
			SYNTAX Unsigned32
			MAX-ACCESS not-accessible
			STATUS current
			DESCRIPTION
				"This represents the CPE LLDP-MED network policy index value."
			::= { zhoneCpeLldpMedPolicyListEntry 1 }

		
		-- 1.3.6.1.4.1.5504.5.16.1.35.2.1.2
		zhoneCpeLldpMedPolicyListRowStatus OBJECT-TYPE
			SYNTAX RowStatus
			MAX-ACCESS read-create
			STATUS current
			DESCRIPTION
				"Used to create, modify or delete an entry in this table."
			DEFVAL { active }
			::= { zhoneCpeLldpMedPolicyListEntry 2 }

		
		-- 1.3.6.1.4.1.5504.5.16.1.35.2.1.3
		zhoneCpeLldpMedPolicyListProfileName OBJECT-TYPE
			SYNTAX ZhoneAdminString
			MAX-ACCESS read-create
			STATUS current
			DESCRIPTION
				"Profile name for this cpe-lldp-med-policy-list profile. This must be 
				unique, and is writable only on creation."
			::= { zhoneCpeLldpMedPolicyListEntry 3 }

		
		-- 1.3.6.1.4.1.5504.5.16.1.35.2.1.4
		zhoneCpeLldpMedPolicyListDeviceDiscoveryNotify OBJECT-TYPE
			SYNTAX ZhoneEnabledFlag
			MAX-ACCESS read-create
			STATUS current
			DESCRIPTION
				"This object is used to enable device discovery notifications on the CPE, on a per port basis.
				This field enables/disables the ONT trap notification to MxK whenever it discovers
				a new remote LLDP device, looses connectivity with a discovered LLDP device or 
				when there is a change of attribute of a discovered LLDP device.
								
				The value enabled(1) means notifications are enabled on the CPE.
				The value disabled(2) means notifications are not enabled on the CPE."
			DEFVAL { disabled }
			::= { zhoneCpeLldpMedPolicyListEntry 4 }

		
		-- 1.3.6.1.4.1.5504.5.16.1.35.2.1.5
		zhoneCpeLldpMedPolicyListNotificationInterval OBJECT-TYPE
			SYNTAX Unsigned32 (5..3600)
			UNITS "seconds"
			MAX-ACCESS read-create
			STATUS current
			DESCRIPTION
				"This object controls the transmission of LLDP notifications.
								
				The agent must not generate more than one lldpRemTablesChange
				notification-event in the indicated period, where a
				'notification-event' is the transmission of a single
				notification PDU type to a list of notification destinations.
				If additional changes in lldpRemoteSystemsData object
				groups occur within the indicated throttling period,
				then these trap- events must be suppressed by the
				agent. MXK should periodically check the value of
				lldpStatsRemTableLastChangeTime to detect any missed
				lldpRemTablesChange notification-events, e.g. due to
				throttling or transmission loss.
								
				If notification transmission is enabled for particular ports,
				the suggested default throttling period is 5 seconds."
			DEFVAL { 5 }
			::= { zhoneCpeLldpMedPolicyListEntry 5 }

		
		-- 1.3.6.1.4.1.5504.5.16.1.36
		zhoneCpeLldpMedPolicy OBJECT-IDENTITY
			STATUS current
			DESCRIPTION 
				"Link Layer Discover Protocol MED network policy objects"
			::= { zhoneCpeObjectID 36 }

		
		-- 1.3.6.1.4.1.5504.5.16.1.36.1
		zhoneCpeLldpMedPolicyIndexTable OBJECT-TYPE
			SYNTAX SEQUENCE OF ZhoneCpeLldpMedPolicyIndexEntry
			MAX-ACCESS not-accessible
			STATUS current
			DESCRIPTION
				"Table of next available indexes for each LLDP-MED network policy."
			::= { zhoneCpeLldpMedPolicy 1 }

		
		-- 1.3.6.1.4.1.5504.5.16.1.36.1.1
		zhoneCpeLldpMedPolicyIndexEntry OBJECT-TYPE
			SYNTAX ZhoneCpeLldpMedPolicyIndexEntry
			MAX-ACCESS not-accessible
			STATUS current
			DESCRIPTION
				"Row in the zhoneCpeLldpMedPolicyIndex table."
			INDEX { zhoneCpeLldpMedPolicyListIndex }
			::= { zhoneCpeLldpMedPolicyIndexTable 1 }

		
		ZhoneCpeLldpMedPolicyIndexEntry ::=
			SEQUENCE { 
				zhoneCpeLldpMedPolicyIndexEntryIndexNext
					Integer32
			 }

		-- 1.3.6.1.4.1.5504.5.16.1.36.1.1.1
		zhoneCpeLldpMedPolicyIndexEntryIndexNext OBJECT-TYPE
			SYNTAX Integer32
			MAX-ACCESS read-only
			STATUS current
			DESCRIPTION
				"Next available entry index for row in zhoneCpeLldpMedPolicyTable."
			::= { zhoneCpeLldpMedPolicyIndexEntry 1 }

		
		-- 1.3.6.1.4.1.5504.5.16.1.36.2
		zhoneCpeLldpMedPolicyTable OBJECT-TYPE
			SYNTAX SEQUENCE OF ZhoneCpeLldpMedPolicyEntry
			MAX-ACCESS not-accessible
			STATUS current
			DESCRIPTION
				"The table of Cpe Lldp Med Policy entries."
			::= { zhoneCpeLldpMedPolicy 2 }

		
		-- 1.3.6.1.4.1.5504.5.16.1.36.2.1
		zhoneCpeLldpMedPolicyEntry OBJECT-TYPE
			SYNTAX ZhoneCpeLldpMedPolicyEntry
			MAX-ACCESS not-accessible
			STATUS current
			DESCRIPTION
				"A row in the Cpe Lldp Med Policy table."
			INDEX { zhoneCpeLldpMedPolicyListIndex, zhoneCpeLldpMedPolicyEntryIndex }
			::= { zhoneCpeLldpMedPolicyTable 1 }

		
		ZhoneCpeLldpMedPolicyEntry ::=
			SEQUENCE { 
				zhoneCpeLldpMedPolicyEntryIndex
					Unsigned32,
				zhoneCpeLldpMedPolicyRowStatus
					RowStatus,
				zhoneCpeLldpMedPolicyAdminState
					ZhoneEnabledFlag,
				zhoneCpeLldpMedPolicyAppType
					INTEGER,
				zhoneCpeLldpMedPolicyVlanId
					Unsigned32,
				zhoneCpeLldpMedPolicyCos
					Unsigned32,
				zhoneCpeLldpMedPolicyDscp
					OCTET STRING
			 }

		-- 1.3.6.1.4.1.5504.5.16.1.36.2.1.1
		zhoneCpeLldpMedPolicyEntryIndex OBJECT-TYPE
			SYNTAX Unsigned32
			MAX-ACCESS not-accessible
			STATUS current
			DESCRIPTION
				"The entry index within the LLDP-MED network policy list"
			::= { zhoneCpeLldpMedPolicyEntry 1 }

		
		-- 1.3.6.1.4.1.5504.5.16.1.36.2.1.2
		zhoneCpeLldpMedPolicyRowStatus OBJECT-TYPE
			SYNTAX RowStatus
			MAX-ACCESS read-create
			STATUS current
			DESCRIPTION
				"Used to create, modify or delete an entry in this table."
			DEFVAL { active }
			::= { zhoneCpeLldpMedPolicyEntry 2 }

		
		-- 1.3.6.1.4.1.5504.5.16.1.36.2.1.3
		zhoneCpeLldpMedPolicyAdminState OBJECT-TYPE
			SYNTAX ZhoneEnabledFlag
			MAX-ACCESS read-create
			STATUS current
			DESCRIPTION
				"Enable/disable the network policy."
			DEFVAL { enabled }
			::= { zhoneCpeLldpMedPolicyEntry 3 }

		
		-- 1.3.6.1.4.1.5504.5.16.1.36.2.1.4
		zhoneCpeLldpMedPolicyAppType OBJECT-TYPE
			SYNTAX INTEGER
				{
				voice(1),
				voicesignal(2),
				guestvoice(3),
				guestvoicesignal(4),
				softphone(5),
				videoconf(6),
				videostreaming(7),
				videosignal(8)
				}
			MAX-ACCESS read-create
			STATUS current
			DESCRIPTION
				"The media type that defines the primary function of the application 
				for the policy advertised by an endpoint."
			DEFVAL { voice }
			::= { zhoneCpeLldpMedPolicyEntry 4 }

		
		-- 1.3.6.1.4.1.5504.5.16.1.36.2.1.5
		zhoneCpeLldpMedPolicyVlanId OBJECT-TYPE
			SYNTAX Unsigned32 (0..4096)
			MAX-ACCESS read-create
			STATUS current
			DESCRIPTION
				"The VLAN ID of the application for the policy advertised by an 
				endpoint."
			DEFVAL { '0'b }
			::= { zhoneCpeLldpMedPolicyEntry 5 }

		
		-- 1.3.6.1.4.1.5504.5.16.1.36.2.1.6
		zhoneCpeLldpMedPolicyCos OBJECT-TYPE
			SYNTAX Unsigned32 (0..8)
			MAX-ACCESS read-create
			STATUS current
			DESCRIPTION
				"The Class-Of-Service of the application for the policy advertised by 
				an endpoint."
			DEFVAL { '0'b }
			::= { zhoneCpeLldpMedPolicyEntry 6 }

		
		-- 1.3.6.1.4.1.5504.5.16.1.36.2.1.7
		zhoneCpeLldpMedPolicyDscp OBJECT-TYPE
			SYNTAX OCTET STRING (SIZE (1..8))
			MAX-ACCESS read-create
			STATUS current
			DESCRIPTION
				"This parameter indicates DSCP value for cpe lldp med policy traffic.
				
				Valid code values:
				
				<0-63>   Differentiated services codepoint value 
				   af11     Mark packets with AF11 dscp (001010) 
				   af12     Mark packets with AF12 dscp (001100) 
				   af13     Mark packets with AF13 dscp (001110) 
				   af21     Mark packets with AF21 dscp (010010) 
				   af22     Mark packets with AF22 dscp (010100) 
				   af23     Mark packets with AF23 dscp (010110) 
				   af31     Mark packets with AF31 dscp (011010) 
				   af32     Mark packets with AF32 dscp (011100) 
				   af33     Mark packets with AF33 dscp (011110) 
				   af41     Mark packets with AF41 dscp (100010) 
				   af42     Mark packets with AF42 dscp (100100) 
				   af43     Mark packets with AF43 dscp (100110) 
				   cs1      Mark packets with CS1(precedence 1) dscp (001000) 
				   cs2      Mark packets with CS2(precedence 2) dscp (010000) 
				   cs3      Mark packets with CS3(precedence 3) dscp (011000) 
				   cs4      Mark packets with CS4(precedence 4) dscp (100000) 
				   cs5      Mark packets with CS5(precedence 5) dscp (101000) 
				   cs6      Mark packets with CS6(precedence 6) dscp (110000) 
				   cs7      Mark packets with CS7(precedence 7) dscp (111000) 
				   default  Mark packets with default dscp (000000) 
				   ef       Mark packets with EF dscp (101110) 
				"
			::= { zhoneCpeLldpMedPolicyEntry 7 }

		
		-- 1.3.6.1.4.1.5504.5.16.1.37
		zhoneCpeAutoCfgRule OBJECT-IDENTITY
			STATUS current
			DESCRIPTION 
				"Rule for selecting template to apply for CPE auto-configuration."
			::= { zhoneCpeObjectID 37 }

		
		-- 1.3.6.1.4.1.5504.5.16.1.37.1
		zhoneCpeAutoCfgRuleIndexNext OBJECT-TYPE
			SYNTAX Unsigned32
			MAX-ACCESS read-only
			STATUS current
			DESCRIPTION
				"Next available entry in zhoneCpeAutoCfgRuleTable."
			::= { zhoneCpeAutoCfgRule 1 }

		
		-- 1.3.6.1.4.1.5504.5.16.1.37.2
		zhoneCpeAutoCfgRuleTable OBJECT-TYPE
			SYNTAX SEQUENCE OF ZhoneCpeAutoCfgRuleEntry
			MAX-ACCESS not-accessible
			STATUS current
			DESCRIPTION
				"Table of rules for selecting templates to apply 
				in auto-configuration."
			::= { zhoneCpeAutoCfgRule 2 }

		
		-- 1.3.6.1.4.1.5504.5.16.1.37.2.1
		zhoneCpeAutoCfgRuleEntry OBJECT-TYPE
			SYNTAX ZhoneCpeAutoCfgRuleEntry
			MAX-ACCESS not-accessible
			STATUS current
			DESCRIPTION
				"Row in the auto-config rule table."
			INDEX { zhoneCpeAutoCfgRuleIndex }
			::= { zhoneCpeAutoCfgRuleTable 1 }

		
		ZhoneCpeAutoCfgRuleEntry ::=
			SEQUENCE { 
				zhoneCpeAutoCfgRuleIndex
					Unsigned32,
				zhoneCpeAutoCfgRuleAdminState
					ZhoneAdminState,
				zhoneCpeAutoCfgRulePriority
					Integer32,
				zhoneCpeAutoCfgRuleMatchExpression
					OCTET STRING,
				zhoneCpeAutoCfgRuleServiceTemplate
					InterfaceIndex,
				zhoneCpeAutoCfgRuleTargetUni
					OCTET STRING,
				zhoneCpeAutoCfgRuleDeleteBeforeApply
					TruthValue,
				zhoneCpeAutoCfgRuleRowStatus
					ZhoneRowStatus,
				zhoneCpeAutoCfgRuleProfileName
					ZhoneAdminString
			 }

		-- 1.3.6.1.4.1.5504.5.16.1.37.2.1.1
		zhoneCpeAutoCfgRuleIndex OBJECT-TYPE
			SYNTAX Unsigned32
			MAX-ACCESS not-accessible
			STATUS current
			DESCRIPTION
				"This represents the index in the auto-cfg-rule table."
			::= { zhoneCpeAutoCfgRuleEntry 1 }

		
		-- 1.3.6.1.4.1.5504.5.16.1.37.2.1.2
		zhoneCpeAutoCfgRuleAdminState OBJECT-TYPE
			SYNTAX ZhoneAdminState
			MAX-ACCESS read-create
			STATUS current
			DESCRIPTION
				"If down, this rule will not participate in rule matching."
			DEFVAL { 1 }
			::= { zhoneCpeAutoCfgRuleEntry 2 }

		
		-- 1.3.6.1.4.1.5504.5.16.1.37.2.1.3
		zhoneCpeAutoCfgRulePriority OBJECT-TYPE
			SYNTAX Integer32 (1..2147483647)
			MAX-ACCESS read-create
			STATUS current
			DESCRIPTION
				"1 is the lowest priority. When conflicting rules match, the one 
				with the hightest priority is used."
			DEFVAL { 1 }
			::= { zhoneCpeAutoCfgRuleEntry 3 }

		
		-- 1.3.6.1.4.1.5504.5.16.1.37.2.1.4
		zhoneCpeAutoCfgRuleMatchExpression OBJECT-TYPE
			SYNTAX OCTET STRING (SIZE (0..256))
			MAX-ACCESS read-create
			STATUS current
			DESCRIPTION
				"Logical expression telling which CPEs should be configured
				according to this rule.
				elements are:
				keyword followed by value. Multiple elements can be connected
				with AND.
				Keywords are:
				model - specified model ID
				slot - specifies slot number or numbers
				olt - specifies GPON OLT number or numbers
				
				example:
				model 2426 AND slot 6 AND olt 1-4,7
				
				In this example, apply to model 2426 discovered on olts 
				1, 2, 3, 4, or 7 on slot 6."
			DEFVAL { "" }
			::= { zhoneCpeAutoCfgRuleEntry 4 }

		
		-- 1.3.6.1.4.1.5504.5.16.1.37.2.1.5
		zhoneCpeAutoCfgRuleServiceTemplate OBJECT-TYPE
			SYNTAX InterfaceIndex
			MAX-ACCESS read-create
			STATUS current
			DESCRIPTION
				"The ifIndex of the virtual ONU supplying the service template
				for this rule."
			::= { zhoneCpeAutoCfgRuleEntry 5 }

		
		-- 1.3.6.1.4.1.5504.5.16.1.37.2.1.6
		zhoneCpeAutoCfgRuleTargetUni OBJECT-TYPE
			SYNTAX OCTET STRING (SIZE (0..32))
			MAX-ACCESS read-create
			STATUS current
			DESCRIPTION
				"Which unis from the template should be applied by this rule.
				This consists of a uni type followed by one or more uni numbers,
				separated by commas, or with ranges indicated by '-'. The
				word 'all' may be used to indicate all ports of that type.
				
				example: eth 1-3
				
				In this example, apply services on the provisioned ethernet 
				port on the service template to ethernet ports 1, 2, and 3 of
				the matched CPE.
				
				If this field is blank, then the entire service template is
				applied to the CPE.
				
				"
			DEFVAL { "" }
			::= { zhoneCpeAutoCfgRuleEntry 6 }

		
		-- 1.3.6.1.4.1.5504.5.16.1.37.2.1.7
		zhoneCpeAutoCfgRuleDeleteBeforeApply OBJECT-TYPE
			SYNTAX TruthValue
			MAX-ACCESS read-create
			STATUS current
			DESCRIPTION
				"If true, any existing services on the target unis are removed
				prior to applying the service template.
				If the targetUni field is blank and this field is true, then
				all services on the CPE are removed before the service 
				template is applied."
			DEFVAL { true }
			::= { zhoneCpeAutoCfgRuleEntry 7 }

		
		-- 1.3.6.1.4.1.5504.5.16.1.37.2.1.8
		zhoneCpeAutoCfgRuleRowStatus OBJECT-TYPE
			SYNTAX ZhoneRowStatus
			MAX-ACCESS read-create
			STATUS current
			DESCRIPTION
				"Use to create, modify, or delete a row in this table."
			::= { zhoneCpeAutoCfgRuleEntry 8 }

		
		-- 1.3.6.1.4.1.5504.5.16.1.37.2.1.9
		zhoneCpeAutoCfgRuleProfileName OBJECT-TYPE
			SYNTAX ZhoneAdminString
			MAX-ACCESS read-create
			STATUS current
			DESCRIPTION
				"The profile name of the rule."
			::= { zhoneCpeAutoCfgRuleEntry 9 }

		
		-- 1.3.6.1.4.1.5504.5.16.1.38
		zhoneCpeCfgGlobalSettings OBJECT-IDENTITY
			STATUS current
			DESCRIPTION 
				"System-wide settings for CPE config."
			::= { zhoneCpeObjectID 38 }

		
		-- 1.3.6.1.4.1.5504.5.16.1.38.1
		zhoneCpeCfgAutoAssign OBJECT-TYPE
			SYNTAX ZhoneEnabledFlag
			MAX-ACCESS read-write
			STATUS current
			DESCRIPTION
				"Automatically assign ONU IDs to discovered ONU serial numbers."
			DEFVAL { disabled }
			::= { zhoneCpeCfgGlobalSettings 1 }

		
		-- 1.3.6.1.4.1.5504.5.16.1.38.2
		zhoneCpeCfgAutoConfig OBJECT-TYPE
			SYNTAX ZhoneEnabledFlag
			MAX-ACCESS read-write
			STATUS current
			DESCRIPTION
				"When an ONU is auto-assigned, provision that ONU based on the matching auto config rule."
			DEFVAL { disabled }
			::= { zhoneCpeCfgGlobalSettings 2 }

		
		-- 1.3.6.1.4.1.5504.5.16.1.38.3
		zhoneCpeCfgParamsStr OBJECT-TYPE
			SYNTAX OCTET STRING (SIZE (0..256))
			MAX-ACCESS read-write
			STATUS current
			DESCRIPTION
				"Spare field for temporary parameters."
			DEFVAL { "" }
			::= { zhoneCpeCfgGlobalSettings 3 }

		
		-- 1.3.6.1.4.1.5504.5.16.1.38.4
		zhoneCpeCfgDerivedMacBpppoe OBJECT-TYPE
			SYNTAX ZhoneEnabledFlag
			MAX-ACCESS read-write
			STATUS current
			DESCRIPTION
				"This field is used to enable/disable derived WAN MAC for PPPoE Bridge."
			DEFVAL { enabled }
			::= { zhoneCpeCfgGlobalSettings 4 }

		
		-- 1.3.6.1.4.1.5504.5.16.1.38.5
		zhoneCpeCfgDerivedMacBrouted OBJECT-TYPE
			SYNTAX ZhoneEnabledFlag
			MAX-ACCESS read-write
			STATUS current
			DESCRIPTION
				"This field is used to enable/disable derived WAN MAC for B-Routed Bridge"
			DEFVAL { enabled }
			::= { zhoneCpeCfgGlobalSettings 5 }

		
		-- 1.3.6.1.4.1.5504.5.16.1.38.6
		zhoneCpeCfgDecoupleServiceTemplate OBJECT-TYPE
			SYNTAX INTEGER
				{
				enabled(1),
				disabled(2)
				}
			MAX-ACCESS read-write
			STATUS current
			DESCRIPTION
				"This Field is used to specify whether decouple service template is enabled/disabled."
			DEFVAL { enabled }
			::= { zhoneCpeCfgGlobalSettings 6 }

		
		-- 1.3.6.1.4.1.5504.5.16.1.38.7
		zhoneCpeCfgModelIdFetch OBJECT-TYPE
			SYNTAX ZhoneEnabledFlag
			MAX-ACCESS read-write
			STATUS current
			DESCRIPTION
				"When enabled, model ID is determined for a CPE when
				its serial number is discovered. When disabled, the
				model ID is not determined until the CPE is assigned,
				unless auto-assign is enabled."
			DEFVAL { enabled }
			::= { zhoneCpeCfgGlobalSettings 7 }

		
		-- 1.3.6.1.4.1.5504.5.16.1.39
		zhoneCpeLldpRemoteTable OBJECT-TYPE
			SYNTAX SEQUENCE OF ZhoneCpeLldpRemoteEntry
			MAX-ACCESS not-accessible
			STATUS current
			DESCRIPTION
				"CPE LLDP remote table."
			::= { zhoneCpeObjectID 39 }

		
		-- 1.3.6.1.4.1.5504.5.16.1.39.1
		zhoneCpeLldpRemoteEntry OBJECT-TYPE
			SYNTAX ZhoneCpeLldpRemoteEntry
			MAX-ACCESS not-accessible
			STATUS current
			DESCRIPTION
				"A row in the Cpe Lldp Rem table."
			INDEX { zhoneCpeIfIndex, zhoneCpeTpType, zhoneCpeTpIndex, zhoneCpeLldpRemoteIndex }
			::= { zhoneCpeLldpRemoteTable 1 }

		
		ZhoneCpeLldpRemoteEntry ::=
			SEQUENCE { 
				zhoneCpeLldpRemoteIndex
					Unsigned32,
				zhoneCpeLldpRemoteChassisId
					OCTET STRING,
				zhoneCpeLldpRemotePortId
					OCTET STRING,
				zhoneCpeLldpRemoteSysName
					SnmpAdminString,
				zhoneCpeLldpRemoteHardwareRev
					SnmpAdminString,
				zhoneCpeLldpRemoteFirmwareRev
					SnmpAdminString,
				zhoneCpeLldpRemoteSoftwareRev
					SnmpAdminString,
				zhoneCpeLldpRemoteModelName
					SnmpAdminString,
				zhoneCpeLldpRemoteSerialNum
					SnmpAdminString,
				zhoneCpeLldpRemoteRetVal
					Integer32
			 }

		-- 1.3.6.1.4.1.5504.5.16.1.39.1.1
		zhoneCpeLldpRemoteIndex OBJECT-TYPE
			SYNTAX Unsigned32 (1..2147483647)
			MAX-ACCESS not-accessible
			STATUS current
			DESCRIPTION
				"The Cpe LLDP remote index."
			::= { zhoneCpeLldpRemoteEntry 1 }

		
		-- 1.3.6.1.4.1.5504.5.16.1.39.1.2
		zhoneCpeLldpRemoteChassisId OBJECT-TYPE
			SYNTAX OCTET STRING (SIZE (1..255))
			MAX-ACCESS read-only
			STATUS current
			DESCRIPTION
				"The string value used to identify the chassis component associated
				with the remote system."
			::= { zhoneCpeLldpRemoteEntry 2 }

		
		-- 1.3.6.1.4.1.5504.5.16.1.39.1.3
		zhoneCpeLldpRemotePortId OBJECT-TYPE
			SYNTAX OCTET STRING (SIZE (1..255))
			MAX-ACCESS read-only
			STATUS current
			DESCRIPTION
				"The string value used to identify the port component associated with the
				remote system."
			::= { zhoneCpeLldpRemoteEntry 3 }

		
		-- 1.3.6.1.4.1.5504.5.16.1.39.1.4
		zhoneCpeLldpRemoteSysName OBJECT-TYPE
			SYNTAX SnmpAdminString (SIZE (0..255))
			MAX-ACCESS read-only
			STATUS current
			DESCRIPTION
				"The string value used to identify the system name of the remote system."
			::= { zhoneCpeLldpRemoteEntry 4 }

		
		-- 1.3.6.1.4.1.5504.5.16.1.39.1.5
		zhoneCpeLldpRemoteHardwareRev OBJECT-TYPE
			SYNTAX SnmpAdminString (SIZE (0..32))
			MAX-ACCESS read-only
			STATUS current
			DESCRIPTION
				"The vendor-specific hardware revision string as advertised by the remote endpoint."
			::= { zhoneCpeLldpRemoteEntry 5 }

		
		-- 1.3.6.1.4.1.5504.5.16.1.39.1.6
		zhoneCpeLldpRemoteFirmwareRev OBJECT-TYPE
			SYNTAX SnmpAdminString (SIZE (0..32))
			MAX-ACCESS read-only
			STATUS current
			DESCRIPTION
				"The vendor-specific firmware revision string as advertised by the remote endpoint."
			::= { zhoneCpeLldpRemoteEntry 6 }

		
		-- 1.3.6.1.4.1.5504.5.16.1.39.1.7
		zhoneCpeLldpRemoteSoftwareRev OBJECT-TYPE
			SYNTAX SnmpAdminString (SIZE (0..32))
			MAX-ACCESS read-only
			STATUS current
			DESCRIPTION
				"The vendor-specific software revision string as advertised by the remote endpoint."
			::= { zhoneCpeLldpRemoteEntry 7 }

		
		-- 1.3.6.1.4.1.5504.5.16.1.39.1.8
		zhoneCpeLldpRemoteModelName OBJECT-TYPE
			SYNTAX SnmpAdminString (SIZE (0..32))
			MAX-ACCESS read-only
			STATUS current
			DESCRIPTION
				"The vendor-specific model name as advertised by the remote endpoint."
			::= { zhoneCpeLldpRemoteEntry 8 }

		
		-- 1.3.6.1.4.1.5504.5.16.1.39.1.9
		zhoneCpeLldpRemoteSerialNum OBJECT-TYPE
			SYNTAX SnmpAdminString (SIZE (0..32))
			MAX-ACCESS read-only
			STATUS current
			DESCRIPTION
				"The vendor-specific serial number as advertised by the remote endpoint."
			::= { zhoneCpeLldpRemoteEntry 9 }

		
		-- 1.3.6.1.4.1.5504.5.16.1.39.1.10
		zhoneCpeLldpRemoteRetVal OBJECT-TYPE
			SYNTAX Integer32
			MAX-ACCESS read-only
			STATUS current
			DESCRIPTION
				"Zhone Enhanced Status return value, used to return LLDP 
				error codes ( LLDP disabled, no devices attached, etc )
				from the linecard back to the uplink."
			::= { zhoneCpeLldpRemoteEntry 10 }

		
		-- 1.3.6.1.4.1.5504.5.16.1.40
		zhoneCpeConfigTable OBJECT-TYPE
			SYNTAX SEQUENCE OF ZhoneCpeConfigEntry
			MAX-ACCESS not-accessible
			STATUS current
			DESCRIPTION
				"Configuration parameters applying to a single CPE.
				This profile is auto-created."
			::= { zhoneCpeObjectID 40 }

		
		-- 1.3.6.1.4.1.5504.5.16.1.40.1
		zhoneCpeConfigEntry OBJECT-TYPE
			SYNTAX ZhoneCpeConfigEntry
			MAX-ACCESS not-accessible
			STATUS current
			DESCRIPTION
				"A row in the CPE config table."
			INDEX { zhoneCpeConfigIfIndex }
			::= { zhoneCpeConfigTable 1 }

		
		ZhoneCpeConfigEntry ::=
			SEQUENCE { 
				zhoneCpeConfigIfIndex
					InterfaceIndex,
				zhoneCpeConfigMEProfileName
					ZhoneAdminString,
				zhoneCpeConfigGenericProfileName
					ZhoneAdminString,
				zhoneCpeConfigPhysicalTraps
					ZhoneEnabledFlag,
				zhoneCpeConfigLineStatusTraps
					INTEGER,
				zhoneCpeConfigAutoUpgrade
					ZhoneEnabledFlag,
				zhoneCpeConfigLinkStatusAlarmSeverity
					INTEGER
			 }

		-- 1.3.6.1.4.1.5504.5.16.1.40.1.1
		zhoneCpeConfigIfIndex OBJECT-TYPE
			SYNTAX InterfaceIndex
			MAX-ACCESS not-accessible
			STATUS current
			DESCRIPTION
				"IfIndex of the cpe interface stacked on the physical"
			::= { zhoneCpeConfigEntry 1 }

		
		-- 1.3.6.1.4.1.5504.5.16.1.40.1.2
		zhoneCpeConfigMEProfileName OBJECT-TYPE
			SYNTAX ZhoneAdminString
			MAX-ACCESS read-create
			STATUS current
			DESCRIPTION
				"This is the name of a Profile that contains commands which 
				can configure a CPE. It is expected that this Profile contain 
				commands that configure the Managed Entities (ME) on an
				CPE."
			DEFVAL { "" }
			::= { zhoneCpeConfigEntry 2 }

		
		-- 1.3.6.1.4.1.5504.5.16.1.40.1.3
		zhoneCpeConfigGenericProfileName OBJECT-TYPE
			SYNTAX ZhoneAdminString
			MAX-ACCESS read-create
			STATUS current
			DESCRIPTION
				"This is the name of a Profile that contains commands which 
				can configure a CPE It is expected that this profile contain 
				generic commands that are common to multiple CPEs."
			DEFVAL { "" }
			::= { zhoneCpeConfigEntry 3 }

		
		-- 1.3.6.1.4.1.5504.5.16.1.40.1.4
		zhoneCpeConfigPhysicalTraps OBJECT-TYPE
			SYNTAX ZhoneEnabledFlag
			MAX-ACCESS read-create
			STATUS current
			DESCRIPTION
				"If enabled, then an asynchronous notification from the CPE with 
				ME class ONT-G triggers an omciOnuAlarms trap. The alarm conditions 
				for this ME class are: equipment alarm, powering alarm, battery 
				missing, battery failure, battery low, physical intrusion alarm, 
				and self-test failure."
			DEFVAL { disabled }
			::= { zhoneCpeConfigEntry 4 }

		
		-- 1.3.6.1.4.1.5504.5.16.1.40.1.5
		zhoneCpeConfigLineStatusTraps OBJECT-TYPE
			SYNTAX INTEGER
				{
				enabled(1),
				disabled(2),
				auto(3),
				linkonly(4)
				}
			MAX-ACCESS read-create
			STATUS current
			DESCRIPTION
				"If enabled, then gponOnuLineStatusChange traps, and also LinkUp/LinkDown 
				traps, are sent whenever line status changes between up and down. If 
				disabled, none of these traps is sent. If auto, then line status traps 
				are sent if the 'dying gasp' flag is on (for line down), or if the 
				'dying gasp' flag was on (for line up). Link down/up traps are not sent."
			DEFVAL { disabled }
			::= { zhoneCpeConfigEntry 5 }

		
		-- 1.3.6.1.4.1.5504.5.16.1.40.1.6
		zhoneCpeConfigAutoUpgrade OBJECT-TYPE
			SYNTAX ZhoneEnabledFlag
			MAX-ACCESS read-create
			STATUS current
			DESCRIPTION
				"If enabled, then the ONU s/w will be upgraded if the ONU version
				does not match the assoicated remote upgrade profile.  Changing
				this variable to disabled will not abort a remote software
				upgrade already in progress.
				"
			DEFVAL { enabled }
			::= { zhoneCpeConfigEntry 6 }

		
		-- 1.3.6.1.4.1.5504.5.16.1.40.1.7
		zhoneCpeConfigLinkStatusAlarmSeverity OBJECT-TYPE
			SYNTAX INTEGER
				{
				critical(1),
				major(2),
				minor(3)
				}
			MAX-ACCESS read-create
			STATUS current
			DESCRIPTION
				"Based on the severity set in this field LinkUp/LinkDown
				alarms are raised."
			DEFVAL { minor }
			::= { zhoneCpeConfigEntry 7 }

		
		-- 1.3.6.1.4.1.5504.5.16.1.41
		zhoneCpeVlanFilterList OBJECT-IDENTITY
			STATUS current
			DESCRIPTION 
				"VLAN Filter List Objects."
			::= { zhoneCpeObjectID 41 }

		
		-- 1.3.6.1.4.1.5504.5.16.1.41.1
		zhoneCpeVlanFilterListIndexNext OBJECT-TYPE
			SYNTAX Integer32
			MAX-ACCESS read-only
			STATUS current
			DESCRIPTION
				"This object contains an appropriate value to be used for the
				zhoneCpeVlanFilterListIndex when creating entries in the zhoneCpeVlanFilterListTable.
				The value 0 indicates that no unassigned entries are available. To obtain the
				zhoneCpeVlanFilterListIndex value for a new entry, the manager issues a management
				protocol retrieval operation to obtain the current value of this object.  After each
				retrieval, the agent should modify the value to the next unassigned index.
				
				After a manager retrieves a value the agent will determine through its local
				policy when this index value will be made available for reuse."
			::= { zhoneCpeVlanFilterList 1 }

		
		-- 1.3.6.1.4.1.5504.5.16.1.41.2
		zhoneCpeVlanFilterListTable OBJECT-TYPE
			SYNTAX SEQUENCE OF ZhoneCpeVlanFilterListEntry
			MAX-ACCESS not-accessible
			STATUS current
			DESCRIPTION
				"The table of CPE VLAN Filter List entries."
			::= { zhoneCpeVlanFilterList 2 }

		
		-- 1.3.6.1.4.1.5504.5.16.1.41.2.1
		zhoneCpeVlanFilterListEntry OBJECT-TYPE
			SYNTAX ZhoneCpeVlanFilterListEntry
			MAX-ACCESS not-accessible
			STATUS current
			DESCRIPTION
				"Row in the zhoneCpeVlanFilterList table."
			INDEX { zhoneCpeVlanFilterListIndex }
			::= { zhoneCpeVlanFilterListTable 1 }

		
		ZhoneCpeVlanFilterListEntry ::=
			SEQUENCE { 
				zhoneCpeVlanFilterListIndex
					Unsigned32,
				zhoneCpeVlanFilterListRowStatus
					RowStatus,
				zhoneCpeVlanFilterListProfileName
					ZhoneAdminString
			 }

		-- 1.3.6.1.4.1.5504.5.16.1.41.2.1.2
		zhoneCpeVlanFilterListIndex OBJECT-TYPE
			SYNTAX Unsigned32
			MAX-ACCESS not-accessible
			STATUS current
			DESCRIPTION
				"Index number for the zhoneCpeDnsHostList table entry."
			::= { zhoneCpeVlanFilterListEntry 2 }

		
		-- 1.3.6.1.4.1.5504.5.16.1.41.2.1.3
		zhoneCpeVlanFilterListRowStatus OBJECT-TYPE
			SYNTAX RowStatus
			MAX-ACCESS read-create
			STATUS current
			DESCRIPTION
				"Used to create, modify or delete an entry in this table."
			DEFVAL { active }
			::= { zhoneCpeVlanFilterListEntry 3 }

		
		-- 1.3.6.1.4.1.5504.5.16.1.41.2.1.4
		zhoneCpeVlanFilterListProfileName OBJECT-TYPE
			SYNTAX ZhoneAdminString
			MAX-ACCESS read-create
			STATUS current
			DESCRIPTION
				"Profile name for this cpe-dns-host profile. This must be 
				unique, and is writable only on creation."
			DEFVAL { "" }
			::= { zhoneCpeVlanFilterListEntry 4 }

		
		-- 1.3.6.1.4.1.5504.5.16.1.42
		zhoneCpeVlanFilter OBJECT-IDENTITY
			STATUS current
			DESCRIPTION 
				"Description."
			::= { zhoneCpeObjectID 42 }

		
		-- 1.3.6.1.4.1.5504.5.16.1.42.1
		zhoneCpeVlanFilterIndexTable OBJECT-TYPE
			SYNTAX SEQUENCE OF ZhoneCpeVlanFilterIndexEntry
			MAX-ACCESS not-accessible
			STATUS current
			DESCRIPTION
				"Table of next available values for CPE VLAN Filter Entry index."
			::= { zhoneCpeVlanFilter 1 }

		
		-- 1.3.6.1.4.1.5504.5.16.1.42.1.1
		zhoneCpeVlanFilterIndexEntry OBJECT-TYPE
			SYNTAX ZhoneCpeVlanFilterIndexEntry
			MAX-ACCESS not-accessible
			STATUS current
			DESCRIPTION
				"Row in the zhoneCpeVlanFilterIndex table."
			INDEX { zhoneCpeDnsHostListIndex }
			::= { zhoneCpeVlanFilterIndexTable 1 }

		
		ZhoneCpeVlanFilterIndexEntry ::=
			SEQUENCE { 
				zhoneCpeVlanFilterIndexEntryIndexNext
					Integer32
			 }

		-- 1.3.6.1.4.1.5504.5.16.1.42.1.1.1
		zhoneCpeVlanFilterIndexEntryIndexNext OBJECT-TYPE
			SYNTAX Integer32
			MAX-ACCESS read-only
			STATUS current
			DESCRIPTION
				"Next available entry index for row in zhoneCpeVlanFilterTable."
			::= { zhoneCpeVlanFilterIndexEntry 1 }

		
		-- 1.3.6.1.4.1.5504.5.16.1.42.2
		zhoneCpeVlanFilterTable OBJECT-TYPE
			SYNTAX SEQUENCE OF ZhoneCpeVlanFilterEntry
			MAX-ACCESS not-accessible
			STATUS current
			DESCRIPTION
				"The table of CPE VLAN Filter entries."
			::= { zhoneCpeVlanFilter 2 }

		
		-- 1.3.6.1.4.1.5504.5.16.1.42.2.1
		zhoneCpeVlanFilterEntry OBJECT-TYPE
			SYNTAX ZhoneCpeVlanFilterEntry
			MAX-ACCESS not-accessible
			STATUS current
			DESCRIPTION
				"Single entry in CPE VLAN Filter table"
			INDEX { zhoneCpeVlanFilterListIndex, zhoneCpeVlanFilterEntryIndex }
			::= { zhoneCpeVlanFilterTable 1 }

		
		ZhoneCpeVlanFilterEntry ::=
			SEQUENCE { 
				zhoneCpeVlanFilterEntryIndex
					Unsigned32,
				zhoneCpeVlanFilterRowStatus
					RowStatus,
				zhoneCpeVlanFilterAdminState
					ZhoneAdminState,
				zhoneCpeVlanFilterPriority
					Unsigned32,
				zhoneCpeVlanFilterSrcMac
					OCTET STRING,
				zhoneCpeVlanFilterMacMask
					OCTET STRING,
				zhoneCpeVlanFilterSrcIp
					OCTET STRING,
				zhoneCpeVlanFilterDestIp
					OCTET STRING,
				zhoneCpeVlanFilterDscp
					OCTET STRING,
				zhoneCpeVlanFilterDiscard
					TruthValue,
				zhoneCpeVlanFilterNewVlan
					Unsigned32,
				zhoneCpeVlanFilterNewCos
					Unsigned32,
				zhoneCpeVlanFilterNewDscp
					OCTET STRING,
				zhoneCpeVlanFilterEtherType
					INTEGER
			 }

		-- 1.3.6.1.4.1.5504.5.16.1.42.2.1.1
		zhoneCpeVlanFilterEntryIndex OBJECT-TYPE
			SYNTAX Unsigned32
			MAX-ACCESS not-accessible
			STATUS current
			DESCRIPTION
				"Index for this entry within the CpeDnsHost list."
			::= { zhoneCpeVlanFilterEntry 1 }

		
		-- 1.3.6.1.4.1.5504.5.16.1.42.2.1.2
		zhoneCpeVlanFilterRowStatus OBJECT-TYPE
			SYNTAX RowStatus
			MAX-ACCESS read-create
			STATUS current
			DESCRIPTION
				"Used to create, modify or delete an entry in this table."
			DEFVAL { active }
			::= { zhoneCpeVlanFilterEntry 2 }

		
		-- 1.3.6.1.4.1.5504.5.16.1.42.2.1.3
		zhoneCpeVlanFilterAdminState OBJECT-TYPE
			SYNTAX ZhoneAdminState
			MAX-ACCESS read-create
			STATUS current
			DESCRIPTION
				"Must be UP for the rule to be active.  DOWN is used to turn off
				a rule without deleting it.  Default value is UP."
			DEFVAL { 1 }
			::= { zhoneCpeVlanFilterEntry 3 }

		
		-- 1.3.6.1.4.1.5504.5.16.1.42.2.1.4
		zhoneCpeVlanFilterPriority OBJECT-TYPE
			SYNTAX Unsigned32 (1..10)
			MAX-ACCESS read-create
			STATUS current
			DESCRIPTION
				"When multiple VLAN filter rules are applied to the same physical
				port and aningress packet matches more than one rule, the rule with
				the highest priority will be applied.  Value from 1 to 10 with 
				1 being the highest priority."
			DEFVAL { 1 }
			::= { zhoneCpeVlanFilterEntry 4 }

		
		-- 1.3.6.1.4.1.5504.5.16.1.42.2.1.5
		zhoneCpeVlanFilterSrcMac OBJECT-TYPE
			SYNTAX OCTET STRING (SIZE (0..18))
			MAX-ACCESS read-create
			STATUS current
			DESCRIPTION
				"Specifies the base MAC value when used as part of a Classifier.
				
				This is an ascii string of the form nn:nn:nn:nn:nn:nn with a
				NULL terminator."
			DEFVAL { "" }
			::= { zhoneCpeVlanFilterEntry 5 }

		
		-- 1.3.6.1.4.1.5504.5.16.1.42.2.1.6
		zhoneCpeVlanFilterMacMask OBJECT-TYPE
			SYNTAX OCTET STRING (SIZE (0..18))
			MAX-ACCESS read-create
			STATUS current
			DESCRIPTION
				"Specifies the mask to use when comparing an ingress packet to the
				configured source MAC value.
				
				This is an ascii string of the form nn:nn:nn:nn:nn:nn with a
				NULL terminator."
			DEFVAL { "" }
			::= { zhoneCpeVlanFilterEntry 6 }

		
		-- 1.3.6.1.4.1.5504.5.16.1.42.2.1.7
		zhoneCpeVlanFilterSrcIp OBJECT-TYPE
			SYNTAX OCTET STRING (SIZE (0..19))
			MAX-ACCESS read-create
			STATUS current
			DESCRIPTION
				"Specifies the source IP address and prefix used as part of the classifier.
				The Prefix is the number of bits starting from the left to create an IP mask.
				For example: 19216.8.1.0/24
				
				This is an ascii string of the form nnn.nnn.nnn.nnn/mm."
			DEFVAL { "" }
			::= { zhoneCpeVlanFilterEntry 7 }

		
		-- 1.3.6.1.4.1.5504.5.16.1.42.2.1.8
		zhoneCpeVlanFilterDestIp OBJECT-TYPE
			SYNTAX OCTET STRING (SIZE (0..19))
			MAX-ACCESS read-create
			STATUS current
			DESCRIPTION
				"Specifies the destination IP address and prefix used as part of the classifier.
				The Prefix is the number of bits starting from the left to create an IP mask.
				For example: 19216.8.1.0/24
				
				This is an ascii string of the form nnn.nnn.nnn.nnn/mm."
			DEFVAL { "" }
			::= { zhoneCpeVlanFilterEntry 8 }

		
		-- 1.3.6.1.4.1.5504.5.16.1.42.2.1.9
		zhoneCpeVlanFilterDscp OBJECT-TYPE
			SYNTAX OCTET STRING (SIZE (1..8))
			MAX-ACCESS read-create
			STATUS current
			DESCRIPTION
				"Specifies the DSCP, Differentiated Services Code Point, value used as
				part of the classifier..  It is an 8 byte string, 0-63 DSCP values
				or names.
				
				Valid code values:
				
				<0-63>   Differentiated services codepoint value 
				   af11     Mark packets with AF11 dscp (001010) 
				   af12     Mark packets with AF12 dscp (001100) 
				   af13     Mark packets with AF13 dscp (001110) 
				   af21     Mark packets with AF21 dscp (010010) 
				   af22     Mark packets with AF22 dscp (010100) 
				   af23     Mark packets with AF23 dscp (010110) 
				   af31     Mark packets with AF31 dscp (011010) 
				   af32     Mark packets with AF32 dscp (011100) 
				   af33     Mark packets with AF33 dscp (011110) 
				   af41     Mark packets with AF41 dscp (100010) 
				   af42     Mark packets with AF42 dscp (100100) 
				   af43     Mark packets with AF43 dscp (100110) 
				   cs1      Mark packets with CS1(precedence 1) dscp (001000) 
				   cs2      Mark packets with CS2(precedence 2) dscp (010000) 
				   cs3      Mark packets with CS3(precedence 3) dscp (011000) 
				   cs4      Mark packets with CS4(precedence 4) dscp (100000) 
				   cs5      Mark packets with CS5(precedence 5) dscp (101000) 
				   cs6      Mark packets with CS6(precedence 6) dscp (110000) 
				   cs7      Mark packets with CS7(precedence 7) dscp (111000) 
				   default  Mark packets with default dscp (000000) 
				   ef       Mark packets with EF dscp (101110) "
			DEFVAL { "0" }
			::= { zhoneCpeVlanFilterEntry 9 }

		
		-- 1.3.6.1.4.1.5504.5.16.1.42.2.1.10
		zhoneCpeVlanFilterDiscard OBJECT-TYPE
			SYNTAX TruthValue
			MAX-ACCESS read-create
			STATUS current
			DESCRIPTION
				"When enabled, all packets that match the Classification Rule will be
				dropped."
			DEFVAL { false }
			::= { zhoneCpeVlanFilterEntry 10 }

		
		-- 1.3.6.1.4.1.5504.5.16.1.42.2.1.11
		zhoneCpeVlanFilterNewVlan OBJECT-TYPE
			SYNTAX Unsigned32 (0..4095)
			MAX-ACCESS read-create
			STATUS current
			DESCRIPTION
				"When enabled, all packets that match the Classification Rule will be
				dropped."
			DEFVAL { 0 }
			::= { zhoneCpeVlanFilterEntry 11 }

		
		-- 1.3.6.1.4.1.5504.5.16.1.42.2.1.12
		zhoneCpeVlanFilterNewCos OBJECT-TYPE
			SYNTAX Unsigned32 (0..7)
			MAX-ACCESS read-create
			STATUS current
			DESCRIPTION
				"When discrd all packets is disabled, specifies the VLAN Priority value to
				apply to packets that match the Classification Rule."
			DEFVAL { 0 }
			::= { zhoneCpeVlanFilterEntry 12 }

		
		-- 1.3.6.1.4.1.5504.5.16.1.42.2.1.13
		zhoneCpeVlanFilterNewDscp OBJECT-TYPE
			SYNTAX OCTET STRING (SIZE (1..8))
			MAX-ACCESS read-create
			STATUS current
			DESCRIPTION
				"When discard all packets is disabled, specifies the DSP value to apply to
				packets that match the Classification Rule.
				
				
				Valid code values:
				
				<0-63>   Differentiated services codepoint value 
				   af11     Mark packets with AF11 dscp (001010) 
				   af12     Mark packets with AF12 dscp (001100) 
				   af13     Mark packets with AF13 dscp (001110) 
				   af21     Mark packets with AF21 dscp (010010) 
				   af22     Mark packets with AF22 dscp (010100) 
				   af23     Mark packets with AF23 dscp (010110) 
				   af31     Mark packets with AF31 dscp (011010) 
				   af32     Mark packets with AF32 dscp (011100) 
				   af33     Mark packets with AF33 dscp (011110) 
				   af41     Mark packets with AF41 dscp (100010) 
				   af42     Mark packets with AF42 dscp (100100) 
				   af43     Mark packets with AF43 dscp (100110) 
				   cs1      Mark packets with CS1(precedence 1) dscp (001000) 
				   cs2      Mark packets with CS2(precedence 2) dscp (010000) 
				   cs3      Mark packets with CS3(precedence 3) dscp (011000) 
				   cs4      Mark packets with CS4(precedence 4) dscp (100000) 
				   cs5      Mark packets with CS5(precedence 5) dscp (101000) 
				   cs6      Mark packets with CS6(precedence 6) dscp (110000) 
				   cs7      Mark packets with CS7(precedence 7) dscp (111000) 
				   default  Mark packets with default dscp (000000) 
				   ef       Mark packets with EF dscp (101110) "
			DEFVAL { "0" }
			::= { zhoneCpeVlanFilterEntry 13 }

		
		-- 1.3.6.1.4.1.5504.5.16.1.42.2.1.14
		zhoneCpeVlanFilterEtherType OBJECT-TYPE
			SYNTAX INTEGER
				{
				any(1),
				ipv4(2),
				ipv6(3),
				arp(4),
				pppoediscovery(5),
				pppoesession(6)
				}
			MAX-ACCESS read-create
			STATUS current
			DESCRIPTION
				"Specifies the Ethernet Type used as part of the classifier"
			DEFVAL { any }
			::= { zhoneCpeVlanFilterEntry 14 }

		
		-- 1.3.6.1.4.1.5504.5.16.1.43
		zhoneCpeMacIpLocationTable OBJECT-TYPE
			SYNTAX SEQUENCE OF ZhoneCpeMacIpLocationEntry
			MAX-ACCESS not-accessible
			STATUS current
			DESCRIPTION
				"CPE MAC/IP location collected from CPE.
				
				This is an internal profile that is not exposed.  
				
				MIB handler will reject all requests to access this profile."
			::= { zhoneCpeObjectID 43 }

		
		-- 1.3.6.1.4.1.5504.5.16.1.43.1
		zhoneCpeMacIpLocationEntry OBJECT-TYPE
			SYNTAX ZhoneCpeMacIpLocationEntry
			MAX-ACCESS not-accessible
			STATUS current
			DESCRIPTION
				"Single entry in table"
			INDEX { zhoneCpeMacIpLocationCpeIfIndex, zhoneCpeMacIpLocationShelf, zhoneCpeMacIpLocationSlot, zhoneCpeMacIpLocationPort, zhoneCpeMacIpLocationSubPort, 
				zhoneCpeMacIpLocationAddrType, zhoneCpeMacIpLocationAddr }
			::= { zhoneCpeMacIpLocationTable 1 }

		
		ZhoneCpeMacIpLocationEntry ::=
			SEQUENCE { 
				zhoneCpeMacIpLocationCpeIfIndex
					InterfaceIndex,
				zhoneCpeMacIpLocationShelf
					ZhoneShelfValue,
				zhoneCpeMacIpLocationSlot
					ZhoneSlotValue,
				zhoneCpeMacIpLocationPort
					Unsigned32,
				zhoneCpeMacIpLocationSubPort
					Unsigned32,
				zhoneCpeMacIpLocationAddrType
					ZhoneMacIpAddrType,
				zhoneCpeMacIpLocationAddr
					PhysAddress,
				zhoneCpeMacIpLocationCpePortTpType
					TpType,
				zhoneCpeMacIpLocationCpePortTpIndex
					Unsigned32,
				zhoneCpeMacIpLocationCpePortIfName
					ZhoneCpeIfName,
				zhoneCpeMacIpLocationCpePortVlan
					Unsigned32,
				zhoneCpeMacIpLocationCpePortStatus
					OCTET STRING
			 }

		-- 1.3.6.1.4.1.5504.5.16.1.43.1.1
		zhoneCpeMacIpLocationCpeIfIndex OBJECT-TYPE
			SYNTAX InterfaceIndex
			MAX-ACCESS read-only
			STATUS current
			DESCRIPTION
				"IfIndex of CPE which has the MAC/IP address.
				For GPON, it will be the ONU ifIndex.  For Ethernet, 
				it will be the Ethernet physical."
			::= { zhoneCpeMacIpLocationEntry 1 }

		
		-- 1.3.6.1.4.1.5504.5.16.1.43.1.2
		zhoneCpeMacIpLocationShelf OBJECT-TYPE
			SYNTAX ZhoneShelfValue
			MAX-ACCESS read-write
			STATUS current
			DESCRIPTION
				"Shelf value of CPE which has the MAC/IP address"
			::= { zhoneCpeMacIpLocationEntry 2 }

		
		-- 1.3.6.1.4.1.5504.5.16.1.43.1.3
		zhoneCpeMacIpLocationSlot OBJECT-TYPE
			SYNTAX ZhoneSlotValue
			MAX-ACCESS read-only
			STATUS current
			DESCRIPTION
				"Slot value of CPE which has the MAC/IP address"
			::= { zhoneCpeMacIpLocationEntry 3 }

		
		-- 1.3.6.1.4.1.5504.5.16.1.43.1.4
		zhoneCpeMacIpLocationPort OBJECT-TYPE
			SYNTAX Unsigned32
			MAX-ACCESS read-only
			STATUS current
			DESCRIPTION
				"Port value of CPE which has the MAC/IP address"
			::= { zhoneCpeMacIpLocationEntry 4 }

		
		-- 1.3.6.1.4.1.5504.5.16.1.43.1.5
		zhoneCpeMacIpLocationSubPort OBJECT-TYPE
			SYNTAX Unsigned32
			MAX-ACCESS read-only
			STATUS current
			DESCRIPTION
				"Subport value of CPE which has the MAC/IP address"
			::= { zhoneCpeMacIpLocationEntry 5 }

		
		-- 1.3.6.1.4.1.5504.5.16.1.43.1.6
		zhoneCpeMacIpLocationAddrType OBJECT-TYPE
			SYNTAX ZhoneMacIpAddrType
			MAX-ACCESS read-only
			STATUS current
			DESCRIPTION
				"MAC, IPv4, or IPv6 address."
			::= { zhoneCpeMacIpLocationEntry 6 }

		
		-- 1.3.6.1.4.1.5504.5.16.1.43.1.7
		zhoneCpeMacIpLocationAddr OBJECT-TYPE
			SYNTAX PhysAddress
			MAX-ACCESS read-only
			STATUS current
			DESCRIPTION
				"MAC/IP address"
			::= { zhoneCpeMacIpLocationEntry 7 }

		
		-- 1.3.6.1.4.1.5504.5.16.1.43.1.8
		zhoneCpeMacIpLocationCpePortTpType OBJECT-TYPE
			SYNTAX TpType
			MAX-ACCESS read-only
			STATUS current
			DESCRIPTION
				"CPE Port TpType for the MAC/IP address.
				
				If MAC/IP not found ( or 'mac find' not supported ) then this 
				value will be zero."
			::= { zhoneCpeMacIpLocationEntry 8 }

		
		-- 1.3.6.1.4.1.5504.5.16.1.43.1.9
		zhoneCpeMacIpLocationCpePortTpIndex OBJECT-TYPE
			SYNTAX Unsigned32
			MAX-ACCESS read-only
			STATUS current
			DESCRIPTION
				"CPE Port TpIndex for the MAC/IP address.
				
				If MAC/IP not found ( or 'mac find' not supported ) then this 
				value will be zero."
			::= { zhoneCpeMacIpLocationEntry 9 }

		
		-- 1.3.6.1.4.1.5504.5.16.1.43.1.10
		zhoneCpeMacIpLocationCpePortIfName OBJECT-TYPE
			SYNTAX ZhoneCpeIfName
			MAX-ACCESS read-only
			STATUS current
			DESCRIPTION
				"CPE port ifName reported by the CPE.
				
				If MAC/IP not found ( or 'mac find' not supported ) then this 
				value will be zero."
			::= { zhoneCpeMacIpLocationEntry 10 }

		
		-- 1.3.6.1.4.1.5504.5.16.1.43.1.11
		zhoneCpeMacIpLocationCpePortVlan OBJECT-TYPE
			SYNTAX Unsigned32
			MAX-ACCESS read-only
			STATUS current
			DESCRIPTION
				"CPE Port VLAN for the MAC/IP.
				
				If MAC/IP not found ( or 'mac find' not supported ) then this 
				value will be zero."
			::= { zhoneCpeMacIpLocationEntry 11 }

		
		-- 1.3.6.1.4.1.5504.5.16.1.43.1.12
		zhoneCpeMacIpLocationCpePortStatus OBJECT-TYPE
			SYNTAX OCTET STRING
			MAX-ACCESS read-only
			STATUS current
			DESCRIPTION
				"Current CPE Port status.
				
				If MAC/IP not found ( or 'mac find' not supported ) then this 
				value will be zero."
			::= { zhoneCpeMacIpLocationEntry 12 }

		
		-- 1.3.6.1.4.1.5504.5.16.1.44
		zhoneCpeInventoryDataTable OBJECT-TYPE
			SYNTAX SEQUENCE OF ZhoneCpeInventoryDataEntry
			MAX-ACCESS not-accessible
			STATUS current
			DESCRIPTION
				"Informations retrieved from CPEs
				This profile is auto-created."
			::= { zhoneCpeObjectID 44 }

		
		-- 1.3.6.1.4.1.5504.5.16.1.44.1
		zhoneCpeInventoryDataEntry OBJECT-TYPE
			SYNTAX ZhoneCpeInventoryDataEntry
			MAX-ACCESS not-accessible
			STATUS current
			DESCRIPTION
				"A row in the CPE inventoryData table."
			INDEX { zhoneCpeInventoryDataIfIndex }
			::= { zhoneCpeInventoryDataTable 1 }

		
		ZhoneCpeInventoryDataEntry ::=
			SEQUENCE { 
				zhoneCpeInventoryDataIfIndex
					InterfaceIndex,
				zhoneCpeInventoryDataModel
					OCTET STRING,
				zhoneCpeInventoryDataImageVersionActive
					OCTET STRING,
				zhoneCpeInventoryDataImageVersionStandby
					OCTET STRING,
				zhoneCpeInventoryDataSnmpDataSync
					Unsigned32,
				zhoneCpeInventoryDataSerialNoVendorId
					ZhoneAdminString,
				zhoneCpeInventoryDataSerialNoVendorSpecific
					ZhoneAdminString
			 }

		-- 1.3.6.1.4.1.5504.5.16.1.44.1.1
		zhoneCpeInventoryDataIfIndex OBJECT-TYPE
			SYNTAX InterfaceIndex
			MAX-ACCESS not-accessible
			STATUS current
			DESCRIPTION
				"IfIndex of the cpe interface stacked on the physical."
			::= { zhoneCpeInventoryDataEntry 1 }

		
		-- 1.3.6.1.4.1.5504.5.16.1.44.1.2
		zhoneCpeInventoryDataModel OBJECT-TYPE
			SYNTAX OCTET STRING (SIZE (0..20))
			MAX-ACCESS read-only
			STATUS current
			DESCRIPTION
				"Model ID returned from this CPE."
			::= { zhoneCpeInventoryDataEntry 2 }

		
		-- 1.3.6.1.4.1.5504.5.16.1.44.1.3
		zhoneCpeInventoryDataImageVersionActive OBJECT-TYPE
			SYNTAX OCTET STRING (SIZE (0..64))
			MAX-ACCESS read-only
			STATUS current
			DESCRIPTION
				"Version information for the active s/w image."
			::= { zhoneCpeInventoryDataEntry 3 }

		
		-- 1.3.6.1.4.1.5504.5.16.1.44.1.4
		zhoneCpeInventoryDataImageVersionStandby OBJECT-TYPE
			SYNTAX OCTET STRING (SIZE (0..64))
			MAX-ACCESS read-only
			STATUS current
			DESCRIPTION
				"Version information for the standby s/w image."
			::= { zhoneCpeInventoryDataEntry 4 }

		
		-- 1.3.6.1.4.1.5504.5.16.1.44.1.5
		zhoneCpeInventoryDataSnmpDataSync OBJECT-TYPE
			SYNTAX Unsigned32
			MAX-ACCESS read-only
			STATUS current
			DESCRIPTION
				"If the SNMP provisioning change value returned from the CPE 
				matches the MXK value, config not required."
			DEFVAL { 0 }
			::= { zhoneCpeInventoryDataEntry 5 }

		
		-- 1.3.6.1.4.1.5504.5.16.1.44.1.6
		zhoneCpeInventoryDataSerialNoVendorId OBJECT-TYPE
			SYNTAX ZhoneAdminString (SIZE (0..4))
			MAX-ACCESS read-only
			STATUS current
			DESCRIPTION
				"This is a string of 4 ascii characters representing the vendor 
				ID portion of the CPE serial number.
				Example: 'ZNTS' for Zhone."
			DEFVAL { "ZNTS" }
			::= { zhoneCpeInventoryDataEntry 6 }

		
		-- 1.3.6.1.4.1.5504.5.16.1.44.1.7
		zhoneCpeInventoryDataSerialNoVendorSpecific OBJECT-TYPE
			SYNTAX ZhoneAdminString (SIZE (1..10))
			MAX-ACCESS read-only
			STATUS current
			DESCRIPTION
				"This is a string of ascii decimal digits representing the vendor-specific
				portion of the CPE serial number."
			DEFVAL { "0" }
			::= { zhoneCpeInventoryDataEntry 7 }

		
		-- 1.3.6.1.4.1.5504.5.16.1.45
		zhoneCpeAccessCtrlList OBJECT-IDENTITY
			STATUS current
			DESCRIPTION 
				"CPE Ethernet/WLan access control list object"
			::= { zhoneCpeObjectID 45 }

		
		-- 1.3.6.1.4.1.5504.5.16.1.45.1
		zhoneCpeAccessCtrlListIndexNext OBJECT-TYPE
			SYNTAX Integer32
			MAX-ACCESS read-only
			STATUS current
			DESCRIPTION
				"This object contains an appropriate value to be used for the
				zhoneCpeAccessCtrlListIndex when creating entries in the zhoneCpeAccessCtrlListTable.
				The value 0 indicates that no unassigned entries are available. To obtain the
				zhoneCpeAccessCtrlListIndex value for a new entry, the manager issues a management
				protocol retrieval operation to obtain the current value of this object.  After each
				retrieval, the agent should modify the value to the next unassigned index.
								
				After a manager retrieves a value the agent will determine through its local
				policy when this index value will be made available for reuse"
			::= { zhoneCpeAccessCtrlList 1 }

		
		-- 1.3.6.1.4.1.5504.5.16.1.45.2
		zhoneCpeAccessCtrlListTable OBJECT-TYPE
			SYNTAX SEQUENCE OF ZhoneCpeAccessCtrlListEntry
			MAX-ACCESS not-accessible
			STATUS current
			DESCRIPTION
				"The table of CPE Access control list entries"
			::= { zhoneCpeAccessCtrlList 2 }

		
		-- 1.3.6.1.4.1.5504.5.16.1.45.2.1
		zhoneCpeAccessCtrlListEntry OBJECT-TYPE
			SYNTAX ZhoneCpeAccessCtrlListEntry
			MAX-ACCESS not-accessible
			STATUS current
			DESCRIPTION
				"A row in the cpe access list table"
			INDEX { zhoneCpeAccessCtrlListIndex }
			::= { zhoneCpeAccessCtrlListTable 1 }

		
		ZhoneCpeAccessCtrlListEntry ::=
			SEQUENCE { 
				zhoneCpeAccessCtrlListIndex
					Unsigned32,
				zhoneCpeAccessCtrlListRowStatus
					RowStatus,
				zhoneCpeAccessCtrlListProfileName
					ZhoneAdminString,
				zhoneCpeAccessCtrlListType
					INTEGER
			 }

		-- 1.3.6.1.4.1.5504.5.16.1.45.2.1.1
		zhoneCpeAccessCtrlListIndex OBJECT-TYPE
			SYNTAX Unsigned32
			MAX-ACCESS not-accessible
			STATUS current
			DESCRIPTION
				"Index number for the zhoneCpeAccessCtrlList Table entry"
			::= { zhoneCpeAccessCtrlListEntry 1 }

		
		-- 1.3.6.1.4.1.5504.5.16.1.45.2.1.2
		zhoneCpeAccessCtrlListRowStatus OBJECT-TYPE
			SYNTAX RowStatus
			MAX-ACCESS read-create
			STATUS current
			DESCRIPTION
				"Used to create, modify or delete an entry in this table"
			DEFVAL { active }
			::= { zhoneCpeAccessCtrlListEntry 2 }

		
		-- 1.3.6.1.4.1.5504.5.16.1.45.2.1.3
		zhoneCpeAccessCtrlListProfileName OBJECT-TYPE
			SYNTAX ZhoneAdminString
			MAX-ACCESS read-create
			STATUS current
			DESCRIPTION
				"Profile name for this cpe-access-ctrl-list profile. This must be
				unique, and is writable only on creation"
			DEFVAL { "" }
			::= { zhoneCpeAccessCtrlListEntry 3 }

		
		-- 1.3.6.1.4.1.5504.5.16.1.45.2.1.4
		zhoneCpeAccessCtrlListType OBJECT-TYPE
			SYNTAX INTEGER
				{
				blacklist(1),
				whitelist(2)
				}
			MAX-ACCESS read-create
			STATUS current
			DESCRIPTION
				"This field specifies the control mode for the access control
				list.Value can be whilelist or blacklist. 
				Whitelist mode will allow only those packets that match the
				configured Filter Rules for the portand all others are 
				blocked. 
				Blacklist mode will block all packets that match the 
				configured Filter Rules for the port, and all others 
				will be allowed"
			DEFVAL { blacklist }
			::= { zhoneCpeAccessCtrlListEntry 4 }

		
		-- 1.3.6.1.4.1.5504.5.16.1.46
		zhoneCpeAccessCtrl OBJECT-IDENTITY
			STATUS current
			DESCRIPTION 
				"CPE access ctrl objects"
			::= { zhoneCpeObjectID 46 }

		
		-- 1.3.6.1.4.1.5504.5.16.1.46.1
		zhoneCpeAccessCtrlIndexTable OBJECT-TYPE
			SYNTAX SEQUENCE OF ZhoneCpeAccessCtrlIndexEntry
			MAX-ACCESS not-accessible
			STATUS current
			DESCRIPTION
				"Table of next available values for CPE Access Control entry Index"
			::= { zhoneCpeAccessCtrl 1 }

		
		-- 1.3.6.1.4.1.5504.5.16.1.46.1.1
		zhoneCpeAccessCtrlIndexEntry OBJECT-TYPE
			SYNTAX ZhoneCpeAccessCtrlIndexEntry
			MAX-ACCESS not-accessible
			STATUS current
			DESCRIPTION
				"A row in the cpe-access-ctrl entry index table"
			INDEX { zhoneCpeAccessCtrlListIndex }
			::= { zhoneCpeAccessCtrlIndexTable 1 }

		
		ZhoneCpeAccessCtrlIndexEntry ::=
			SEQUENCE { 
				zhoneCpeAccessCtrlIndexEntryNextIndex
					Unsigned32
			 }

		-- 1.3.6.1.4.1.5504.5.16.1.46.1.1.1
		zhoneCpeAccessCtrlIndexEntryNextIndex OBJECT-TYPE
			SYNTAX Unsigned32
			MAX-ACCESS read-only
			STATUS current
			DESCRIPTION
				"Next available entry index for row in zhoneCpeAccessCtrl Table"
			::= { zhoneCpeAccessCtrlIndexEntry 1 }

		
		-- 1.3.6.1.4.1.5504.5.16.1.46.2
		zhoneCpeAccessCtrlTable OBJECT-TYPE
			SYNTAX SEQUENCE OF ZhoneCpeAccessCtrlEntry
			MAX-ACCESS not-accessible
			STATUS current
			DESCRIPTION
				"A table of cpe-access-ctrl profiles"
			::= { zhoneCpeAccessCtrl 2 }

		
		-- 1.3.6.1.4.1.5504.5.16.1.46.2.1
		zhoneCpeAccessCtrlEntry OBJECT-TYPE
			SYNTAX ZhoneCpeAccessCtrlEntry
			MAX-ACCESS not-accessible
			STATUS current
			DESCRIPTION
				"A row of the cpe access ctrl profile"
			INDEX { zhoneCpeAccessCtrlListIndex, zhoneCpeAccessCtrlEntryIndex }
			::= { zhoneCpeAccessCtrlTable 1 }

		
		ZhoneCpeAccessCtrlEntry ::=
			SEQUENCE { 
				zhoneCpeAccessCtrlEntryIndex
					Unsigned32,
				zhoneCpeAccessCtrlRowStatus
					RowStatus,
				zhoneCpeAccessCtrlSrcIp
					OCTET STRING,
				zhoneCpeAccessCtrlProtocol
					INTEGER,
				zhoneCpeAccessCtrlSrcMac
					OCTET STRING,
				zhoneCpeAccessCtrlMacMask
					OCTET STRING
			 }

		-- 1.3.6.1.4.1.5504.5.16.1.46.2.1.1
		zhoneCpeAccessCtrlEntryIndex OBJECT-TYPE
			SYNTAX Unsigned32
			MAX-ACCESS not-accessible
			STATUS current
			DESCRIPTION
				"Index for this entry in the cpe-access-ctrl entry table"
			::= { zhoneCpeAccessCtrlEntry 1 }

		
		-- 1.3.6.1.4.1.5504.5.16.1.46.2.1.2
		zhoneCpeAccessCtrlRowStatus OBJECT-TYPE
			SYNTAX RowStatus
			MAX-ACCESS read-create
			STATUS current
			DESCRIPTION
				"allows to create, modify or delete a row in this table"
			DEFVAL { active }
			::= { zhoneCpeAccessCtrlEntry 2 }

		
		-- 1.3.6.1.4.1.5504.5.16.1.46.2.1.3
		zhoneCpeAccessCtrlSrcIp OBJECT-TYPE
			SYNTAX OCTET STRING (SIZE (0..19))
			MAX-ACCESS read-create
			STATUS current
			DESCRIPTION
				"The IP address or subnet to filter. 
				If the Prefix is 32 then the whole address is used. 
				Otherwise the prefix indicates the subnet to filter against.
				Example: 192.168.2.0/24."
			DEFVAL { "" }
			::= { zhoneCpeAccessCtrlEntry 3 }

		
		-- 1.3.6.1.4.1.5504.5.16.1.46.2.1.4
		zhoneCpeAccessCtrlProtocol OBJECT-TYPE
			SYNTAX INTEGER
				{
				any(0),
				icmp(1),
				igmp(2),
				tcp(3),
				udp(4)
				}
			MAX-ACCESS read-create
			STATUS current
			DESCRIPTION
				"Protocol to filter"
			DEFVAL { 0 }
			::= { zhoneCpeAccessCtrlEntry 4 }

		
		-- 1.3.6.1.4.1.5504.5.16.1.46.2.1.5
		zhoneCpeAccessCtrlSrcMac OBJECT-TYPE
			SYNTAX OCTET STRING (SIZE (0..18))
			MAX-ACCESS read-create
			STATUS current
			DESCRIPTION
				"specifies the base MAC value to filter"
			DEFVAL { "" }
			::= { zhoneCpeAccessCtrlEntry 5 }

		
		-- 1.3.6.1.4.1.5504.5.16.1.46.2.1.6
		zhoneCpeAccessCtrlMacMask OBJECT-TYPE
			SYNTAX OCTET STRING (SIZE (0..18))
			MAX-ACCESS read-create
			STATUS current
			DESCRIPTION
				"Mask by which to filter MAC address. For example a MAC Mask 
				of ff:ff:ff:00:00:00 would filter against the first six 
				digits of the MAC address."
			DEFVAL { "" }
			::= { zhoneCpeAccessCtrlEntry 6 }

		
		-- 1.3.6.1.4.1.5504.5.16.1.47
		zhoneCpeAutoCfgTable OBJECT-TYPE
			SYNTAX SEQUENCE OF ZhoneCpeAutoCfgEntry
			MAX-ACCESS not-accessible
			STATUS current
			DESCRIPTION
				"Auto configuration parameters applying to a single CPE."
			::= { zhoneCpeObjectID 47 }

		
		-- 1.3.6.1.4.1.5504.5.16.1.47.1
		zhoneCpeAutoCfgEntry OBJECT-TYPE
			SYNTAX ZhoneCpeAutoCfgEntry
			MAX-ACCESS not-accessible
			STATUS current
			DESCRIPTION
				"A row in the CPE auto config table."
			INDEX { zhoneCpeAutoCfgIfIndex }
			::= { zhoneCpeAutoCfgTable 1 }

		
		ZhoneCpeAutoCfgEntry ::=
			SEQUENCE { 
				zhoneCpeAutoCfgIfIndex
					InterfaceIndex,
				zhoneCpeAutoCfgState
					INTEGER
			 }

		-- 1.3.6.1.4.1.5504.5.16.1.47.1.1
		zhoneCpeAutoCfgIfIndex OBJECT-TYPE
			SYNTAX InterfaceIndex
			MAX-ACCESS not-accessible
			STATUS current
			DESCRIPTION
				"IfIndex of the cpe interface stacked on the physical."
			::= { zhoneCpeAutoCfgEntry 1 }

		
		-- 1.3.6.1.4.1.5504.5.16.1.47.1.2
		zhoneCpeAutoCfgState OBJECT-TYPE
			SYNTAX INTEGER
				{
				init(1),
				done(2),
				disabled(3),
				error(4)
				}
			MAX-ACCESS read-only
			STATUS current
			DESCRIPTION
				"Track whether the ONU has been auto-configured."
			DEFVAL { init }
			::= { zhoneCpeAutoCfgEntry 2 }

		
		-- 1.3.6.1.4.1.5504.5.16.1.48
		zhoneCpeOnuModelSpecificEthInfoTable OBJECT-TYPE
			SYNTAX SEQUENCE OF ZhoneCpeOnuModelSpecificEthInfoEntry
			MAX-ACCESS not-accessible
			STATUS current
			DESCRIPTION
				"This table is used to specify model specific information for ethernet
				interfaces.  The index of this table is same as the table that 
				represents the CPE model info (zhoneCpeOnuModelInfoTable)."
			::= { zhoneCpeObjectID 48 }

		
		-- 1.3.6.1.4.1.5504.5.16.1.48.1
		zhoneCpeOnuModelSpecificEthInfoEntry OBJECT-TYPE
			SYNTAX ZhoneCpeOnuModelSpecificEthInfoEntry
			MAX-ACCESS not-accessible
			STATUS current
			DESCRIPTION
				"Row in the zhoneCpeOnuModelSpecificEthInfo table."
			INDEX { zhoneCpeOnuModelInfoIndex }
			::= { zhoneCpeOnuModelSpecificEthInfoTable 1 }

		
		ZhoneCpeOnuModelSpecificEthInfoEntry ::=
			SEQUENCE { 
				zhoneCpeOnuModelEthMaxPower
					Unsigned32,
				zhoneCpeOnuModelEthPorts
					Zhone32PortBitmask,
				zhoneCpeOnuModelEthGponWanPort
					Unsigned32,
				zhoneCpeOnuModelEthAeWanPort 
					Unsigned32,
				zhoneCpeOnuModelEthSfpPorts
					Zhone32PortBitmask
			 }

		-- 1.3.6.1.4.1.5504.5.16.1.48.1.1
		zhoneCpeOnuModelEthMaxPower OBJECT-TYPE
			SYNTAX Unsigned32 (0..2147483647)
			MAX-ACCESS read-only
			STATUS current
			DESCRIPTION
				"A integer value that represents the maximum PoE power that can be 
				configured for this model."
			::= { zhoneCpeOnuModelSpecificEthInfoEntry 1 }

		
		-- 1.3.6.1.4.1.5504.5.16.1.48.1.2
		zhoneCpeOnuModelEthPorts OBJECT-TYPE
			SYNTAX Zhone32PortBitmask
			MAX-ACCESS read-only
			STATUS current
			DESCRIPTION
				"A bitmask that represents the presence of ethernet ports in
				this model.  A bit value if 1 represents presence of the port
				at the location."
			::= { zhoneCpeOnuModelSpecificEthInfoEntry 2 }

		
		-- 1.3.6.1.4.1.5504.5.16.1.48.1.3
		zhoneCpeOnuModelEthGponWanPort OBJECT-TYPE
			SYNTAX Unsigned32 (0..2147483647)
			MAX-ACCESS read-only
			STATUS current
			DESCRIPTION
				"A integer value that represents the WAN port number for the
				GPON flavor of this model."
			::= { zhoneCpeOnuModelSpecificEthInfoEntry 3 }

		
		-- 1.3.6.1.4.1.5504.5.16.1.48.1.4
		zhoneCpeOnuModelEthAeWanPort  OBJECT-TYPE
			SYNTAX Unsigned32 (0..2147483647)
			MAX-ACCESS read-only
			STATUS current
			DESCRIPTION
				"A integer value that represents the WAN port number for the
				Active Ethernet flavor of this model."
			::= { zhoneCpeOnuModelSpecificEthInfoEntry 4 }

		
		-- 1.3.6.1.4.1.5504.5.16.1.48.1.5
		zhoneCpeOnuModelEthSfpPorts OBJECT-TYPE
			SYNTAX Zhone32PortBitmask
			MAX-ACCESS read-only
			STATUS current
			DESCRIPTION
				"A bitmask that represents whether the specific Ethernet port is
				SFP or not. A bit value of 1 represents the Ethernet port at
				the bit location is a SFP port."
			::= { zhoneCpeOnuModelSpecificEthInfoEntry 5 }

		
		-- 1.3.6.1.4.1.5504.5.16.1.49
		zhoneCpeOnuModelSpecificWlanInfoTable OBJECT-TYPE
			SYNTAX SEQUENCE OF ZhoneCpeOnuModelSpecificWlanInfoEntry
			MAX-ACCESS not-accessible
			STATUS current
			DESCRIPTION
				"This table is used to specify model specific information for WLAN
				interfaces.  The index of this table is same as the table that 
				represents the CPE model info (zhoneCpeOnuModelInfoTable)"
			::= { zhoneCpeObjectID 49 }

		
		-- 1.3.6.1.4.1.5504.5.16.1.49.1
		zhoneCpeOnuModelSpecificWlanInfoEntry OBJECT-TYPE
			SYNTAX ZhoneCpeOnuModelSpecificWlanInfoEntry
			MAX-ACCESS not-accessible
			STATUS current
			DESCRIPTION
				"Row in the zhoneCpeOnuModelSpecificWlanInfo table."
			INDEX { zhoneCpeOnuModelInfoIndex }
			::= { zhoneCpeOnuModelSpecificWlanInfoTable 1 }

		
		ZhoneCpeOnuModelSpecificWlanInfoEntry ::=
			SEQUENCE { 
				zhoneCpeOnuModelWlanNumOfPorts
					Unsigned32,
				zhoneCpeOnuModelWlanNumOfRadios
					Unsigned32
			 }

		-- 1.3.6.1.4.1.5504.5.16.1.49.1.1
		zhoneCpeOnuModelWlanNumOfPorts OBJECT-TYPE
			SYNTAX Unsigned32 (0..2147483647)
			MAX-ACCESS read-only
			STATUS current
			DESCRIPTION
				"A integer value that represents the number of
				WLAN ports supported by the model.  Please 
				note that a single radio can support multiple
				WLAN ports. Each WLAN port represents a Wifi 
				SSID supported by the model."
			::= { zhoneCpeOnuModelSpecificWlanInfoEntry 1 }

		
		-- 1.3.6.1.4.1.5504.5.16.1.49.1.2
		zhoneCpeOnuModelWlanNumOfRadios OBJECT-TYPE
			SYNTAX Unsigned32 (0..2147483647)
			MAX-ACCESS read-only
			STATUS current
			DESCRIPTION
				"A integer value that represents the number of
				physical radios ports supported by the model.
				One physical radio can support more than one
				virutal WLANs (SSIDs)."
			::= { zhoneCpeOnuModelSpecificWlanInfoEntry 2 }

		
		-- 1.3.6.1.4.1.5504.5.16.1.50
		zhoneCpeOnuModelSpecificWlanRadioInfoTable OBJECT-TYPE
			SYNTAX SEQUENCE OF ZhoneCpeOnuModelSpecificWlanRadioInfoEntry
			MAX-ACCESS not-accessible
			STATUS current
			DESCRIPTION
				"This table is used to specify attributes of
				the physical radio supported by the specific model.
				The number of entries to this table is
				controlled by zhoneCpeOnuModelWlanNumOfRadios 
				of the zhoneCpeOnuModelSpecificWlanInfoTable.
				This table has two indices:
				    (1) first index is the same as the table that 
				        represents the CPE model info
				        (zhoneCpeOnuModelInfoTable)
				    (2) Index of the physical radio."
			::= { zhoneCpeObjectID 50 }

		
		-- 1.3.6.1.4.1.5504.5.16.1.50.1
		zhoneCpeOnuModelSpecificWlanRadioInfoEntry OBJECT-TYPE
			SYNTAX ZhoneCpeOnuModelSpecificWlanRadioInfoEntry
			MAX-ACCESS not-accessible
			STATUS current
			DESCRIPTION
				"Row in the zhoneCpeOnuModelSpecificWlanRadioInfoTable table."
			INDEX { zhoneCpeOnuModelInfoIndex, zhoneCpeOnuModelRadioIndex }
			::= { zhoneCpeOnuModelSpecificWlanRadioInfoTable 1 }

		
		ZhoneCpeOnuModelSpecificWlanRadioInfoEntry ::=
			SEQUENCE { 
				zhoneCpeOnuModelRadioIndex
					Unsigned32,
				zhoneCpeOnuModelWlanBaseCfgIndex
					Unsigned32,
				zhoneCpeOnuModelWlanBandSupported
					BITS,
				zhoneCpeOnuModelWlanRealAccessPointInfo
					Zhone32PortBitmask,
				zhoneCpeOnuModelWlanVirtualAccessPointInfo
					Zhone32PortBitmask
			 }

		-- 1.3.6.1.4.1.5504.5.16.1.50.1.1
		zhoneCpeOnuModelRadioIndex OBJECT-TYPE
			SYNTAX Unsigned32 (1..2147483647)
			MAX-ACCESS not-accessible
			STATUS current
			DESCRIPTION
				"This index represents the physical radio."
			::= { zhoneCpeOnuModelSpecificWlanRadioInfoEntry 1 }

		
		-- 1.3.6.1.4.1.5504.5.16.1.50.1.2
		zhoneCpeOnuModelWlanBaseCfgIndex OBJECT-TYPE
			SYNTAX Unsigned32 (0..2147483647)
			MAX-ACCESS read-only
			STATUS current
			DESCRIPTION
				"A integer value that represents basic wireless
				adapter interface index."
			::= { zhoneCpeOnuModelSpecificWlanRadioInfoEntry 2 }

		
		-- 1.3.6.1.4.1.5504.5.16.1.50.1.3
		zhoneCpeOnuModelWlanBandSupported OBJECT-TYPE
			SYNTAX BITS
				{
				band2dot4ghz(0),
				band5ghz(1),
				cfgband20mhz(2),
				cfgband40mhz(3),
				cfgband20in2g40in5g(4),
				cfgband80mhz(5)
				}
			MAX-ACCESS read-only
			STATUS current
			DESCRIPTION
				"A bitmask that represents broadcast operational 
				bands supported by the physical radio."
			::= { zhoneCpeOnuModelSpecificWlanRadioInfoEntry 3 }

		
		-- 1.3.6.1.4.1.5504.5.16.1.50.1.4
		zhoneCpeOnuModelWlanRealAccessPointInfo OBJECT-TYPE
			SYNTAX Zhone32PortBitmask
			MAX-ACCESS read-only
			STATUS current
			DESCRIPTION
				"A bitmask that represents the WLAN port on
				which the physical radio is present for
				this model."
			::= { zhoneCpeOnuModelSpecificWlanRadioInfoEntry 4 }

		
		-- 1.3.6.1.4.1.5504.5.16.1.50.1.5
		zhoneCpeOnuModelWlanVirtualAccessPointInfo OBJECT-TYPE
			SYNTAX Zhone32PortBitmask
			MAX-ACCESS read-only
			STATUS current
			DESCRIPTION
				"A bitmask that represents the WLAN ports that
				are associated with this physical radio."
			::= { zhoneCpeOnuModelSpecificWlanRadioInfoEntry 5 }

		
		-- 1.3.6.1.4.1.5504.9.1.36
		zhoneCpeSipDialPlanGroup OBJECT-GROUP
			OBJECTS { zhoneCpeSipDialPlanRowStatus, zhoneCpeSipDialPlanIndexNext, zhoneCpeSipDialPlanFormat, zhoneCpeSipDialPlanString }
			STATUS current
			DESCRIPTION 
				"Cpe Sip Dial Plan Table objects."
			::= { zhoneGroups 36 }

		
		-- 1.3.6.1.4.1.5504.9.1.37
		zhoneCpeVoipServerGroup OBJECT-GROUP
			OBJECTS { zhoneCpeVoipServerRowStatus, zhoneCpeVoipProfileName, zhoneCpeVoipPrimaryServer, zhoneCpeVoipSecondaryServer, zhoneCpeVoipSipRegExpirationTime, 
				zhoneCpeVoipSipReRegHeadStartTime, zhoneCpeVoipSipDomain, zhoneCpeVoipSipRegistrar, zhoneCpeVoipSoftSwitch, zhoneCpeVoipMgcVersion, 
				zhoneCpeVoipMgcMessageFormat, zhoneCpeVoipMgcMaximumRetryTime, zhoneCpeVoipMgcMaximumRetryAttempts, zhoneCpeVoipMgcServiceChangeDelay, zhoneCpeVoipMgcTerminationIdBase, 
				zhoneCpeVoipReleaseTimer, zhoneCpeVoipRohTimer, zhoneCpeVoipDscpMark, zhoneCpeVoipPiggyBackEvents, zhoneCpeVoipOobToneEvents, 
				zhoneCpeVoipOobDtmfEvents, zhoneCpeVoipOobCasEvents, zhoneCpeVoipPartialDialTimeout, zhoneCpeVoipServerSignallingProtocol, zhoneCpeVoipServerPortId, 
				zhoneCpeVoipServerOutboundServer, zhoneCpeVoipCasEventsPassingMethod, zhoneCpeVoipDtmfEventsPassingMethod, zhoneCpeVoipCriticalDialTimeout, zhoneCpeVoipServerIndexNext, 
				zhoneCpeVoipFeaturesWarmLineTimer, zhoneCpeVoipFeaturesHotLineNumber, zhoneCpeVoipFeaturesHotLine, zhoneCpeVoipMgcpPersistentNotify, zhoneCpeVoipMgcpClientAddressMode, 
				zhoneCpeVoipPbxNumber, zhoneCpeVoipSignalingDscp, zhoneCpeVoipRtpDscp, zhoneCpeVoipSipRegRetryTime }
			STATUS current
			DESCRIPTION 
				"Cpe Voip Server Table objects."
			::= { zhoneGroups 37 }

		
		-- 1.3.6.1.4.1.5504.9.1.38
		zhoneCpeIpGroup OBJECT-GROUP
			OBJECTS { zhoneCpeIpRowStatus, zhoneCpeHostIp, zhoneCpeIpServerProfileIndex }
			STATUS current
			DESCRIPTION 
				"Cpe Ip Table objects."
			::= { zhoneGroups 38 }

		
		-- 1.3.6.1.4.1.5504.9.1.39
		zhoneCpeIpServerGroup OBJECT-GROUP
			OBJECTS { zhoneCpeIpServerRowStatus, zhoneCpeIpServerProfileName, zhoneCpeIpServerHostIpOption, zhoneCpeIpServerNetmask, zhoneCpeIpServerGateway, 
				zhoneCpeIpServerPrimaryDns, zhoneCpeIpServerNat, zhoneCpeIpServerFirewallAccess, zhoneCpeIpServerIgmpFunction, zhoneCpeIpServerSecureForward, 
				zhoneCpeIpServerDnsType, zhoneCpeIpServerDnsSrc, zhoneCpeIpServerDefaultIface, zhoneCpeIpServerMtu, zhoneCpeIpServerOption82RemoteId, 
				zhoneCpeIpServerOption82CircuitId, zhoneCpeIpServerDhcpServer, zhoneCpeIpServerDhcpSnooping, zhoneCpeIpServerIpv6DnsType, zhoneCpeIpServerIpv6SecondaryDns, 
				zhoneCpeIpServerIpv6PrimaryDns, zhoneCpeIpServerIpv6Gateway, zhoneCpeIpServerIpv6PrefixLength, zhoneCpeIpServerIpv6HostIpOption, zhoneCpeIpServerIgmpv3, 
				zhoneCpeIpServerIgmpSnoopingQuerier, zhoneCpeIpServerSecondaryDns, zhoneCpeIpServerIndexNext }
			STATUS current
			DESCRIPTION 
				"Cpe Ip Server objects."
			::= { zhoneGroups 39 }

		
		-- 1.3.6.1.4.1.5504.9.1.40
		zhoneCpeVoipFeaturesGroup OBJECT-GROUP
			OBJECTS { zhoneCpeVoipFeaturesRowStatus, zhoneCpeVoipFeaturesProfileName, zhoneCpeVoipFeaturesAnnouncementType, zhoneCpeVoipCidFeatures, zhoneCpeVoipCallWaitingFeatures, 
				zhoneCpeVoipCallProgressOrTransferFeatures, zhoneCpeVoipFeaturesIndexNext, zhoneCpeVoipFeaturesWarmLineTimer, zhoneCpeVoipFeaturesHotLineNumber, zhoneCpeVoipFeaturesHotLine, 
				zhoneCpeVoipFeaturesConferenceUri, zhoneCpeVoipFeaturesConferenceOptions, zhoneCpeVoipCallPresentationFeatures, zhoneCpeVoipServerIndexNext }
			STATUS current
			DESCRIPTION 
				"Cpe Voip Features Table objects."
			::= { zhoneGroups 40 }

		
		-- 1.3.6.1.4.1.5504.9.1.41
		zhoneCpeVoipMediaGroup OBJECT-GROUP
			OBJECTS { zhoneCpeVoipMediaRowStatus, zhoneCpeVoipMediaProfileName, zhoneCpeVoipMediaEchoCancel, zhoneCpeVoipFaxMode, zhoneCpeVoipCodecSelectionFirstOrder, 
				zhoneCpeVoipPacketPeriodSelectionFirstOrder, zhoneCpeVoipSilenceSuppressionFirstOrder, zhoneCpeVoipCodecSelectionSecondOrder, zhoneCpeVoipPacketPeriodSelectionSecondOrder, zhoneCpeVoipSilenceSuppressionSecondOrder, 
				zhoneCpeVoipCodecSelectionThirdOrder, zhoneCpeVoipPacketPeriodSelectionThirdOrder, zhoneCpeVoipSilenceSuppressionThirdOrder, zhoneCpeVoipCodecSelectionFourthOrder, zhoneCpeVoipPacketPeriodSelectionFourthOrder, 
				zhoneCpeVoipMediaHookFlashTimerMax, zhoneCpeVoipMediaHookFlashTimerMin, zhoneCpeVoipSilenceSuppressionFourthOrder, zhoneCpeVoipMediaIndexNext }
			STATUS current
			DESCRIPTION 
				"Cpe Voip Media Table objects."
			::= { zhoneGroups 41 }

		
		-- 1.3.6.1.4.1.5504.9.1.42
		zhoneCpeVoipSubscriberGroup OBJECT-GROUP
			OBJECTS { zhoneCpeVoipSubscriberRowStatus, zhoneCpeVoipSubscriberAdminState, zhoneCpeVoipSubscriberDialNumber, zhoneCpeVoipSubscriberDisplayName, zhoneCpeVoipSubscriberUserName, 
				zhoneCpeVoipSubscriberPassword, zhoneCpeVoipServerProfileIndex, zhoneCpeVoipFeaturesProfileIndex, zhoneCpeVoipSubscriberPhoneFollowsWan, zhoneCpeVoipSubscriberDescription, 
				zhoneCpeVoipMediaProfileIndex, zhoneCpeVoipSubscriberImpedance, zhoneCpeVoipSubscriberRxGain, zhoneCpeVoipSubscriberTxGain, zhoneCpeVoipSubscriberTransmissionPath, 
				zhoneCpeVoipSubscriberSignallingCode }
			STATUS current
			DESCRIPTION 
				"Cpe Voip Subscriber Table objects."
			::= { zhoneGroups 42 }

		
		-- 1.3.6.1.4.1.5504.9.1.43
		zhoneCpeEthSubscriberGroup OBJECT-GROUP
			OBJECTS { zhoneCpeEthSubscriberRowStatus, zhoneCpeEthSubscriberAdminState, zhoneCpeEthSubscriberLoopback, zhoneCpeTrafficManagementProfileIndex, zhoneCpeEthSubscriberLineStatusAlarm, 
				zhoneCpeEthSubscriberAlarmSeverity, zhoneCpeEthSubscriberPowerRange, zhoneCpeEthSubscriberPowerShed, zhoneCpeEthSubscriberLldpMedList, zhoneCpeEthSubscriberCustomPowerRange, 
				zhoneCpeEthSubscriberDescription, zhoneCpeEthSubscriberVlanFilterList, zhoneCpeEthSubscriberAuthenticationMode, zhoneCpeEthSubscriberAccessControlListProfileIndex, zhoneCpeVideoProfileIndex, 
				zhoneCpeEthSubscriberRate, zhoneCpeEthSubscriberDuplex, zhoneCpeEthSubscriberMtu, zhoneCpeEthSubscriberPortType, zhoneCpeEthSubscriberPauseTime, 
				zhoneCpeEthSubscriberMode, zhoneCpeEthSubscriberPowerFeed }
			STATUS current
			DESCRIPTION 
				"Cpe Eth Subscriber Table objects."
			::= { zhoneGroups 43 }

		
		-- 1.3.6.1.4.1.5504.9.1.44
		zhoneCpeVideoGroup OBJECT-GROUP
			OBJECTS { zhoneCpeVideoRowStatus, zhoneCpeVideoProfileName, zhoneCpeVideoMaxSimultaneousGroups, zhoneCpeVideoMaxMulticastBandwidth, zhoneCpeVideoBandwidthEnforce, 
				zhoneCpeVideoIgmpVersion, zhoneCpeVideoIgmpFunction, zhoneCpeVideoImmediateLeave, zhoneCpeVideoUpstreamIgmpRate, zhoneCpeVideoRobustness, 
				zhoneCpeVideoAccessControlList, zhoneCpeVideoIndexNext }
			STATUS current
			DESCRIPTION 
				"Cpe Video Table objects."
			::= { zhoneGroups 44 }

		
		-- 1.3.6.1.4.1.5504.9.1.45
		zhoneCpeVideoAccessControlGroup OBJECT-GROUP
			OBJECTS { zhoneCpeVideoAccessControlRowStatus, zhoneCpeVideoAccessControlProfileName, zhoneCpeVideoAccessControlType, zhoneCpeVideoAccessControlSrcIp, zhoneCpeVideoAccessControlDstIpStart, 
				zhoneCpeVideoAccessControlDstIpEnd, zhoneCpeVideoAccessControlImputedGroupBw, zhoneCpeVideoAccessControlIndexNext }
			STATUS current
			DESCRIPTION 
				"Cpe Video Access Control List Table objects."
			::= { zhoneGroups 45 }

		
		-- 1.3.6.1.4.1.5504.9.1.46
		zhoneCpePweSubscriberGroup OBJECT-GROUP
			OBJECTS { zhoneCpePweSubscriberRowStatus, zhoneCpePweSubscriberAdminState, zhoneCpePweSubscriberLoopback, zhoneCpePweSubscriberNearEndPort, zhoneCpePweSubscriberFarEndIp, 
				zhoneCpePweSubscriberFarEndPort, zhoneCpePweSubscriberAlarmSeverity, zhoneCpePweSubscriberLineStatusAlarm, zhoneCpePweSubscriberDescription, zhoneCpePweSubscriberDestMac, 
				zhoneCpePweSubscriberOuterMplsLabel, zhoneCpePweSubscriberInnerMplsLabel, zhoneCpePweSubscriberEcid, zhoneCpePweProfileIndex, zhoneCpePweSubscriberLineLength
				 }
			STATUS current
			DESCRIPTION 
				"Cpe Pwe Subscriber Table objects."
			::= { zhoneGroups 46 }

		
		-- 1.3.6.1.4.1.5504.9.1.47
		zhoneCpePweGroup OBJECT-GROUP
			OBJECTS { zhoneCpePweRowStatus, zhoneCpePweProfileName, zhoneCpePweTransport, zhoneCpePweServiceType, zhoneCpePwePayloadSize, 
				zhoneCpePwePayloadEncapsulationDelay, zhoneCpePweTimingMode, zhoneCpePweChannelAssign, zhoneCpePweClockReference, zhoneCpePweRtpTimeStampMode, 
				zhoneCpePweJitterBufMax, zhoneCpePweJitterBufDesired, zhoneCpePweFillPolicy, zhoneCpePweMisconnectedDeclarePolicy, zhoneCpePweMisconnectedClearPolicy, 
				zhoneCpePweLossPacketDeclarePolicy, zhoneCpePweOverrunUnderrunDeclarePolicy, zhoneCpePweOverrunUnderrunClearPolicy, zhoneCpePweMalformedDeclarePolicy, zhoneCpePweMalformedClearPolicy, 
				zhoneCpePweRBitTransmitSetPolicy, zhoneCpePweRBitTransmitClearPolicy, zhoneCpePweRBitReceivePolicy, zhoneCpePweLBitReceivePolicy, zhoneCpePweSesThreshold, 
				zhoneCpePweCdvTolerance, zhoneCpePweChannelAssociatedSignalling, zhoneCpePweMplsTpType, zhoneCpePweSSrcPayload, zhoneCpePweSSrcSignalling, 
				zhoneCpePweExpectedSSrcPayload, zhoneCpePweExpectedSSrcSignalling, zhoneCpePwePtypePayload, zhoneCpePwePtypeSignalling, zhoneCpePweExpectedPTypePayload, 
				zhoneCpePweDs1Framing, zhoneCpePweDs1Mode, zhoneCpePweEncoding, zhoneCpePweLineType, zhoneCpePweIndexNext, 
				zhoneCpePweExpectedPTypeSignalling, zhoneCpePweSignalling, zhoneCpePweLossPacketClearPolicy, zhoneCpePweDscp }
			STATUS current
			DESCRIPTION 
				"Cpe Pwe Table objects."
			::= { zhoneGroups 47 }

		
		-- 1.3.6.1.4.1.5504.9.1.48
		zhoneCpeOnuModelInfoGroup OBJECT-GROUP
			OBJECTS { zhoneCpeOnuModelName, zhoneCpeOnuBatteryBackup, zhoneCpeOnuSipPlarSupported, zhoneCpeOnuEthSlotNumber, zhoneCpeOnuNumberOfEthPorts, 
				zhoneCpeOnuPotsSlotNumber, zhoneCpeOnuNumberOfPotsPorts, zhoneCpeOnuRfVideoSlotNumber, zhoneCpeOnuNumberOfRfVideoPorts, zhoneCpeOnuCesSlotNumber, 
				zhoneCpeOnuNumberOfCesPorts, zhoneCpeOnuModelInfoRGBridged, zhoneCpeOnuNumberOfWlanPorts, zhoneCpeOnuModelInfoRg, zhoneCpeOnuModelInfoRgVoip, 
				zhoneCpeOnuModelInfoRgPwe, zhoneCpeOnuModelInfoTftpDnld, zhoneCpeOnuSipSupported, zhoneCpeOnuH248Supported, zhoneCpeOnuMgcpSupported, 
				zhoneCpeOnuT1Supported, zhoneCpeOnuE1Supported, zhoneCpeOnuNumberOfPoEPorts, zhoneCpeOnuModelSpecificInfo }
			STATUS current
			DESCRIPTION 
				"Cpe Onu ModelInfo Table objects."
			::= { zhoneGroups 48 }

		
		-- 1.3.6.1.4.1.5504.9.1.49
		zhoneCpeConnectionGroup OBJECT-GROUP
			OBJECTS { zhoneCpeConnectionRowStatus, zhoneCpeConnectionVlanCos, zhoneCpeConnectionSlanCos, zhoneCpeConnectionVlanTpId, zhoneCpeConnectionSlanTpId, 
				zhoneCpeConnectionTranslateVlanId, zhoneCpeConnectionTranslateVlanCos, zhoneCpeConnectionTranslateVlanTpId, zhoneCpeConnectionTranslateSlanId, zhoneCpeConnectionTranslateSlanCos, 
				zhoneCpeConnectionFloodingGport, zhoneCpeConnectionDscpToCosProfileIndex, zhoneCpeConnectionRgMode, zhoneCpeConnectionGuidedCos, zhoneCpeConnectionGuidedVlanId, 
				zhoneCpeConnectionMacBridgePortInfo, zhoneCpeConnectionVideoGport, zhoneCpeConnectionTranslateSlanTpId }
			STATUS current
			DESCRIPTION 
				"Cpe connection table objects"
			::= { zhoneGroups 49 }

		
		-- 1.3.6.1.4.1.5504.9.1.50
		zhoneCpeRfSubscriberGroup OBJECT-GROUP
			OBJECTS { zhoneCpeRfSubscriberRowStatus, zhoneCpeRfSubscriberAdminState, zhoneCpeRfSubscriberLineStatusAlarm, zhoneCpeRfSubscriberAlarmSeverity, zhoneCpeRfSubscriberDescription
				 }
			STATUS current
			DESCRIPTION 
				"Cpe RF Subscriber table objects."
			::= { zhoneGroups 50 }

		
		-- 1.3.6.1.4.1.5504.9.1.51
		zhoneCpeTrafficManagementGroup OBJECT-GROUP
			OBJECTS { zhoneCpeTrafficManagementProfileName, zhoneCpeTrafficManagementUpstreamSIR, zhoneCpeTrafficManagementUpstreamPIR, zhoneCpeTrafficManagementUpstreamPriority, zhoneCpeTrafficManagementUpstreamWeight, 
				zhoneCpeTrafficManagementDownstreamSIR, zhoneCpeTrafficManagementDownstreamPIR, zhoneCpeTrafficManagementDownstreamPriority, zhoneCpeTrafficManagementPeakBurstSize, zhoneCpeTrafficManagementDownstreamWeight, 
				zhoneCpeTrafficManagementIndexNext, zhoneCpeTrafficManagementRowStatus }
			STATUS current
			DESCRIPTION 
				"Cpe Traffic Management table objects."
			::= { zhoneGroups 51 }

		
		-- 1.3.6.1.4.1.5504.9.1.53
		zhoneCpeSystemGroup OBJECT-GROUP
			OBJECTS { zhoneCpeSystemRowStatus, zhoneCpeSystemCommonProfileIndex, zhoneCpeSystemMgcpClientName, zhoneCpeSystemRadiusNasIdentifier, zhoneCpeSystemTr69ServerConnReqUsername, 
				zhoneCpeSystemTr69ServerConnReqPassword }
			STATUS current
			DESCRIPTION 
				"Cpe System table objects."
			::= { zhoneGroups 53 }

		
		-- 1.3.6.1.4.1.5504.9.1.54
		zhoneCpeSystemCommonGroup OBJECT-GROUP
			OBJECTS { zhoneCpeSystemCommonProfileIndex, zhoneCpeSystemCommonIndexNext, zhoneCpeSystemCommonRowStatus, zhoneCpeSystemCommonProfileName, zhoneCpeSystemCommonFirewall, 
				zhoneCpeSystemCommonSyncCookieProtection, zhoneCpeSystemCommonCrossVlanRouting, zhoneCpeStaticRouteListProfileIndex, zhoneCpeSystemCommonTr69Inform, zhoneCpeSystemCommonInformInterval, 
				zhoneCpeSystemCommonAcsUrl, zhoneCpeSystemCommonAcsUsername, zhoneCpeSystemCommonUserPassword, zhoneCpeSystemCommonSupportPassword, zhoneCpeSystemCommonAdminPassword, 
				zhoneCpeSystemCommonPowerRestoreDelay, zhoneCpeSystemCommonPowerShutdownDelay, zhoneCpeSystemCommonPowerSupply, zhoneCpeSystemCommonAcsPassword, zhoneCpeSystemCommonLanServiceMode, 
				zhoneCpeSystemCommonStagTpid, zhoneCpeSystemCommonBridgeLoopDetect, zhoneCpeSystemCommonBlockUpstreamDhcpOffer, zhoneCpeSystemCommonBlockDownstreamDnsQuery, zhoneCpeSystemCommonCrossVlanMulticast, 
				zhoneCpeSystemCommonPrioritizationMethod, zhoneCpeSystemCommonAuthKeyTxEnabled, zhoneCpeSystemCommonAuthServerTimeout, zhoneCpeSystemCommonAuthQuietPeriod, zhoneCpeSystemCommonReAuthPeriod, 
				zhoneCpeSystemCommonReAuthEnabled, zhoneCpeSystemCommonGuestVlan, zhoneCpeSystemCommonAccSecondarySharedSecret, zhoneCpeSystemCommonAccServerSecondaryPortNum, zhoneCpeSystemCommonAccServerSecondaryAddr, 
				zhoneCpeSystemCommonAccPrimarySharedSecret, zhoneCpeSystemCommonAccServerPrimaryPortNum, zhoneCpeSystemCommonAccServerPrimaryAddr, zhoneCpeSystemCommonAuthSecondarySharedSecret, zhoneCpeSystemCommonAuthServerSecondaryPortNum, 
				zhoneCpeSystemCommonAuthServerSecondaryAddr, zhoneCpeSystemCommonAuthPrimarySharedSecret, zhoneCpeSystemCommonAuthServerPrimaryAddr, zhoneCpeSystemCommonSchedulingMethod, zhoneCpeDnsHostListProfile, 
				zhoneCpeSystemCommonGroupId1Name, zhoneCpeSystemCommonGroupId1Vlan, zhoneCpeSystemCommonGroupId2Name, zhoneCpeSystemCommonAuthServerPrimaryPortNum, zhoneCpeSystemCommonGroupId3Vlan, 
				zhoneCpeSystemCommonGroupId3Name, zhoneCpeSystemCommonTr69CfgConnReqAuth, zhoneCpeSystemCommonGroupId2Vlan, zhoneCpeSystemCommonMaxSupplicantsPerVLAN }
			STATUS current
			DESCRIPTION 
				"Cpe Systen Common table objects."
			::= { zhoneGroups 54 }

		
		-- 1.3.6.1.4.1.5504.9.1.55
		zhoneCpeInterfaceVlanGroup OBJECT-GROUP
			OBJECTS { zhoneCpeInterfaceVlanRowStatus, zhoneCpeIpServerProfile, zhoneCpeInterfaceVlanIpv6Address, zhoneCpeDhcpServerProfileIndex, zhoneCpeInterfaceVlanRgMode, 
				zhoneCpeInterfaceVlanTranslateVlanId, zhoneCpeInterfaceVlanTranslateVlanCos, zhoneCpeInterfaceVlanTranslateSlanId, zhoneCpeInterfaceVlanTranslateSlanCos, zhoneCpeInterfaceVlanTranslateSlanTpId, 
				zhoneCpeInterfaceVlanIpAddress, zhoneCpePortFwdListProfileIndex }
			STATUS current
			DESCRIPTION 
				"Cpe Interface Vlan table objects."
			::= { zhoneGroups 55 }

		
		-- 1.3.6.1.4.1.5504.9.1.56
		zhoneCpeDhcpServerGroup OBJECT-GROUP
			OBJECTS { zhoneCpeDhcpServerIndexNext, zhoneCpeDhcpServerRowStatus, zhoneCpeDhcpServerProfileName, zhoneCpeDhcpServerStartAddress, zhoneCpeDhcpServerEndAddress, 
				zhoneCpeDhcpServerLeaseTime, zhoneCpeDhcpServerConditionalServerListProfile, zhoneCpeDhcpServerIpv6DhcpServer, zhoneCpeDhcpServerIpv6DhcpMode, zhoneCpeDhcpServerIpv6RouterAdvertise, 
				zhoneCpeDhcpServerIpv6LeaseTime , zhoneCpeDhcpServerIpv6StartAddress, zhoneCpeDhcpServerIpv6EndAddress }
			STATUS current
			DESCRIPTION 
				"Cpe Dhcp Server table objects."
			::= { zhoneGroups 56 }

		
		-- 1.3.6.1.4.1.5504.9.1.57
		zhoneCpePppoeGroup OBJECT-GROUP
			OBJECTS { zhoneCpePppoeRowStatus, zhoneCpePppoeUsername, zhoneCpePppoePassword, zhoneCpePppoeAuthentication, zhoneCpePppoeRetryInterval, 
				zhoneCpePppoeIdleDisconnectTime }
			STATUS current
			DESCRIPTION 
				"Cpe Pppoe table objects."
			::= { zhoneGroups 57 }

		
		-- 1.3.6.1.4.1.5504.9.1.58
		zhoneCpeWlanSubscriberGroup OBJECT-GROUP
			OBJECTS { zhoneCpeWlanSubscriberRowStatus, zhoneCpeWlanSubscriberAdminState, zhoneCpeWlanSubscriberSsid, zhoneCpeWlanSubscriberEncryptKey, zhoneCpeWlanSubscriberDevicePin, 
				zhoneCpeWlanSubscriberRadiusKey, zhoneCpeWlanProfileIndex, zhoneCpeAccessControlListProfileIndex, zhoneCpeWdsMacListProfileIndex, zhoneCpeWlanAdvProfileIndex, 
				zhoneCpeWlanSubscriberDescription }
			STATUS current
			DESCRIPTION 
				"Cpe Wlan Subscriber table objects."
			::= { zhoneGroups 58 }

		
		-- 1.3.6.1.4.1.5504.9.1.59
		zhoneCpeWlanGroup OBJECT-GROUP
			OBJECTS { zhoneCpeWlanIndexNext, zhoneCpeWlanRowStatus, zhoneCpeWlanProfileName, zhoneCpeWlanHideAccessPoint, zhoneCpeWlanIsolateClients, 
				zhoneCpeWlanWmmAdvertise, zhoneCpeWlanMcastFwd, zhoneCpeWlanMaxClients, zhoneCpeWlanNetAuthentication, zhoneCpeWlanWpaGroupRekeyInterval, 
				zhoneCpeWlanWpaEncryption, zhoneCpeWlanWepEncryption, zhoneCpeWlanWepStrength, zhoneCpeWlanRadiusServerIp, zhoneCpeWlanRadiusPort, 
				zhoneCpeWlanWpa2PreAuthentication, zhoneCpeWlanNetReAuthenticationInterval }
			STATUS current
			DESCRIPTION 
				"Cpe Wlan table objects."
			::= { zhoneGroups 59 }

		
		-- 1.3.6.1.4.1.5504.9.1.60
		zhoneCpeStaticRouteListGroup OBJECT-GROUP
			OBJECTS { zhoneCpeStaticRouteListIndexNext, zhoneCpeStaticRouteListRowStatus, zhoneCpeStaticRouteListProfileName }
			STATUS current
			DESCRIPTION 
				"Cpe Static Route List table objects."
			::= { zhoneGroups 60 }

		
		-- 1.3.6.1.4.1.5504.9.1.61
		zhoneCpeStaticRouteGroup OBJECT-GROUP
			OBJECTS { zhoneCpeStaticRouteRowStatus, zhoneCpeStaticRouteDestinationIp, zhoneCpeStaticRouteNetmask, zhoneCpeStaticRouteGateway, zhoneCpeStaticRouteMetric, 
				zhoneCpeStaticRouteEntryIndexNext }
			STATUS current
			DESCRIPTION 
				"Cpe Static Route table objects."
			::= { zhoneGroups 61 }

		
		-- 1.3.6.1.4.1.5504.9.1.62
		zhoneCpePortFwdListGroup OBJECT-GROUP
			OBJECTS { zhoneCpePortFwdListIndexNext, zhoneCpePortFwdListRowStatus, zhoneCpePortFwdListProfileName }
			STATUS current
			DESCRIPTION 
				"Cpe Port Fwd  List table objects."
			::= { zhoneGroups 62 }

		
		-- 1.3.6.1.4.1.5504.9.1.63
		zhoneCpePortFwdGroup OBJECT-GROUP
			OBJECTS { zhoneCpePortFwdRowStatus, zhoneCpePortFwdType, zhoneCpePortFwdPortStart, zhoneCpePortFwdPortEnd, zhoneCpePortFwdProtocol, 
				zhoneCpePortFwdPrivatePort, zhoneCpePortFwdPrivateIp, zhoneCpePortFwdEntryIndexNext }
			STATUS current
			DESCRIPTION 
				"Cpe Port Fwd table objects."
			::= { zhoneGroups 63 }

		
		-- 1.3.6.1.4.1.5504.9.1.64
		zhoneCpeServiceApplicationGroup OBJECT-GROUP
			OBJECTS { zhoneCpeServiceApplicationTemplateType, zhoneCpeServiceApplicationTemplateId, zhoneCpeServiceApplicationVirtualConnection, zhoneCpeServiceApplicationTpType, zhoneCpeServiceApplicationTpIndex, 
				zhoneCpeServiceApplicationRowStatus, zhoneCpeServiceApplicationVlan, zhoneCpeServiceApplicationSlan }
			STATUS current
			DESCRIPTION 
				"Description."
			::= { zhoneGroups 64 }

		
		-- 1.3.6.1.4.1.5504.9.1.65
		zhoneCpeDnsHostListGroup OBJECT-GROUP
			OBJECTS { zhoneCpeDnsHostListIndexNext, zhoneCpeDnsHostListRowStatus, zhoneCpeDnsHostListProfileName }
			STATUS current
			DESCRIPTION 
				"Cpe Dns Host List objects"
			::= { zhoneGroups 65 }

		
		-- 1.3.6.1.4.1.5504.9.1.66
		zhoneCpeDnsHostGroup OBJECT-GROUP
			OBJECTS { zhoneCpeDnsHostIndexEntryIndexNext, zhoneCpeDnsHostRowStatus, zhoneCpeDnsHostDomainName, zhoneCpeDnsHostIpAddress }
			STATUS current
			DESCRIPTION 
				"Cpe Dns Host Objects."
			::= { zhoneGroups 66 }

		
		-- 1.3.6.1.4.1.5504.9.1.67
		zhoneCpeWlanAdvGroup OBJECT-GROUP
			OBJECTS { zhoneCpeWlanAdvRowStatus, zhoneCpeWlanAdvProfileName, zhoneCpeWlanAdvChannel, zhoneCpeWlanAdvAutoChanTimer, zhoneCpeWlanAdvDot11nMode, 
				zhoneCpeWlanAdvDot11nRate, zhoneCpeWlanAdvDot1nProtection, zhoneCpeWlanAdvDot1nClientOnly, zhoneCpeWlanAdvRate54G, zhoneCpeWlanAdvMcastRate, 
				zhoneCpeWlanAdvBasicRate, zhoneCpeWlanAdvFragmentationThreshold, zhoneCpeWlanAdvRtsThreshold, zhoneCpeWlanAdvDtimInterval, zhoneCpeWlanAdvBeaconInterval, 
				zhoneCpeWlanAdvGlobalMaxClients, zhoneCpeWlanAdvXpressTechnology, zhoneCpeWlanAdvTxPower, zhoneCpeWlanAdvWmm, zhoneCpeWlanAdvWmmNoAck, 
				zhoneCpeWlanAdvWmmApsd, zhoneCpeWlanAdvApMode, zhoneCpeWlanAdvBridgeRestrict, zhoneCpeWlanAdvWps, zhoneCpeWlanAdvWpsAddClientMethod, 
				zhoneCpeWlanAdvWpsApMode, zhoneCpeWlanAdvDualBandCfgBands, zhoneCpeWlanAdvDualBandCfgRegModes, zhoneCpeWlanAdvDualBandPreNetworkRadarCheck, zhoneCpeWlanAdvDualBandInNetworkRadarCheck, 
				zhoneCpeWlanAdvDualBandCfgTpcMitigationModes, zhoneCpeWlanAdvCfgBandwidth, zhoneCpeWlanAdvBeamformingTx, zhoneCpeWlanAdvPhysicalRadioInterface, zhoneCpeWlanAdvBeamformingRx, 
				zhoneCpeWlanAdvIndexNext }
			STATUS current
			DESCRIPTION 
				"Cpe Wlan Advanced table objects."
			::= { zhoneGroups 67 }

		
		-- 1.3.6.1.4.1.5504.9.1.68
		zhoneCpeCondDhcpSrvListGroup OBJECT-GROUP
			OBJECTS { zhoneCpeCondDhcpSrvListProfileName, zhoneCpeCondDhcpSrvIndexEntryIndexNext, zhoneCpeCondiDhcpSrvListIndexNext, zhoneCpeCondDhcpSrvListRowStatus }
			STATUS current
			DESCRIPTION 
				"Cpe Conditional DHCP server list objects"
			::= { zhoneGroups 68 }

		
		-- 1.3.6.1.4.1.5504.9.1.69
		zhoneCpeCondDhcpSrvGroup OBJECT-GROUP
			OBJECTS { zhoneCpeCondDhcpSrvAdminState, zhoneCpeCondDhcpSrvPriorityOrder, zhoneCpeCondDhcpVciOui, zhoneCpeCondDhcpSrvVciMatch, zhoneCpeCondDhcpSrvStartAddr, 
				zhoneCpeCondDhcpSrvEndAddr, zhoneCpeCondDhcpSrvWanVlan, zhoneCpeCondDhcpSrvPortFwdRule, zhoneCpeCondDhcpSrvStartPort, zhoneCpeCondDhcpSrvPrivatePort, 
				zhoneCpeCondDhcpSrvProtocol, zhoneCpeCondDhcpSrvPriDns, zhoneCpeCondDhcpSrvSecDns, zhoneCpeCondDhcpSrvPriNpt, zhoneCpeCondDhcpSrvSecNpt, 
				zhoneCpeCondDhcpSrvPermanent, zhoneCpeCondDhcpSrvVsi, zhoneCpeCondDhcpSrvRowStatus }
			STATUS current
			DESCRIPTION 
				"Cpe Conditional DHCP server objects"
			::= { zhoneGroups 69 }

		
		-- 1.3.6.1.4.1.5504.9.1.70
		zhoneCpeCmdGroup OBJECT-GROUP
			OBJECTS { zhoneCpeCmdOperation, zhoneCpeCmdSrcIfIndex, zhoneCpeCmdSrcShelf, zhoneCpeCmdSrcSlot, zhoneCpeCmdSrcPort, 
				zhoneCpeCmdSrcSubport, zhoneCpeCmdSrcTpType, zhoneCpeCmdSrcTpIndex, zhoneCpeCmdDstIfIndex, zhoneCpeCmdDstShelf, 
				zhoneCpeCmdDstSlot, zhoneCpeCmdDstPort, zhoneCpeCmdDstSubport, zhoneCpeCmdDstTpType, zhoneCpeCmdDstTpIndex, 
				zhoneCpeCmdString, zhoneCpeCmdSvcTemplateType, zhoneCpeCmdSvcTemplateId, zhoneCpeCmdSvcTemplateIfIndex, zhoneCpeCmdSvcTemplateVirtualConn, 
				zhoneCpeCmdSvcTemplateTpType, zhoneCpeCmdSvcTemplateTpIndex, zhoneCpeCmdSvcTemplateVlan, zhoneCpeCmdSvcTemplateSlan, zhoneCpeCmdOverrideTpIndex, 
				zhoneCpeCmdOverrideVlanId, zhoneCpeCmdOverrideVlanCos, zhoneCpeCmdOverrideSlanId, zhoneCpeCmdOverrideSlanCos, zhoneCpeCmdStatus, 
				zoneCpeCmdErrorCode }
			STATUS current
			DESCRIPTION 
				"CPE command objects"
			::= { zhoneGroups 70 }

		
		-- 1.3.6.1.4.1.5504.9.1.71
		zhoneCpeLldpMedPolicyListGroup OBJECT-GROUP
			OBJECTS { zhoneCpeLldpMedPolicyListIndexNext, zhoneCpeLldpMedPolicyListRowStatus, zhoneCpeLldpMedPolicyListProfileName, zhoneCpeLldpMedPolicyListDeviceDiscoveryNotify, zhoneCpeLldpMedPolicyListNotificationInterval
				 }
			STATUS current
			DESCRIPTION 
				"Cpe LLDP-MED network policy list objects"
			::= { zhoneGroups 71 }

		
		-- 1.3.6.1.4.1.5504.9.1.72
		zhoneCpeLldpMedPolicyGroup OBJECT-GROUP
			OBJECTS { zhoneCpeLldpMedPolicyIndexEntryIndexNext, zhoneCpeLldpMedPolicyRowStatus, zhoneCpeLldpMedPolicyAdminState, zhoneCpeLldpMedPolicyAppType, zhoneCpeLldpMedPolicyVlanId, 
				zhoneCpeLldpMedPolicyCos, zhoneCpeLldpMedPolicyDscp }
			STATUS current
			DESCRIPTION 
				"Cpe LLDP-MED network policy objects"
			::= { zhoneGroups 72 }

		
		-- 1.3.6.1.4.1.5504.9.1.73
		zhoneCpeAutoCfgRuleGroup OBJECT-GROUP
			OBJECTS { zhoneCpeAutoCfgRuleAdminState, zhoneCpeAutoCfgRulePriority, zhoneCpeAutoCfgRuleMatchExpression, zhoneCpeAutoCfgRuleTargetUni, zhoneCpeAutoCfgRuleDeleteBeforeApply, 
				zhoneCpeAutoCfgRuleRowStatus, zhoneCpeAutoCfgRuleProfileName, zhoneCpeAutoCfgRuleServiceTemplate, zhoneCpeAutoCfgRuleIndexNext }
			STATUS current
			DESCRIPTION 
				"Description."
			::= { zhoneGroups 73 }

		
		-- 1.3.6.1.4.1.5504.9.1.74
		zhoneCpeCfgGlobalSettingsGroup OBJECT-GROUP
			OBJECTS { zhoneCpeCfgAutoAssign, zhoneCpeCfgAutoConfig, zhoneCpeCfgParamsStr, zhoneCpeCfgDerivedMacBpppoe, zhoneCpeCfgDerivedMacBrouted, 
				zhoneCpeCfgDecoupleServiceTemplate, zhoneCpeCfgModelIdFetch }
			STATUS current
			DESCRIPTION 
				"Description."
			::= { zhoneGroups 74 }

		
		-- 1.3.6.1.4.1.5504.9.1.75
		zhoneCpeLldpRemoteGroup OBJECT-GROUP
			OBJECTS { zhoneCpeLldpRemoteChassisId, zhoneCpeLldpRemotePortId, zhoneCpeLldpRemoteSysName, zhoneCpeLldpRemoteHardwareRev, zhoneCpeLldpRemoteFirmwareRev, 
				zhoneCpeLldpRemoteSoftwareRev, zhoneCpeLldpRemoteModelName, zhoneCpeLldpRemoteSerialNum, zhoneCpeLldpRemoteRetVal }
			STATUS current
			DESCRIPTION 
				"Description."
			::= { zhoneGroups 75 }

		
		-- 1.3.6.1.4.1.5504.9.1.83
		zhoneCpeConfigGroup OBJECT-GROUP
			OBJECTS { zhoneCpeConfigMEProfileName, zhoneCpeConfigGenericProfileName, zhoneCpeConfigPhysicalTraps, zhoneCpeConfigLineStatusTraps, zhoneCpeConfigAutoUpgrade, 
				zhoneCpeConfigLinkStatusAlarmSeverity }
			STATUS current
			DESCRIPTION 
				"Description."
			::= { zhoneGroups 83 }

		
		-- 1.3.6.1.4.1.5504.9.1.86
		zhoneCpeVlanFilterListGroup OBJECT-GROUP
			OBJECTS { zhoneCpeVlanFilterListProfileName, zhoneCpeVlanFilterListIndexNext, zhoneCpeVlanFilterListRowStatus }
			STATUS current
			DESCRIPTION 
				"Objects in the CpeVlanFilterList profile."
			::= { zhoneGroups 86 }

		
		-- 1.3.6.1.4.1.5504.9.1.87
		zhoneCpeVlanFilterGroup OBJECT-GROUP
			OBJECTS { zhoneCpeVlanFilterAdminState, zhoneCpeVlanFilterPriority, zhoneCpeVlanFilterSrcMac, zhoneCpeVlanFilterMacMask, zhoneCpeVlanFilterSrcIp, 
				zhoneCpeVlanFilterDestIp, zhoneCpeVlanFilterDscp, zhoneCpeVlanFilterDiscard, zhoneCpeVlanFilterNewVlan, zhoneCpeVlanFilterNewCos, 
				zhoneCpeVlanFilterEtherType, zhoneCpeVlanFilterNewDscp, zhoneCpeVlanFilterIndexEntryIndexNext, zhoneCpeVlanFilterRowStatus }
			STATUS current
			DESCRIPTION 
				"Objects in the cpeVlanFilter profile."
			::= { zhoneGroups 87 }

		
		-- 1.3.6.1.4.1.5504.9.1.88
		zhoneCpeMacIpLocationGroup OBJECT-GROUP
			OBJECTS { zhoneCpeMacIpLocationShelf, zhoneCpeMacIpLocationSlot, zhoneCpeMacIpLocationPort, zhoneCpeMacIpLocationSubPort, zhoneCpeMacIpLocationAddr, 
				zhoneCpeMacIpLocationAddrType, zhoneCpeMacIpLocationCpeIfIndex, zhoneCpeMacIpLocationCpePortTpIndex, zhoneCpeMacIpLocationCpePortIfName, zhoneCpeMacIpLocationCpePortVlan, 
				zhoneCpeMacIpLocationCpePortStatus, zhoneCpeMacIpLocationCpePortTpType }
			STATUS current
			DESCRIPTION 
				"Description."
			::= { zhoneGroups 88 }

		
		-- 1.3.6.1.4.1.5504.9.1.89
		zhoneCpeInventoryDataGroup OBJECT-GROUP
			OBJECTS { zhoneCpeInventoryDataModel, zhoneCpeInventoryDataImageVersionActive, zhoneCpeInventoryDataImageVersionStandby, zhoneCpeInventoryDataSnmpDataSync, zhoneCpeInventoryDataSerialNoVendorId, 
				zhoneCpeInventoryDataSerialNoVendorSpecific }
			STATUS current
			DESCRIPTION 
				"Objects in the zhoneCpeInventoryData profile."
			::= { zhoneGroups 89 }

		
		-- 1.3.6.1.4.1.5504.9.1.90
		zhoneCpeAccessCtrlListGroup OBJECT-GROUP
			OBJECTS { zhoneCpeAccessCtrlListProfileName, zhoneCpeAccessCtrlListRowStatus, zhoneCpeAccessCtrlListType, zhoneCpeAccessCtrlListIndexNext }
			STATUS current
			DESCRIPTION 
				"objects in cpeAccessCtrlList profile"
			::= { zhoneGroups 90 }

		
		-- 1.3.6.1.4.1.5504.9.1.91
		zhoneCpeAccessCtrlGroup OBJECT-GROUP
			OBJECTS { zhoneCpeAccessCtrlRowStatus, zhoneCpeAccessCtrlProtocol, zhoneCpeAccessCtrlSrcMac, zhoneCpeAccessCtrlSrcIp, zhoneCpeAccessCtrlMacMask, 
				zhoneCpeAccessCtrlIndexEntryNextIndex }
			STATUS current
			DESCRIPTION 
				"objects of cpeAccessCtrl profile"
			::= { zhoneGroups 91 }

		
		-- 1.3.6.1.4.1.5504.9.1.93
		zhoneCpeAutoCfgGroup OBJECT-GROUP
			OBJECTS { zhoneCpeAutoCfgState }
			STATUS current
			DESCRIPTION 
				"objects of cpeAutoCfg profile"
			::= { zhoneGroups 93 }

		
		-- 1.3.6.1.4.1.5504.9.1.94
		zhoneCpeOnuModelSpecificEthGroup OBJECT-GROUP
			OBJECTS { zhoneCpeOnuModelEthMaxPower, zhoneCpeOnuModelEthGponWanPort, zhoneCpeOnuModelEthSfpPorts, zhoneCpeOnuModelEthAeWanPort , zhoneCpeOnuModelEthPorts
				 }
			STATUS current
			DESCRIPTION 
				"Objects of Ethernet related model specific information."
			::= { zhoneGroups 94 }

		
		-- 1.3.6.1.4.1.5504.9.1.95
		zhoneCpeOnuModelSpecificWlanGroup OBJECT-GROUP
			OBJECTS { zhoneCpeOnuModelWlanNumOfPorts, zhoneCpeOnuModelWlanNumOfRadios }
			STATUS current
			DESCRIPTION 
				"Objects of WLAN related model specific information."
			::= { zhoneGroups 95 }

		
		-- 1.3.6.1.4.1.5504.9.1.96
		zhoneCpeOnuModelSpecificWlanRadioGroup OBJECT-GROUP
			OBJECTS { zhoneCpeOnuModelWlanBaseCfgIndex, zhoneCpeOnuModelWlanBandSupported, zhoneCpeOnuModelWlanRealAccessPointInfo, zhoneCpeOnuModelWlanVirtualAccessPointInfo }
			STATUS current
			DESCRIPTION 
				"Objects of physical radio related model specific information."
			::= { zhoneGroups 96 }

		
	
	END

--
-- phyCPE.mib
--
