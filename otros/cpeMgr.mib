--
-- cpeMgr.mib
-- MIB generated by MG-SOFT Visual MIB Builder Version 3.0 Build 285
-- Tuesday, May 31, 2011 at 08:47:16
--

    CPE-MANAGER DEFINITIONS ::= BEGIN
 
        IMPORTS
            ifIndex            
                FROM IF-MIB            
            OBJECT-GROUP, MODULE-COMPLIANCE, NOTIFICATION-GROUP            
                FROM SNMPv2-CONF            
            IpAddress, Integer32, Unsigned32, OBJECT-TYPE, MODULE-IDENTITY, 
            OBJECT-IDENTITY, NOTIFICATION-TYPE            
                FROM SNMPv2-SMI            
            TruthValue, MacAddress            
                FROM SNMPv2-TC            
            cpeMgr            
                FROM ZHONE-SYSTEM-MIB            
            ZhoneRowStatus            
                FROM Zhone-TC;
    
    
--  To create the Profile files:
-- /vob/zhonetools/bin/pahrser.pl cpeMgr.mib 
-- 
-- To create the mib handler files:
-- /vob/EPILOGUE/binaries/emissary/solaris/mibcomp Zhone.mib Zhone-TC.mib     \
-- iftype.mib rfc1907.mib rfc2233.mib rfc2571.mib rfc2514.mib comIpRD.mib     \
-- comIpRec.mib genIntfTranslationTable.mib genSystem.mib -start cpeMgr -stub \
-- -o cpeMgrHdlr.c cpeMgr.mib
-- 
-- To create the css files:
-- /vob/zhonetools/bin/pahrser.pl -css cpeMgr.mib
-- 
-- 
-- 
-- 
-- 
-- 
-- 
-- 
-- 
-- 
-- 
-- 
-- 
        -- 1.3.6.1.4.1.5504.3.1.21.1
        cpeMgrModule MODULE-IDENTITY 
            LAST-UPDATED "201105131042Z"		-- May 13, 2011 at 10:42 GMT
            ORGANIZATION 
                "Zhone Technologies, Inc."
            CONTACT-INFO 
                "  Postal: 
                Zhone Technologies, Inc.
                @ Zhone Way
                7001 Oakport Street
                Oakland, CA  94621
                USA
                Toll-Free: +1 877-ZHONE20 (+1 877-946-6320)
                Tel: +1-510-777-7000
                Fax: +1-510-777-7001
                E-mail: support@zhone.com"
            DESCRIPTION 
                "The CPE Configuration Manager (a.k.a. Zero Touch Configuration)
                provides the ability for management software to automatically 
                maintain CPE software version and boot time configuration on Zhone 
                manufactured CPEs.  To support this feature, Zhone CO equipment must
                maintain a database correlating a specified link with the required 
                software version and configuration of the CPE at the far end of that 
                link.  This information is used to verify that the connected CPE is 
                running the correct software image and is correctly configured.  If 
                it is not, the CPE will be automatically reconfigured to the correct 
                software version and configuration as configured by these tables."
            REVISION "201105130917Z"		-- May 13, 2011 at 09:17 GMT
            DESCRIPTION 
                "Add fields for cpeConfigRp provisioning scripts and variables.
                Add support for CPE reporting its state to the CO device."
            REVISION "201102080648Z"		-- February 08, 2011 at 06:48 GMT
            DESCRIPTION 
                "Change string sizes for many fields (filenames, versions, username,
                password) and add reported base and specific paths since they will 
                be used for config file validation."
            REVISION "201010281206Z"		-- October 28, 2010 at 12:06 GMT
            DESCRIPTION 
                "Fix writable enums using value zero.
                Remove 'null terminator' verbage from descriptions.
                Add trap and current status fields for CPEs."
            REVISION "201009220742Z"		-- September 22, 2010 at 07:42 GMT
            DESCRIPTION 
                "Add ZHONE_KEYWORD_QUICK_ACCESS indexing."
            REVISION "201005181000Z"		-- May 18, 2010 at 10:00 GMT
            DESCRIPTION 
                "First pass definition of CPE Manager and CPE Configuration Manager MIB."
            ::= { cpeMgr 1 }

        
    
    
--
-- Node definitions
--
    
--  Node definitions
-- 
        -- 1.3.6.1.4.1.5504.3.1.21.1.1
        cpeMgrGlobal OBJECT-IDENTITY
            STATUS current
            DESCRIPTION 
                "Global objects used by CPE Manager."
            ::= { cpeMgrModule 1 }

        
        -- 1.3.6.1.4.1.5504.3.1.21.1.1.1
        cpeMgrGlobalObjects OBJECT-IDENTITY
            STATUS current
            DESCRIPTION 
                "CPE Manager Global Objects."
            ::= { cpeMgrGlobal 1 }

        
        -- 1.3.6.1.4.1.5504.3.1.21.1.1.1.1
        cpeMgrLocalVlanId OBJECT-TYPE
            SYNTAX Unsigned32
            MAX-ACCESS read-write
            STATUS current
            DESCRIPTION
                "Local VLAN ID used as the management VLAN between a CO device and 
                locally managed CPEs.  This VLAN should not be used for anything other 
                than management traffic between the CO and CPEs.  Once CPE management 
                interfaces are created using this VLAN, it can not be changed.  Also
                note, CPEs must be preprovisioned with a DHCP client on this VLAN for
                cpeMgr to operate correctly."
            DEFVAL { 7 }
            ::= { cpeMgrGlobalObjects 1 }

        
        -- 1.3.6.1.4.1.5504.3.1.21.1.1.1.2
        cpeMgrLocalSlanId OBJECT-TYPE
            SYNTAX Unsigned32
            MAX-ACCESS read-write
            STATUS current
            DESCRIPTION
                "Local SLAN ID used as the management SLAN between a CO device and 
                locally managed CPEs.  This SLAN should not be used for anything other 
                than management traffic between the CO and CPEs.  Once CPE management 
                interfaces are created using this SLAN, it can not be changed.  Also
                note, CPEs must be preprovisioned with a DHCP client on this SLAN for
                cpeMgr to operate correctly."
            ::= { cpeMgrGlobalObjects 2 }

        
        -- 1.3.6.1.4.1.5504.3.1.21.1.1.1.3
        cpeCfgMgrConcurrentUpdateLimit OBJECT-TYPE
            SYNTAX Unsigned32
            MAX-ACCESS read-write
            STATUS current
            DESCRIPTION
                "The number of CPEs that can be granted the short lease IP with required
                updates by this CO device before an update storm is declared.  Since
                downloads and uploads of files from a CPE will be NAT/PAT'ed at the CO
                CPU, too many at one time can impact CO performance.  This field 
                provides for tuning this performance as the local environment allows."
            DEFVAL { 5 }
            ::= { cpeMgrGlobalObjects 3 }

        
        -- 1.3.6.1.4.1.5504.3.1.21.1.1.2
        cpeMgrGlobalConformance OBJECT-IDENTITY
            STATUS current
            DESCRIPTION 
                "CPE Manager Global Objects Conformance."
            ::= { cpeMgrGlobal 2 }

        
        -- 1.3.6.1.4.1.5504.3.1.21.1.1.2.1
        cpeMgrGlobalGroups OBJECT-IDENTITY
            STATUS current
            DESCRIPTION 
                "CPE Manager Global Conformance Groups."
            ::= { cpeMgrGlobalConformance 1 }

        
        -- 1.3.6.1.4.1.5504.3.1.21.1.1.2.1.1
        cpeMgrGlobalGroup OBJECT-GROUP
            OBJECTS { cpeMgrLocalVlanId, cpeMgrLocalSlanId, cpeCfgMgrConcurrentUpdateLimit }
            STATUS current
            DESCRIPTION 
                "Global parameters used by the CPE Manager application."
            ::= { cpeMgrGlobalGroups 1 }

        
        -- 1.3.6.1.4.1.5504.3.1.21.1.1.2.2
        cpeMgrGlobalCompliances OBJECT-IDENTITY
            STATUS current
            DESCRIPTION 
                "CPE Manager Compliances."
            ::= { cpeMgrGlobalConformance 2 }

        
--  this module
        -- 1.3.6.1.4.1.5504.3.1.21.1.1.2.2.1
        cpeMgrGlobalCompliance MODULE-COMPLIANCE
            STATUS current
            DESCRIPTION 
                "The compliance statement for managed CPE Manager global entities."
            MODULE -- this module
                MANDATORY-GROUPS { cpeMgrGlobalGroup }
            ::= { cpeMgrGlobalCompliances 1 }

        
        -- 1.3.6.1.4.1.5504.3.1.21.1.2
        cpeConfigMgr OBJECT-IDENTITY
            STATUS current
            DESCRIPTION 
                "CPE Configuration Manager."
            ::= { cpeMgrModule 2 }

        
        -- 1.3.6.1.4.1.5504.3.1.21.1.2.0
        cpeConfigMgrNotifications OBJECT-IDENTITY
            STATUS current
            DESCRIPTION 
                "CPE Config Manager Notifications."
            ::= { cpeConfigMgr 0 }

        
        -- 1.3.6.1.4.1.5504.3.1.21.1.2.0.1
        cpeConfigMgrClientOperational NOTIFICATION-TYPE
            OBJECTS { ifIndex, cpeConfigMgrUsed, reportedCpeSerialNumber, reportedCpeRegistrationID }
            STATUS current
            DESCRIPTION 
                "Trap flagging a CPE as operational.  This means the listed CPE did
                not need any image or configuration updates and was granted the 
                operational lease time on its IP."
            ::= { cpeConfigMgrNotifications 1 }

        
        -- 1.3.6.1.4.1.5504.3.1.21.1.2.0.2
        cpeConfigMgrClientDysfunctional NOTIFICATION-TYPE
            OBJECTS { ifIndex, cpeConfigMgrUsed, cpeConfigMgrMemberStatus }
            STATUS current
            DESCRIPTION 
                "Trap flagging a CPE as having repeated update errors.  This means 
                the listed CPE repeatedly attempted to perform an update and 
                failed.  At this point the CPE is granted a long lease time on its
                IP and no required updates.  This will allow other CPEs an 
                opportunity to update."
            ::= { cpeConfigMgrNotifications 2 }

        
        -- 1.3.6.1.4.1.5504.3.1.21.1.2.0.3
        cpeConfigMgrMismatchType NOTIFICATION-TYPE
            OBJECTS { ifIndex, cpeConfigMgrGroupMembership, reportedCpeType }
            STATUS current
            DESCRIPTION 
                "This trap from CPE Config Manager on a CO device is sent 
                when a CPE's reportedCpeType does not match any cpeType's 
                defined by cpeConfigMgr's of the same cpeConfigMgrGroup.
                
                This trap indicates a configuration error that needs
                attention."
            ::= { cpeConfigMgrNotifications 3 }

        
        -- 1.3.6.1.4.1.5504.3.1.21.1.2.0.4
        cpeConfigMgrMismatchSoftwareVersion NOTIFICATION-TYPE
            OBJECTS { ifIndex, cpeConfigMgrUsed, requiredCpeSoftwareVersion, reportedCpeSoftwareVersion }
            STATUS current
            DESCRIPTION 
                "This trap from CPE Config Manager on a CO device is sent 
                when the software version reported by the CPE does not agree
                with the software version required by the cpeConfigMgr."
            ::= { cpeConfigMgrNotifications 4 }

        
        -- 1.3.6.1.4.1.5504.3.1.21.1.2.0.5
        cpeConfigMgrMismatchWebUIVersion NOTIFICATION-TYPE
            OBJECTS { ifIndex, cpeConfigMgrUsed, requiredCpeWebUIVersion, reportedCpeWebUIVersion }
            STATUS current
            DESCRIPTION 
                "This trap from CPE Config Manager on a CO device is sent 
                when the WebUI version reported by the CPE does not agree
                with the WebUI version required by the cpeConfigMgr"
            ::= { cpeConfigMgrNotifications 5 }

        
        -- 1.3.6.1.4.1.5504.3.1.21.1.2.0.6
        cpeConfigMgrMismatchConfigFile NOTIFICATION-TYPE
            OBJECTS { ifIndex, cpeConfigMgrUsed, reportedCpeConfigFilename, reportedDwnldSrvrBasePath, reportedDwnldSrvrSpecificPath
                 }
            STATUS current
            DESCRIPTION 
                "This trap from CPE Config Manager on a CO device is sent when
                the config filename reported by the CPE does not agree with
                either the cpeGenericConfigFile required by the cpeConfigMgr
                or the cpeSpecificConfigFile required by the cpeConfigMgrMember.
                The comparison of the generic config file includes matching the
                cpeConfigMgrDownloadBasePath with the base path reported by the
                CPE.  The comparison of the specific config file included 
                matching cpeConfigMgrDownloadBasePath with the base path 
                reported by the CPE and matching cpeSpecificDownloadPath with 
                the specific path reported by the CPE."
            ::= { cpeConfigMgrNotifications 6 }

        
        -- 1.3.6.1.4.1.5504.3.1.21.1.2.0.7
        cpeConfigMgrUpdateError NOTIFICATION-TYPE
            OBJECTS { ifIndex, cpeConfigMgrUsed, cpeConfigMgrMemberStatus }
            STATUS current
            DESCRIPTION 
                "This trap from CPE Config Manager on a CO device is sent 
                if it detects an update to a CPE failed."
            ::= { cpeConfigMgrNotifications 7 }

        
        -- 1.3.6.1.4.1.5504.3.1.21.1.2.1
        cpeConfigMgrObjects OBJECT-IDENTITY
            STATUS current
            DESCRIPTION 
                "CPE Configuration Manager Objects."
            ::= { cpeConfigMgr 1 }

        
        -- 1.3.6.1.4.1.5504.3.1.21.1.2.1.1
        cpeConfigMgrTable OBJECT-TYPE
            SYNTAX SEQUENCE OF CpeConfigMgrEntry
            MAX-ACCESS not-accessible
            STATUS current
            DESCRIPTION
                "The CPE Configuration Manager Table defines the common attributes 
                applicable to a specific CPE type.  There can be multiple 
                cpeConfigMgrEntry's for each type of CPE to allow customers to 
                define managed CPE groups specific to different end user 
                requirements, versions and configurations.
                
                This table is indexed by a simple integer; however the user must 
                define a text name for each entry for easier management and 
                recognition.
                
                For most of these fields only rudimentary validation can be performed
                at the CO device.  The accuracy of these fields is left up to the 
                user.  Note that a cpeConfigMgrEntry can not be deleted if any 
                cpeConfigMgrMembers reference it.  The members must be deleted first 
                before the manager can be deleted.
                "
            ::= { cpeConfigMgrObjects 1 }

        
        -- 1.3.6.1.4.1.5504.3.1.21.1.2.1.1.1
        cpeConfigMgrEntry OBJECT-TYPE
            SYNTAX CpeConfigMgrEntry
            MAX-ACCESS not-accessible
            STATUS current
            DESCRIPTION
                "One CPE Configuration Manager."
            INDEX { cpeConfigMgrIndex }
            ::= { cpeConfigMgrTable 1 }

        
        CpeConfigMgrEntry ::=
            SEQUENCE { 
                cpeConfigMgrRowStatus
                    ZhoneRowStatus,
                cpeConfigMgrIndex
                    Integer32,
                cpeConfigMgrName
                    OCTET STRING,
                cpeConfigMgrGroup
                    Integer32,
                managedCpeType
                    OCTET STRING,
                requiredCpeSoftwareVersion
                    OCTET STRING,
                requiredCpeSoftwareFilename
                    OCTET STRING,
                requiredCpeWebUIVersion
                    OCTET STRING,
                requiredCpeWebUIFilename
                    OCTET STRING,
                requiredCpeGenericConfigFile
                    OCTET STRING,
                cpeLeaseTimeUpdate
                    Integer32,
                cpeLeaseTimeOperational
                    Integer32,
                cpeConfigMgrDwnldSrvrToUsed
                    Unsigned32,
                cpeConfigMgrDownloadBasePath
                    OCTET STRING,
                cpeConfigMgrDownloadSecureMode
                    INTEGER,
                cpeConfigMgrTrapsEnabled
                    TruthValue,
                cpeConfigScriptIndex
                    Unsigned32,
                cpeConfigVarsIndex
                    Unsigned32
             }

        -- 1.3.6.1.4.1.5504.3.1.21.1.2.1.1.1.1
        cpeConfigMgrRowStatus OBJECT-TYPE
            SYNTAX ZhoneRowStatus
            MAX-ACCESS read-create
            STATUS current
            DESCRIPTION
                "The standard field for creating/destroying an entry via SNMP."
            ::= { cpeConfigMgrEntry 1 }

        
--  Table index also used as profile address.
        -- 1.3.6.1.4.1.5504.3.1.21.1.2.1.1.1.2
        cpeConfigMgrIndex OBJECT-TYPE
            SYNTAX Integer32 (1..2147483647)
            MAX-ACCESS accessible-for-notify
            STATUS current
            DESCRIPTION
                "Index to the cpeConfigMgrTable."
            ::= { cpeConfigMgrEntry 2 }

        
        -- 1.3.6.1.4.1.5504.3.1.21.1.2.1.1.1.3
        cpeConfigMgrName OBJECT-TYPE
            SYNTAX OCTET STRING (SIZE (1..32))
            MAX-ACCESS read-create
            STATUS current
            DESCRIPTION
                "This is an ASCII string containing the customer assigned name.
                Maximum length is 32 characters, and no whitespaces are allowed."
            DEFVAL { "" }
            ::= { cpeConfigMgrEntry 3 }

        
        -- 1.3.6.1.4.1.5504.3.1.21.1.2.1.1.1.4
        cpeConfigMgrGroup OBJECT-TYPE
            SYNTAX Integer32
            MAX-ACCESS read-create
            STATUS current
            DESCRIPTION
                "The value of this field will be a simple integer defining a 
                group of associated cpeConfigMgr's.  All cpeConfigMgr's with 
                the same group value form this association.  This association 
                allows the defining of multiple CPE type configurations for a 
                given interface.  Each cpeConfigMgrMember will be assigned to 
                a cpeConfigMgrGroup.  The attached CPE must be one of the 
                types supported by this group, or an error will be logged 
                and/or trapped."
            DEFVAL { 0 }
            ::= { cpeConfigMgrEntry 4 }

        
        -- 1.3.6.1.4.1.5504.3.1.21.1.2.1.1.1.5
        managedCpeType OBJECT-TYPE
            SYNTAX OCTET STRING (SIZE (1..16))
            MAX-ACCESS read-create
            STATUS current
            DESCRIPTION
                "This field designates the type of CPE configured by this entry.  This 
                string must match the string returned by the attached CPE exactly."
            DEFVAL { "" }
            ::= { cpeConfigMgrEntry 5 }

        
        -- 1.3.6.1.4.1.5504.3.1.21.1.2.1.1.1.6
        requiredCpeSoftwareVersion OBJECT-TYPE
            SYNTAX OCTET STRING (SIZE (0..32))
            MAX-ACCESS read-create
            STATUS current
            DESCRIPTION
                "A string defining the software version.  If the value of this field 
                doesn't match the software version string returned by the CPE exactly,
                then a software update will be initiated for the connected CPE.  If 
                this field is a NULL string, then the software version will not be 
                managed."
            DEFVAL { "" }
            ::= { cpeConfigMgrEntry 6 }

        
        -- 1.3.6.1.4.1.5504.3.1.21.1.2.1.1.1.7
        requiredCpeSoftwareFilename OBJECT-TYPE
            SYNTAX OCTET STRING (SIZE (0..32))
            MAX-ACCESS read-create
            STATUS current
            DESCRIPTION
                "A string that specifies the filename the CPE must download if the 
                requiredCpeSoftwareVersion comparison fails.  This file must be 
                available in the base path location on the download server."
            DEFVAL { "" }
            ::= { cpeConfigMgrEntry 7 }

        
        -- 1.3.6.1.4.1.5504.3.1.21.1.2.1.1.1.8
        requiredCpeWebUIVersion OBJECT-TYPE
            SYNTAX OCTET STRING (SIZE (0..32))
            MAX-ACCESS read-create
            STATUS current
            DESCRIPTION
                "A string defining the WebUI version.  This version string must match 
                exactly what the CPE returns or an upgrade of the WebUI file will be 
                initiated.
                
                This only applies to certain CPE types.  The CO device will not 
                restrict setting this for CPEs that do not support it, but doing 
                so will likely cause problems.
                
                If this field is left blank, but requiredCpeWebUIFilename is set, the 
                CPE will be told to download a new WebUI file whenever it is also
                told to download a new software image file.  This allows the WebUI
                file to be tied directly to the software image version."
            DEFVAL { "" }
            ::= { cpeConfigMgrEntry 8 }

        
        -- 1.3.6.1.4.1.5504.3.1.21.1.2.1.1.1.9
        requiredCpeWebUIFilename OBJECT-TYPE
            SYNTAX OCTET STRING (SIZE (0..32))
            MAX-ACCESS read-create
            STATUS current
            DESCRIPTION
                "A string that specifies the filename the CPE must download if the 
                requiredCpeWebUIVersion comparison fails.  This file must be 
                available in the base path location on the download server."
            DEFVAL { "" }
            ::= { cpeConfigMgrEntry 9 }

        
        -- 1.3.6.1.4.1.5504.3.1.21.1.2.1.1.1.10
        requiredCpeGenericConfigFile OBJECT-TYPE
            SYNTAX OCTET STRING (SIZE (0..32))
            MAX-ACCESS read-create
            STATUS current
            DESCRIPTION
                "A string defining the generic configuration filename for CPEs using 
                this manager.  The CPE must specify this filename to the CO device.  
                If the names do not match exactly, the CO device will inform the CPE 
                to download this file from the download server at the base path
                location.
                
                The cpeConfigMgrMemberEntry for attached CPEs may define a specific
                configuration filename in the cpeSpecificConfigFile field that will 
                supersede this generic file."
            DEFVAL { "" }
            ::= { cpeConfigMgrEntry 10 }

        
        -- 1.3.6.1.4.1.5504.3.1.21.1.2.1.1.1.11
        cpeLeaseTimeUpdate OBJECT-TYPE
            SYNTAX Integer32
            UNITS "Seconds"
            MAX-ACCESS read-create
            STATUS current
            DESCRIPTION
                "The short lease time (in seconds) granted to a CPE during download
                of files.  This value is also used for throttling a download storms.  
                The default value for this field will be 5 minutes.  This value 
                should be long enough to accommodate the maximum time to download 
                all files a CPE may need."
            DEFVAL { 300 }
            ::= { cpeConfigMgrEntry 11 }

        
        -- 1.3.6.1.4.1.5504.3.1.21.1.2.1.1.1.12
        cpeLeaseTimeOperational OBJECT-TYPE
            SYNTAX Integer32
            UNITS "Seconds"
            MAX-ACCESS read-create
            STATUS current
            DESCRIPTION
                "The long lease time (in seconds) granted to a CPE if there is no
                upgrade required.  The default for this value will be one day.  
                This value should be short enough to accommodate frequent checks 
                for configuration changes, but not too frequent to burden the CO 
                device.
                
                If this device repeatedly fails to successfully update, this long
                lease time may be issued with no required updates to allow other
                CPEs time to update."
            DEFVAL { 86400 }
            ::= { cpeConfigMgrEntry 12 }

        
        -- 1.3.6.1.4.1.5504.3.1.21.1.2.1.1.1.13
        cpeConfigMgrDwnldSrvrToUsed OBJECT-TYPE
            SYNTAX Unsigned32
            MAX-ACCESS read-create
            STATUS current
            DESCRIPTION
                "Index of a cpeConfigMgrDownloadServerEntry containing the download
                server details this cpeConfigMgr passes to attached CPEs.  This 
                field must match an existing cpeCfgMgrDwnldSrvrIndex field.
                If it does not, no download server information will be sent to the
                CPE when needed."
            ::= { cpeConfigMgrEntry 13 }

        
        -- 1.3.6.1.4.1.5504.3.1.21.1.2.1.1.1.14
        cpeConfigMgrDownloadBasePath OBJECT-TYPE
            SYNTAX OCTET STRING (SIZE (0..32))
            MAX-ACCESS read-create
            STATUS current
            DESCRIPTION
                "A string that specifies the directory path to the base location of 
                configuration files on the download server for this cpeConfigMgr.
                This path location will contain the software image, webUI file, 
                generic configuration file, and sub-paths to CPE specific files.
                
                This path is also used when checking the CPEs reported configuration
                with the required configuration for this CPE in CPE Config Manager."
            DEFVAL { "" }
            ::= { cpeConfigMgrEntry 14 }

        
        -- 1.3.6.1.4.1.5504.3.1.21.1.2.1.1.1.15
        cpeConfigMgrDownloadSecureMode OBJECT-TYPE
            SYNTAX INTEGER
                {
                disabled(1),
                enabled(2),
                noPreference(3)
                }
            MAX-ACCESS read-create
            STATUS current
            DESCRIPTION
                "The desired security mode to use for downloading files.  It can be 
                one of three values: 
                  1 = do not use secure download methods (use ftp or tftp), 
                  2 = use secure download methods (sftp) 
                  3 = no preference, 
                "
            DEFVAL { noPreference }
            ::= { cpeConfigMgrEntry 15 }

        
        -- 1.3.6.1.4.1.5504.3.1.21.1.2.1.1.1.16
        cpeConfigMgrTrapsEnabled OBJECT-TYPE
            SYNTAX TruthValue
            MAX-ACCESS read-create
            STATUS current
            DESCRIPTION
                "Enables or disables whether traps are sent from the CO device
                for events relating to this cpeConfigMgr."
            DEFVAL { true }
            ::= { cpeConfigMgrEntry 16 }

        
        -- 1.3.6.1.4.1.5504.3.1.21.1.2.1.1.1.17
        cpeConfigScriptIndex OBJECT-TYPE
            SYNTAX Unsigned32
            MAX-ACCESS read-create
            STATUS current
            DESCRIPTION
                "Index of the cpe-config-script profile used to provision CPEs associated
                with the manager.  Note, the cpe-config-script profile may still be called
                a gpon-onu-omci-me-profile from which this method of provisioning was
                extrapolated."
            ::= { cpeConfigMgrEntry 17 }

        
        -- 1.3.6.1.4.1.5504.3.1.21.1.2.1.1.1.18
        cpeConfigVarsIndex OBJECT-TYPE
            SYNTAX Unsigned32
            MAX-ACCESS read-create
            STATUS current
            DESCRIPTION
                "Index of the cpe-config-vars profile used to provision CPEs associated
                with the manager.  The cpe-config-vars profile defines variables and their
                values used by the cpe-config-script.  Note, the cpe-config-vars profile 
                may still be called a gpon-onu-omci-generic-profile from which it is
                modeled after."
            ::= { cpeConfigMgrEntry 18 }

        
        -- 1.3.6.1.4.1.5504.3.1.21.1.2.1.2
        cpeConfigMgrDownloadServerTable OBJECT-TYPE
            SYNTAX SEQUENCE OF CpeConfigMgrDownloadServerEntry
            MAX-ACCESS not-accessible
            STATUS current
            DESCRIPTION
                "Table defining download servers used by CPEs."
            ::= { cpeConfigMgrObjects 2 }

        
        -- 1.3.6.1.4.1.5504.3.1.21.1.2.1.2.1
        cpeConfigMgrDownloadServerEntry OBJECT-TYPE
            SYNTAX CpeConfigMgrDownloadServerEntry
            MAX-ACCESS not-accessible
            STATUS current
            DESCRIPTION
                "Entry defining a download server used by CPE Config Manager Member
                CPEs."
            INDEX { cpeCfgMgrDwnldSrvrIndex }
            ::= { cpeConfigMgrDownloadServerTable 1 }

        
        CpeConfigMgrDownloadServerEntry ::=
            SEQUENCE { 
                cpeCfgMgrDwnldSrvrRowStatus
                    ZhoneRowStatus,
                cpeCfgMgrDwnldSrvrIndex
                    Unsigned32,
                cpeCfgMgrDwnldSrvrIP
                    IpAddress,
                cpeCfgMgrDwnldSrvrUsername
                    OCTET STRING,
                cpeCfgMgrDwnldSrvrPassword
                    OCTET STRING,
                cpeCfgMgrDwnldSrvrDefault
                    TruthValue
             }

        -- 1.3.6.1.4.1.5504.3.1.21.1.2.1.2.1.1
        cpeCfgMgrDwnldSrvrRowStatus OBJECT-TYPE
            SYNTAX ZhoneRowStatus
            MAX-ACCESS read-create
            STATUS current
            DESCRIPTION
                "RowStatus object used to create an instance in this table."
            ::= { cpeConfigMgrDownloadServerEntry 1 }

        
        -- 1.3.6.1.4.1.5504.3.1.21.1.2.1.2.1.2
        cpeCfgMgrDwnldSrvrIndex OBJECT-TYPE
            SYNTAX Unsigned32
            MAX-ACCESS read-create
            STATUS current
            DESCRIPTION
                "Unique number used to identify this download server instance.  
                This field is the table index."
            ::= { cpeConfigMgrDownloadServerEntry 2 }

        
        -- 1.3.6.1.4.1.5504.3.1.21.1.2.1.2.1.3
        cpeCfgMgrDwnldSrvrIP OBJECT-TYPE
            SYNTAX IpAddress
            MAX-ACCESS read-create
            STATUS current
            DESCRIPTION
                "The IP address of the server hosting update files available to
                CPEs.  This server must support the file transfer methods required 
                by the CPEs (ftp or sftp) for both upload and download."
            DEFVAL { '00000000'h }
            ::= { cpeConfigMgrDownloadServerEntry 3 }

        
        -- 1.3.6.1.4.1.5504.3.1.21.1.2.1.2.1.4
        cpeCfgMgrDwnldSrvrUsername OBJECT-TYPE
            SYNTAX OCTET STRING (SIZE (0..16))
            MAX-ACCESS read-create
            STATUS current
            DESCRIPTION
                "Username the CPE uses when accessing files on the download server."
            DEFVAL { "" }
            ::= { cpeConfigMgrDownloadServerEntry 4 }

        
        -- 1.3.6.1.4.1.5504.3.1.21.1.2.1.2.1.5
        cpeCfgMgrDwnldSrvrPassword OBJECT-TYPE
            SYNTAX OCTET STRING (SIZE (0..16))
            MAX-ACCESS read-create
            STATUS current
            DESCRIPTION
                "Password the CPE uses when accessing files on the download server."
            DEFVAL { "" }
            ::= { cpeConfigMgrDownloadServerEntry 5 }

        
        -- 1.3.6.1.4.1.5504.3.1.21.1.2.1.2.1.6
        cpeCfgMgrDwnldSrvrDefault OBJECT-TYPE
            SYNTAX TruthValue
            MAX-ACCESS read-create
            STATUS current
            DESCRIPTION
                "Indicates this download server is used as the default download 
                server when creating cpeConfigMgrEntry's.  This is only used during
                config time, and not during runtime.  
                
                If set to TRUE, and a new cpeConfigMgrEntry is created that does
                not specify a cpeConfigMgrDwnldSrvrToUsed value, then the index of
                this instance will be used."
            ::= { cpeConfigMgrDownloadServerEntry 6 }

        
        -- 1.3.6.1.4.1.5504.3.1.21.1.2.1.3
        cpeConfigMgrMemberTable OBJECT-TYPE
            SYNTAX SEQUENCE OF CpeConfigMgrMemberEntry
            MAX-ACCESS not-accessible
            STATUS current
            DESCRIPTION
                "The cpeConfigMgrMemberTable associates configured cpe-mgr interfaces
                with defined cpeConfigMgrEntrys.  It also provides a means to 
                associate a unique configuration file to the attached CPEs.
                
                This table is indexed by the cpeIfIndex field."
            ::= { cpeConfigMgrObjects 3 }

        
        -- 1.3.6.1.4.1.5504.3.1.21.1.2.1.3.1
        cpeConfigMgrMemberEntry OBJECT-TYPE
            SYNTAX CpeConfigMgrMemberEntry
            MAX-ACCESS not-accessible
            STATUS current
            DESCRIPTION
                "One CPE associated with a defined CPE Configuration Manager."
            INDEX { ifIndex }
            ::= { cpeConfigMgrMemberTable 1 }

        
        CpeConfigMgrMemberEntry ::=
            SEQUENCE { 
                cpeConfigMgrMemberRowStatus
                    ZhoneRowStatus,
                cpeConfigMgrGroupMembership
                    Unsigned32,
                cpeSpecificConfigFile
                    OCTET STRING,
                cpeSpecificDownloadPath
                    OCTET STRING,
                cpeConfigMgrMemberTrapsEnabled
                    TruthValue
             }

        -- 1.3.6.1.4.1.5504.3.1.21.1.2.1.3.1.1
        cpeConfigMgrMemberRowStatus OBJECT-TYPE
            SYNTAX ZhoneRowStatus
            MAX-ACCESS read-create
            STATUS current
            DESCRIPTION
                "The standard field for creating/destroying an entry via SNMP."
            ::= { cpeConfigMgrMemberEntry 1 }

        
        -- 1.3.6.1.4.1.5504.3.1.21.1.2.1.3.1.2
        cpeConfigMgrGroupMembership OBJECT-TYPE
            SYNTAX Unsigned32
            MAX-ACCESS read-create
            STATUS current
            DESCRIPTION
                "This is the cpeConfigMgrGroup from the cpeConfigMgr table 
                indicating which group this CPE is a member.  This field is  
                required and must point to a valid cpeConfigMgrGroup."
            DEFVAL { 0 }
            ::= { cpeConfigMgrMemberEntry 2 }

        
        -- 1.3.6.1.4.1.5504.3.1.21.1.2.1.3.1.3
        cpeSpecificConfigFile OBJECT-TYPE
            SYNTAX OCTET STRING (SIZE (0..32))
            MAX-ACCESS read-create
            STATUS current
            DESCRIPTION
                "A string defining the specific configuration filename for this CPE.  
                The CPE must specify this filename to the CO device.  If the names do 
                not match exactly, the CO device will inform the CPE to download this 
                file from the download server.  This file must be available at the 
                specific download path."
            DEFVAL { "" }
            ::= { cpeConfigMgrMemberEntry 3 }

        
        -- 1.3.6.1.4.1.5504.3.1.21.1.2.1.3.1.4
        cpeSpecificDownloadPath OBJECT-TYPE
            SYNTAX OCTET STRING (SIZE (0..40))
            MAX-ACCESS read-create
            STATUS current
            DESCRIPTION
                "This field defines the path to CPE specific files.  This path is a
                sub-path to cpeConfigMgrDownloadBasePath.  This path is also used
                when checking the CPEs reported specific configuration with the 
                required configuration in CPE Config Manager.
                
                The default value of this field can take two forms depending on 
                the port type:
                1.  <CO Public IP>/<slot>/<port>/<subport>/<interface type>
                2.  <CO Public IP>/<interface name>-<interface type>
                If the interface type can span multiple physical ports (i.e. bond 
                groups), the second method will be used to define the default 
                value.
                
                Operators are free to define their own values, however, this path
                must exist for files to be downloaded.  If the CPE is required to
                upload to this path, it may create this path before doing the
                upload.
                
                
                The total path the CPE will use to access specific files is a 
                concatenation of these two path fields:
                  <cpeConfigMgrDownloadBasePath>/<cpeSpecificDownloadPath>
                "
            DEFVAL { "" }
            ::= { cpeConfigMgrMemberEntry 4 }

        
        -- 1.3.6.1.4.1.5504.3.1.21.1.2.1.3.1.5
        cpeConfigMgrMemberTrapsEnabled OBJECT-TYPE
            SYNTAX TruthValue
            MAX-ACCESS read-create
            STATUS current
            DESCRIPTION
                "Enables or disables whether traps are sent from the CO device
                for events relating to this cpeConfigMgrMember."
            DEFVAL { true }
            ::= { cpeConfigMgrMemberEntry 5 }

        
        -- 1.3.6.1.4.1.5504.3.1.21.1.2.1.4
        cpeConfigMgrMemberStatusTable OBJECT-TYPE
            SYNTAX SEQUENCE OF CpeConfigMgrMemberStatusEntry
            MAX-ACCESS not-accessible
            STATUS current
            DESCRIPTION
                "Table of runtime details of CPE Config Manager Members."
            ::= { cpeConfigMgrObjects 4 }

        
        -- 1.3.6.1.4.1.5504.3.1.21.1.2.1.4.1
        cpeConfigMgrMemberStatusEntry OBJECT-TYPE
            SYNTAX CpeConfigMgrMemberStatusEntry
            MAX-ACCESS not-accessible
            STATUS current
            DESCRIPTION
                "Runtime details of one CPE Config Manager Member."
            INDEX { ifIndex }
            ::= { cpeConfigMgrMemberStatusTable 1 }

        
        CpeConfigMgrMemberStatusEntry ::=
            SEQUENCE { 
                cpeConfigMgrMemberStatus
                    BITS,
                cpeConfigMgrUsed
                    Integer32,
                reportedCpeType
                    OCTET STRING,
                reportedCpeSoftwareVersion
                    OCTET STRING,
                reportedCpeWebUIVersion
                    OCTET STRING,
                reportedCpeConfigFilename
                    OCTET STRING,
                reportedCpeSerialNumber
                    OCTET STRING,
                reportedCpeRegistrationID
                    OCTET STRING,
                reportedCpeFSAN
                    OCTET STRING,
                reportedCpeMacAddress
                    MacAddress,
                reportedDwnldSrvrBasePath
                    OCTET STRING,
                reportedDwnldSrvrSpecificPath
                    OCTET STRING,
                reportedCpeState
                    Integer32
             }

        -- 1.3.6.1.4.1.5504.3.1.21.1.2.1.4.1.1
        cpeConfigMgrMemberStatus OBJECT-TYPE
            SYNTAX BITS
                {
                notCompared(0),
                noUpdateRequired(1),
                upgradeInfoSent(2),
                errorsDetected(3),
                cpeTypeMismatch(4),
                downloadStormThrottled(5),
                updateRetryLimitExceeded(6),
                softwareUpgradeNeeded(7),
                webuiUpgradeNeeded(8),
                configUpdateNeeded(9),
                configBackupNeeded(10),
                provisioningPending(11),
                provisioningActive(12),
                provisioningError(13)
                }
            MAX-ACCESS read-only
            STATUS current
            DESCRIPTION
                "Status indication for the latest configuration of this CPE.  
                
                Note, this field will change to ‘Not compared’ each time any 
                field in this profile or it’s parent cpeConfigMgr is modified."
            ::= { cpeConfigMgrMemberStatusEntry 1 }

        
        -- 1.3.6.1.4.1.5504.3.1.21.1.2.1.4.1.2
        cpeConfigMgrUsed OBJECT-TYPE
            SYNTAX Integer32
            MAX-ACCESS read-only
            STATUS current
            DESCRIPTION
                "The index into the cpeConfigMgr table for the specific CPE Config 
                Manager used.  The cpeConfigMgr will be found based on matching
                the cpeCofnigMgrGroupMembership and reportedCpeType to the 
                cpeConfigMgrGroup and managedCpeType fields in the cpeConfigMgr 
                table."
            DEFVAL { 0 }
            ::= { cpeConfigMgrMemberStatusEntry 2 }

        
        -- 1.3.6.1.4.1.5504.3.1.21.1.2.1.4.1.3
        reportedCpeType OBJECT-TYPE
            SYNTAX OCTET STRING (SIZE (0..16))
            MAX-ACCESS read-only
            STATUS current
            DESCRIPTION
                "The cpeType value received from the attached CPE, used to 
                compare against the value in cpeConfigMgrEntry.managedCpeType."
            DEFVAL { "" }
            ::= { cpeConfigMgrMemberStatusEntry 3 }

        
        -- 1.3.6.1.4.1.5504.3.1.21.1.2.1.4.1.4
        reportedCpeSoftwareVersion OBJECT-TYPE
            SYNTAX OCTET STRING (SIZE (0..32))
            MAX-ACCESS read-only
            STATUS current
            DESCRIPTION
                "A string containing the software image version received from the CPE.
                If this string does not exactly match the value of 
                requiredCpeSoftwareVersion, a software image update will be initiated 
                by the managing CO device."
            DEFVAL { "" }
            ::= { cpeConfigMgrMemberStatusEntry 4 }

        
        -- 1.3.6.1.4.1.5504.3.1.21.1.2.1.4.1.5
        reportedCpeWebUIVersion OBJECT-TYPE
            SYNTAX OCTET STRING (SIZE (0..32))
            MAX-ACCESS read-only
            STATUS current
            DESCRIPTION
                "A string containing the WebUI image version received from the CPE.  If
                this string does not exactly match the value of 
                requiredCpeWebUIVersion, a WebUI image update will be initiated by the
                managing CO device.
                
                Not all CPE types require or support a separate WebUI file."
            DEFVAL { "" }
            ::= { cpeConfigMgrMemberStatusEntry 5 }

        
        -- 1.3.6.1.4.1.5504.3.1.21.1.2.1.4.1.6
        reportedCpeConfigFilename OBJECT-TYPE
            SYNTAX OCTET STRING (SIZE (0..32))
            MAX-ACCESS read-only
            STATUS current
            DESCRIPTION
                "The filename of the configuration the CPE is currently running.  This
                filename must exactly match the value of cpeSpecificConfigFile or 
                requiredCpeGenericConfigFile."
            ::= { cpeConfigMgrMemberStatusEntry 6 }

        
        -- 1.3.6.1.4.1.5504.3.1.21.1.2.1.4.1.7
        reportedCpeSerialNumber OBJECT-TYPE
            SYNTAX OCTET STRING (SIZE (0..8))
            MAX-ACCESS read-only
            STATUS current
            DESCRIPTION
                "A string containing the serial number reported by the CPE."
            DEFVAL { "" }
            ::= { cpeConfigMgrMemberStatusEntry 7 }

        
        -- 1.3.6.1.4.1.5504.3.1.21.1.2.1.4.1.8
        reportedCpeRegistrationID OBJECT-TYPE
            SYNTAX OCTET STRING (SIZE (0..10))
            MAX-ACCESS read-only
            STATUS current
            DESCRIPTION
                "A string containing the registration ID reported by the CPE."
            DEFVAL { "" }
            ::= { cpeConfigMgrMemberStatusEntry 8 }

        
        -- 1.3.6.1.4.1.5504.3.1.21.1.2.1.4.1.9
        reportedCpeFSAN OBJECT-TYPE
            SYNTAX OCTET STRING (SIZE (0..16))
            MAX-ACCESS read-only
            STATUS current
            DESCRIPTION
                "A string containing the FSAN value reported by the CPE.  The FSAN is a
                string of ASCII decimal digits representing the vendor-specific portion
                of the onu serial number in hex format"
            DEFVAL { "" }
            ::= { cpeConfigMgrMemberStatusEntry 9 }

        
        -- 1.3.6.1.4.1.5504.3.1.21.1.2.1.4.1.10
        reportedCpeMacAddress OBJECT-TYPE
            SYNTAX MacAddress
            MAX-ACCESS read-only
            STATUS current
            DESCRIPTION
                "The MAC address used by the CPE on the cpe-mgr interface."
            ::= { cpeConfigMgrMemberStatusEntry 10 }

        
        -- 1.3.6.1.4.1.5504.3.1.21.1.2.1.4.1.11
        reportedDwnldSrvrBasePath OBJECT-TYPE
            SYNTAX OCTET STRING (SIZE (0..32))
            MAX-ACCESS read-only
            STATUS current
            DESCRIPTION
                "The cpeConfigMgrDownloadBasePath the CPE last received and now 
                reports back to the CO."
            DEFVAL { "" }
            ::= { cpeConfigMgrMemberStatusEntry 11 }

        
        -- 1.3.6.1.4.1.5504.3.1.21.1.2.1.4.1.12
        reportedDwnldSrvrSpecificPath OBJECT-TYPE
            SYNTAX OCTET STRING (SIZE (0..40))
            MAX-ACCESS read-only
            STATUS current
            DESCRIPTION
                "The cpeSpecificDownloadPath the CPE last received and now 
                reports back to the CO."
            DEFVAL { "" }
            ::= { cpeConfigMgrMemberStatusEntry 12 }

        
        -- 1.3.6.1.4.1.5504.3.1.21.1.2.1.4.1.13
        reportedCpeState OBJECT-TYPE
            SYNTAX Integer32
            MAX-ACCESS read-only
            STATUS current
            DESCRIPTION
                "CPE State as reported by the CPE itself.  This may not be completely
                accurate due to errors detected on the CO side.  For example, if the
                update of a CPE is throttled, the CPE is told no updates required.
                In this state the CPE will consider itself 'operational', but the
                CO side knows otherwise."
            DEFVAL { -1 }
            ::= { cpeConfigMgrMemberStatusEntry 13 }

        
        -- 1.3.6.1.4.1.5504.3.1.21.1.2.2
        cpeConfigMgrConformance OBJECT-IDENTITY
            STATUS current
            DESCRIPTION 
                "CPE Configuration Manager Conformance."
            ::= { cpeConfigMgr 2 }

        
        -- 1.3.6.1.4.1.5504.3.1.21.1.2.2.1
        cpeConfigMgrGroups OBJECT-IDENTITY
            STATUS current
            DESCRIPTION 
                "CPE Configuraiton Manager conformance groups."
            ::= { cpeConfigMgrConformance 1 }

        
        -- 1.3.6.1.4.1.5504.3.1.21.1.2.2.1.1
        cpeConfigMgrObjectGroup OBJECT-GROUP
            OBJECTS { cpeConfigMgrRowStatus, cpeConfigMgrIndex, cpeConfigMgrName, cpeConfigMgrGroup, managedCpeType, 
                requiredCpeSoftwareVersion, requiredCpeSoftwareFilename, requiredCpeWebUIVersion, requiredCpeWebUIFilename, requiredCpeGenericConfigFile, 
                cpeLeaseTimeUpdate, cpeLeaseTimeOperational, cpeConfigMgrDownloadBasePath, cpeConfigMgrDownloadSecureMode, cpeConfigVarsIndex, 
                cpeConfigScriptIndex, cpeConfigMgrTrapsEnabled, cpeConfigMgrDwnldSrvrToUsed }
            STATUS current
            DESCRIPTION 
                "A common set of objects used to maintain software version and 
                generic configuration for a specific type of a group member CPE."
            ::= { cpeConfigMgrGroups 1 }

        
        -- 1.3.6.1.4.1.5504.3.1.21.1.2.2.1.2
        cpeConfigMgrDownloadServerGroup OBJECT-GROUP
            OBJECTS { cpeCfgMgrDwnldSrvrRowStatus, cpeCfgMgrDwnldSrvrIndex, cpeCfgMgrDwnldSrvrIP, cpeCfgMgrDwnldSrvrUsername, cpeCfgMgrDwnldSrvrPassword, 
                cpeCfgMgrDwnldSrvrDefault }
            STATUS current
            DESCRIPTION 
                "Objects used to define a download server used by CPEs managed by
                CPE Configuration manager."
            ::= { cpeConfigMgrGroups 2 }

        
        -- 1.3.6.1.4.1.5504.3.1.21.1.2.2.1.3
        cpeConfigMgrMemberObjectGroup OBJECT-GROUP
            OBJECTS { cpeConfigMgrMemberRowStatus, cpeConfigMgrGroupMembership, cpeSpecificConfigFile, cpeSpecificDownloadPath, cpeConfigMgrMemberTrapsEnabled, 
                cpeConfigMgrMemberStatus, cpeConfigMgrUsed, reportedCpeType, reportedCpeSoftwareVersion, reportedCpeWebUIVersion, 
                reportedCpeConfigFilename, reportedCpeSerialNumber, reportedCpeRegistrationID, reportedCpeFSAN, reportedCpeMacAddress, 
                reportedDwnldSrvrBasePath, reportedDwnldSrvrSpecificPath, reportedCpeState }
            STATUS current
            DESCRIPTION 
                "A unique set of objects connecting a CPE link to a 
                CPE Config Manager, assigning a unique configuration to the 
                CPE, and maintaining a configuration status."
            ::= { cpeConfigMgrGroups 3 }

        
        -- 1.3.6.1.4.1.5504.3.1.21.1.2.2.1.4
        cpeConfigMgrNotificationsObjectGroup NOTIFICATION-GROUP
            NOTIFICATIONS { cpeConfigMgrClientOperational, cpeConfigMgrClientDysfunctional, cpeConfigMgrMismatchType, cpeConfigMgrMismatchSoftwareVersion, cpeConfigMgrMismatchWebUIVersion, 
                cpeConfigMgrMismatchConfigFile, cpeConfigMgrUpdateError }
            STATUS current
            DESCRIPTION 
                "Notifications for various cpeConfigMgr events and errors."
            ::= { cpeConfigMgrGroups 4 }

        
        -- 1.3.6.1.4.1.5504.3.1.21.1.2.2.2
        cpeConfigMgrCompliances OBJECT-IDENTITY
            STATUS current
            DESCRIPTION 
                "CPE Configuration Manager Compliances."
            ::= { cpeConfigMgrConformance 2 }

        
--  this module
        -- 1.3.6.1.4.1.5504.3.1.21.1.2.2.2.1
        cpeConfigMgrCompliance MODULE-COMPLIANCE
            STATUS current
            DESCRIPTION 
                "The compliance statement for managed entities
                supporting CPE Configuration Manager."
            MODULE -- this module
                MANDATORY-GROUPS { cpeConfigMgrObjectGroup, cpeConfigMgrMemberObjectGroup, cpeConfigMgrDownloadServerGroup }
                GROUP cpeConfigMgrNotificationsObjectGroup
                    DESCRIPTION 
                        "It's good to communicate, but not required."
            ::= { cpeConfigMgrCompliances 1 }

        
        -- 1.3.6.1.4.1.5504.3.1.21.1.3
        cpeConfigMgrClient OBJECT-IDENTITY
            STATUS current
            DESCRIPTION 
                "CPE Configuration Manager Client."
            ::= { cpeMgrModule 3 }

        
        -- 1.3.6.1.4.1.5504.3.1.21.1.3.0
        cpeCfgMgrClientNotifications OBJECT-IDENTITY
            STATUS current
            DESCRIPTION 
                "CPE Configuration Manager Client notifications."
            ::= { cpeConfigMgrClient 0 }

        
        -- 1.3.6.1.4.1.5504.3.1.21.1.3.0.1
        cpeCfgMgrClientSoftwareDownloadFailed NOTIFICATION-TYPE
            OBJECTS { cpeCfgMgrClientSerialNumber, cpeCfgMgrClientRegistrationID, cpeCfgMgrClientState, cpeCfgMgrClientErrorDescription, cpeCfgMgrClientRequiredUpdates, 
                cpeCfgMgrClientReceivedSwFilename, cpeCfgMgrClientDwnldSrvrBasePath, cpeCfgMgrClientDwnldSrvrIP, cpeCfgMgrClientDwnldSrvrUsername, cpeCfgMgrClientDwnldSrvrSecureMode
                 }
            STATUS current
            DESCRIPTION 
                "Trap sent by a CPE when the download of the software image 
                initiated by CPE Config Manager fails."
            ::= { cpeCfgMgrClientNotifications 1 }

        
        -- 1.3.6.1.4.1.5504.3.1.21.1.3.0.2
        cpeCfgMgrClientSoftwareInstallFailed NOTIFICATION-TYPE
            OBJECTS { cpeCfgMgrClientSerialNumber, cpeCfgMgrClientRegistrationID, cpeCfgMgrClientState, cpeCfgMgrClientErrorDescription, cpeCfgMgrClientRequiredUpdates, 
                cpeCfgMgrClientReceivedSwFilename, cpeCfgMgrClientDwnldSrvrBasePath, cpeCfgMgrClientDwnldSrvrIP, cpeCfgMgrClientDwnldSrvrUsername, cpeCfgMgrClientDwnldSrvrSecureMode
                 }
            STATUS current
            DESCRIPTION 
                "Trap sent by a CPE when the installation of the software image
                as required by CPE Config Manager fails."
            ::= { cpeCfgMgrClientNotifications 2 }

        
        -- 1.3.6.1.4.1.5504.3.1.21.1.3.0.3
        cpeCfgMgrClientWebUIDownloadFailed NOTIFICATION-TYPE
            OBJECTS { cpeCfgMgrClientSerialNumber, cpeCfgMgrClientRegistrationID, cpeCfgMgrClientState, cpeCfgMgrClientErrorDescription, cpeCfgMgrClientRequiredUpdates, 
                cpeCfgMgrClientReceivedWebUIFilename, cpeCfgMgrClientDwnldSrvrBasePath, cpeCfgMgrClientDwnldSrvrIP, cpeCfgMgrClientDwnldSrvrUsername, cpeCfgMgrClientDwnldSrvrSecureMode
                 }
            STATUS current
            DESCRIPTION 
                "Trap sent by a CPE when the download of the WebUI file initiated
                by CPE Config Manager fails."
            ::= { cpeCfgMgrClientNotifications 3 }

        
        -- 1.3.6.1.4.1.5504.3.1.21.1.3.0.4
        cpeCfgMgrClientWebUIInstallFailed NOTIFICATION-TYPE
            OBJECTS { cpeCfgMgrClientSerialNumber, cpeCfgMgrClientRegistrationID, cpeCfgMgrClientState, cpeCfgMgrClientErrorDescription, cpeCfgMgrClientRequiredUpdates, 
                cpeCfgMgrClientDwnldSrvrBasePath, cpeCfgMgrClientDwnldSrvrIP, cpeCfgMgrClientDwnldSrvrUsername, cpeCfgMgrClientReceivedWebUIFilename, cpeCfgMgrClientDwnldSrvrSecureMode
                 }
            STATUS current
            DESCRIPTION 
                "Trap sent by a CPE when the installation of the WebUI file
                required by CPE Config Manager fails."
            ::= { cpeCfgMgrClientNotifications 4 }

        
        -- 1.3.6.1.4.1.5504.3.1.21.1.3.0.5
        cpeCfgMgrClientConfigDownloadFailed NOTIFICATION-TYPE
            OBJECTS { cpeCfgMgrClientSerialNumber, cpeCfgMgrClientRegistrationID, cpeCfgMgrClientState, cpeCfgMgrClientErrorDescription, cpeCfgMgrClientRequiredUpdates, 
                cpeCfgMgrClientReceivedGenericCfgFilename, cpeCfgMgrClientReceivedSpecificCfgFilename, cpeCfgMgrClientDwnldSrvrBasePath, cpeCfgMgrClientDwnldSpecificPath, cpeCfgMgrClientDwnldSrvrIP, 
                cpeCfgMgrClientDwnldSrvrUsername, cpeCfgMgrClientDwnldSrvrSecureMode }
            STATUS current
            DESCRIPTION 
                "Trap sent by a CPE when the download of a configuration file 
                initiated by CPE Config Manager fails."
            ::= { cpeCfgMgrClientNotifications 5 }

        
        -- 1.3.6.1.4.1.5504.3.1.21.1.3.0.6
        cpeCfgMgrClientConfigUpdateFailed NOTIFICATION-TYPE
            OBJECTS { cpeCfgMgrClientSerialNumber, cpeCfgMgrClientRegistrationID, cpeCfgMgrClientState, cpeCfgMgrClientErrorDescription, cpeCfgMgrClientRequiredUpdates, 
                cpeCfgMgrClientReceivedGenericCfgFilename, cpeCfgMgrClientReceivedSpecificCfgFilename, cpeCfgMgrClientDwnldSrvrBasePath, cpeCfgMgrClientDwnldSpecificPath, cpeCfgMgrClientDwnldSrvrIP, 
                cpeCfgMgrClientDwnldSrvrUsername, cpeCfgMgrClientDwnldSrvrSecureMode }
            STATUS current
            DESCRIPTION 
                "Trap sent by a CPE when updating to a configuration file required
                by CPE Config Manager fails."
            ::= { cpeCfgMgrClientNotifications 6 }

        
        -- 1.3.6.1.4.1.5504.3.1.21.1.3.0.7
        cpeCfgMgrClientConfigBackupFailed NOTIFICATION-TYPE
            OBJECTS { cpeCfgMgrClientSerialNumber, cpeCfgMgrClientRegistrationID, cpeCfgMgrClientState, cpeCfgMgrClientErrorDescription, cpeCfgMgrClientRequiredUpdates, 
                cpeCfgMgrClientReceivedSpecificCfgFilename, cpeCfgMgrClientDwnldSrvrBasePath, cpeCfgMgrClientDwnldSpecificPath, cpeCfgMgrClientDwnldSrvrIP, cpeCfgMgrClientDwnldSrvrUsername, 
                cpeCfgMgrClientDwnldSrvrSecureMode }
            STATUS current
            DESCRIPTION 
                "Trap sent by a CPE when the upload of a configuration file
                initiated by CPE Config Manager fails."
            ::= { cpeCfgMgrClientNotifications 7 }

        
        -- 1.3.6.1.4.1.5504.3.1.21.1.3.0.8
        cpeCfgMgrClientLevelReady NOTIFICATION-TYPE
            OBJECTS { cpeCfgMgrClientSerialNumber, cpeCfgMgrClientRegistrationID, cpeCfgMgrClientState, cpeCfgMgrClientMacAddress, cpeCfgMgrClientFSAN, 
                cpeCfgMgrPublicIPAddress, cpeCfgMgrBaseProtocolPort }
            STATUS current
            DESCRIPTION 
                "Trap sent by a CPE reporting its configuration level after it has
                completed all updates available from CPE Config Manager."
            ::= { cpeCfgMgrClientNotifications 8 }

        
        -- 1.3.6.1.4.1.5504.3.1.21.1.3.0.9
        cpeCfgMgrClientConfigBackupDone NOTIFICATION-TYPE
            OBJECTS { cpeCfgMgrClientSerialNumber, cpeCfgMgrClientRegistrationID, cpeCfgMgrClientState, cpeCfgMgrClientRequiredUpdates, cpeCfgMgrClientReceivedSpecificCfgFilename, 
                cpeCfgMgrClientDwnldSrvrBasePath, cpeCfgMgrClientDwnldSpecificPath, cpeCfgMgrClientDwnldSrvrIP, cpeCfgMgrClientDwnldSrvrUsername, cpeCfgMgrClientDwnldSrvrSecureMode
                 }
            STATUS current
            DESCRIPTION 
                "Trap sent by a CPE when the upload of a configuration file
                initiated by CPE Config Manager completes successfully."
            ::= { cpeCfgMgrClientNotifications 9 }

        
        -- 1.3.6.1.4.1.5504.3.1.21.1.3.1
        cpeCfgMgrClientObjects OBJECT-IDENTITY
            STATUS current
            DESCRIPTION 
                "CPE Configuration Manager Client Objects."
            ::= { cpeConfigMgrClient 1 }

        
        -- 1.3.6.1.4.1.5504.3.1.21.1.3.1.1
        cpeCfgMgrClientIdObjects OBJECT-IDENTITY
            STATUS current
            DESCRIPTION 
                "CPE Configuration Manager Client Identity Objects."
            ::= { cpeCfgMgrClientObjects 1 }

        
        -- 1.3.6.1.4.1.5504.3.1.21.1.3.1.1.1
        cpeCfgMgrClientSerialNumber OBJECT-TYPE
            SYNTAX OCTET STRING (SIZE (0..8))
            MAX-ACCESS read-only
            STATUS current
            DESCRIPTION
                "The serial number of this CPE."
            DEFVAL { "" }
            ::= { cpeCfgMgrClientIdObjects 1 }

        
        -- 1.3.6.1.4.1.5504.3.1.21.1.3.1.1.2
        cpeCfgMgrClientRegistrationID OBJECT-TYPE
            SYNTAX OCTET STRING (SIZE (0..10))
            MAX-ACCESS read-only
            STATUS current
            DESCRIPTION
                "The registration ID of this CPE."
            DEFVAL { "" }
            ::= { cpeCfgMgrClientIdObjects 2 }

        
        -- 1.3.6.1.4.1.5504.3.1.21.1.3.1.1.3
        cpeCfgMgrClientFSAN OBJECT-TYPE
            SYNTAX OCTET STRING (SIZE (0..16))
            MAX-ACCESS read-only
            STATUS current
            DESCRIPTION
                "A string containing the FSAN value of this CPE.  The FSAN is a string 
                of ASCII decimal digits representing the vendor-specific portion of 
                the onu serial number in hex format"
            DEFVAL { "" }
            ::= { cpeCfgMgrClientIdObjects 3 }

        
        -- 1.3.6.1.4.1.5504.3.1.21.1.3.1.1.4
        cpeCfgMgrClientMacAddress OBJECT-TYPE
            SYNTAX MacAddress
            MAX-ACCESS read-only
            STATUS current
            DESCRIPTION
                "The MAC address used by this CPE on the cpe-mgr interface."
            ::= { cpeCfgMgrClientIdObjects 4 }

        
        -- 1.3.6.1.4.1.5504.3.1.21.1.3.1.1.5
        cpeCfgMgrClientSysName OBJECT-TYPE
            SYNTAX OCTET STRING (SIZE (0..32))
            MAX-ACCESS read-only
            STATUS current
            DESCRIPTION
                "Read only access to the sysName of this CPE."
            ::= { cpeCfgMgrClientIdObjects 5 }

        
        -- 1.3.6.1.4.1.5504.3.1.21.1.3.1.2
        cpeCfgMgrClientStatusObjects OBJECT-IDENTITY
            STATUS current
            DESCRIPTION 
                "CPE Configuration Manager Client Status Objects."
            ::= { cpeCfgMgrClientObjects 2 }

        
        -- 1.3.6.1.4.1.5504.3.1.21.1.3.1.2.1
        cpeCfgMgrClientState OBJECT-TYPE
            SYNTAX INTEGER
                {
                error(0),
                starting(1),
                dhcpRequesting(2),
                dhcpRenewing(3),
                dhcpShortLeaseWaiting(4),
                downloadingSoftware(5),
                downloadingWebUI(6),
                downloadingGenericConfig(7),
                downloadingSpecificConfig(8),
                installingSoftware(9),
                installingWebUI(10),
                installingGenericConfig(11),
                installingSpecificConfig(12),
                backingUpConfig(13),
                genericOperational(99),
                operational(100)
                }
            MAX-ACCESS read-only
            STATUS current
            DESCRIPTION
                "Current status of CPE Config Manager operations on this CPE."
            DEFVAL { starting }
            ::= { cpeCfgMgrClientStatusObjects 1 }

        
        -- 1.3.6.1.4.1.5504.3.1.21.1.3.1.2.2
        cpeCfgMgrClientErrorDescription OBJECT-TYPE
            SYNTAX OCTET STRING (SIZE (0..128))
            MAX-ACCESS read-only
            STATUS current
            DESCRIPTION
                "Textual description of the most recent error that may have occurred
                while downloading a file, upgrading the software, updating the 
                configuration, or backing up the configuration for this CPE."
            DEFVAL { "" }
            ::= { cpeCfgMgrClientStatusObjects 2 }

        
        -- 1.3.6.1.4.1.5504.3.1.21.1.3.1.2.3
        cpeCfgMgrClientCurrentSwVersion OBJECT-TYPE
            SYNTAX OCTET STRING (SIZE (0..32))
            MAX-ACCESS read-only
            STATUS current
            DESCRIPTION
                "A text string containing the currently running software image version.
                This string is reported to the CO via DHCP for CPE Config Manager
                support."
            DEFVAL { "" }
            ::= { cpeCfgMgrClientStatusObjects 3 }

        
        -- 1.3.6.1.4.1.5504.3.1.21.1.3.1.2.4
        cpeCfgMgrClientCurrentWebUIVersion OBJECT-TYPE
            SYNTAX OCTET STRING (SIZE (0..32))
            MAX-ACCESS read-only
            STATUS current
            DESCRIPTION
                "A text string containing the currently installed WebUI version.  This 
                string is reported to the CO via DHCP for CPE Config Manager support."
            DEFVAL { "" }
            ::= { cpeCfgMgrClientStatusObjects 4 }

        
        -- 1.3.6.1.4.1.5504.3.1.21.1.3.1.2.5
        cpeCfgMgrClientLastInstalledConfigFile OBJECT-TYPE
            SYNTAX OCTET STRING (SIZE (0..32))
            MAX-ACCESS read-only
            STATUS current
            DESCRIPTION
                "A text string containing the configuration filename most recently
                installed by CPE Config Manager.  This string is reported to the CO 
                via DHCP for CPE Config Manager support."
            DEFVAL { "" }
            ::= { cpeCfgMgrClientStatusObjects 5 }

        
        -- 1.3.6.1.4.1.5504.3.1.21.1.3.1.2.6
        cpeCfgMgrClientLastDwnldSrvrBasePath OBJECT-TYPE
            SYNTAX OCTET STRING (SIZE (0..32))
            MAX-ACCESS read-only
            STATUS current
            DESCRIPTION
                "A text string containing the download server base path most recently
                used for uploading or downloading files for CPE Config Manager.  
                This string is reported to the CO for config file validation."
            DEFVAL { "" }
            ::= { cpeCfgMgrClientStatusObjects 6 }

        
        -- 1.3.6.1.4.1.5504.3.1.21.1.3.1.2.7
        cpeCfgMgrClientLastDwnldSrvrSpecificPath OBJECT-TYPE
            SYNTAX OCTET STRING (SIZE (0..40))
            MAX-ACCESS read-only
            STATUS current
            DESCRIPTION
                "A text string containing the download server specific path most 
                recently used for uploading or downloading files for CPE Config 
                Manager.  This string is reported to the CO for config file 
                validation."
            DEFVAL { "" }
            ::= { cpeCfgMgrClientStatusObjects 7 }

        
        -- 1.3.6.1.4.1.5504.3.1.21.1.3.1.3
        cpeCfgMgrClientUpdateObjects OBJECT-IDENTITY
            STATUS current
            DESCRIPTION 
                "CPE Configuration Manager Client Update Objects."
            ::= { cpeCfgMgrClientObjects 3 }

        
        -- 1.3.6.1.4.1.5504.3.1.21.1.3.1.3.1
        cpeCfgMgrClientRequiredUpdates OBJECT-TYPE
            SYNTAX BITS
                {
                software(0),
                webUI(1),
                config(2),
                backup(3)
                }
            MAX-ACCESS read-write
            STATUS current
            DESCRIPTION
                "This field indicates the current list of required updates this CPE
                needs to complete.
                
                The 'backup' bit tells the CPE to generate a config backup of the 
                running config to the download storage area.
                
                    software(0): Software image file must be updated.
                    webUI(1):    WebUI file must be updated.
                    config(2):   Config file must be updated.
                    backup(3):   CPE must backup its running config
                "
            ::= { cpeCfgMgrClientUpdateObjects 1 }

        
        -- 1.3.6.1.4.1.5504.3.1.21.1.3.1.3.2
        cpeCfgMgrClientReceivedSwFilename OBJECT-TYPE
            SYNTAX OCTET STRING (SIZE (0..32))
            MAX-ACCESS read-write
            STATUS current
            DESCRIPTION
                "A string specifying the software filename the CPE must download.  The 
                CPE will be required to download this file when the 
                reportedCpeSoftwareVersion it reported to the CO device does not 
                exactly match the requiredCpeSoftwareVersion in the cpeConfigMgrEntry."
            DEFVAL { "" }
            ::= { cpeCfgMgrClientUpdateObjects 2 }

        
        -- 1.3.6.1.4.1.5504.3.1.21.1.3.1.3.3
        cpeCfgMgrClientReceivedWebUIFilename OBJECT-TYPE
            SYNTAX OCTET STRING (SIZE (0..32))
            MAX-ACCESS read-write
            STATUS current
            DESCRIPTION
                "A string specifying the WebUI filename the CPE must download.  The CPE
                will be required to download this file when the reportedCpeWebUIVersion
                it reported to the CO device does not exactly match the 
                requiredCpeWebUIVersion in the cpeConfigMgrEntry."
            DEFVAL { "" }
            ::= { cpeCfgMgrClientUpdateObjects 3 }

        
        -- 1.3.6.1.4.1.5504.3.1.21.1.3.1.3.4
        cpeCfgMgrClientReceivedGenericCfgFilename OBJECT-TYPE
            SYNTAX OCTET STRING (SIZE (0..32))
            MAX-ACCESS read-write
            STATUS current
            DESCRIPTION
                "A string specifying the generic config filename for this CPE.  The CPE
                must download this file if the reportedCpeConfigFilename it reported
                to the CO device doesn't exactly match either the 
                requiredCpeGenericConfigFile in the cpeConfigMgrEntry or the 
                cpeSpecificConfigFile in the cpeConfigMgrMemberEntry, and either no
                cpeCfgMgrClientReceivedSpecificCfgFilename was received from the CO or
                the download or use of the specific config file fails."
            DEFVAL { "" }
            ::= { cpeCfgMgrClientUpdateObjects 4 }

        
        -- 1.3.6.1.4.1.5504.3.1.21.1.3.1.3.5
        cpeCfgMgrClientReceivedSpecificCfgFilename OBJECT-TYPE
            SYNTAX OCTET STRING (SIZE (0..32))
            MAX-ACCESS read-write
            STATUS current
            DESCRIPTION
                "A string specifying the specific config filename for this CPE.  The
                CPE must download this file if the reportedCpeConfigFilename it reported
                to the CO device doesn't exactly match the cpeSpecificConfigFile in 
                the cpeConfigMgrMemberEntry."
            DEFVAL { "" }
            ::= { cpeCfgMgrClientUpdateObjects 5 }

        
        -- 1.3.6.1.4.1.5504.3.1.21.1.3.1.3.6
        cpeCfgMgrClientForceUpdate OBJECT-TYPE
            SYNTAX INTEGER
                {
                none(0),
                renewDhcp(1),
                updateConfig(2)
                }
            MAX-ACCESS read-write
            STATUS current
            DESCRIPTION
                "Writable object causing the immediate update of the CPE.  After 
                initiating the requested update, this field reverts to the 'none'
                state.
                
                renewDhcp - Simply restarts the DHCP handshake.  This could cause
                an update if the configuration on the CO device has changed.
                
                updateConfig - This resets any previous configuration information
                and restarts the DHCP handshake.  This has the effect of forcing
                a download and install of the configuration file even if it was
                the same as the previously installed file."
            DEFVAL { none }
            ::= { cpeCfgMgrClientUpdateObjects 6 }

        
        -- 1.3.6.1.4.1.5504.3.1.21.1.3.1.4
        cpeCfgMgrClientDownloadServerObjects OBJECT-IDENTITY
            STATUS current
            DESCRIPTION 
                "CPE Configuration Manager Download Server Objects."
            ::= { cpeCfgMgrClientObjects 4 }

        
        -- 1.3.6.1.4.1.5504.3.1.21.1.3.1.4.1
        cpeCfgMgrClientDwnldSrvrIP OBJECT-TYPE
            SYNTAX IpAddress
            MAX-ACCESS read-write
            STATUS current
            DESCRIPTION
                "The IP address of the server hosting files for download by CPEs.  
                This will likely be the ZMS server."
            ::= { cpeCfgMgrClientDownloadServerObjects 1 }

        
        -- 1.3.6.1.4.1.5504.3.1.21.1.3.1.4.2
        cpeCfgMgrClientDwnldSrvrUsername OBJECT-TYPE
            SYNTAX OCTET STRING (SIZE (0..16))
            MAX-ACCESS read-write
            STATUS current
            DESCRIPTION
                "Username the CPE uses when downloading files from the download server."
            DEFVAL { "" }
            ::= { cpeCfgMgrClientDownloadServerObjects 2 }

        
        -- 1.3.6.1.4.1.5504.3.1.21.1.3.1.4.3
        cpeCfgMgrClientDwnldSrvrPassword OBJECT-TYPE
            SYNTAX OCTET STRING (SIZE (0..16))
            MAX-ACCESS read-write
            STATUS current
            DESCRIPTION
                "Password the CPE uses when downloading files from the download server."
            DEFVAL { "" }
            ::= { cpeCfgMgrClientDownloadServerObjects 3 }

        
        -- 1.3.6.1.4.1.5504.3.1.21.1.3.1.4.4
        cpeCfgMgrClientDwnldSrvrSecureMode OBJECT-TYPE
            SYNTAX INTEGER
                {
                disabled(1),
                enabled(2),
                noPreference(3)
                }
            MAX-ACCESS read-write
            STATUS current
            DESCRIPTION
                "The desired security mode to use for downloading files.  It can be 
                one of three values: 
                  1 = do not use secure download methods (use ftp or tftp), 
                  2 = use secure download methods (sftp),
                  3 = no preference."
            DEFVAL { noPreference }
            ::= { cpeCfgMgrClientDownloadServerObjects 4 }

        
        -- 1.3.6.1.4.1.5504.3.1.21.1.3.1.4.5
        cpeCfgMgrClientDwnldSrvrBasePath OBJECT-TYPE
            SYNTAX OCTET STRING (SIZE (0..32))
            MAX-ACCESS read-write
            STATUS current
            DESCRIPTION
                "The base path location on the download server where update files
                are available."
            DEFVAL { "" }
            ::= { cpeCfgMgrClientDownloadServerObjects 5 }

        
        -- 1.3.6.1.4.1.5504.3.1.21.1.3.1.4.6
        cpeCfgMgrClientDwnldSpecificPath OBJECT-TYPE
            SYNTAX OCTET STRING (SIZE (0..40))
            MAX-ACCESS read-write
            STATUS current
            DESCRIPTION
                "The specific path location on the download server where CPE
                specific files are available.  This path is a sub-path of the base
                path.  The total path is a concatenation of the two strings as
                follows:
                  <base path>/<specific path>"
            DEFVAL { "" }
            ::= { cpeCfgMgrClientDownloadServerObjects 6 }

        
        -- 1.3.6.1.4.1.5504.3.1.21.1.3.1.5
        cpeCfgMgrClientCoObjects OBJECT-IDENTITY
            STATUS current
            DESCRIPTION 
                "CPE Configuration Manager Client CO Objects."
            ::= { cpeCfgMgrClientObjects 5 }

        
        -- 1.3.6.1.4.1.5504.3.1.21.1.3.1.5.1
        cpeCfgMgrPublicIPAddress OBJECT-TYPE
            SYNTAX IpAddress
            MAX-ACCESS read-write
            STATUS current
            DESCRIPTION
                "This is the Public side IP Address used by CPE Config Manager on 
                the CO device.  It is not necessarily the IP used by the CO to 
                communicate with the CPE."
            ::= { cpeCfgMgrClientCoObjects 1 }

        
        -- 1.3.6.1.4.1.5504.3.1.21.1.3.1.5.2
        cpeCfgMgrBaseProtocolPort OBJECT-TYPE
            SYNTAX Integer32
            MAX-ACCESS read-write
            STATUS current
            DESCRIPTION
                "Base protocol port used for NAT/PAT access of this CPE via the CO
                device."
            DEFVAL { 0 }
            ::= { cpeCfgMgrClientCoObjects 2 }

        
        -- 1.3.6.1.4.1.5504.3.1.21.1.3.1.5.3
        cpeCfgMgrSlot OBJECT-TYPE
            SYNTAX Integer32
            MAX-ACCESS read-write
            STATUS current
            DESCRIPTION
                "Slot identifier for the port on the CO device connected to this CPE."
            DEFVAL { 0 }
            ::= { cpeCfgMgrClientCoObjects 3 }

        
        -- 1.3.6.1.4.1.5504.3.1.21.1.3.1.5.4
        cpeCfgMgrPort OBJECT-TYPE
            SYNTAX Integer32
            MAX-ACCESS read-write
            STATUS current
            DESCRIPTION
                "Port identifier on the CO device slot connected to this CPE."
            DEFVAL { 0 }
            ::= { cpeCfgMgrClientCoObjects 4 }

        
        -- 1.3.6.1.4.1.5504.3.1.21.1.3.1.5.5
        cpeCfgMgrSubport OBJECT-TYPE
            SYNTAX Integer32
            MAX-ACCESS read-write
            STATUS current
            DESCRIPTION
                "Subport identifier on the CO device's port connected to this CPE."
            DEFVAL { 0 }
            ::= { cpeCfgMgrClientCoObjects 5 }

        
        -- 1.3.6.1.4.1.5504.3.1.21.1.3.1.5.6
        cpeCfgMgrInterfaceName OBJECT-TYPE
            SYNTAX OCTET STRING (SIZE (0..32))
            MAX-ACCESS read-write
            STATUS current
            DESCRIPTION
                "Interface name on the CO device connected to this CPE."
            DEFVAL { "" }
            ::= { cpeCfgMgrClientCoObjects 6 }

        
        -- 1.3.6.1.4.1.5504.3.1.21.1.3.2
        cpeCfgMgrClientConformance OBJECT-IDENTITY
            STATUS current
            DESCRIPTION 
                "CPE Configuration Manager Client Conformance."
            ::= { cpeConfigMgrClient 2 }

        
        -- 1.3.6.1.4.1.5504.3.1.21.1.3.2.1
        cpeCfgMgrClientGroups OBJECT-IDENTITY
            STATUS current
            DESCRIPTION 
                "CPE Configuration Manager Client conformance groups."
            ::= { cpeCfgMgrClientConformance 1 }

        
        -- 1.3.6.1.4.1.5504.3.1.21.1.3.2.1.1
        cpeCfgMgrClientObjectGroup OBJECT-GROUP
            OBJECTS { cpeCfgMgrClientSerialNumber, cpeCfgMgrClientRegistrationID, cpeCfgMgrClientFSAN, cpeCfgMgrClientMacAddress, cpeCfgMgrClientSysName, 
                cpeCfgMgrClientErrorDescription, cpeCfgMgrClientRequiredUpdates, cpeCfgMgrClientReceivedSwFilename, cpeCfgMgrClientReceivedWebUIFilename, cpeCfgMgrClientReceivedGenericCfgFilename, 
                cpeCfgMgrClientReceivedSpecificCfgFilename, cpeCfgMgrClientForceUpdate, cpeCfgMgrClientDwnldSrvrIP, cpeCfgMgrClientDwnldSrvrUsername, cpeCfgMgrClientDwnldSrvrPassword, 
                cpeCfgMgrClientDwnldSrvrSecureMode, cpeCfgMgrClientDwnldSrvrBasePath, cpeCfgMgrClientDwnldSpecificPath, cpeCfgMgrPublicIPAddress, cpeCfgMgrBaseProtocolPort, 
                cpeCfgMgrSlot, cpeCfgMgrPort, cpeCfgMgrSubport, cpeCfgMgrClientCurrentSwVersion, cpeCfgMgrClientCurrentWebUIVersion, 
                cpeCfgMgrClientLastInstalledConfigFile, cpeCfgMgrClientLastDwnldSrvrBasePath, cpeCfgMgrClientLastDwnldSrvrSpecificPath, cpeCfgMgrInterfaceName, cpeCfgMgrClientState
                 }
            STATUS current
            DESCRIPTION 
                "These objects are required for CPEs supporting CPE Configuration
                Manager controls."
            ::= { cpeCfgMgrClientGroups 1 }

        
        -- 1.3.6.1.4.1.5504.3.1.21.1.3.2.1.2
        cpeCfgMgrClientNotificationsGroup NOTIFICATION-GROUP
            NOTIFICATIONS { cpeCfgMgrClientSoftwareDownloadFailed, cpeCfgMgrClientSoftwareInstallFailed, cpeCfgMgrClientWebUIDownloadFailed, cpeCfgMgrClientWebUIInstallFailed, cpeCfgMgrClientConfigDownloadFailed, 
                cpeCfgMgrClientConfigUpdateFailed, cpeCfgMgrClientConfigBackupFailed, cpeCfgMgrClientLevelReady, cpeCfgMgrClientConfigBackupDone }
            STATUS current
            DESCRIPTION 
                "Notifications from a CPE being managed by CPE Config
                manager."
            ::= { cpeCfgMgrClientGroups 2 }

        
        -- 1.3.6.1.4.1.5504.3.1.21.1.3.2.2
        cpeCfgMgrClientCompliances OBJECT-IDENTITY
            STATUS current
            DESCRIPTION 
                "CPE Configuration Manager Client compliances."
            ::= { cpeCfgMgrClientConformance 2 }

        
--  this module
        -- 1.3.6.1.4.1.5504.3.1.21.1.3.2.2.1
        cpeCfgMgrClientCompliance MODULE-COMPLIANCE
            STATUS current
            DESCRIPTION 
                "CPE Config Compliance."
            MODULE -- this module
                MANDATORY-GROUPS { cpeCfgMgrClientObjectGroup, cpeCfgMgrClientNotificationsGroup }
            ::= { cpeCfgMgrClientCompliances 1 }

        
    
    END

--
-- cpeMgr.mib
--
