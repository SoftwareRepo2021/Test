--
-- sle-device-mib.mib
-- MIB generated by MG-SOFT Visual MIB Builder Version 6.0  Build 88
-- Tuesday, September 02, 2014 at 12:17:03
--

--  sle-device-mib.mib
-- MIB generated by MG-SOFT Visual MIB Builder Version 6.0  Build 88
-- Monday, August 27, 2012 at 13:36:26
-- 
--  sle-device-mib.mib
-- MIB generated by MG-SOFT Visual MIB Builder Version 6.0  Build 88
-- Tuesday, January 17, 2012 at 11:51:02
-- 
--  sle-device-mib.mib
-- MIB generated by MG-SOFT Visual MIB Builder Version 6.0  Build 88
-- Wednesday, January 04, 2012 at 10:43:50
-- 
--  sle-device-mib.mib
-- MIB generated by MG-SOFT Visual MIB Builder Version 6.0  Build 88
-- Wednesday, October 26, 2011 at 11:56:00
-- 

	SLE-DEVICE-MIB DEFINITIONS ::= BEGIN
 
		IMPORTS
			sleMgmt			
				FROM DASAN-SMI			
			SleControlStatusType, SleControlRequestResultType			
				FROM SLE-TC-MIB			
			OBJECT-GROUP, NOTIFICATION-GROUP			
				FROM SNMPv2-CONF			
			TimeTicks, IpAddress, Integer32, Unsigned32, Gauge32, 
			BITS, OBJECT-TYPE, MODULE-IDENTITY, NOTIFICATION-TYPE			
				FROM SNMPv2-SMI;
	
	
		-- 1.3.6.1.4.1.6296.101.2
		sleDevice MODULE-IDENTITY 
			LAST-UPDATED "200412100852Z"		-- December 10, 2004 at 08:52 GMT
			ORGANIZATION 
				"Organization."
			CONTACT-INFO 
				"Contact-info."
			DESCRIPTION 
				"Description."
			::= { sleMgmt 2 }

		
	
	
--
-- Node definitions
--
	
		-- 1.3.6.1.4.1.6296.101.2.1
		sleDeviceBase OBJECT IDENTIFIER ::= { sleDevice 1 }

		
		-- 1.3.6.1.4.1.6296.101.2.1.1
		sleDeviceBaseInfo OBJECT IDENTIFIER ::= { sleDeviceBase 1 }

		
		-- 1.3.6.1.4.1.6296.101.2.1.1.1
		sleDeviceEthernetPortNum OBJECT-TYPE
			SYNTAX Integer32
			MAX-ACCESS read-only
			STATUS current
			DESCRIPTION
				"The number of ethernet port."
			::= { sleDeviceBaseInfo 1 }

		
		-- 1.3.6.1.4.1.6296.101.2.1.1.2
		sleDevicePowerNum OBJECT-TYPE
			SYNTAX Integer32
			MAX-ACCESS read-only
			STATUS current
			DESCRIPTION
				"The number of power module"
			::= { sleDeviceBaseInfo 2 }

		
		-- 1.3.6.1.4.1.6296.101.2.1.1.3
		sleDeviceFanModuleNum OBJECT-TYPE
			SYNTAX Integer32
			MAX-ACCESS read-only
			STATUS current
			DESCRIPTION
				"The number of FAN module"
			::= { sleDeviceBaseInfo 3 }

		
		-- 1.3.6.1.4.1.6296.101.2.1.1.4
		sleDeviceTemperatureNum OBJECT-TYPE
			SYNTAX Integer32
			MAX-ACCESS read-only
			STATUS current
			DESCRIPTION
				"The number of temperature sensor"
			::= { sleDeviceBaseInfo 4 }

		
		-- 1.3.6.1.4.1.6296.101.2.1.1.5
		sleDeviceFanStartTemperature OBJECT-TYPE
			SYNTAX Integer32
			MAX-ACCESS read-only
			STATUS current
			DESCRIPTION
				"The temperature value which begins to turn fan."
			::= { sleDeviceBaseInfo 5 }

		
		-- 1.3.6.1.4.1.6296.101.2.1.1.6
		sleDeviceFanStopTemperature OBJECT-TYPE
			SYNTAX Integer32
			MAX-ACCESS read-only
			STATUS current
			DESCRIPTION
				"The temperature value which stops fan."
			::= { sleDeviceBaseInfo 6 }

		
		-- 1.3.6.1.4.1.6296.101.2.1.1.7
		sleDeviceJumboFrameStatus OBJECT-TYPE
			SYNTAX INTEGER
				{
				enable(1),
				disable(2)
				}
			MAX-ACCESS read-only
			STATUS current
			DESCRIPTION
				"The global jumbo-frame status.
				2011/01/20 V5924CR only support this."
			::= { sleDeviceBaseInfo 7 }

		
		-- 1.3.6.1.4.1.6296.101.2.1.1.8
		sleDeviceEnvironmentMonitoringStatus OBJECT-TYPE
			SYNTAX INTEGER
				{
				notInstallAIU(0),
				normalOpen(1),
				normalClose(2)
				}
			MAX-ACCESS read-only
			STATUS current
			DESCRIPTION
				"The alarm input mode of environment monitoring for AIU"
			::= { sleDeviceBaseInfo 8 }

		
		-- 1.3.6.1.4.1.6296.101.2.1.2
		sleDeviceBaseControl OBJECT IDENTIFIER ::= { sleDeviceBase 2 }

		
		-- 1.3.6.1.4.1.6296.101.2.1.2.1
		sleDeviceControlRequest OBJECT-TYPE
			SYNTAX INTEGER
				{
				setDeviceTemperatureThreshold(1),
				setDeviceJumboFrameStatus(2),
				setDeviceLEDTest(3),
				setEnvironmentMonitoringStatus(4)
				}
			MAX-ACCESS read-write
			STATUS current
			DESCRIPTION
				"set an administrative state of FAN module"
			::= { sleDeviceBaseControl 1 }

		
		-- 1.3.6.1.4.1.6296.101.2.1.2.2
		sleDeviceControlStatus OBJECT-TYPE
			SYNTAX SleControlStatusType
			MAX-ACCESS read-only
			STATUS current
			DESCRIPTION
				"Description."
			::= { sleDeviceBaseControl 2 }

		
		-- 1.3.6.1.4.1.6296.101.2.1.2.3
		sleDeviceControlTimer OBJECT-TYPE
			SYNTAX Gauge32
			MAX-ACCESS read-write
			STATUS current
			DESCRIPTION
				"Description."
			::= { sleDeviceBaseControl 3 }

		
		-- 1.3.6.1.4.1.6296.101.2.1.2.4
		sleDeviceControlTimeStamp OBJECT-TYPE
			SYNTAX TimeTicks
			MAX-ACCESS read-only
			STATUS current
			DESCRIPTION
				"Description."
			::= { sleDeviceBaseControl 4 }

		
		-- 1.3.6.1.4.1.6296.101.2.1.2.5
		sleDeviceControlReqResult OBJECT-TYPE
			SYNTAX SleControlRequestResultType
			MAX-ACCESS read-only
			STATUS current
			DESCRIPTION
				"Description."
			::= { sleDeviceBaseControl 5 }

		
		-- 1.3.6.1.4.1.6296.101.2.1.2.6
		sleDeviceControlFanStartTemperature OBJECT-TYPE
			SYNTAX Integer32
			MAX-ACCESS read-write
			STATUS current
			DESCRIPTION
				"Description."
			::= { sleDeviceBaseControl 6 }

		
		-- 1.3.6.1.4.1.6296.101.2.1.2.7
		sleDeviceControlFanStopTemperature OBJECT-TYPE
			SYNTAX Integer32
			MAX-ACCESS read-write
			STATUS current
			DESCRIPTION
				"Description."
			::= { sleDeviceBaseControl 7 }

		
		-- 1.3.6.1.4.1.6296.101.2.1.2.8
		sleDeviceControlJumboFrameStatus OBJECT-TYPE
			SYNTAX INTEGER
				{
				enable(1),
				disable(2)
				}
			MAX-ACCESS read-write
			STATUS current
			DESCRIPTION
				"The global jumbo-frame status.
				2011/01/20 V5924CR only support this."
			::= { sleDeviceBaseControl 8 }

		
		-- 1.3.6.1.4.1.6296.101.2.1.2.9
		sleDeviceControlEnvironmentMonitoringStatus OBJECT-TYPE
			SYNTAX INTEGER
				{
				normalOpen(1),
				normalClose(2)
				}
			MAX-ACCESS read-only
			STATUS current
			DESCRIPTION
				"The alarm input mode of environment monitoring for AIU"
			::= { sleDeviceBaseControl 9 }

		
		-- 1.3.6.1.4.1.6296.101.2.1.3
		sleDeviceBaseNotification OBJECT IDENTIFIER ::= { sleDeviceBase 3 }

		
		-- 1.3.6.1.4.1.6296.101.2.1.3.1
		sleDeviceTemperatureThresholdChanged NOTIFICATION-TYPE
			OBJECTS { sleDeviceFanStartTemperature, sleDeviceFanStopTemperature, sleDeviceControlRequest, sleDeviceControlTimeStamp, sleDeviceControlReqResult
				 }
			STATUS current
			DESCRIPTION 
				"Description."
			::= { sleDeviceBaseNotification 1 }

		
		-- 1.3.6.1.4.1.6296.101.2.1.3.2
		sleDeviceJumboFrameChanged NOTIFICATION-TYPE
			OBJECTS { sleDeviceControlRequest, sleDeviceControlTimeStamp, sleDeviceControlReqResult, sleDeviceControlJumboFrameStatus }
			STATUS current
			DESCRIPTION 
				"Description."
			::= { sleDeviceBaseNotification 2 }

		
		-- 1.3.6.1.4.1.6296.101.2.1.3.3
		sleDeviceLEDTestChanged NOTIFICATION-TYPE
			OBJECTS { sleDeviceControlRequest, sleDeviceControlTimeStamp, sleDeviceControlReqResult }
			STATUS current
			DESCRIPTION 
				"Description."
			::= { sleDeviceBaseNotification 3 }

		
		-- 1.3.6.1.4.1.6296.101.2.1.3.4
		sleDeviceEnvironmentMonitoringStatusChanged NOTIFICATION-TYPE
			OBJECTS { sleDeviceControlRequest, sleDeviceControlTimeStamp, sleDeviceControlReqResult, sleDeviceEnvironmentMonitoringStatus }
			STATUS current
			DESCRIPTION 
				"setEnvironmentMonitoringStatus "
			::= { sleDeviceBaseNotification 4 }

		
		-- 1.3.6.1.4.1.6296.101.2.2
		sleEthernetPort OBJECT IDENTIFIER ::= { sleDevice 2 }

		
		-- 1.3.6.1.4.1.6296.101.2.2.1
		sleEthernetPortTable OBJECT-TYPE
			SYNTAX SEQUENCE OF SleEthernetPortEntry
			MAX-ACCESS not-accessible
			STATUS current
			DESCRIPTION
				"Description."
			::= { sleEthernetPort 1 }

		
		-- 1.3.6.1.4.1.6296.101.2.2.1.1
		sleEthernetPortEntry OBJECT-TYPE
			SYNTAX SleEthernetPortEntry
			MAX-ACCESS not-accessible
			STATUS current
			DESCRIPTION
				"Description."
			INDEX { sleEthernetPortIndex }
			::= { sleEthernetPortTable 1 }

		
		SleEthernetPortEntry ::=
			SEQUENCE { 
				sleEthernetPortIndex
					INTEGER,
				sleEthernetPortPhyIndex
					Integer32,
				sleEthernetPortType
					INTEGER,
				sleEthernetPortAdminStatus
					INTEGER,
				sleEthernetPortOperStatus
					INTEGER,
				sleEthernetPortTransmissionRate
					Integer32,
				sleEthernetPortDuplexMode
					INTEGER,
				sleEthernetPortFlowControl
					INTEGER,
				sleEthernetPortNegotiationMode
					INTEGER,
				sleEthernetPortJumboFrameSize
					Integer32,
				sleEthernetPortSfpTransceiver
					INTEGER,
				sleEthernetPortSfpVendorName
					OCTET STRING,
				sleEthernetPortSfpVendorPartNumber
					OCTET STRING,
				sleEthernetPortSfpVendorRevision
					OCTET STRING,
				sleEthernetPortSfpVendorSerialNumber
					OCTET STRING,
				sleEthernetPortSfpDateCode
					OCTET STRING,
				sleEthernetPortPhysicalRemoteChassis
					OCTET STRING,
				sleEthernetPortPhysicalRemoteSlot
					Integer32,
				sleEthernetPortPhysicalRemotePort
					Integer32,
				sleEthernetPortPhysicalLinkDiscoveryMode
					INTEGER,
				sleEthernetPortSfpTransceiverType
					INTEGER,
				sleEthernetPortSfpTransceiverDetailType
					INTEGER,
				sleEthernetPortSlotIndex
					Integer32,
				sleEthernetPortSlotPortIndex
					Integer32,
				sleEthernetPortAdminTransmissionRate
					Integer32,
				sleEthernetPortAdminDuplexMode
					INTEGER,
				sleEthernetPortAdminFlowControl
					INTEGER,
				sleEthernetPortAdminNegotiationMode
					INTEGER,
				sleEthernetPortAdminReason
					INTEGER
			 }

		-- 1.3.6.1.4.1.6296.101.2.2.1.1.1
		sleEthernetPortIndex OBJECT-TYPE
			SYNTAX INTEGER (1..255)
			MAX-ACCESS read-only
			STATUS current
			DESCRIPTION
				"The port index."
			::= { sleEthernetPortEntry 1 }

		
		-- 1.3.6.1.4.1.6296.101.2.2.1.1.2
		sleEthernetPortPhyIndex OBJECT-TYPE
			SYNTAX Integer32
			MAX-ACCESS read-only
			STATUS current
			DESCRIPTION
				"The physical index of entity mib."
			::= { sleEthernetPortEntry 2 }

		
		-- 1.3.6.1.4.1.6296.101.2.2.1.1.3
		sleEthernetPortType OBJECT-TYPE
			SYNTAX INTEGER
				{
				unknown(0),
				electrical(1),
				optical(2)
				}
			MAX-ACCESS read-only
			STATUS current
			DESCRIPTION
				"The type of port.
				It is not planed to made a automatic switchover between optical and electrical interfaces."
			::= { sleEthernetPortEntry 3 }

		
		-- 1.3.6.1.4.1.6296.101.2.2.1.1.4
		sleEthernetPortAdminStatus OBJECT-TYPE
			SYNTAX INTEGER
				{
				up(1),
				down(2),
				notAvailable(3)
				}
			MAX-ACCESS read-only
			STATUS current
			DESCRIPTION
				"The admin status of port."
			::= { sleEthernetPortEntry 4 }

		
		-- 1.3.6.1.4.1.6296.101.2.2.1.1.5
		sleEthernetPortOperStatus OBJECT-TYPE
			SYNTAX INTEGER
				{
				up(1),
				down(2),
				notAvailable(3)
				}
			MAX-ACCESS read-only
			STATUS current
			DESCRIPTION
				"The oper status of port"
			::= { sleEthernetPortEntry 5 }

		
		-- 1.3.6.1.4.1.6296.101.2.2.1.1.6
		sleEthernetPortTransmissionRate OBJECT-TYPE
			SYNTAX Integer32 (10 | 100 | 1000 | 10000)
			MAX-ACCESS read-only
			STATUS current
			DESCRIPTION
				"The speed of port. Unit is Mbit/s.
				This configurations are only useful for electrical interfaces.
				Optical - interfaces will always support 1000 MBIT/s"
			::= { sleEthernetPortEntry 6 }

		
		-- 1.3.6.1.4.1.6296.101.2.2.1.1.7
		sleEthernetPortDuplexMode OBJECT-TYPE
			SYNTAX INTEGER
				{
				full(1),
				half(2),
				notAvailable(3)
				}
			MAX-ACCESS read-only
			STATUS current
			DESCRIPTION
				"The duplex status of port."
			::= { sleEthernetPortEntry 7 }

		
		-- 1.3.6.1.4.1.6296.101.2.2.1.1.8
		sleEthernetPortFlowControl OBJECT-TYPE
			SYNTAX INTEGER
				{
				disabled(1),
				enabledSymetrical(2),
				enabledAsymetrical(3),
				enabledBoth(4),
				notAvailable(5)
				}
			MAX-ACCESS read-only
			STATUS current
			DESCRIPTION
				"The flow-control mode of port."
			::= { sleEthernetPortEntry 8 }

		
		-- 1.3.6.1.4.1.6296.101.2.2.1.1.9
		sleEthernetPortNegotiationMode OBJECT-TYPE
			SYNTAX INTEGER
				{
				auto(1),
				force(2),
				notAvailable(3)
				}
			MAX-ACCESS read-only
			STATUS current
			DESCRIPTION
				"The Auto Negotiation mode of port. "
			::= { sleEthernetPortEntry 9 }

		
		-- 1.3.6.1.4.1.6296.101.2.2.1.1.10
		sleEthernetPortJumboFrameSize OBJECT-TYPE
			SYNTAX Integer32 (0 | 1518..9216)
			MAX-ACCESS read-only
			STATUS current
			DESCRIPTION
				"The jumbo frame's size of port.
				If the value is zero, it means that it is not set up."
			::= { sleEthernetPortEntry 10 }

		
		-- 1.3.6.1.4.1.6296.101.2.2.1.1.11
		sleEthernetPortSfpTransceiver OBJECT-TYPE
			SYNTAX INTEGER
				{
				unknown(0),
				electrical(1),
				electricalCoaxial(2),
				opticalLongHaul(3),
				opticalShortHaul(4),
				optical10G(5),
				opticalGpon(6)
				}
			MAX-ACCESS read-only
			STATUS current
			DESCRIPTION
				"Description."
			::= { sleEthernetPortEntry 11 }

		
		-- 1.3.6.1.4.1.6296.101.2.2.1.1.12
		sleEthernetPortSfpVendorName OBJECT-TYPE
			SYNTAX OCTET STRING
			MAX-ACCESS read-only
			STATUS current
			DESCRIPTION
				"Description."
			::= { sleEthernetPortEntry 12 }

		
		-- 1.3.6.1.4.1.6296.101.2.2.1.1.13
		sleEthernetPortSfpVendorPartNumber OBJECT-TYPE
			SYNTAX OCTET STRING
			MAX-ACCESS read-only
			STATUS current
			DESCRIPTION
				"Description."
			::= { sleEthernetPortEntry 13 }

		
		-- 1.3.6.1.4.1.6296.101.2.2.1.1.14
		sleEthernetPortSfpVendorRevision OBJECT-TYPE
			SYNTAX OCTET STRING
			MAX-ACCESS read-only
			STATUS current
			DESCRIPTION
				"Description."
			::= { sleEthernetPortEntry 14 }

		
		-- 1.3.6.1.4.1.6296.101.2.2.1.1.15
		sleEthernetPortSfpVendorSerialNumber OBJECT-TYPE
			SYNTAX OCTET STRING
			MAX-ACCESS read-only
			STATUS current
			DESCRIPTION
				"Description."
			::= { sleEthernetPortEntry 15 }

		
		-- 1.3.6.1.4.1.6296.101.2.2.1.1.16
		sleEthernetPortSfpDateCode OBJECT-TYPE
			SYNTAX OCTET STRING
			MAX-ACCESS read-only
			STATUS current
			DESCRIPTION
				"Description."
			::= { sleEthernetPortEntry 16 }

		
		-- 1.3.6.1.4.1.6296.101.2.2.1.1.17
		sleEthernetPortPhysicalRemoteChassis OBJECT-TYPE
			SYNTAX OCTET STRING
			MAX-ACCESS read-only
			STATUS current
			DESCRIPTION
				"Description."
			::= { sleEthernetPortEntry 17 }

		
		-- 1.3.6.1.4.1.6296.101.2.2.1.1.18
		sleEthernetPortPhysicalRemoteSlot OBJECT-TYPE
			SYNTAX Integer32
			MAX-ACCESS read-only
			STATUS current
			DESCRIPTION
				"Description."
			::= { sleEthernetPortEntry 18 }

		
		-- 1.3.6.1.4.1.6296.101.2.2.1.1.19
		sleEthernetPortPhysicalRemotePort OBJECT-TYPE
			SYNTAX Integer32
			MAX-ACCESS read-only
			STATUS current
			DESCRIPTION
				"Description."
			::= { sleEthernetPortEntry 19 }

		
		-- 1.3.6.1.4.1.6296.101.2.2.1.1.20
		sleEthernetPortPhysicalLinkDiscoveryMode OBJECT-TYPE
			SYNTAX INTEGER
				{
				none(1),
				manual(2),
				automatic(3)
				}
			MAX-ACCESS read-only
			STATUS current
			DESCRIPTION
				"Description."
			::= { sleEthernetPortEntry 20 }

		
		-- 1.3.6.1.4.1.6296.101.2.2.1.1.21
		sleEthernetPortSfpTransceiverType OBJECT-TYPE
			SYNTAX INTEGER
				{
				sfp(1),
				gbit(2),
				xfp(3),
				unknown(255)
				}
			MAX-ACCESS read-only
			STATUS current
			DESCRIPTION
				"The type of SFP transceiver."
			::= { sleEthernetPortEntry 21 }

		
		-- 1.3.6.1.4.1.6296.101.2.2.1.1.22
		sleEthernetPortSfpTransceiverDetailType OBJECT-TYPE
			SYNTAX INTEGER
				{
				fiber1000Sx(1),
				fiber1000Lx(2),
				fiber1000Cx(3),
				fiber1000T(4),
				fiber100lLxLx10(5),
				fiber100Fx(6),
				fiberBx10(7),
				fiberPx(8),
				fiberOc3MmSr(9),
				fiberOc3SmIr(10),
				fiberOc3SmLr(11),
				fiber1000Zx(12),
				unknown(255)
				}
			MAX-ACCESS read-write
			STATUS current
			DESCRIPTION
				"The detailed-type of SFP transceiver."
			::= { sleEthernetPortEntry 22 }

		
		-- 1.3.6.1.4.1.6296.101.2.2.1.1.23
		sleEthernetPortSlotIndex OBJECT-TYPE
			SYNTAX Integer32
			MAX-ACCESS read-only
			STATUS current
			DESCRIPTION
				"The slot index."
			::= { sleEthernetPortEntry 23 }

		
		-- 1.3.6.1.4.1.6296.101.2.2.1.1.24
		sleEthernetPortSlotPortIndex OBJECT-TYPE
			SYNTAX Integer32
			MAX-ACCESS read-only
			STATUS current
			DESCRIPTION
				"The slot's port index."
			::= { sleEthernetPortEntry 24 }

		
		-- 1.3.6.1.4.1.6296.101.2.2.1.1.25
		sleEthernetPortAdminTransmissionRate OBJECT-TYPE
			SYNTAX Integer32 (10 | 100 | 1000 | 10000)
			MAX-ACCESS read-only
			STATUS current
			DESCRIPTION
				"The speed of port. Unit is Mbit/s.
				This configurations are only useful for electrical interfaces.
				Optical - interfaces will always support 1000 MBIT/s"
			::= { sleEthernetPortEntry 25 }

		
		-- 1.3.6.1.4.1.6296.101.2.2.1.1.26
		sleEthernetPortAdminDuplexMode OBJECT-TYPE
			SYNTAX INTEGER
				{
				full(1),
				half(2),
				notAvailable(255)
				}
			MAX-ACCESS read-only
			STATUS current
			DESCRIPTION
				"The duplex status of port."
			::= { sleEthernetPortEntry 26 }

		
		-- 1.3.6.1.4.1.6296.101.2.2.1.1.27
		sleEthernetPortAdminFlowControl OBJECT-TYPE
			SYNTAX INTEGER
				{
				disabled(1),
				enableSend(2),
				enableReceive(3),
				enabledBoth(4)
				}
			MAX-ACCESS read-only
			STATUS current
			DESCRIPTION
				"The flow-control mode of port."
			::= { sleEthernetPortEntry 27 }

		
		-- 1.3.6.1.4.1.6296.101.2.2.1.1.28
		sleEthernetPortAdminNegotiationMode OBJECT-TYPE
			SYNTAX INTEGER
				{
				auto(1),
				force(2),
				notAvailable(255)
				}
			MAX-ACCESS read-only
			STATUS current
			DESCRIPTION
				"The Auto Negotiation mode of port. "
			::= { sleEthernetPortEntry 28 }

		
		-- 1.3.6.1.4.1.6296.101.2.2.1.1.29
		sleEthernetPortAdminReason OBJECT-TYPE
			SYNTAX INTEGER
				{
				none(0),
				user(1),
				xllcf(2),
				all(3)
				}
			MAX-ACCESS read-only
			STATUS current
			DESCRIPTION
				"The admin down reason of port."
			::= { sleEthernetPortEntry 29 }

		
		-- 1.3.6.1.4.1.6296.101.2.2.2
		sleEthernetPortControl OBJECT IDENTIFIER ::= { sleEthernetPort 2 }

		
		-- 1.3.6.1.4.1.6296.101.2.2.2.1
		sleEthernetPortControlRequest OBJECT-TYPE
			SYNTAX INTEGER { setEthernetPortProfile(1) }
			MAX-ACCESS read-write
			STATUS current
			DESCRIPTION
				"Description."
			::= { sleEthernetPortControl 1 }

		
		-- 1.3.6.1.4.1.6296.101.2.2.2.2
		sleEthernetPortControlStatus OBJECT-TYPE
			SYNTAX SleControlStatusType
			MAX-ACCESS read-only
			STATUS current
			DESCRIPTION
				"Description."
			::= { sleEthernetPortControl 2 }

		
		-- 1.3.6.1.4.1.6296.101.2.2.2.3
		sleEthernetPortControlTimer OBJECT-TYPE
			SYNTAX Gauge32
			MAX-ACCESS read-write
			STATUS current
			DESCRIPTION
				"Description."
			::= { sleEthernetPortControl 3 }

		
		-- 1.3.6.1.4.1.6296.101.2.2.2.4
		sleEthernetPortControlTimeStamp OBJECT-TYPE
			SYNTAX TimeTicks
			MAX-ACCESS read-only
			STATUS current
			DESCRIPTION
				"Description."
			::= { sleEthernetPortControl 4 }

		
		-- 1.3.6.1.4.1.6296.101.2.2.2.5
		sleEthernetPortControlReqResult OBJECT-TYPE
			SYNTAX SleControlRequestResultType
			MAX-ACCESS read-only
			STATUS current
			DESCRIPTION
				"Description."
			::= { sleEthernetPortControl 5 }

		
		-- 1.3.6.1.4.1.6296.101.2.2.2.6
		sleEthernetPortControlIndex OBJECT-TYPE
			SYNTAX Integer32
			MAX-ACCESS read-write
			STATUS current
			DESCRIPTION
				"Description."
			::= { sleEthernetPortControl 6 }

		
		-- 1.3.6.1.4.1.6296.101.2.2.2.7
		sleEthernetPortControlType OBJECT-TYPE
			SYNTAX INTEGER
				{
				unknown(0),
				electrical(1),
				optical(2)
				}
			MAX-ACCESS read-write
			STATUS current
			DESCRIPTION
				"Description."
			::= { sleEthernetPortControl 7 }

		
		-- 1.3.6.1.4.1.6296.101.2.2.2.8
		sleEthernetPortControlAdminStatus OBJECT-TYPE
			SYNTAX INTEGER
				{
				up(1),
				down(2),
				notAvailable(3)
				}
			MAX-ACCESS read-write
			STATUS current
			DESCRIPTION
				"Description."
			::= { sleEthernetPortControl 8 }

		
		-- 1.3.6.1.4.1.6296.101.2.2.2.9
		sleEthernetPortControlTransmissionRate OBJECT-TYPE
			SYNTAX Integer32 (10 | 100 | 1000 | 10000)
			MAX-ACCESS read-write
			STATUS current
			DESCRIPTION
				"Description.The speed of port. Unit is Mbit/s.
				This configurations are only useful for electrical interfaces.
				Optical - interfaces will always support 1000 MBIT/s"
			::= { sleEthernetPortControl 9 }

		
		-- 1.3.6.1.4.1.6296.101.2.2.2.10
		sleEthernetPortControlDuplexMode OBJECT-TYPE
			SYNTAX INTEGER
				{
				full(1),
				half(2),
				notAvailable(3)
				}
			MAX-ACCESS read-write
			STATUS current
			DESCRIPTION
				"Description."
			::= { sleEthernetPortControl 10 }

		
		-- 1.3.6.1.4.1.6296.101.2.2.2.11
		sleEthernetPortControlFlowControl OBJECT-TYPE
			SYNTAX INTEGER
				{
				disabled(1),
				enabledSymetrical(2),
				enabledAsymetrical(3),
				enabledBoth(4),
				notAvailable(5)
				}
			MAX-ACCESS read-write
			STATUS current
			DESCRIPTION
				"Description."
			::= { sleEthernetPortControl 11 }

		
		-- 1.3.6.1.4.1.6296.101.2.2.2.12
		sleEthernetPortControlNegotiationMode OBJECT-TYPE
			SYNTAX INTEGER
				{
				auto(1),
				force(2),
				notAvailable(3)
				}
			MAX-ACCESS read-write
			STATUS current
			DESCRIPTION
				"Description."
			::= { sleEthernetPortControl 12 }

		
		-- 1.3.6.1.4.1.6296.101.2.2.2.13
		sleEthernetPortControlJumboFrameSize OBJECT-TYPE
			SYNTAX Integer32 (0 | 1518..9000)
			MAX-ACCESS read-write
			STATUS current
			DESCRIPTION
				"Description. If the value is zero, it means erasing the set-up value.
				"
			::= { sleEthernetPortControl 13 }

		
		-- 1.3.6.1.4.1.6296.101.2.2.2.14
		sleEthernetPortControlPhysicalRemoteChassis OBJECT-TYPE
			SYNTAX OCTET STRING
			MAX-ACCESS read-write
			STATUS current
			DESCRIPTION
				"Description."
			::= { sleEthernetPortControl 14 }

		
		-- 1.3.6.1.4.1.6296.101.2.2.2.15
		sleEthernetPortControlPhysicalRemoteSlot OBJECT-TYPE
			SYNTAX Integer32
			MAX-ACCESS read-write
			STATUS current
			DESCRIPTION
				"Description."
			::= { sleEthernetPortControl 15 }

		
		-- 1.3.6.1.4.1.6296.101.2.2.2.16
		sleEthernetPortControlPhysicalRemotePort OBJECT-TYPE
			SYNTAX Integer32
			MAX-ACCESS read-write
			STATUS current
			DESCRIPTION
				"Description."
			::= { sleEthernetPortControl 16 }

		
		-- 1.3.6.1.4.1.6296.101.2.2.2.17
		sleEthernetPortControlPhysicalLinkDiscoveryMode OBJECT-TYPE
			SYNTAX INTEGER
				{
				none(1),
				manual(2),
				automatic(3)
				}
			MAX-ACCESS read-write
			STATUS current
			DESCRIPTION
				"Description."
			::= { sleEthernetPortControl 17 }

		
		-- 1.3.6.1.4.1.6296.101.2.2.3
		sleEthernetPortNotification OBJECT IDENTIFIER ::= { sleEthernetPort 3 }

		
		-- 1.3.6.1.4.1.6296.101.2.2.3.1
		sleEthernetPortChanged NOTIFICATION-TYPE
			OBJECTS { sleEthernetPortType, sleEthernetPortAdminStatus, sleEthernetPortTransmissionRate, sleEthernetPortDuplexMode, sleEthernetPortFlowControl, 
				sleEthernetPortNegotiationMode, sleEthernetPortJumboFrameSize, sleEthernetPortSfpVendorName, sleEthernetPortSfpVendorPartNumber, sleEthernetPortSfpVendorRevision, 
				sleEthernetPortSfpVendorSerialNumber, sleEthernetPortSfpDateCode, sleEthernetPortPhysicalRemoteChassis, sleEthernetPortPhysicalRemoteSlot, sleEthernetPortPhysicalRemotePort, 
				sleEthernetPortPhysicalLinkDiscoveryMode, sleEthernetPortControlRequest, sleEthernetPortControlTimeStamp, sleEthernetPortControlReqResult }
			STATUS current
			DESCRIPTION 
				"Description."
			::= { sleEthernetPortNotification 1 }

		
		-- 1.3.6.1.4.1.6296.101.2.2.4
		sleEthernetPortDMITable OBJECT-TYPE
			SYNTAX SEQUENCE OF SleEthernetPortDMIEntry
			MAX-ACCESS not-accessible
			STATUS current
			DESCRIPTION
				"Description."
			::= { sleEthernetPort 4 }

		
		-- 1.3.6.1.4.1.6296.101.2.2.4.1
		sleEthernetPortDMIEntry OBJECT-TYPE
			SYNTAX SleEthernetPortDMIEntry
			MAX-ACCESS not-accessible
			STATUS current
			DESCRIPTION
				"Description."
			INDEX { sleEthernetPortDMIIndex }
			::= { sleEthernetPortDMITable 1 }

		
		SleEthernetPortDMIEntry ::=
			SEQUENCE { 
				sleEthernetPortDMIIndex
					INTEGER,
				sleEthernetPortDMITemper
					OCTET STRING,
				sleEthernetPortDMIVoltage
					OCTET STRING,
				sleEthernetPortDMITxBias
					OCTET STRING,
				sleEthernetPortDMITxPower
					OCTET STRING,
				sleEthernetPortDMIRxPower
					OCTET STRING
			 }

		-- 1.3.6.1.4.1.6296.101.2.2.4.1.1
		sleEthernetPortDMIIndex OBJECT-TYPE
			SYNTAX INTEGER (1..255)
			MAX-ACCESS read-only
			STATUS current
			DESCRIPTION
				"Port Index."
			::= { sleEthernetPortDMIEntry 1 }

		
		-- 1.3.6.1.4.1.6296.101.2.2.4.1.2
		sleEthernetPortDMITemper OBJECT-TYPE
			SYNTAX OCTET STRING
			MAX-ACCESS read-only
			STATUS current
			DESCRIPTION
				"Internally measured module temperature."
			::= { sleEthernetPortDMIEntry 2 }

		
		-- 1.3.6.1.4.1.6296.101.2.2.4.1.3
		sleEthernetPortDMIVoltage OBJECT-TYPE
			SYNTAX OCTET STRING
			MAX-ACCESS read-only
			STATUS current
			DESCRIPTION
				"Internally measured supply voltage in transceiver."
			::= { sleEthernetPortDMIEntry 3 }

		
		-- 1.3.6.1.4.1.6296.101.2.2.4.1.4
		sleEthernetPortDMITxBias OBJECT-TYPE
			SYNTAX OCTET STRING
			MAX-ACCESS read-only
			STATUS current
			DESCRIPTION
				"Internally measured TX Bias Current."
			::= { sleEthernetPortDMIEntry 4 }

		
		-- 1.3.6.1.4.1.6296.101.2.2.4.1.5
		sleEthernetPortDMITxPower OBJECT-TYPE
			SYNTAX OCTET STRING
			MAX-ACCESS read-only
			STATUS current
			DESCRIPTION
				"Measured TX output power."
			::= { sleEthernetPortDMIEntry 5 }

		
		-- 1.3.6.1.4.1.6296.101.2.2.4.1.6
		sleEthernetPortDMIRxPower OBJECT-TYPE
			SYNTAX OCTET STRING
			MAX-ACCESS read-only
			STATUS current
			DESCRIPTION
				"Measured RX input power."
			::= { sleEthernetPortDMIEntry 6 }

		
		-- 1.3.6.1.4.1.6296.101.2.2.5
		sleEthernetSFPTable OBJECT-TYPE
			SYNTAX SEQUENCE OF SleEthernetSFPEntry
			MAX-ACCESS not-accessible
			STATUS current
			DESCRIPTION
				"Description."
			::= { sleEthernetPort 5 }

		
		-- 1.3.6.1.4.1.6296.101.2.2.5.1
		sleEthernetSFPEntry OBJECT-TYPE
			SYNTAX SleEthernetSFPEntry
			MAX-ACCESS not-accessible
			STATUS current
			DESCRIPTION
				"Description."
			INDEX { sleEthernetSfpIndex }
			::= { sleEthernetSFPTable 1 }

		
		SleEthernetSFPEntry ::=
			SEQUENCE { 
				sleEthernetSfpIndex
					Integer32,
				sleEthernetSfpTransceiver
					INTEGER,
				sleEthernetSfpVendorName
					OCTET STRING,
				sleEthernetSfpVendorPartNumber
					OCTET STRING,
				sleEthernetSfpVendorRevision
					OCTET STRING,
				sleEthernetSfpVendorSerialNumber
					OCTET STRING,
				sleEthernetSfpDateCode
					OCTET STRING,
				sleEthernetSfpTransceiverType
					INTEGER,
				sleEthernetSfpTransceiverDetailType
					INTEGER,
				sleEthernetSfpTransceiverCodes
					OCTET STRING,
				sleEthernetSfpSpeed
					OCTET STRING,
				sleEthernetSfpLength
					Integer32,
				sleEthernetSfpWaveLength
					Integer32,
				sleEthernetSfpMultimodeLengthOm1
					Integer32,
				sleEthernetSfpMultimodeLengthOm2
					Integer32,
				sleEthernetSfpMultimodeLengthOm3
					Integer32,
				sleEthernetSfpTransceiverDetailTypeStr
					OCTET STRING,
				sleEthernetSfpTransceiverLengthStr
					OCTET STRING,
				sleEthernetSfpWaveLengthStr
					OCTET STRING,
				sleEthernetSfpConnectorType
					OCTET STRING
			 }

		-- 1.3.6.1.4.1.6296.101.2.2.5.1.1
		sleEthernetSfpIndex OBJECT-TYPE
			SYNTAX Integer32 (1..65556)
			MAX-ACCESS read-only
			STATUS current
			DESCRIPTION
				"The SFP index."
			::= { sleEthernetSFPEntry 1 }

		
		-- 1.3.6.1.4.1.6296.101.2.2.5.1.2
		sleEthernetSfpTransceiver OBJECT-TYPE
			SYNTAX INTEGER
				{
				unknown(0),
				electrical(1),
				electricalCoaxial(2),
				opticalLongHaul(3),
				opticalShortHaul(4),
				optical10G(5),
				opticalGpon(6)
				}
			MAX-ACCESS read-only
			STATUS current
			DESCRIPTION
				"The type of SFP"
			::= { sleEthernetSFPEntry 2 }

		
		-- 1.3.6.1.4.1.6296.101.2.2.5.1.3
		sleEthernetSfpVendorName OBJECT-TYPE
			SYNTAX OCTET STRING
			MAX-ACCESS read-only
			STATUS current
			DESCRIPTION
				"The vendor name of SFP"
			::= { sleEthernetSFPEntry 3 }

		
		-- 1.3.6.1.4.1.6296.101.2.2.5.1.4
		sleEthernetSfpVendorPartNumber OBJECT-TYPE
			SYNTAX OCTET STRING
			MAX-ACCESS read-only
			STATUS current
			DESCRIPTION
				"The part number of SFP"
			::= { sleEthernetSFPEntry 4 }

		
		-- 1.3.6.1.4.1.6296.101.2.2.5.1.5
		sleEthernetSfpVendorRevision OBJECT-TYPE
			SYNTAX OCTET STRING
			MAX-ACCESS read-only
			STATUS current
			DESCRIPTION
				"The revision of SFP"
			::= { sleEthernetSFPEntry 5 }

		
		-- 1.3.6.1.4.1.6296.101.2.2.5.1.6
		sleEthernetSfpVendorSerialNumber OBJECT-TYPE
			SYNTAX OCTET STRING
			MAX-ACCESS read-only
			STATUS current
			DESCRIPTION
				"The serial number of SFP"
			::= { sleEthernetSFPEntry 6 }

		
		-- 1.3.6.1.4.1.6296.101.2.2.5.1.7
		sleEthernetSfpDateCode OBJECT-TYPE
			SYNTAX OCTET STRING
			MAX-ACCESS read-only
			STATUS current
			DESCRIPTION
				"The manufacturing date of SFP"
			::= { sleEthernetSFPEntry 7 }

		
		-- 1.3.6.1.4.1.6296.101.2.2.5.1.8
		sleEthernetSfpTransceiverType OBJECT-TYPE
			SYNTAX INTEGER
				{
				sfp(1),
				gbic(2),
				xfp(3),
				unknown(255)
				}
			MAX-ACCESS read-only
			STATUS current
			DESCRIPTION
				"The type of SFP transceiver."
			::= { sleEthernetSFPEntry 8 }

		
		-- 1.3.6.1.4.1.6296.101.2.2.5.1.9
		sleEthernetSfpTransceiverDetailType OBJECT-TYPE
			SYNTAX INTEGER
				{
				fiber1000Sx(1),
				fiber1000Lx(2),
				fiber1000Cx(3),
				fiber1000T(4),
				fiber100lLxLx10(5),
				fiber100Fx(6),
				fiberBx10(7),
				fiberPx(8),
				fiberOc3MmSr(9),
				fiberOc3SmIr(10),
				fiberOc3SmLr(11),
				fiber1000Zx(12),
				base10GSR(64),
				base10GLR(65),
				base10GER(66),
				base10GLRM(67),
				base10GSW(68),
				base10GLW(69),
				base10GEW(70),
				base10GEWorZW(71),
				unknown(255)
				}
			MAX-ACCESS read-write
			STATUS current
			DESCRIPTION
				"The detailed-type of SFP transceiver."
			::= { sleEthernetSFPEntry 9 }

		
		-- 1.3.6.1.4.1.6296.101.2.2.5.1.10
		sleEthernetSfpTransceiverCodes OBJECT-TYPE
			SYNTAX OCTET STRING (SIZE (1..8))
			MAX-ACCESS read-only
			STATUS current
			DESCRIPTION
				"The transceiver codes.
				In case of SFP, reference SFP-8472 Rev 11.0
				  - Table 3.5: Transceiver codes (Address A0h)
				  - Table 3.5a: SONET Compliance Specifiers (A0h)
				In case of XFP, reference XFP Specification Revision 4.5 (August 31,2005)
				  - Table 40 Transceiver codes
				"
			::= { sleEthernetSFPEntry 10 }

		
		-- 1.3.6.1.4.1.6296.101.2.2.5.1.11
		sleEthernetSfpSpeed OBJECT-TYPE
			SYNTAX OCTET STRING
			MAX-ACCESS read-only
			STATUS current
			DESCRIPTION
				"The speed of SFP"
			::= { sleEthernetSFPEntry 11 }

		
		-- 1.3.6.1.4.1.6296.101.2.2.5.1.12
		sleEthernetSfpLength OBJECT-TYPE
			SYNTAX Integer32
			MAX-ACCESS read-only
			STATUS current
			DESCRIPTION
				"The length of SFP"
			::= { sleEthernetSFPEntry 12 }

		
		-- 1.3.6.1.4.1.6296.101.2.2.5.1.13
		sleEthernetSfpWaveLength OBJECT-TYPE
			SYNTAX Integer32
			MAX-ACCESS read-only
			STATUS current
			DESCRIPTION
				"The wavelength of SFP"
			::= { sleEthernetSFPEntry 13 }

		
		-- 1.3.6.1.4.1.6296.101.2.2.5.1.14
		sleEthernetSfpMultimodeLengthOm1 OBJECT-TYPE
			SYNTAX Integer32
			MAX-ACCESS read-only
			STATUS current
			DESCRIPTION
				"The Flame rating is 62.5um(OM1). This is used only for 10G SFP module with multi-mode.
				ref) 50/125 Multimode Fiber Optic 
				50/125 is one of the most commonly used multimode optical fiber, the other commonly used is 62.5/125 types. 
				There is a special kind 50/125 multimode fibers, which is called OM3 50/125. People usually refer 62.5/125 as the OM1 MMF, 
				common type 50/125 MMF as OM2, OM3 is also 50/125, but it is different from OM2 because it support 10Gig data transmission. 
				The OM3 50/125 fiber optic cable is also called laser optimized fiber cable. 
				Both OM1 and OM2 multimode cables use the orange color jacket (standard practice for commonly used indoor multimode), 
				OM3 use a special color, which is called Aqua."
			::= { sleEthernetSFPEntry 14 }

		
		-- 1.3.6.1.4.1.6296.101.2.2.5.1.15
		sleEthernetSfpMultimodeLengthOm2 OBJECT-TYPE
			SYNTAX Integer32
			MAX-ACCESS read-only
			STATUS current
			DESCRIPTION
				"The Flame rating is 50um(OM2). This is used only for 10G SFP module with multi-mode.
				ref) 50/125 Multimode Fiber Optic 
				50/125 is one of the most commonly used multimode optical fiber, the other commonly used is 62.5/125 types. 
				There is a special kind 50/125 multimode fibers, which is called OM3 50/125. People usually refer 62.5/125 as the OM1 MMF, 
				common type 50/125 MMF as OM2, OM3 is also 50/125, but it is different from OM2 because it support 10Gig data transmission. 
				The OM3 50/125 fiber optic cable is also called laser optimized fiber cable. 
				Both OM1 and OM2 multimode cables use the orange color jacket (standard practice for commonly used indoor multimode), 
				OM3 use a special color, which is called Aqua."
			::= { sleEthernetSFPEntry 15 }

		
		-- 1.3.6.1.4.1.6296.101.2.2.5.1.16
		sleEthernetSfpMultimodeLengthOm3 OBJECT-TYPE
			SYNTAX Integer32
			MAX-ACCESS read-only
			STATUS current
			DESCRIPTION
				"The Flame rating is 50um(OM3). This is used only for 10G SFP module with multi-mode.
				ref) 50/125 Multimode Fiber Optic 
				50/125 is one of the most commonly used multimode optical fiber, the other commonly used is 62.5/125 types. 
				There is a special kind 50/125 multimode fibers, which is called OM3 50/125. People usually refer 62.5/125 as the OM1 MMF, 
				common type 50/125 MMF as OM2, OM3 is also 50/125, but it is different from OM2 because it support 10Gig data transmission. 
				The OM3 50/125 fiber optic cable is also called laser optimized fiber cable. 
				Both OM1 and OM2 multimode cables use the orange color jacket (standard practice for commonly used indoor multimode), 
				OM3 use a special color, which is called Aqua."
			::= { sleEthernetSFPEntry 16 }

		
		-- 1.3.6.1.4.1.6296.101.2.2.5.1.17
		sleEthernetSfpTransceiverDetailTypeStr OBJECT-TYPE
			SYNTAX OCTET STRING
			MAX-ACCESS read-only
			STATUS current
			DESCRIPTION
				"Description."
			::= { sleEthernetSFPEntry 17 }

		
		-- 1.3.6.1.4.1.6296.101.2.2.5.1.18
		sleEthernetSfpTransceiverLengthStr OBJECT-TYPE
			SYNTAX OCTET STRING
			MAX-ACCESS read-only
			STATUS current
			DESCRIPTION
				"Description."
			::= { sleEthernetSFPEntry 18 }

		
		-- 1.3.6.1.4.1.6296.101.2.2.5.1.19
		sleEthernetSfpWaveLengthStr OBJECT-TYPE
			SYNTAX OCTET STRING
			MAX-ACCESS read-only
			STATUS current
			DESCRIPTION
				"Description."
			::= { sleEthernetSFPEntry 19 }

		
		-- 1.3.6.1.4.1.6296.101.2.2.5.1.20
		sleEthernetSfpConnectorType OBJECT-TYPE
			SYNTAX OCTET STRING
			MAX-ACCESS read-only
			STATUS current
			DESCRIPTION
				"Description."
			::= { sleEthernetSFPEntry 20 }

		
		-- 1.3.6.1.4.1.6296.101.2.2.6
		sleEthernetSFPControl OBJECT IDENTIFIER ::= { sleEthernetPort 6 }

		
		-- 1.3.6.1.4.1.6296.101.2.2.6.1
		sleEthernetSFPControlRequest OBJECT-TYPE
			SYNTAX INTEGER { setSFPRemoteReset(1) }
			MAX-ACCESS read-write
			STATUS current
			DESCRIPTION
				"Description."
			::= { sleEthernetSFPControl 1 }

		
		-- 1.3.6.1.4.1.6296.101.2.2.6.2
		sleEthernetSFPControlStatus OBJECT-TYPE
			SYNTAX SleControlStatusType
			MAX-ACCESS read-only
			STATUS current
			DESCRIPTION
				"Description."
			::= { sleEthernetSFPControl 2 }

		
		-- 1.3.6.1.4.1.6296.101.2.2.6.3
		sleEthernetSFPControlTimer OBJECT-TYPE
			SYNTAX Gauge32
			MAX-ACCESS read-write
			STATUS current
			DESCRIPTION
				"Description."
			::= { sleEthernetSFPControl 3 }

		
		-- 1.3.6.1.4.1.6296.101.2.2.6.4
		sleEthernetSFPControlTimeStamp OBJECT-TYPE
			SYNTAX TimeTicks
			MAX-ACCESS read-only
			STATUS current
			DESCRIPTION
				"Description."
			::= { sleEthernetSFPControl 4 }

		
		-- 1.3.6.1.4.1.6296.101.2.2.6.5
		sleEthernetSFPControlReqResult OBJECT-TYPE
			SYNTAX SleControlRequestResultType
			MAX-ACCESS read-only
			STATUS current
			DESCRIPTION
				"Description."
			::= { sleEthernetSFPControl 5 }

		
		-- 1.3.6.1.4.1.6296.101.2.2.6.6
		sleEthernetSFPControlIndex OBJECT-TYPE
			SYNTAX Integer32
			MAX-ACCESS read-write
			STATUS current
			DESCRIPTION
				"Description."
			::= { sleEthernetSFPControl 6 }

		
		-- 1.3.6.1.4.1.6296.101.2.2.7
		sleEthernetSFPNotification OBJECT IDENTIFIER ::= { sleEthernetPort 7 }

		
		-- 1.3.6.1.4.1.6296.101.2.2.7.1
		sleEthernetSFPRemoteReset NOTIFICATION-TYPE
			OBJECTS { sleEthernetSFPControlRequest, sleEthernetSFPControlTimeStamp, sleEthernetSFPControlReqResult, sleEthernetSFPControlIndex }
			STATUS current
			DESCRIPTION 
				"Description."
			::= { sleEthernetSFPNotification 1 }

		
		-- 1.3.6.1.4.1.6296.101.2.3
		slePower OBJECT IDENTIFIER ::= { sleDevice 3 }

		
		-- 1.3.6.1.4.1.6296.101.2.3.1
		slePowerTable OBJECT-TYPE
			SYNTAX SEQUENCE OF SlePowerEntry
			MAX-ACCESS not-accessible
			STATUS current
			DESCRIPTION
				"Description."
			::= { slePower 1 }

		
		-- 1.3.6.1.4.1.6296.101.2.3.1.1
		slePowerEntry OBJECT-TYPE
			SYNTAX SlePowerEntry
			MAX-ACCESS not-accessible
			STATUS current
			DESCRIPTION
				"Description."
			INDEX { slePowerIndex }
			::= { slePowerTable 1 }

		
		SlePowerEntry ::=
			SEQUENCE { 
				slePowerIndex
					INTEGER,
				slePowerPhyIndex
					Integer32,
				slePowerState
					INTEGER,
				slePowerType
					INTEGER,
				slePowerPSUType
					INTEGER
			 }

		-- 1.3.6.1.4.1.6296.101.2.3.1.1.1
		slePowerIndex OBJECT-TYPE
			SYNTAX INTEGER (1..255)
			MAX-ACCESS read-only
			STATUS current
			DESCRIPTION
				"A unique value, greater than zero, for each module. It is recommended that values are assigned contiguously starting from 1. The value for each interface sub-layer must remain constant at least from one re-initialization of the entity's network management system to the next re-initialization."
			::= { slePowerEntry 1 }

		
		-- 1.3.6.1.4.1.6296.101.2.3.1.1.2
		slePowerPhyIndex OBJECT-TYPE
			SYNTAX Integer32
			MAX-ACCESS read-only
			STATUS current
			DESCRIPTION
				"entPhysicalIndex of Power Modules (0: Internal, -1: uninstalled)"
			::= { slePowerEntry 2 }

		
--  
		-- 1.3.6.1.4.1.6296.101.2.3.1.1.3
		slePowerState OBJECT-TYPE
			SYNTAX INTEGER
				{
				failure(0),
				ok(1)
				}
			MAX-ACCESS read-only
			STATUS current
			DESCRIPTION
				"Power status information."
			::= { slePowerEntry 3 }

		
		-- 1.3.6.1.4.1.6296.101.2.3.1.1.4
		slePowerType OBJECT-TYPE
			SYNTAX INTEGER
				{
				ac(1),
				dc(2),
				unknown(3),
				psu(4)
				}
			MAX-ACCESS read-only
			STATUS current
			DESCRIPTION
				"Power type information."
			::= { slePowerEntry 4 }

		
		-- 1.3.6.1.4.1.6296.101.2.3.1.1.5
		slePowerPSUType OBJECT-TYPE
			SYNTAX INTEGER
				{
				psuA(1),
				psuS(2),
				unknown(255)
				}
			MAX-ACCESS read-only
			STATUS current
			DESCRIPTION
				"The type of Power Supply Unit.(DC)"
			::= { slePowerEntry 5 }

		
		-- 1.3.6.1.4.1.6296.101.2.4
		sleFanModule OBJECT IDENTIFIER ::= { sleDevice 4 }

		
		-- 1.3.6.1.4.1.6296.101.2.4.1
		sleFanModuleTable OBJECT-TYPE
			SYNTAX SEQUENCE OF SleFanModuleEntry
			MAX-ACCESS not-accessible
			STATUS current
			DESCRIPTION
				"Description."
			::= { sleFanModule 1 }

		
		-- 1.3.6.1.4.1.6296.101.2.4.1.1
		sleFanModuleEntry OBJECT-TYPE
			SYNTAX SleFanModuleEntry
			MAX-ACCESS not-accessible
			STATUS current
			DESCRIPTION
				"Description."
			INDEX { sleFanModuleIndex }
			::= { sleFanModuleTable 1 }

		
		SleFanModuleEntry ::=
			SEQUENCE { 
				sleFanModuleIndex
					INTEGER,
				sleFanModulePhyIndex
					Integer32,
				sleFanModuleUnitNum
					Integer32,
				sleFanModuleAdminState
					INTEGER,
				sleFanModuleSpeedThreshold
					Integer32
			 }

		-- 1.3.6.1.4.1.6296.101.2.4.1.1.1
		sleFanModuleIndex OBJECT-TYPE
			SYNTAX INTEGER (1..255)
			MAX-ACCESS read-only
			STATUS current
			DESCRIPTION
				"A unique value, greater than zero, for each module. It is recommended that values are assigned contiguously starting from 1."
			::= { sleFanModuleEntry 1 }

		
		-- 1.3.6.1.4.1.6296.101.2.4.1.1.2
		sleFanModulePhyIndex OBJECT-TYPE
			SYNTAX Integer32
			MAX-ACCESS read-only
			STATUS current
			DESCRIPTION
				"entPhysicalIndex of FAN Modules. (0: Internal, -1: uninstalled)"
			::= { sleFanModuleEntry 2 }

		
		-- 1.3.6.1.4.1.6296.101.2.4.1.1.3
		sleFanModuleUnitNum OBJECT-TYPE
			SYNTAX Integer32
			MAX-ACCESS read-only
			STATUS current
			DESCRIPTION
				"The number of unit in FAN module"
			::= { sleFanModuleEntry 3 }

		
		-- 1.3.6.1.4.1.6296.101.2.4.1.1.4
		sleFanModuleAdminState OBJECT-TYPE
			SYNTAX INTEGER
				{
				off(0),
				on(1),
				auto(2)
				}
			MAX-ACCESS read-only
			STATUS current
			DESCRIPTION
				"An administrative state of FAN module"
			::= { sleFanModuleEntry 4 }

		
		-- 1.3.6.1.4.1.6296.101.2.4.1.1.5
		sleFanModuleSpeedThreshold OBJECT-TYPE
			SYNTAX Integer32
			MAX-ACCESS read-only
			STATUS current
			DESCRIPTION
				"Fan-speed threshold"
			::= { sleFanModuleEntry 5 }

		
		-- 1.3.6.1.4.1.6296.101.2.4.2
		sleFanModuleControl OBJECT IDENTIFIER ::= { sleFanModule 2 }

		
		-- 1.3.6.1.4.1.6296.101.2.4.2.1
		sleFanModuleControlRequest OBJECT-TYPE
			SYNTAX INTEGER
				{
				setFanAdminState(1),
				setFanSpeedThreshold(2)
				}
			MAX-ACCESS read-write
			STATUS current
			DESCRIPTION
				"set an administrative state of FAN module"
			::= { sleFanModuleControl 1 }

		
		-- 1.3.6.1.4.1.6296.101.2.4.2.2
		sleFanModuleControlStatus OBJECT-TYPE
			SYNTAX SleControlStatusType
			MAX-ACCESS read-only
			STATUS current
			DESCRIPTION
				"Description."
			::= { sleFanModuleControl 2 }

		
		-- 1.3.6.1.4.1.6296.101.2.4.2.3
		sleFanModuleControlTimer OBJECT-TYPE
			SYNTAX Gauge32
			MAX-ACCESS read-write
			STATUS current
			DESCRIPTION
				"Description."
			::= { sleFanModuleControl 3 }

		
		-- 1.3.6.1.4.1.6296.101.2.4.2.4
		sleFanModuleControlTimeStamp OBJECT-TYPE
			SYNTAX TimeTicks
			MAX-ACCESS read-only
			STATUS current
			DESCRIPTION
				"Description."
			::= { sleFanModuleControl 4 }

		
		-- 1.3.6.1.4.1.6296.101.2.4.2.5
		sleFanModuleControlReqResult OBJECT-TYPE
			SYNTAX SleControlRequestResultType
			MAX-ACCESS read-only
			STATUS current
			DESCRIPTION
				"Description."
			::= { sleFanModuleControl 5 }

		
		-- 1.3.6.1.4.1.6296.101.2.4.2.6
		sleFanModuleControlIndex OBJECT-TYPE
			SYNTAX Integer32
			MAX-ACCESS read-write
			STATUS current
			DESCRIPTION
				"Description."
			::= { sleFanModuleControl 6 }

		
		-- 1.3.6.1.4.1.6296.101.2.4.2.7
		sleFanModuleControlAdminState OBJECT-TYPE
			SYNTAX INTEGER
				{
				off(0),
				on(1),
				auto(2)
				}
			MAX-ACCESS read-write
			STATUS current
			DESCRIPTION
				"An administrative state of FAN module"
			::= { sleFanModuleControl 7 }

		
		-- 1.3.6.1.4.1.6296.101.2.4.2.8
		sleFanModuleControlSpeedThreshold OBJECT-TYPE
			SYNTAX Integer32
			MAX-ACCESS read-write
			STATUS current
			DESCRIPTION
				"Fan-speed threshold"
			::= { sleFanModuleControl 8 }

		
		-- 1.3.6.1.4.1.6296.101.2.4.3
		sleFanModuleNotification OBJECT IDENTIFIER ::= { sleFanModule 3 }

		
		-- 1.3.6.1.4.1.6296.101.2.4.3.1
		sleFanAdminStateChanged NOTIFICATION-TYPE
			OBJECTS { sleFanModuleAdminState, sleFanModuleControlRequest, sleFanModuleControlTimeStamp, sleFanModuleControlReqResult }
			STATUS current
			DESCRIPTION 
				"Description."
			::= { sleFanModuleNotification 1 }

		
		-- 1.3.6.1.4.1.6296.101.2.4.3.2
		sleFanSpeedThresholdChanged NOTIFICATION-TYPE
			OBJECTS { sleFanModuleControlRequest, sleFanModuleControlTimeStamp, sleFanModuleControlReqResult, sleFanModuleControlIndex, sleFanModuleControlSpeedThreshold
				 }
			STATUS current
			DESCRIPTION 
				"Description."
			::= { sleFanModuleNotification 2 }

		
		-- 1.3.6.1.4.1.6296.101.2.5
		sleFanUnit OBJECT IDENTIFIER ::= { sleDevice 5 }

		
		-- 1.3.6.1.4.1.6296.101.2.5.1
		sleFanUnitTable OBJECT-TYPE
			SYNTAX SEQUENCE OF SleFanUnitEntry
			MAX-ACCESS not-accessible
			STATUS current
			DESCRIPTION
				"Description."
			::= { sleFanUnit 1 }

		
		-- 1.3.6.1.4.1.6296.101.2.5.1.1
		sleFanUnitEntry OBJECT-TYPE
			SYNTAX SleFanUnitEntry
			MAX-ACCESS not-accessible
			STATUS current
			DESCRIPTION
				"Description."
			INDEX { sleFanModuleIndex, sleFanUnitIndex }
			::= { sleFanUnitTable 1 }

		
		SleFanUnitEntry ::=
			SEQUENCE { 
				sleFanUnitIndex
					INTEGER,
				sleFanUnitOperState
					INTEGER,
				sleFanUnitSpeed
					Integer32
			 }

		-- 1.3.6.1.4.1.6296.101.2.5.1.1.1
		sleFanUnitIndex OBJECT-TYPE
			SYNTAX INTEGER (1..255)
			MAX-ACCESS read-only
			STATUS current
			DESCRIPTION
				"A unique number in FAN module"
			::= { sleFanUnitEntry 1 }

		
		-- 1.3.6.1.4.1.6296.101.2.5.1.1.2
		sleFanUnitOperState OBJECT-TYPE
			SYNTAX INTEGER
				{
				failure(0),
				ok(1),
				stop(2)
				}
			MAX-ACCESS read-only
			STATUS current
			DESCRIPTION
				"An operational state of FAN unit"
			::= { sleFanUnitEntry 2 }

		
		-- 1.3.6.1.4.1.6296.101.2.5.1.1.3
		sleFanUnitSpeed OBJECT-TYPE
			SYNTAX Integer32
			MAX-ACCESS read-only
			STATUS current
			DESCRIPTION
				"Speed of FAN unit"
			::= { sleFanUnitEntry 3 }

		
		-- 1.3.6.1.4.1.6296.101.2.6
		sleTemperature OBJECT IDENTIFIER ::= { sleDevice 6 }

		
--     1.3.6.1.4.1.6296.101.2.6.1
-- 1.3.6.1.4.1.6296.101.2.6.1
-- 1.3.6.1.4.1.6296.101.2.6.1
-- 1.3.6.1.4.1.6296.101.2.6.1
		-- 1.3.6.1.4.1.6296.101.2.6.1
		sleTemperatureTable OBJECT-TYPE
			SYNTAX SEQUENCE OF SleTemperatureEntry
			MAX-ACCESS not-accessible
			STATUS current
			DESCRIPTION
				"Description."
			::= { sleTemperature 1 }

		
--     1.3.6.1.4.1.6296.101.2.6.1.1
-- 1.3.6.1.4.1.6296.101.2.6.1.1
-- 1.3.6.1.4.1.6296.101.2.6.1.1
-- 1.3.6.1.4.1.6296.101.2.6.1.1
		-- 1.3.6.1.4.1.6296.101.2.6.1.1
		sleTemperatureEntry OBJECT-TYPE
			SYNTAX SleTemperatureEntry
			MAX-ACCESS not-accessible
			STATUS current
			DESCRIPTION
				"Description."
			INDEX { sleTemperatureIndex }
			::= { sleTemperatureTable 1 }

		
		SleTemperatureEntry ::=
			SEQUENCE { 
				sleTemperatureIndex
					INTEGER,
				sleTemperatureState
					INTEGER,
				sleTemperatureValue
					Integer32,
				sleTemperatureHighThreshold
					Integer32,
				sleTemperatureLowThreshold
					Integer32,
				sleTemperatureWarnHighThreshold
					Integer32,
				sleTemperatureWarnLowThreshold
					Integer32,
				sleTemperatureWarnDuration
					Integer32,
				sleTemperatureAlarmHighThreshold
					Integer32,
				sleTemperatureAlarmLowThreshold
					Integer32,
				sleTemperatureAlarmDuration
					Integer32
			 }

--     1.3.6.1.4.1.6296.101.2.6.1.1.1
-- 1.3.6.1.4.1.6296.101.2.6.1.1.1
-- 1.3.6.1.4.1.6296.101.2.6.1.1.1
-- 1.3.6.1.4.1.6296.101.2.6.1.1.1
		-- 1.3.6.1.4.1.6296.101.2.6.1.1.1
		sleTemperatureIndex OBJECT-TYPE
			SYNTAX INTEGER (1..255)
			MAX-ACCESS read-only
			STATUS current
			DESCRIPTION
				"A unique value, greater than zero, for each module. It is recommended that values are assigned contiguously starting from 1."
			::= { sleTemperatureEntry 1 }

		
--     1.3.6.1.4.1.6296.101.2.6.1.1.2
-- 1.3.6.1.4.1.6296.101.2.6.1.1.2
-- 1.3.6.1.4.1.6296.101.2.6.1.1.2
-- 1.3.6.1.4.1.6296.101.2.6.1.1.2
		-- 1.3.6.1.4.1.6296.101.2.6.1.1.2
		sleTemperatureState OBJECT-TYPE
			SYNTAX INTEGER
				{
				failure(0),
				ok(1),
				others(2)
				}
			MAX-ACCESS read-only
			STATUS current
			DESCRIPTION
				"Temperature status information"
			::= { sleTemperatureEntry 2 }

		
--     1.3.6.1.4.1.6296.101.2.6.1.1.3
-- 1.3.6.1.4.1.6296.101.2.6.1.1.3
-- 1.3.6.1.4.1.6296.101.2.6.1.1.3
-- 1.3.6.1.4.1.6296.101.2.6.1.1.3
		-- 1.3.6.1.4.1.6296.101.2.6.1.1.3
		sleTemperatureValue OBJECT-TYPE
			SYNTAX Integer32
			MAX-ACCESS read-only
			STATUS current
			DESCRIPTION
				"The value of temperature sensor. (unit: C)"
			::= { sleTemperatureEntry 3 }

		
--     1.3.6.1.4.1.6296.101.2.6.1.1.4
-- 1.3.6.1.4.1.6296.101.2.6.1.1.4
-- 1.3.6.1.4.1.6296.101.2.6.1.1.4
-- 1.3.6.1.4.1.6296.101.2.6.1.1.4
		-- 1.3.6.1.4.1.6296.101.2.6.1.1.4
		sleTemperatureHighThreshold OBJECT-TYPE
			SYNTAX Integer32
			MAX-ACCESS read-only
			STATUS current
			DESCRIPTION
				"The High threshold of temperature."
			::= { sleTemperatureEntry 4 }

		
--     1.3.6.1.4.1.6296.101.2.6.1.1.5
-- 1.3.6.1.4.1.6296.101.2.6.1.1.5
-- 1.3.6.1.4.1.6296.101.2.6.1.1.5
-- 1.3.6.1.4.1.6296.101.2.6.1.1.5
		-- 1.3.6.1.4.1.6296.101.2.6.1.1.5
		sleTemperatureLowThreshold OBJECT-TYPE
			SYNTAX Integer32
			MAX-ACCESS read-only
			STATUS current
			DESCRIPTION
				"The Low threshold of temperature."
			::= { sleTemperatureEntry 5 }

		
--      1.3.6.1.4.1.6296.101.2.6.1.1.6
-- 1.3.6.1.4.1.6296.101.2.6.1.1.6
-- 1.3.6.1.4.1.6296.101.2.6.1.1.6
-- 1.3.6.1.4.1.6296.101.2.6.1.1.6
-- 1.3.6.1.4.1.6296.101.2.6.1.1.6
		-- 1.3.6.1.4.1.6296.101.2.6.1.1.6
		sleTemperatureWarnHighThreshold OBJECT-TYPE
			SYNTAX Integer32 (-40..100)
			MAX-ACCESS read-only
			STATUS current
			DESCRIPTION
				"The High threshold of temperature."
			::= { sleTemperatureEntry 6 }

		
--      1.3.6.1.4.1.6296.101.2.6.1.1.7
-- 1.3.6.1.4.1.6296.101.2.6.1.1.7
-- 1.3.6.1.4.1.6296.101.2.6.1.1.7
-- 1.3.6.1.4.1.6296.101.2.6.1.1.7
-- 1.3.6.1.4.1.6296.101.2.6.1.1.7
		-- 1.3.6.1.4.1.6296.101.2.6.1.1.7
		sleTemperatureWarnLowThreshold OBJECT-TYPE
			SYNTAX Integer32 (-40..100)
			MAX-ACCESS read-only
			STATUS current
			DESCRIPTION
				"The Low threshold of temperature."
			::= { sleTemperatureEntry 7 }

		
--      1.3.6.1.4.1.6296.101.2.6.1.1.8
-- 1.3.6.1.4.1.6296.101.2.6.1.1.8
-- 1.3.6.1.4.1.6296.101.2.6.1.1.8
-- 1.3.6.1.4.1.6296.101.2.6.1.1.8
-- 1.3.6.1.4.1.6296.101.2.6.1.1.8
		-- 1.3.6.1.4.1.6296.101.2.6.1.1.8
		sleTemperatureWarnDuration OBJECT-TYPE
			SYNTAX Integer32 (0..300)
			MAX-ACCESS read-only
			STATUS current
			DESCRIPTION
				"Duration-time units by the 5 sec.
				0: Clear threshold."
			::= { sleTemperatureEntry 8 }

		
--      1.3.6.1.4.1.6296.101.2.6.1.1.9
-- 1.3.6.1.4.1.6296.101.2.6.1.1.9
-- 1.3.6.1.4.1.6296.101.2.6.1.1.9
-- 1.3.6.1.4.1.6296.101.2.6.1.1.9
-- 1.3.6.1.4.1.6296.101.2.6.1.1.9
		-- 1.3.6.1.4.1.6296.101.2.6.1.1.9
		sleTemperatureAlarmHighThreshold OBJECT-TYPE
			SYNTAX Integer32 (-40..100)
			MAX-ACCESS read-only
			STATUS current
			DESCRIPTION
				"The High threshold of temperature."
			::= { sleTemperatureEntry 9 }

		
--      1.3.6.1.4.1.6296.101.2.6.1.1.10
-- 1.3.6.1.4.1.6296.101.2.6.1.1.10
-- 1.3.6.1.4.1.6296.101.2.6.1.1.10
-- 1.3.6.1.4.1.6296.101.2.6.1.1.10
-- 1.3.6.1.4.1.6296.101.2.6.1.1.10
		-- 1.3.6.1.4.1.6296.101.2.6.1.1.10
		sleTemperatureAlarmLowThreshold OBJECT-TYPE
			SYNTAX Integer32 (-40..100)
			MAX-ACCESS read-only
			STATUS current
			DESCRIPTION
				"The Low threshold of temperature."
			::= { sleTemperatureEntry 10 }

		
--      1.3.6.1.4.1.6296.101.2.6.1.1.11
-- 1.3.6.1.4.1.6296.101.2.6.1.1.11
-- 1.3.6.1.4.1.6296.101.2.6.1.1.11
-- 1.3.6.1.4.1.6296.101.2.6.1.1.11
-- 1.3.6.1.4.1.6296.101.2.6.1.1.11
		-- 1.3.6.1.4.1.6296.101.2.6.1.1.11
		sleTemperatureAlarmDuration OBJECT-TYPE
			SYNTAX Integer32 (0..300)
			MAX-ACCESS read-only
			STATUS current
			DESCRIPTION
				"Duration-time units by the 5 sec.
				0: Clear threshold."
			::= { sleTemperatureEntry 11 }

		
--     1.3.6.1.4.1.6296.101.2.6.2
-- 1.3.6.1.4.1.6296.101.2.6.2
-- 1.3.6.1.4.1.6296.101.2.6.2
-- 1.3.6.1.4.1.6296.101.2.6.2
		-- 1.3.6.1.4.1.6296.101.2.6.2
		sleTemperatureControl OBJECT IDENTIFIER ::= { sleTemperature 2 }

		
--     1.3.6.1.4.1.6296.101.2.6.2.1
-- 1.3.6.1.4.1.6296.101.2.6.2.1
-- 1.3.6.1.4.1.6296.101.2.6.2.1
-- 1.3.6.1.4.1.6296.101.2.6.2.1
		-- 1.3.6.1.4.1.6296.101.2.6.2.1
		sleTemperatureControlRequest OBJECT-TYPE
			SYNTAX INTEGER
				{
				setTempThreshold(1),
				setTempAlarmThreshold(2),
				setTempWarnThreshold(3)
				}
			MAX-ACCESS read-write
			STATUS current
			DESCRIPTION
				"set an administrative state of FAN module"
			::= { sleTemperatureControl 1 }

		
--     1.3.6.1.4.1.6296.101.2.6.2.2
-- 1.3.6.1.4.1.6296.101.2.6.2.2
-- 1.3.6.1.4.1.6296.101.2.6.2.2
-- 1.3.6.1.4.1.6296.101.2.6.2.2
		-- 1.3.6.1.4.1.6296.101.2.6.2.2
		sleTemperatureControlStatus OBJECT-TYPE
			SYNTAX SleControlStatusType
			MAX-ACCESS read-only
			STATUS current
			DESCRIPTION
				"Description."
			::= { sleTemperatureControl 2 }

		
--     1.3.6.1.4.1.6296.101.2.6.2.3
-- 1.3.6.1.4.1.6296.101.2.6.2.3
-- 1.3.6.1.4.1.6296.101.2.6.2.3
-- 1.3.6.1.4.1.6296.101.2.6.2.3
		-- 1.3.6.1.4.1.6296.101.2.6.2.3
		sleTemperatureControlTimer OBJECT-TYPE
			SYNTAX Gauge32
			MAX-ACCESS read-write
			STATUS current
			DESCRIPTION
				"Description."
			::= { sleTemperatureControl 3 }

		
--     1.3.6.1.4.1.6296.101.2.6.2.4
-- 1.3.6.1.4.1.6296.101.2.6.2.4
-- 1.3.6.1.4.1.6296.101.2.6.2.4
-- 1.3.6.1.4.1.6296.101.2.6.2.4
		-- 1.3.6.1.4.1.6296.101.2.6.2.4
		sleTemperatureControlTimeStamp OBJECT-TYPE
			SYNTAX TimeTicks
			MAX-ACCESS read-only
			STATUS current
			DESCRIPTION
				"Description."
			::= { sleTemperatureControl 4 }

		
--     1.3.6.1.4.1.6296.101.2.6.2.5
-- 1.3.6.1.4.1.6296.101.2.6.2.5
-- 1.3.6.1.4.1.6296.101.2.6.2.5
-- 1.3.6.1.4.1.6296.101.2.6.2.5
		-- 1.3.6.1.4.1.6296.101.2.6.2.5
		sleTemperatureControlReqResult OBJECT-TYPE
			SYNTAX SleControlRequestResultType
			MAX-ACCESS read-only
			STATUS current
			DESCRIPTION
				"Description."
			::= { sleTemperatureControl 5 }

		
--     1.3.6.1.4.1.6296.101.2.6.2.6
-- 1.3.6.1.4.1.6296.101.2.6.2.6
-- 1.3.6.1.4.1.6296.101.2.6.2.6
-- 1.3.6.1.4.1.6296.101.2.6.2.6
		-- 1.3.6.1.4.1.6296.101.2.6.2.6
		sleTemperatureControlIndex OBJECT-TYPE
			SYNTAX Integer32
			MAX-ACCESS read-write
			STATUS current
			DESCRIPTION
				"The Temperature index"
			::= { sleTemperatureControl 6 }

		
--     1.3.6.1.4.1.6296.101.2.6.2.7
-- 1.3.6.1.4.1.6296.101.2.6.2.7
-- 1.3.6.1.4.1.6296.101.2.6.2.7
-- 1.3.6.1.4.1.6296.101.2.6.2.7
		-- 1.3.6.1.4.1.6296.101.2.6.2.7
		sleTemperatureControlHighThreshold OBJECT-TYPE
			SYNTAX Integer32
			MAX-ACCESS read-write
			STATUS current
			DESCRIPTION
				"The High threshold of temperature."
			::= { sleTemperatureControl 7 }

		
--     1.3.6.1.4.1.6296.101.2.6.2.8
-- 1.3.6.1.4.1.6296.101.2.6.2.8
-- 1.3.6.1.4.1.6296.101.2.6.2.8
-- 1.3.6.1.4.1.6296.101.2.6.2.8
		-- 1.3.6.1.4.1.6296.101.2.6.2.8
		sleTemperatureControlLowThreshold OBJECT-TYPE
			SYNTAX Integer32
			MAX-ACCESS read-write
			STATUS current
			DESCRIPTION
				"The Low threshold of temperature."
			::= { sleTemperatureControl 8 }

		
--      1.3.6.1.4.1.6296.101.2.6.2.9
-- 1.3.6.1.4.1.6296.101.2.6.2.9
-- 1.3.6.1.4.1.6296.101.2.6.2.9
-- 1.3.6.1.4.1.6296.101.2.6.2.9
-- 1.3.6.1.4.1.6296.101.2.6.2.9
		-- 1.3.6.1.4.1.6296.101.2.6.2.9
		sleTemperatureControlDuration OBJECT-TYPE
			SYNTAX Integer32 (0..300)
			MAX-ACCESS read-write
			STATUS current
			DESCRIPTION
				"Duration-time units by the 5 sec.
				0: Clear threshold."
			::= { sleTemperatureControl 9 }

		
--     1.3.6.1.4.1.6296.101.2.6.3
-- 1.3.6.1.4.1.6296.101.2.6.3
-- 1.3.6.1.4.1.6296.101.2.6.3
-- 1.3.6.1.4.1.6296.101.2.6.3
		-- 1.3.6.1.4.1.6296.101.2.6.3
		sleTemperatureNotification OBJECT IDENTIFIER ::= { sleTemperature 3 }

		
--       1.3.6.1.4.1.6296.101.2.6.3.1
-- 1.3.6.1.4.1.6296.101.2.6.3.1
-- 1.3.6.1.4.1.6296.101.2.6.3.1
-- 1.3.6.1.4.1.6296.101.2.6.3.1
-- 1.3.6.1.4.1.6296.101.2.6.3.1
-- 1.3.6.1.4.1.6296.101.2.6.3.1
		-- 1.3.6.1.4.1.6296.101.2.6.3.1
		sleTemperatureThresholdChanged NOTIFICATION-TYPE
			OBJECTS { sleTemperatureControlRequest, sleTemperatureControlTimeStamp, sleTemperatureControlReqResult, sleTemperatureIndex, sleTemperatureWarnHighThreshold, 
				sleTemperatureWarnLowThreshold, sleTemperatureWarnDuration, sleTemperatureAlarmHighThreshold, sleTemperatureAlarmLowThreshold, sleTemperatureLowThreshold, 
				sleTemperatureAlarmDuration, sleTemperatureHighThreshold }
			STATUS current
			DESCRIPTION 
				"Description."
			::= { sleTemperatureNotification 1 }

		
		-- 1.3.6.1.4.1.6296.101.2.7
		sleBattery OBJECT IDENTIFIER ::= { sleDevice 7 }

		
--     1.3.6.1.4.1.6296.101.2.7.1
-- 1.3.6.1.4.1.6296.101.2.7.1
-- 1.3.6.1.4.1.6296.101.2.7.1
-- 1.3.6.1.4.1.6296.101.2.7.1
		-- 1.3.6.1.4.1.6296.101.2.7.1
		sleBatteryTable OBJECT-TYPE
			SYNTAX SEQUENCE OF SleBatteryEntry
			MAX-ACCESS not-accessible
			STATUS current
			DESCRIPTION
				"Description."
			::= { sleBattery 1 }

		
--     1.3.6.1.4.1.6296.101.2.7.1.1
-- 1.3.6.1.4.1.6296.101.2.7.1.1
-- 1.3.6.1.4.1.6296.101.2.7.1.1
-- 1.3.6.1.4.1.6296.101.2.7.1.1
		-- 1.3.6.1.4.1.6296.101.2.7.1.1
		sleBatteryEntry OBJECT-TYPE
			SYNTAX SleBatteryEntry
			MAX-ACCESS not-accessible
			STATUS current
			DESCRIPTION
				"Description."
			INDEX { sleBatteryIndex }
			::= { sleBatteryTable 1 }

		
		SleBatteryEntry ::=
			SEQUENCE { 
				sleBatteryIndex
					INTEGER,
				sleOperationPowerType
					INTEGER,
				sleOperationPowerInfo
					OCTET STRING,
				slePSUACPowerState
					INTEGER,
				slePSUTemperture
					Integer32,
				slePSUTempThreshold
					Integer32,
				slePSUOutVoltage
					OCTET STRING,
				slePSUOverTemp
					INTEGER,
				slePSUFirmwareVer
					Integer32,
				sleRBUEquipState
					INTEGER,
				sleRBUModeStaus
					OCTET STRING,
				sleRBUTemperature1
					Integer32,
				sleRBUTemperature2
					Integer32,
				sleRBUTempLowThreshold
					Integer32,
				sleRBUOutVoltage
					OCTET STRING,
				sleRBUChargeCurrent
					Integer32,
				sleRBURemainCapacity
					Integer32,
				sleRBUOverTemp
					INTEGER,
				sleBatteryLow
					INTEGER,
				sleRBUTempHighThreshold
					Integer32,
				sleRBUBTStatus
					INTEGER,
				sleRBUBTThreshold
					Integer32,
				sleRBURechargeVoltage
					Integer32,
				sleBatteryCellStatus
					INTEGER,
				sleBPSUACHardwareVer
					Integer32
			 }

--     1.3.6.1.4.1.6296.101.2.7.1.1.1
-- 1.3.6.1.4.1.6296.101.2.7.1.1.1
-- 1.3.6.1.4.1.6296.101.2.7.1.1.1
-- 1.3.6.1.4.1.6296.101.2.7.1.1.1
		-- 1.3.6.1.4.1.6296.101.2.7.1.1.1
		sleBatteryIndex OBJECT-TYPE
			SYNTAX INTEGER (1..256)
			MAX-ACCESS read-only
			STATUS current
			DESCRIPTION
				"The index of battery charger."
			::= { sleBatteryEntry 1 }

		
--     1.3.6.1.4.1.6296.101.2.7.1.1.2
-- 1.3.6.1.4.1.6296.101.2.7.1.1.2
-- 1.3.6.1.4.1.6296.101.2.7.1.1.2
-- 1.3.6.1.4.1.6296.101.2.7.1.1.2
		-- 1.3.6.1.4.1.6296.101.2.7.1.1.2
		sleOperationPowerType OBJECT-TYPE
			SYNTAX INTEGER
				{
				ac(0),
				rbu(1)
				}
			MAX-ACCESS read-only
			STATUS current
			DESCRIPTION
				"Power Type."
			::= { sleBatteryEntry 2 }

		
--     1.3.6.1.4.1.6296.101.2.7.1.1.3
-- 1.3.6.1.4.1.6296.101.2.7.1.1.3
-- 1.3.6.1.4.1.6296.101.2.7.1.1.3
-- 1.3.6.1.4.1.6296.101.2.7.1.1.3
		-- 1.3.6.1.4.1.6296.101.2.7.1.1.3
		sleOperationPowerInfo OBJECT-TYPE
			SYNTAX OCTET STRING
			MAX-ACCESS read-only
			STATUS current
			DESCRIPTION
				"Operation Power Info."
			::= { sleBatteryEntry 3 }

		
--     1.3.6.1.4.1.6296.101.2.7.1.1.4
-- 1.3.6.1.4.1.6296.101.2.7.1.1.4
-- 1.3.6.1.4.1.6296.101.2.7.1.1.4
-- 1.3.6.1.4.1.6296.101.2.7.1.1.4
		-- 1.3.6.1.4.1.6296.101.2.7.1.1.4
		slePSUACPowerState OBJECT-TYPE
			SYNTAX INTEGER
				{
				ok(0),
				fault(1)
				}
			MAX-ACCESS read-only
			STATUS current
			DESCRIPTION
				"Power State."
			::= { sleBatteryEntry 4 }

		
--     1.3.6.1.4.1.6296.101.2.7.1.1.5
-- 1.3.6.1.4.1.6296.101.2.7.1.1.5
-- 1.3.6.1.4.1.6296.101.2.7.1.1.5
-- 1.3.6.1.4.1.6296.101.2.7.1.1.5
		-- 1.3.6.1.4.1.6296.101.2.7.1.1.5
		slePSUTemperture OBJECT-TYPE
			SYNTAX Integer32
			MAX-ACCESS read-only
			STATUS current
			DESCRIPTION
				"Temperture."
			::= { sleBatteryEntry 5 }

		
--     1.3.6.1.4.1.6296.101.2.7.1.1.6
-- 1.3.6.1.4.1.6296.101.2.7.1.1.6
-- 1.3.6.1.4.1.6296.101.2.7.1.1.6
-- 1.3.6.1.4.1.6296.101.2.7.1.1.6
		-- 1.3.6.1.4.1.6296.101.2.7.1.1.6
		slePSUTempThreshold OBJECT-TYPE
			SYNTAX Integer32
			MAX-ACCESS read-only
			STATUS current
			DESCRIPTION
				"Temperture Threshold."
			::= { sleBatteryEntry 6 }

		
--     1.3.6.1.4.1.6296.101.2.7.1.1.7
-- 1.3.6.1.4.1.6296.101.2.7.1.1.7
-- 1.3.6.1.4.1.6296.101.2.7.1.1.7
-- 1.3.6.1.4.1.6296.101.2.7.1.1.7
		-- 1.3.6.1.4.1.6296.101.2.7.1.1.7
		slePSUOutVoltage OBJECT-TYPE
			SYNTAX OCTET STRING
			MAX-ACCESS read-only
			STATUS current
			DESCRIPTION
				"Voltage."
			::= { sleBatteryEntry 7 }

		
--     1.3.6.1.4.1.6296.101.2.7.1.1.8
-- 1.3.6.1.4.1.6296.101.2.7.1.1.8
-- 1.3.6.1.4.1.6296.101.2.7.1.1.8
-- 1.3.6.1.4.1.6296.101.2.7.1.1.8
		-- 1.3.6.1.4.1.6296.101.2.7.1.1.8
		slePSUOverTemp OBJECT-TYPE
			SYNTAX INTEGER
				{
				normal(0),
				over(1)
				}
			MAX-ACCESS read-only
			STATUS current
			DESCRIPTION
				"Description."
			::= { sleBatteryEntry 8 }

		
--     1.3.6.1.4.1.6296.101.2.7.1.1.9
-- 1.3.6.1.4.1.6296.101.2.7.1.1.9
-- 1.3.6.1.4.1.6296.101.2.7.1.1.9
-- 1.3.6.1.4.1.6296.101.2.7.1.1.9
		-- 1.3.6.1.4.1.6296.101.2.7.1.1.9
		slePSUFirmwareVer OBJECT-TYPE
			SYNTAX Integer32
			MAX-ACCESS read-only
			STATUS current
			DESCRIPTION
				"The firmware version of battery charger for communication to system."
			::= { sleBatteryEntry 9 }

		
--     1.3.6.1.4.1.6296.101.2.7.1.1.10
-- 1.3.6.1.4.1.6296.101.2.7.1.1.10
-- 1.3.6.1.4.1.6296.101.2.7.1.1.10
-- 1.3.6.1.4.1.6296.101.2.7.1.1.10
		-- 1.3.6.1.4.1.6296.101.2.7.1.1.10
		sleRBUEquipState OBJECT-TYPE
			SYNTAX INTEGER
				{
				equipped(0),
				empty(1)
				}
			MAX-ACCESS read-only
			STATUS current
			DESCRIPTION
				"Equipment State."
			::= { sleBatteryEntry 10 }

		
--     1.3.6.1.4.1.6296.101.2.7.1.1.11
-- 1.3.6.1.4.1.6296.101.2.7.1.1.11
-- 1.3.6.1.4.1.6296.101.2.7.1.1.11
-- 1.3.6.1.4.1.6296.101.2.7.1.1.11
		-- 1.3.6.1.4.1.6296.101.2.7.1.1.11
		sleRBUModeStaus OBJECT-TYPE
			SYNTAX OCTET STRING
			MAX-ACCESS read-only
			STATUS current
			DESCRIPTION
				"Description."
			::= { sleBatteryEntry 11 }

		
--     1.3.6.1.4.1.6296.101.2.7.1.1.12
-- 1.3.6.1.4.1.6296.101.2.7.1.1.12
-- 1.3.6.1.4.1.6296.101.2.7.1.1.12
-- 1.3.6.1.4.1.6296.101.2.7.1.1.12
		-- 1.3.6.1.4.1.6296.101.2.7.1.1.12
		sleRBUTemperature1 OBJECT-TYPE
			SYNTAX Integer32
			MAX-ACCESS read-only
			STATUS current
			DESCRIPTION
				"Description."
			::= { sleBatteryEntry 12 }

		
--     1.3.6.1.4.1.6296.101.2.7.1.1.13
-- 1.3.6.1.4.1.6296.101.2.7.1.1.13
-- 1.3.6.1.4.1.6296.101.2.7.1.1.13
-- 1.3.6.1.4.1.6296.101.2.7.1.1.13
		-- 1.3.6.1.4.1.6296.101.2.7.1.1.13
		sleRBUTemperature2 OBJECT-TYPE
			SYNTAX Integer32
			MAX-ACCESS read-only
			STATUS current
			DESCRIPTION
				"."
			::= { sleBatteryEntry 13 }

		
--     1.3.6.1.4.1.6296.101.2.7.1.1.14
-- 1.3.6.1.4.1.6296.101.2.7.1.1.14
-- 1.3.6.1.4.1.6296.101.2.7.1.1.14
-- 1.3.6.1.4.1.6296.101.2.7.1.1.14
		-- 1.3.6.1.4.1.6296.101.2.7.1.1.14
		sleRBUTempLowThreshold OBJECT-TYPE
			SYNTAX Integer32
			MAX-ACCESS read-only
			STATUS current
			DESCRIPTION
				"RBU Low Temperature Threshold."
			::= { sleBatteryEntry 14 }

		
--     1.3.6.1.4.1.6296.101.2.7.1.1.15
-- 1.3.6.1.4.1.6296.101.2.7.1.1.15
-- 1.3.6.1.4.1.6296.101.2.7.1.1.15
-- 1.3.6.1.4.1.6296.101.2.7.1.1.15
		-- 1.3.6.1.4.1.6296.101.2.7.1.1.15
		sleRBUOutVoltage OBJECT-TYPE
			SYNTAX OCTET STRING
			MAX-ACCESS read-only
			STATUS current
			DESCRIPTION
				"RBU Out Voltage."
			::= { sleBatteryEntry 15 }

		
--     1.3.6.1.4.1.6296.101.2.7.1.1.16
-- 1.3.6.1.4.1.6296.101.2.7.1.1.16
-- 1.3.6.1.4.1.6296.101.2.7.1.1.16
-- 1.3.6.1.4.1.6296.101.2.7.1.1.16
		-- 1.3.6.1.4.1.6296.101.2.7.1.1.16
		sleRBUChargeCurrent OBJECT-TYPE
			SYNTAX Integer32
			MAX-ACCESS read-only
			STATUS current
			DESCRIPTION
				"Current Charge."
			::= { sleBatteryEntry 16 }

		
--     1.3.6.1.4.1.6296.101.2.7.1.1.17
-- 1.3.6.1.4.1.6296.101.2.7.1.1.17
-- 1.3.6.1.4.1.6296.101.2.7.1.1.17
-- 1.3.6.1.4.1.6296.101.2.7.1.1.17
		-- 1.3.6.1.4.1.6296.101.2.7.1.1.17
		sleRBURemainCapacity OBJECT-TYPE
			SYNTAX Integer32
			MAX-ACCESS read-only
			STATUS current
			DESCRIPTION
				"Remain Capacity."
			::= { sleBatteryEntry 17 }

		
--     1.3.6.1.4.1.6296.101.2.7.1.1.18
-- 1.3.6.1.4.1.6296.101.2.7.1.1.18
-- 1.3.6.1.4.1.6296.101.2.7.1.1.18
-- 1.3.6.1.4.1.6296.101.2.7.1.1.18
		-- 1.3.6.1.4.1.6296.101.2.7.1.1.18
		sleRBUOverTemp OBJECT-TYPE
			SYNTAX INTEGER
				{
				normal(0),
				over(1),
				under(2)
				}
			MAX-ACCESS read-only
			STATUS current
			DESCRIPTION
				"The  state of Temperature over."
			::= { sleBatteryEntry 18 }

		
--     1.3.6.1.4.1.6296.101.2.7.1.1.19
-- 1.3.6.1.4.1.6296.101.2.7.1.1.19
-- 1.3.6.1.4.1.6296.101.2.7.1.1.19
-- 1.3.6.1.4.1.6296.101.2.7.1.1.19
		-- 1.3.6.1.4.1.6296.101.2.7.1.1.19
		sleBatteryLow OBJECT-TYPE
			SYNTAX INTEGER
				{
				normal(0),
				low(1),
				notAvailable(2)
				}
			MAX-ACCESS read-only
			STATUS current
			DESCRIPTION
				"Battery state."
			::= { sleBatteryEntry 19 }

		
--     1.3.6.1.4.1.6296.101.2.7.1.1.20
-- 1.3.6.1.4.1.6296.101.2.7.1.1.20
-- 1.3.6.1.4.1.6296.101.2.7.1.1.20
-- 1.3.6.1.4.1.6296.101.2.7.1.1.20
		-- 1.3.6.1.4.1.6296.101.2.7.1.1.20
		sleRBUTempHighThreshold OBJECT-TYPE
			SYNTAX Integer32
			MAX-ACCESS read-only
			STATUS current
			DESCRIPTION
				"RBU High Temperature Threshold."
			::= { sleBatteryEntry 20 }

		
--     1.3.6.1.4.1.6296.101.2.7.1.1.21
-- 1.3.6.1.4.1.6296.101.2.7.1.1.21
-- 1.3.6.1.4.1.6296.101.2.7.1.1.21
-- 1.3.6.1.4.1.6296.101.2.7.1.1.21
		-- 1.3.6.1.4.1.6296.101.2.7.1.1.21
		sleRBUBTStatus OBJECT-TYPE
			SYNTAX INTEGER
				{
				enable(1),
				disable(2)
				}
			MAX-ACCESS read-only
			STATUS current
			DESCRIPTION
				"Description."
			::= { sleBatteryEntry 21 }

		
--     1.3.6.1.4.1.6296.101.2.7.1.1.22
-- 1.3.6.1.4.1.6296.101.2.7.1.1.22
-- 1.3.6.1.4.1.6296.101.2.7.1.1.22
-- 1.3.6.1.4.1.6296.101.2.7.1.1.22
		-- 1.3.6.1.4.1.6296.101.2.7.1.1.22
		sleRBUBTThreshold OBJECT-TYPE
			SYNTAX Integer32
			MAX-ACCESS read-only
			STATUS current
			DESCRIPTION
				"Description."
			::= { sleBatteryEntry 22 }

		
--     1.3.6.1.4.1.6296.101.2.7.1.1.23
-- 1.3.6.1.4.1.6296.101.2.7.1.1.23
-- 1.3.6.1.4.1.6296.101.2.7.1.1.23
-- 1.3.6.1.4.1.6296.101.2.7.1.1.23
		-- 1.3.6.1.4.1.6296.101.2.7.1.1.23
		sleRBURechargeVoltage OBJECT-TYPE
			SYNTAX Integer32
			MAX-ACCESS read-only
			STATUS current
			DESCRIPTION
				"Description."
			::= { sleBatteryEntry 23 }

		
--     1.3.6.1.4.1.6296.101.2.7.1.1.24
-- 1.3.6.1.4.1.6296.101.2.7.1.1.24
-- 1.3.6.1.4.1.6296.101.2.7.1.1.24
-- 1.3.6.1.4.1.6296.101.2.7.1.1.24
		-- 1.3.6.1.4.1.6296.101.2.7.1.1.24
		sleBatteryCellStatus OBJECT-TYPE
			SYNTAX INTEGER
				{
				ok(1),
				failure(2)
				}
			MAX-ACCESS read-only
			STATUS current
			DESCRIPTION
				"Description."
			::= { sleBatteryEntry 24 }

		
--     1.3.6.1.4.1.6296.101.2.7.1.1.25
-- 1.3.6.1.4.1.6296.101.2.7.1.1.25
-- 1.3.6.1.4.1.6296.101.2.7.1.1.25
-- 1.3.6.1.4.1.6296.101.2.7.1.1.25
		-- 1.3.6.1.4.1.6296.101.2.7.1.1.25
		sleBPSUACHardwareVer OBJECT-TYPE
			SYNTAX Integer32
			MAX-ACCESS read-only
			STATUS current
			DESCRIPTION
				"Description."
			::= { sleBatteryEntry 25 }

		
--     1.3.6.1.4.1.6296.101.2.7.2
-- 1.3.6.1.4.1.6296.101.2.7.2
-- 1.3.6.1.4.1.6296.101.2.7.2
-- 1.3.6.1.4.1.6296.101.2.7.2
		-- 1.3.6.1.4.1.6296.101.2.7.2
		sleBatteryControl OBJECT IDENTIFIER ::= { sleBattery 2 }

		
--     1.3.6.1.4.1.6296.101.2.7.2.1
-- 1.3.6.1.4.1.6296.101.2.7.2.1
-- 1.3.6.1.4.1.6296.101.2.7.2.1
-- 1.3.6.1.4.1.6296.101.2.7.2.1
		-- 1.3.6.1.4.1.6296.101.2.7.2.1
		sleBatteryControlRequest OBJECT-TYPE
			SYNTAX INTEGER
				{
				setBatteryForceCharge(1),
				setBatteryChargingStart(2),
				setBatteryForceChargeNonStop(3),
				setBatteryBootingTimeStatus(4),
				setBatteryBootingTime(5),
				setBatteryRechargeVoltage(6),
				setPsuAcTemperature(7),
				setBatteryTemperature(8)
				}
			MAX-ACCESS read-write
			STATUS current
			DESCRIPTION
				"Description."
			::= { sleBatteryControl 1 }

		
--     1.3.6.1.4.1.6296.101.2.7.2.2
-- 1.3.6.1.4.1.6296.101.2.7.2.2
-- 1.3.6.1.4.1.6296.101.2.7.2.2
-- 1.3.6.1.4.1.6296.101.2.7.2.2
		-- 1.3.6.1.4.1.6296.101.2.7.2.2
		sleBatteryControlStatus OBJECT-TYPE
			SYNTAX Integer32
			MAX-ACCESS read-write
			STATUS current
			DESCRIPTION
				"Description."
			::= { sleBatteryControl 2 }

		
--     1.3.6.1.4.1.6296.101.2.7.2.3
-- 1.3.6.1.4.1.6296.101.2.7.2.3
-- 1.3.6.1.4.1.6296.101.2.7.2.3
-- 1.3.6.1.4.1.6296.101.2.7.2.3
		-- 1.3.6.1.4.1.6296.101.2.7.2.3
		sleBatteryControlTimer OBJECT-TYPE
			SYNTAX Integer32
			MAX-ACCESS read-write
			STATUS current
			DESCRIPTION
				"Description."
			::= { sleBatteryControl 3 }

		
--     1.3.6.1.4.1.6296.101.2.7.2.4
-- 1.3.6.1.4.1.6296.101.2.7.2.4
-- 1.3.6.1.4.1.6296.101.2.7.2.4
-- 1.3.6.1.4.1.6296.101.2.7.2.4
		-- 1.3.6.1.4.1.6296.101.2.7.2.4
		sleBatteryControlTimeStamp OBJECT-TYPE
			SYNTAX Integer32
			MAX-ACCESS read-write
			STATUS current
			DESCRIPTION
				"Description."
			::= { sleBatteryControl 4 }

		
--     1.3.6.1.4.1.6296.101.2.7.2.5
-- 1.3.6.1.4.1.6296.101.2.7.2.5
-- 1.3.6.1.4.1.6296.101.2.7.2.5
-- 1.3.6.1.4.1.6296.101.2.7.2.5
		-- 1.3.6.1.4.1.6296.101.2.7.2.5
		sleBatteryControlReqResult OBJECT-TYPE
			SYNTAX Integer32
			MAX-ACCESS read-write
			STATUS current
			DESCRIPTION
				"Description."
			::= { sleBatteryControl 5 }

		
--     1.3.6.1.4.1.6296.101.2.7.2.6
-- 1.3.6.1.4.1.6296.101.2.7.2.6
-- 1.3.6.1.4.1.6296.101.2.7.2.6
-- 1.3.6.1.4.1.6296.101.2.7.2.6
		-- 1.3.6.1.4.1.6296.101.2.7.2.6
		sleBatteryControlRBUBTStatus OBJECT-TYPE
			SYNTAX INTEGER
				{
				enable(1),
				disable(2)
				}
			MAX-ACCESS read-write
			STATUS current
			DESCRIPTION
				"Description."
			::= { sleBatteryControl 6 }

		
--     1.3.6.1.4.1.6296.101.2.7.2.7
-- 1.3.6.1.4.1.6296.101.2.7.2.7
-- 1.3.6.1.4.1.6296.101.2.7.2.7
-- 1.3.6.1.4.1.6296.101.2.7.2.7
		-- 1.3.6.1.4.1.6296.101.2.7.2.7
		sleBatteryControlRBUBTThreshold OBJECT-TYPE
			SYNTAX Integer32
			MAX-ACCESS read-write
			STATUS current
			DESCRIPTION
				"Description."
			::= { sleBatteryControl 7 }

		
--     1.3.6.1.4.1.6296.101.2.7.2.8
-- 1.3.6.1.4.1.6296.101.2.7.2.8
-- 1.3.6.1.4.1.6296.101.2.7.2.8
-- 1.3.6.1.4.1.6296.101.2.7.2.8
		-- 1.3.6.1.4.1.6296.101.2.7.2.8
		sleBatteryControlRBURechargeVoltage OBJECT-TYPE
			SYNTAX Integer32
			MAX-ACCESS read-write
			STATUS current
			DESCRIPTION
				"Description."
			::= { sleBatteryControl 8 }

		
--     1.3.6.1.4.1.6296.101.2.7.2.9
-- 1.3.6.1.4.1.6296.101.2.7.2.9
-- 1.3.6.1.4.1.6296.101.2.7.2.9
-- 1.3.6.1.4.1.6296.101.2.7.2.9
		-- 1.3.6.1.4.1.6296.101.2.7.2.9
		sleBatteryControlTemperThresh1 OBJECT-TYPE
			SYNTAX Integer32
			MAX-ACCESS read-write
			STATUS current
			DESCRIPTION
				"Description."
			::= { sleBatteryControl 9 }

		
--     1.3.6.1.4.1.6296.101.2.7.2.10
-- 1.3.6.1.4.1.6296.101.2.7.2.10
-- 1.3.6.1.4.1.6296.101.2.7.2.10
-- 1.3.6.1.4.1.6296.101.2.7.2.10
		-- 1.3.6.1.4.1.6296.101.2.7.2.10
		sleBatteryControlTemperThresh2 OBJECT-TYPE
			SYNTAX Integer32
			MAX-ACCESS read-write
			STATUS current
			DESCRIPTION
				"Description."
			::= { sleBatteryControl 10 }

		
--     1.3.6.1.4.1.6296.101.2.7.3
-- 1.3.6.1.4.1.6296.101.2.7.3
-- 1.3.6.1.4.1.6296.101.2.7.3
-- 1.3.6.1.4.1.6296.101.2.7.3
		-- 1.3.6.1.4.1.6296.101.2.7.3
		sleBatteryNotification OBJECT IDENTIFIER ::= { sleBattery 3 }

		
--     1.3.6.1.4.1.6296.101.2.7.3.1
-- 1.3.6.1.4.1.6296.101.2.7.3.1
-- 1.3.6.1.4.1.6296.101.2.7.3.1
-- 1.3.6.1.4.1.6296.101.2.7.3.1
		-- 1.3.6.1.4.1.6296.101.2.7.3.1
		sleBatteryForceChargeChanged NOTIFICATION-TYPE
			OBJECTS { sleBatteryControlRequest, sleBatteryControlTimeStamp, sleBatteryControlReqResult }
			STATUS current
			DESCRIPTION 
				"Description."
			::= { sleBatteryNotification 1 }

		
--     1.3.6.1.4.1.6296.101.2.7.3.2
-- 1.3.6.1.4.1.6296.101.2.7.3.2
-- 1.3.6.1.4.1.6296.101.2.7.3.2
-- 1.3.6.1.4.1.6296.101.2.7.3.2
		-- 1.3.6.1.4.1.6296.101.2.7.3.2
		sleBatteryChargingStartChanged NOTIFICATION-TYPE
			OBJECTS { sleBatteryControlRequest, sleBatteryControlTimeStamp, sleBatteryControlReqResult }
			STATUS current
			DESCRIPTION 
				"Description."
			::= { sleBatteryNotification 2 }

		
--     1.3.6.1.4.1.6296.101.2.7.3.3
-- 1.3.6.1.4.1.6296.101.2.7.3.3
-- 1.3.6.1.4.1.6296.101.2.7.3.3
-- 1.3.6.1.4.1.6296.101.2.7.3.3
		-- 1.3.6.1.4.1.6296.101.2.7.3.3
		sleBatteryForceChargeNonStopChanged NOTIFICATION-TYPE
			OBJECTS { sleBatteryControlRequest, sleBatteryControlTimeStamp, sleBatteryControlReqResult }
			STATUS current
			DESCRIPTION 
				"Description."
			::= { sleBatteryNotification 3 }

		
--     1.3.6.1.4.1.6296.101.2.7.3.4
-- 1.3.6.1.4.1.6296.101.2.7.3.4
-- 1.3.6.1.4.1.6296.101.2.7.3.4
-- 1.3.6.1.4.1.6296.101.2.7.3.4
		-- 1.3.6.1.4.1.6296.101.2.7.3.4
		sleBatteryRBUBTStatusChanged NOTIFICATION-TYPE
			OBJECTS { sleBatteryControlRequest, sleBatteryControlTimeStamp, sleBatteryControlReqResult, sleRBUBTStatus }
			STATUS current
			DESCRIPTION 
				"Description."
			::= { sleBatteryNotification 4 }

		
--     1.3.6.1.4.1.6296.101.2.7.3.5
-- 1.3.6.1.4.1.6296.101.2.7.3.5
-- 1.3.6.1.4.1.6296.101.2.7.3.5
-- 1.3.6.1.4.1.6296.101.2.7.3.5
		-- 1.3.6.1.4.1.6296.101.2.7.3.5
		sleBatteryRBUBTThresholdChanged NOTIFICATION-TYPE
			OBJECTS { sleBatteryControlRequest, sleBatteryControlTimeStamp, sleBatteryControlReqResult, sleRBUBTThreshold }
			STATUS current
			DESCRIPTION 
				"Description."
			::= { sleBatteryNotification 5 }

		
--     1.3.6.1.4.1.6296.101.2.7.3.6
-- 1.3.6.1.4.1.6296.101.2.7.3.6
-- 1.3.6.1.4.1.6296.101.2.7.3.6
-- 1.3.6.1.4.1.6296.101.2.7.3.6
		-- 1.3.6.1.4.1.6296.101.2.7.3.6
		sleBatteryRBURechargeVoltageChanged NOTIFICATION-TYPE
			OBJECTS { sleBatteryControlRequest, sleBatteryControlTimeStamp, sleBatteryControlReqResult, sleRBURechargeVoltage }
			STATUS current
			DESCRIPTION 
				"Description."
			::= { sleBatteryNotification 6 }

		
--     1.3.6.1.4.1.6296.101.2.7.3.7
-- 1.3.6.1.4.1.6296.101.2.7.3.7
-- 1.3.6.1.4.1.6296.101.2.7.3.7
-- 1.3.6.1.4.1.6296.101.2.7.3.7
		-- 1.3.6.1.4.1.6296.101.2.7.3.7
		sleBatteryPsuAcTemperThreshChanged NOTIFICATION-TYPE
			OBJECTS { sleBatteryControlRequest, sleBatteryControlTimeStamp, sleBatteryControlReqResult, slePSUTempThreshold }
			STATUS current
			DESCRIPTION 
				"Description."
			::= { sleBatteryNotification 7 }

		
--     1.3.6.1.4.1.6296.101.2.7.3.8
-- 1.3.6.1.4.1.6296.101.2.7.3.8
-- 1.3.6.1.4.1.6296.101.2.7.3.8
-- 1.3.6.1.4.1.6296.101.2.7.3.8
		-- 1.3.6.1.4.1.6296.101.2.7.3.8
		sleBatteryRBUTemperThreshChanged NOTIFICATION-TYPE
			OBJECTS { sleBatteryControlRequest, sleBatteryControlTimeStamp, sleBatteryControlReqResult, sleRBUTempLowThreshold, sleRBUTempHighThreshold
				 }
			STATUS current
			DESCRIPTION 
				"Description."
			::= { sleBatteryNotification 8 }

		
--     1.3.6.1.4.1.6296.101.2.7.4
-- 1.3.6.1.4.1.6296.101.2.7.4
-- 1.3.6.1.4.1.6296.101.2.7.4
-- 1.3.6.1.4.1.6296.101.2.7.4
		-- 1.3.6.1.4.1.6296.101.2.7.4
		sleBatteryBackupTable OBJECT-TYPE
			SYNTAX SEQUENCE OF SleBatteryBackupEntry
			MAX-ACCESS not-accessible
			STATUS current
			DESCRIPTION
				"Description."
			::= { sleBattery 4 }

		
--     1.3.6.1.4.1.6296.101.2.7.4.1
-- 1.3.6.1.4.1.6296.101.2.7.4.1
-- 1.3.6.1.4.1.6296.101.2.7.4.1
-- 1.3.6.1.4.1.6296.101.2.7.4.1
		-- 1.3.6.1.4.1.6296.101.2.7.4.1
		sleBatteryBackupEntry OBJECT-TYPE
			SYNTAX SleBatteryBackupEntry
			MAX-ACCESS not-accessible
			STATUS current
			DESCRIPTION
				"Description."
			INDEX { sleBatteryBackupFile }
			::= { sleBatteryBackupTable 1 }

		
		SleBatteryBackupEntry ::=
			SEQUENCE { 
				sleBatteryBackupFile
					OCTET STRING
			 }

--     1.3.6.1.4.1.6296.101.2.7.4.1.1
-- 1.3.6.1.4.1.6296.101.2.7.4.1.1
-- 1.3.6.1.4.1.6296.101.2.7.4.1.1
-- 1.3.6.1.4.1.6296.101.2.7.4.1.1
		-- 1.3.6.1.4.1.6296.101.2.7.4.1.1
		sleBatteryBackupFile OBJECT-TYPE
			SYNTAX OCTET STRING (SIZE (1..64))
			MAX-ACCESS read-only
			STATUS current
			DESCRIPTION
				"Description."
			::= { sleBatteryBackupEntry 1 }

		
--     1.3.6.1.4.1.6296.101.2.7.5
-- 1.3.6.1.4.1.6296.101.2.7.5
-- 1.3.6.1.4.1.6296.101.2.7.5
-- 1.3.6.1.4.1.6296.101.2.7.5
		-- 1.3.6.1.4.1.6296.101.2.7.5
		sleBatteryBackupControl OBJECT IDENTIFIER ::= { sleBattery 5 }

		
--     1.3.6.1.4.1.6296.101.2.7.5.1
-- 1.3.6.1.4.1.6296.101.2.7.5.1
-- 1.3.6.1.4.1.6296.101.2.7.5.1
-- 1.3.6.1.4.1.6296.101.2.7.5.1
		-- 1.3.6.1.4.1.6296.101.2.7.5.1
		sleBatteryBackupControlRequest OBJECT-TYPE
			SYNTAX INTEGER
				{
				setBatteryBackupProfile(1),
				setBatteryUpgrade(2),
				clearBatteryBackupTable(3)
				}
			MAX-ACCESS read-write
			STATUS current
			DESCRIPTION
				"Description."
			::= { sleBatteryBackupControl 1 }

		
--     1.3.6.1.4.1.6296.101.2.7.5.2
-- 1.3.6.1.4.1.6296.101.2.7.5.2
-- 1.3.6.1.4.1.6296.101.2.7.5.2
-- 1.3.6.1.4.1.6296.101.2.7.5.2
		-- 1.3.6.1.4.1.6296.101.2.7.5.2
		sleBatteryBackupControlStatus OBJECT-TYPE
			SYNTAX SleControlStatusType
			MAX-ACCESS read-only
			STATUS current
			DESCRIPTION
				"Description."
			::= { sleBatteryBackupControl 2 }

		
--     1.3.6.1.4.1.6296.101.2.7.5.3
-- 1.3.6.1.4.1.6296.101.2.7.5.3
-- 1.3.6.1.4.1.6296.101.2.7.5.3
-- 1.3.6.1.4.1.6296.101.2.7.5.3
		-- 1.3.6.1.4.1.6296.101.2.7.5.3
		sleBatteryBackupControlTimer OBJECT-TYPE
			SYNTAX Gauge32
			MAX-ACCESS read-write
			STATUS current
			DESCRIPTION
				"Description."
			::= { sleBatteryBackupControl 3 }

		
--     1.3.6.1.4.1.6296.101.2.7.5.4
-- 1.3.6.1.4.1.6296.101.2.7.5.4
-- 1.3.6.1.4.1.6296.101.2.7.5.4
-- 1.3.6.1.4.1.6296.101.2.7.5.4
		-- 1.3.6.1.4.1.6296.101.2.7.5.4
		sleBatteryBackupControlTimeStamp OBJECT-TYPE
			SYNTAX TimeTicks
			MAX-ACCESS read-only
			STATUS current
			DESCRIPTION
				"Description."
			::= { sleBatteryBackupControl 4 }

		
--     1.3.6.1.4.1.6296.101.2.7.5.5
-- 1.3.6.1.4.1.6296.101.2.7.5.5
-- 1.3.6.1.4.1.6296.101.2.7.5.5
-- 1.3.6.1.4.1.6296.101.2.7.5.5
		-- 1.3.6.1.4.1.6296.101.2.7.5.5
		sleBatteryBackupControlReqResult OBJECT-TYPE
			SYNTAX SleControlRequestResultType
			MAX-ACCESS read-only
			STATUS current
			DESCRIPTION
				"Description."
			::= { sleBatteryBackupControl 5 }

		
--     1.3.6.1.4.1.6296.101.2.7.5.6
-- 1.3.6.1.4.1.6296.101.2.7.5.6
-- 1.3.6.1.4.1.6296.101.2.7.5.6
-- 1.3.6.1.4.1.6296.101.2.7.5.6
		-- 1.3.6.1.4.1.6296.101.2.7.5.6
		sleBatteryBackupControlServerIP OBJECT-TYPE
			SYNTAX IpAddress
			MAX-ACCESS read-write
			STATUS current
			DESCRIPTION
				"Description."
			::= { sleBatteryBackupControl 6 }

		
--     1.3.6.1.4.1.6296.101.2.7.5.7
-- 1.3.6.1.4.1.6296.101.2.7.5.7
-- 1.3.6.1.4.1.6296.101.2.7.5.7
-- 1.3.6.1.4.1.6296.101.2.7.5.7
		-- 1.3.6.1.4.1.6296.101.2.7.5.7
		sleBatteryBackupControlUserID OBJECT-TYPE
			SYNTAX OCTET STRING (SIZE (1..64))
			MAX-ACCESS read-write
			STATUS current
			DESCRIPTION
				"Description."
			::= { sleBatteryBackupControl 7 }

		
--     1.3.6.1.4.1.6296.101.2.7.5.8
-- 1.3.6.1.4.1.6296.101.2.7.5.8
-- 1.3.6.1.4.1.6296.101.2.7.5.8
-- 1.3.6.1.4.1.6296.101.2.7.5.8
		-- 1.3.6.1.4.1.6296.101.2.7.5.8
		sleBatteryBackupControlPassword OBJECT-TYPE
			SYNTAX OCTET STRING (SIZE (1..64))
			MAX-ACCESS read-write
			STATUS current
			DESCRIPTION
				"Description."
			::= { sleBatteryBackupControl 8 }

		
--     1.3.6.1.4.1.6296.101.2.7.5.9
-- 1.3.6.1.4.1.6296.101.2.7.5.9
-- 1.3.6.1.4.1.6296.101.2.7.5.9
-- 1.3.6.1.4.1.6296.101.2.7.5.9
		-- 1.3.6.1.4.1.6296.101.2.7.5.9
		sleBatteryBackupControlFlag OBJECT-TYPE
			SYNTAX INTEGER
				{
				download(1),
				upload(2)
				}
			MAX-ACCESS read-write
			STATUS current
			DESCRIPTION
				"Description."
			::= { sleBatteryBackupControl 9 }

		
--     1.3.6.1.4.1.6296.101.2.7.5.10
-- 1.3.6.1.4.1.6296.101.2.7.5.10
-- 1.3.6.1.4.1.6296.101.2.7.5.10
-- 1.3.6.1.4.1.6296.101.2.7.5.10
		-- 1.3.6.1.4.1.6296.101.2.7.5.10
		sleBatteryBackupControlLocalFile OBJECT-TYPE
			SYNTAX OCTET STRING (SIZE (1..64))
			MAX-ACCESS read-write
			STATUS current
			DESCRIPTION
				"Description."
			::= { sleBatteryBackupControl 10 }

		
--     1.3.6.1.4.1.6296.101.2.7.5.11
-- 1.3.6.1.4.1.6296.101.2.7.5.11
-- 1.3.6.1.4.1.6296.101.2.7.5.11
-- 1.3.6.1.4.1.6296.101.2.7.5.11
		-- 1.3.6.1.4.1.6296.101.2.7.5.11
		sleBatteryBackupControlRemoteFile OBJECT-TYPE
			SYNTAX OCTET STRING (SIZE (1..64))
			MAX-ACCESS read-write
			STATUS current
			DESCRIPTION
				"Description."
			::= { sleBatteryBackupControl 11 }

		
--     1.3.6.1.4.1.6296.101.2.7.6
-- 1.3.6.1.4.1.6296.101.2.7.6
-- 1.3.6.1.4.1.6296.101.2.7.6
-- 1.3.6.1.4.1.6296.101.2.7.6
		-- 1.3.6.1.4.1.6296.101.2.7.6
		sleBatterBackupNotification OBJECT IDENTIFIER ::= { sleBattery 6 }

		
--     1.3.6.1.4.1.6296.101.2.7.6.1
-- 1.3.6.1.4.1.6296.101.2.7.6.1
-- 1.3.6.1.4.1.6296.101.2.7.6.1
-- 1.3.6.1.4.1.6296.101.2.7.6.1
		-- 1.3.6.1.4.1.6296.101.2.7.6.1
		sleBatteryBackupProfileChanged NOTIFICATION-TYPE
			OBJECTS { sleBatteryBackupControlRequest, sleBatteryBackupControlTimeStamp, sleBatteryBackupControlReqResult, sleBatteryBackupControlServerIP, sleBatteryBackupControlUserID, 
				sleBatteryBackupControlPassword, sleBatteryBackupControlFlag, sleBatteryBackupControlLocalFile, sleBatteryBackupControlRemoteFile }
			STATUS current
			DESCRIPTION 
				"Description."
			::= { sleBatterBackupNotification 1 }

		
--     1.3.6.1.4.1.6296.101.2.7.6.2
-- 1.3.6.1.4.1.6296.101.2.7.6.2
-- 1.3.6.1.4.1.6296.101.2.7.6.2
-- 1.3.6.1.4.1.6296.101.2.7.6.2
		-- 1.3.6.1.4.1.6296.101.2.7.6.2
		sleBatteryBackupUpgraded NOTIFICATION-TYPE
			OBJECTS { sleBatteryBackupControlRequest, sleBatteryBackupControlTimeStamp, sleBatteryBackupControlReqResult, sleBatteryBackupControlLocalFile }
			STATUS current
			DESCRIPTION 
				"Description."
			::= { sleBatterBackupNotification 2 }

		
--     1.3.6.1.4.1.6296.101.2.7.6.3
-- 1.3.6.1.4.1.6296.101.2.7.6.3
-- 1.3.6.1.4.1.6296.101.2.7.6.3
-- 1.3.6.1.4.1.6296.101.2.7.6.3
		-- 1.3.6.1.4.1.6296.101.2.7.6.3
		sleBatteryBackupTableCleared NOTIFICATION-TYPE
			OBJECTS { sleBatteryBackupControlRequest, sleBatteryBackupControlTimeStamp, sleBatteryBackupControlReqResult, sleBatteryBackupControlLocalFile }
			STATUS current
			DESCRIPTION 
				"Description."
			::= { sleBatterBackupNotification 3 }

		
		-- 1.3.6.1.4.1.6296.101.2.8
		sleDoor OBJECT IDENTIFIER ::= { sleDevice 8 }

		
--     1.3.6.1.4.1.6296.101.2.8.1
-- 1.3.6.1.4.1.6296.101.2.8.1
-- 1.3.6.1.4.1.6296.101.2.8.1
-- 1.3.6.1.4.1.6296.101.2.8.1
		-- 1.3.6.1.4.1.6296.101.2.8.1
		sleDoorInfo OBJECT IDENTIFIER ::= { sleDoor 1 }

		
--     1.3.6.1.4.1.6296.101.2.8.1.1
-- 1.3.6.1.4.1.6296.101.2.8.1.1
-- 1.3.6.1.4.1.6296.101.2.8.1.1
-- 1.3.6.1.4.1.6296.101.2.8.1.1
		-- 1.3.6.1.4.1.6296.101.2.8.1.1
		sleDoorStatus OBJECT-TYPE
			SYNTAX INTEGER
				{
				close(0),
				open(1)
				}
			MAX-ACCESS read-only
			STATUS current
			DESCRIPTION
				"Description."
			::= { sleDoorInfo 1 }

		
		-- 1.3.6.1.4.1.6296.101.2.9
		sleCpu OBJECT IDENTIFIER ::= { sleDevice 9 }

		
--     1.3.6.1.4.1.6296.101.2.9.1
-- 1.3.6.1.4.1.6296.101.2.9.1
-- 1.3.6.1.4.1.6296.101.2.9.1
-- 1.3.6.1.4.1.6296.101.2.9.1
		-- 1.3.6.1.4.1.6296.101.2.9.1
		sleCpuInfo OBJECT IDENTIFIER ::= { sleCpu 1 }

		
--     1.3.6.1.4.1.6296.101.2.9.1.1
-- 1.3.6.1.4.1.6296.101.2.9.1.1
-- 1.3.6.1.4.1.6296.101.2.9.1.1
-- 1.3.6.1.4.1.6296.101.2.9.1.1
		-- 1.3.6.1.4.1.6296.101.2.9.1.1
		sleCpuProcessor OBJECT-TYPE
			SYNTAX OCTET STRING
			MAX-ACCESS read-only
			STATUS current
			DESCRIPTION
				"Description."
			::= { sleCpuInfo 1 }

		
--     1.3.6.1.4.1.6296.101.2.9.1.2
-- 1.3.6.1.4.1.6296.101.2.9.1.2
-- 1.3.6.1.4.1.6296.101.2.9.1.2
-- 1.3.6.1.4.1.6296.101.2.9.1.2
		-- 1.3.6.1.4.1.6296.101.2.9.1.2
		sleCpuModel OBJECT-TYPE
			SYNTAX OCTET STRING
			MAX-ACCESS read-only
			STATUS current
			DESCRIPTION
				"Description."
			::= { sleCpuInfo 2 }

		
--     1.3.6.1.4.1.6296.101.2.9.1.3
-- 1.3.6.1.4.1.6296.101.2.9.1.3
-- 1.3.6.1.4.1.6296.101.2.9.1.3
-- 1.3.6.1.4.1.6296.101.2.9.1.3
		-- 1.3.6.1.4.1.6296.101.2.9.1.3
		sleCpuRevision OBJECT-TYPE
			SYNTAX OCTET STRING
			MAX-ACCESS read-only
			STATUS current
			DESCRIPTION
				"Description."
			::= { sleCpuInfo 3 }

		
--     1.3.6.1.4.1.6296.101.2.9.1.4
-- 1.3.6.1.4.1.6296.101.2.9.1.4
-- 1.3.6.1.4.1.6296.101.2.9.1.4
-- 1.3.6.1.4.1.6296.101.2.9.1.4
		-- 1.3.6.1.4.1.6296.101.2.9.1.4
		sleCpuBogomips OBJECT-TYPE
			SYNTAX OCTET STRING
			MAX-ACCESS read-only
			STATUS current
			DESCRIPTION
				"Description."
			::= { sleCpuInfo 4 }

		
--     1.3.6.1.4.1.6296.101.2.9.1.5
-- 1.3.6.1.4.1.6296.101.2.9.1.5
-- 1.3.6.1.4.1.6296.101.2.9.1.5
-- 1.3.6.1.4.1.6296.101.2.9.1.5
		-- 1.3.6.1.4.1.6296.101.2.9.1.5
		sleCpuManufacturer OBJECT-TYPE
			SYNTAX OCTET STRING
			MAX-ACCESS read-only
			STATUS current
			DESCRIPTION
				"Description."
			::= { sleCpuInfo 5 }

		
--     1.3.6.1.4.1.6296.101.2.9.1.6
-- 1.3.6.1.4.1.6296.101.2.9.1.6
-- 1.3.6.1.4.1.6296.101.2.9.1.6
-- 1.3.6.1.4.1.6296.101.2.9.1.6
		-- 1.3.6.1.4.1.6296.101.2.9.1.6
		sleCpuClock OBJECT-TYPE
			SYNTAX Integer32
			MAX-ACCESS read-only
			STATUS current
			DESCRIPTION
				"Description."
			::= { sleCpuInfo 6 }

		
--     1.3.6.1.4.1.6296.101.2.9.1.7
-- 1.3.6.1.4.1.6296.101.2.9.1.7
-- 1.3.6.1.4.1.6296.101.2.9.1.7
-- 1.3.6.1.4.1.6296.101.2.9.1.7
		-- 1.3.6.1.4.1.6296.101.2.9.1.7
		sleCpuBusClock OBJECT-TYPE
			SYNTAX Integer32
			MAX-ACCESS read-only
			STATUS current
			DESCRIPTION
				"Description."
			::= { sleCpuInfo 7 }

		
		-- 1.3.6.1.4.1.6296.101.2.10
		sleClockModule OBJECT IDENTIFIER ::= { sleDevice 10 }

		
--     1.3.6.1.4.1.6296.101.2.10.1
-- 1.3.6.1.4.1.6296.101.2.10.1
-- 1.3.6.1.4.1.6296.101.2.10.1
-- 1.3.6.1.4.1.6296.101.2.10.1
		-- 1.3.6.1.4.1.6296.101.2.10.1
		sleClockModuleTable OBJECT-TYPE
			SYNTAX SEQUENCE OF SleClockModuleEntry
			MAX-ACCESS not-accessible
			STATUS current
			DESCRIPTION
				"Description."
			::= { sleClockModule 1 }

		
--     1.3.6.1.4.1.6296.101.2.10.1.1
-- 1.3.6.1.4.1.6296.101.2.10.1.1
-- 1.3.6.1.4.1.6296.101.2.10.1.1
-- 1.3.6.1.4.1.6296.101.2.10.1.1
		-- 1.3.6.1.4.1.6296.101.2.10.1.1
		sleClockModuleEntry OBJECT-TYPE
			SYNTAX SleClockModuleEntry
			MAX-ACCESS not-accessible
			STATUS current
			DESCRIPTION
				"Description."
			INDEX { sleClockModuleIndex }
			::= { sleClockModuleTable 1 }

		
		SleClockModuleEntry ::=
			SEQUENCE { 
				sleClockModuleIndex
					INTEGER,
				sleClockModuleBoardId
					INTEGER,
				sleClockModuleInstallStatus
					INTEGER,
				sleClockModuleInitStatus
					INTEGER,
				sleClockModuleOPMode
					INTEGER
			 }

--     1.3.6.1.4.1.6296.101.2.10.1.1.1
-- 1.3.6.1.4.1.6296.101.2.10.1.1.1
-- 1.3.6.1.4.1.6296.101.2.10.1.1.1
-- 1.3.6.1.4.1.6296.101.2.10.1.1.1
		-- 1.3.6.1.4.1.6296.101.2.10.1.1.1
		sleClockModuleIndex OBJECT-TYPE
			SYNTAX INTEGER (1..255)
			MAX-ACCESS read-only
			STATUS current
			DESCRIPTION
				"A unique value, greater than zero, for each module. It is recommended that values are assigned contiguously starting from 1."
			::= { sleClockModuleEntry 1 }

		
--     1.3.6.1.4.1.6296.101.2.10.1.1.2
-- 1.3.6.1.4.1.6296.101.2.10.1.1.2
-- 1.3.6.1.4.1.6296.101.2.10.1.1.2
-- 1.3.6.1.4.1.6296.101.2.10.1.1.2
		-- 1.3.6.1.4.1.6296.101.2.10.1.1.2
		sleClockModuleBoardId OBJECT-TYPE
			SYNTAX INTEGER
				{
				sfuA(1),
				sfuB(2)
				}
			MAX-ACCESS read-only
			STATUS current
			DESCRIPTION
				"Indication of the board identifier."
			::= { sleClockModuleEntry 2 }

		
--     1.3.6.1.4.1.6296.101.2.10.1.1.3
-- 1.3.6.1.4.1.6296.101.2.10.1.1.3
-- 1.3.6.1.4.1.6296.101.2.10.1.1.3
-- 1.3.6.1.4.1.6296.101.2.10.1.1.3
		-- 1.3.6.1.4.1.6296.101.2.10.1.1.3
		sleClockModuleInstallStatus OBJECT-TYPE
			SYNTAX INTEGER
				{
				removed(0),
				installed(1)
				}
			MAX-ACCESS read-only
			STATUS current
			DESCRIPTION
				"The install status of clock module."
			::= { sleClockModuleEntry 3 }

		
--     1.3.6.1.4.1.6296.101.2.10.1.1.4
-- 1.3.6.1.4.1.6296.101.2.10.1.1.4
-- 1.3.6.1.4.1.6296.101.2.10.1.1.4
-- 1.3.6.1.4.1.6296.101.2.10.1.1.4
		-- 1.3.6.1.4.1.6296.101.2.10.1.1.4
		sleClockModuleInitStatus OBJECT-TYPE
			SYNTAX INTEGER
				{
				failure(0),
				ok(1)
				}
			MAX-ACCESS read-only
			STATUS current
			DESCRIPTION
				"The initialization status of clock module."
			::= { sleClockModuleEntry 4 }

		
--     1.3.6.1.4.1.6296.101.2.10.1.1.5
-- 1.3.6.1.4.1.6296.101.2.10.1.1.5
-- 1.3.6.1.4.1.6296.101.2.10.1.1.5
-- 1.3.6.1.4.1.6296.101.2.10.1.1.5
		-- 1.3.6.1.4.1.6296.101.2.10.1.1.5
		sleClockModuleOPMode OBJECT-TYPE
			SYNTAX INTEGER
				{
				freerun(1),
				holdover(2),
				locked(3),
				prelocked2(4),
				prelocked(5),
				lostphase(6),
				unknown(255)
				}
			MAX-ACCESS read-write
			STATUS current
			DESCRIPTION
				"The CM operating mode"
			::= { sleClockModuleEntry 5 }

		
--     1.3.6.1.4.1.6296.101.2.10.2
-- 1.3.6.1.4.1.6296.101.2.10.2
-- 1.3.6.1.4.1.6296.101.2.10.2
-- 1.3.6.1.4.1.6296.101.2.10.2
		-- 1.3.6.1.4.1.6296.101.2.10.2
		sleClockInfo OBJECT IDENTIFIER ::= { sleClockModule 2 }

		
--     1.3.6.1.4.1.6296.101.2.10.2.1
-- 1.3.6.1.4.1.6296.101.2.10.2.1
-- 1.3.6.1.4.1.6296.101.2.10.2.1
-- 1.3.6.1.4.1.6296.101.2.10.2.1
		-- 1.3.6.1.4.1.6296.101.2.10.2.1
		sleClockInfoInSrcType OBJECT-TYPE
			SYNTAX INTEGER
				{
				ntt(1),
				ntt2(2),
				e1(3),
				t1(4),
				unknown(255)
				}
			MAX-ACCESS accessible-for-notify
			STATUS current
			DESCRIPTION
				"The clock input source type."
			::= { sleClockInfo 1 }

		
--     1.3.6.1.4.1.6296.101.2.10.2.2
-- 1.3.6.1.4.1.6296.101.2.10.2.2
-- 1.3.6.1.4.1.6296.101.2.10.2.2
-- 1.3.6.1.4.1.6296.101.2.10.2.2
		-- 1.3.6.1.4.1.6296.101.2.10.2.2
		sleClockInfoInSrcStatus OBJECT-TYPE
			SYNTAX INTEGER
				{
				true(1),
				false(2)
				}
			MAX-ACCESS accessible-for-notify
			STATUS current
			DESCRIPTION
				"The input source is Valid or Invalid."
			::= { sleClockInfo 2 }

		
--     1.3.6.1.4.1.6296.101.2.10.2.3
-- 1.3.6.1.4.1.6296.101.2.10.2.3
-- 1.3.6.1.4.1.6296.101.2.10.2.3
-- 1.3.6.1.4.1.6296.101.2.10.2.3
		-- 1.3.6.1.4.1.6296.101.2.10.2.3
		sleClockInfoInSrcAISStatus OBJECT-TYPE
			SYNTAX INTEGER
				{
				true(1),
				false(2)
				}
			MAX-ACCESS accessible-for-notify
			STATUS current
			DESCRIPTION
				"The AIS is detected or not detected."
			::= { sleClockInfo 3 }

		
--     1.3.6.1.4.1.6296.101.2.10.2.4
-- 1.3.6.1.4.1.6296.101.2.10.2.4
-- 1.3.6.1.4.1.6296.101.2.10.2.4
-- 1.3.6.1.4.1.6296.101.2.10.2.4
		-- 1.3.6.1.4.1.6296.101.2.10.2.4
		sleClockInfoInSrcLoSStatus OBJECT-TYPE
			SYNTAX INTEGER
				{
				true(1),
				false(2)
				}
			MAX-ACCESS accessible-for-notify
			STATUS current
			DESCRIPTION
				"The LoS is detected or not detected"
			::= { sleClockInfo 4 }

		
--     1.3.6.1.4.1.6296.101.2.10.2.5
-- 1.3.6.1.4.1.6296.101.2.10.2.5
-- 1.3.6.1.4.1.6296.101.2.10.2.5
-- 1.3.6.1.4.1.6296.101.2.10.2.5
		-- 1.3.6.1.4.1.6296.101.2.10.2.5
		sleClockInfoInSrcLDSCStatus OBJECT-TYPE
			SYNTAX INTEGER
				{
				true(1),
				false(2)
				}
			MAX-ACCESS accessible-for-notify
			STATUS current
			DESCRIPTION
				"The Line Driver Short Circuit is detected or not detected"
			::= { sleClockInfo 5 }

		
--     1.3.6.1.4.1.6296.101.2.10.2.6
-- 1.3.6.1.4.1.6296.101.2.10.2.6
-- 1.3.6.1.4.1.6296.101.2.10.2.6
-- 1.3.6.1.4.1.6296.101.2.10.2.6
		-- 1.3.6.1.4.1.6296.101.2.10.2.6
		sleClockInfoInSrcNtrClockType OBJECT-TYPE
			SYNTAX BITS
				{
				bit64Khz(0),
				bit8Khz(1),
				bit04Khz(2)
				}
			MAX-ACCESS accessible-for-notify
			STATUS current
			DESCRIPTION
				"The ntr clock is changed."
			::= { sleClockInfo 6 }

		
		-- 1.3.6.1.4.1.6296.101.2.11
		sleSlot OBJECT IDENTIFIER ::= { sleDevice 11 }

		
		-- 1.3.6.1.4.1.6296.101.2.11.1
		sleSlotSystemInfo OBJECT IDENTIFIER ::= { sleSlot 1 }

		
--     1.3.6.1.4.1.6296.101.2.11.1.1
-- 1.3.6.1.4.1.6296.101.2.11.1.1
-- 1.3.6.1.4.1.6296.101.2.11.1.1
-- 1.3.6.1.4.1.6296.101.2.11.1.1
		-- 1.3.6.1.4.1.6296.101.2.11.1.1
		sleSlotSystemInfoTable OBJECT-TYPE
			SYNTAX SEQUENCE OF SleSlotSystemInfoEntry
			MAX-ACCESS not-accessible
			STATUS current
			DESCRIPTION
				"Description."
			::= { sleSlotSystemInfo 1 }

		
--     1.3.6.1.4.1.6296.101.2.11.1.1.1
-- 1.3.6.1.4.1.6296.101.2.11.1.1.1
-- 1.3.6.1.4.1.6296.101.2.11.1.1.1
-- 1.3.6.1.4.1.6296.101.2.11.1.1.1
		-- 1.3.6.1.4.1.6296.101.2.11.1.1.1
		sleSlotSystemInfoEntry OBJECT-TYPE
			SYNTAX SleSlotSystemInfoEntry
			MAX-ACCESS not-accessible
			STATUS current
			DESCRIPTION
				"Description."
			INDEX { sleSlotSystemIndex }
			::= { sleSlotSystemInfoTable 1 }

		
		SleSlotSystemInfoEntry ::=
			SEQUENCE { 
				sleSlotSystemIndex
					Integer32,
				sleSlotSystemUptime
					TimeTicks,
				sleSlotSystemModelName
					OCTET STRING,
				sleSlotSystemSerialNumber
					OCTET STRING,
				sleSlotSystemHWVersion
					OCTET STRING,
				sleSlotSystemBLVersion
					OCTET STRING,
				sleSlotSystemSWCompatibility
					OCTET STRING,
				sleSlotSystemOSVersion
					OCTET STRING,
				sleSlotSystemMacAddress
					OCTET STRING,
				sleSlotSystemCPULoadAll
					OCTET STRING,
				sleSlotSystemCPULoadInterrupt
					OCTET STRING,
				sleSlotSystemMemoryTotal
					Gauge32,
				sleSlotSystemMemoryFree
					Gauge32,
				sleSlotSystemMemoryShared
					Gauge32,
				sleSlotSystemMemoryBuffers
					Gauge32,
				sleSlotSystemMemoryCached
					Gauge32,
				sleSlotSystemMemorySwapTotal
					Gauge32,
				sleSlotSystemMemorySwapFree
					Gauge32,
				sleSlotSystemBootReason
					INTEGER,
				sleSlotSystemBootTime
					Gauge32,
				sleSlotSystemVoltage
					Gauge32,
				sleSlotSystemPowerLevelStatus
					INTEGER,
				sleSlotSystemInfoLEDStatus
					BITS,
				sleSlotSystemInfoPackageVersion
					OCTET STRING,
				sleSlotSystemInfoManufacturer
					OCTET STRING,
				sleSlotSystemInfoManufactureDate
					OCTET STRING
			 }

--     1.3.6.1.4.1.6296.101.2.11.1.1.1.1
-- 1.3.6.1.4.1.6296.101.2.11.1.1.1.1
-- 1.3.6.1.4.1.6296.101.2.11.1.1.1.1
-- 1.3.6.1.4.1.6296.101.2.11.1.1.1.1
		-- 1.3.6.1.4.1.6296.101.2.11.1.1.1.1
		sleSlotSystemIndex OBJECT-TYPE
			SYNTAX Integer32 (1..8)
			MAX-ACCESS read-only
			STATUS current
			DESCRIPTION
				"The system slot index."
			::= { sleSlotSystemInfoEntry 1 }

		
--     1.3.6.1.4.1.6296.101.2.11.1.1.1.2
-- 1.3.6.1.4.1.6296.101.2.11.1.1.1.2
-- 1.3.6.1.4.1.6296.101.2.11.1.1.1.2
-- 1.3.6.1.4.1.6296.101.2.11.1.1.1.2
		-- 1.3.6.1.4.1.6296.101.2.11.1.1.1.2
		sleSlotSystemUptime OBJECT-TYPE
			SYNTAX TimeTicks
			MAX-ACCESS read-only
			STATUS current
			DESCRIPTION
				"The time since the network management portion of the system was last re-initialized."
			::= { sleSlotSystemInfoEntry 2 }

		
--     1.3.6.1.4.1.6296.101.2.11.1.1.1.3
-- 1.3.6.1.4.1.6296.101.2.11.1.1.1.3
-- 1.3.6.1.4.1.6296.101.2.11.1.1.1.3
-- 1.3.6.1.4.1.6296.101.2.11.1.1.1.3
		-- 1.3.6.1.4.1.6296.101.2.11.1.1.1.3
		sleSlotSystemModelName OBJECT-TYPE
			SYNTAX OCTET STRING
			MAX-ACCESS read-only
			STATUS current
			DESCRIPTION
				"The model name."
			::= { sleSlotSystemInfoEntry 3 }

		
--     1.3.6.1.4.1.6296.101.2.11.1.1.1.4
-- 1.3.6.1.4.1.6296.101.2.11.1.1.1.4
-- 1.3.6.1.4.1.6296.101.2.11.1.1.1.4
-- 1.3.6.1.4.1.6296.101.2.11.1.1.1.4
		-- 1.3.6.1.4.1.6296.101.2.11.1.1.1.4
		sleSlotSystemSerialNumber OBJECT-TYPE
			SYNTAX OCTET STRING
			MAX-ACCESS read-only
			STATUS current
			DESCRIPTION
				"The serial number "
			::= { sleSlotSystemInfoEntry 4 }

		
--     1.3.6.1.4.1.6296.101.2.11.1.1.1.5
-- 1.3.6.1.4.1.6296.101.2.11.1.1.1.5
-- 1.3.6.1.4.1.6296.101.2.11.1.1.1.5
-- 1.3.6.1.4.1.6296.101.2.11.1.1.1.5
		-- 1.3.6.1.4.1.6296.101.2.11.1.1.1.5
		sleSlotSystemHWVersion OBJECT-TYPE
			SYNTAX OCTET STRING
			MAX-ACCESS read-only
			STATUS current
			DESCRIPTION
				"The H/W version."
			::= { sleSlotSystemInfoEntry 5 }

		
--     1.3.6.1.4.1.6296.101.2.11.1.1.1.6
-- 1.3.6.1.4.1.6296.101.2.11.1.1.1.6
-- 1.3.6.1.4.1.6296.101.2.11.1.1.1.6
-- 1.3.6.1.4.1.6296.101.2.11.1.1.1.6
		-- 1.3.6.1.4.1.6296.101.2.11.1.1.1.6
		sleSlotSystemBLVersion OBJECT-TYPE
			SYNTAX OCTET STRING
			MAX-ACCESS read-only
			STATUS current
			DESCRIPTION
				"The boot loader�¯s S/W version."
			::= { sleSlotSystemInfoEntry 6 }

		
--     1.3.6.1.4.1.6296.101.2.11.1.1.1.7
-- 1.3.6.1.4.1.6296.101.2.11.1.1.1.7
-- 1.3.6.1.4.1.6296.101.2.11.1.1.1.7
-- 1.3.6.1.4.1.6296.101.2.11.1.1.1.7
		-- 1.3.6.1.4.1.6296.101.2.11.1.1.1.7
		sleSlotSystemSWCompatibility OBJECT-TYPE
			SYNTAX OCTET STRING
			MAX-ACCESS read-only
			STATUS current
			DESCRIPTION
				"The system compatibility."
			::= { sleSlotSystemInfoEntry 7 }

		
--     1.3.6.1.4.1.6296.101.2.11.1.1.1.8
-- 1.3.6.1.4.1.6296.101.2.11.1.1.1.8
-- 1.3.6.1.4.1.6296.101.2.11.1.1.1.8
-- 1.3.6.1.4.1.6296.101.2.11.1.1.1.8
		-- 1.3.6.1.4.1.6296.101.2.11.1.1.1.8
		sleSlotSystemOSVersion OBJECT-TYPE
			SYNTAX OCTET STRING
			MAX-ACCESS read-only
			STATUS current
			DESCRIPTION
				"The version information of current os."
			::= { sleSlotSystemInfoEntry 8 }

		
--     1.3.6.1.4.1.6296.101.2.11.1.1.1.9
-- 1.3.6.1.4.1.6296.101.2.11.1.1.1.9
-- 1.3.6.1.4.1.6296.101.2.11.1.1.1.9
-- 1.3.6.1.4.1.6296.101.2.11.1.1.1.9
		-- 1.3.6.1.4.1.6296.101.2.11.1.1.1.9
		sleSlotSystemMacAddress OBJECT-TYPE
			SYNTAX OCTET STRING
			MAX-ACCESS read-only
			STATUS current
			DESCRIPTION
				"The system�¯s MAC address."
			::= { sleSlotSystemInfoEntry 9 }

		
--     1.3.6.1.4.1.6296.101.2.11.1.1.1.10
-- 1.3.6.1.4.1.6296.101.2.11.1.1.1.10
-- 1.3.6.1.4.1.6296.101.2.11.1.1.1.10
-- 1.3.6.1.4.1.6296.101.2.11.1.1.1.10
		-- 1.3.6.1.4.1.6296.101.2.11.1.1.1.10
		sleSlotSystemCPULoadAll OBJECT-TYPE
			SYNTAX OCTET STRING
			MAX-ACCESS read-only
			STATUS current
			DESCRIPTION
				"The CPU all load for 5/60/600 second. (unit: 0.01%)"
			::= { sleSlotSystemInfoEntry 10 }

		
--     1.3.6.1.4.1.6296.101.2.11.1.1.1.11
-- 1.3.6.1.4.1.6296.101.2.11.1.1.1.11
-- 1.3.6.1.4.1.6296.101.2.11.1.1.1.11
-- 1.3.6.1.4.1.6296.101.2.11.1.1.1.11
		-- 1.3.6.1.4.1.6296.101.2.11.1.1.1.11
		sleSlotSystemCPULoadInterrupt OBJECT-TYPE
			SYNTAX OCTET STRING
			MAX-ACCESS read-only
			STATUS current
			DESCRIPTION
				"The CPU interrupt load for 5/60/600 second. (unit: 0.01%)"
			::= { sleSlotSystemInfoEntry 11 }

		
--     1.3.6.1.4.1.6296.101.2.11.1.1.1.12
-- 1.3.6.1.4.1.6296.101.2.11.1.1.1.12
-- 1.3.6.1.4.1.6296.101.2.11.1.1.1.12
-- 1.3.6.1.4.1.6296.101.2.11.1.1.1.12
		-- 1.3.6.1.4.1.6296.101.2.11.1.1.1.12
		sleSlotSystemMemoryTotal OBJECT-TYPE
			SYNTAX Gauge32
			MAX-ACCESS read-only
			STATUS current
			DESCRIPTION
				"The total memory size (unit: kb)"
			::= { sleSlotSystemInfoEntry 12 }

		
--     1.3.6.1.4.1.6296.101.2.11.1.1.1.13
-- 1.3.6.1.4.1.6296.101.2.11.1.1.1.13
-- 1.3.6.1.4.1.6296.101.2.11.1.1.1.13
-- 1.3.6.1.4.1.6296.101.2.11.1.1.1.13
		-- 1.3.6.1.4.1.6296.101.2.11.1.1.1.13
		sleSlotSystemMemoryFree OBJECT-TYPE
			SYNTAX Gauge32
			MAX-ACCESS read-only
			STATUS current
			DESCRIPTION
				"The freed memory size (unit: kb)"
			::= { sleSlotSystemInfoEntry 13 }

		
--     1.3.6.1.4.1.6296.101.2.11.1.1.1.14
-- 1.3.6.1.4.1.6296.101.2.11.1.1.1.14
-- 1.3.6.1.4.1.6296.101.2.11.1.1.1.14
-- 1.3.6.1.4.1.6296.101.2.11.1.1.1.14
		-- 1.3.6.1.4.1.6296.101.2.11.1.1.1.14
		sleSlotSystemMemoryShared OBJECT-TYPE
			SYNTAX Gauge32
			MAX-ACCESS read-only
			STATUS current
			DESCRIPTION
				"The shared memory size (unit: kb)"
			::= { sleSlotSystemInfoEntry 14 }

		
--     1.3.6.1.4.1.6296.101.2.11.1.1.1.15
-- 1.3.6.1.4.1.6296.101.2.11.1.1.1.15
-- 1.3.6.1.4.1.6296.101.2.11.1.1.1.15
-- 1.3.6.1.4.1.6296.101.2.11.1.1.1.15
		-- 1.3.6.1.4.1.6296.101.2.11.1.1.1.15
		sleSlotSystemMemoryBuffers OBJECT-TYPE
			SYNTAX Gauge32
			MAX-ACCESS read-only
			STATUS current
			DESCRIPTION
				"The buffer size (unit: kb)"
			::= { sleSlotSystemInfoEntry 15 }

		
--     1.3.6.1.4.1.6296.101.2.11.1.1.1.16
-- 1.3.6.1.4.1.6296.101.2.11.1.1.1.16
-- 1.3.6.1.4.1.6296.101.2.11.1.1.1.16
-- 1.3.6.1.4.1.6296.101.2.11.1.1.1.16
		-- 1.3.6.1.4.1.6296.101.2.11.1.1.1.16
		sleSlotSystemMemoryCached OBJECT-TYPE
			SYNTAX Gauge32
			MAX-ACCESS read-only
			STATUS current
			DESCRIPTION
				"The cached memory size (unit: kb)"
			::= { sleSlotSystemInfoEntry 16 }

		
--     1.3.6.1.4.1.6296.101.2.11.1.1.1.17
-- 1.3.6.1.4.1.6296.101.2.11.1.1.1.17
-- 1.3.6.1.4.1.6296.101.2.11.1.1.1.17
-- 1.3.6.1.4.1.6296.101.2.11.1.1.1.17
		-- 1.3.6.1.4.1.6296.101.2.11.1.1.1.17
		sleSlotSystemMemorySwapTotal OBJECT-TYPE
			SYNTAX Gauge32
			MAX-ACCESS read-only
			STATUS current
			DESCRIPTION
				"The total swap memory size (unit: kb)"
			::= { sleSlotSystemInfoEntry 17 }

		
--     1.3.6.1.4.1.6296.101.2.11.1.1.1.18
-- 1.3.6.1.4.1.6296.101.2.11.1.1.1.18
-- 1.3.6.1.4.1.6296.101.2.11.1.1.1.18
-- 1.3.6.1.4.1.6296.101.2.11.1.1.1.18
		-- 1.3.6.1.4.1.6296.101.2.11.1.1.1.18
		sleSlotSystemMemorySwapFree OBJECT-TYPE
			SYNTAX Gauge32
			MAX-ACCESS read-only
			STATUS current
			DESCRIPTION
				"The freed swap memory size (unit: kb)"
			::= { sleSlotSystemInfoEntry 18 }

		
--     1.3.6.1.4.1.6296.101.2.11.1.1.1.19
-- 1.3.6.1.4.1.6296.101.2.11.1.1.1.19
-- 1.3.6.1.4.1.6296.101.2.11.1.1.1.19
-- 1.3.6.1.4.1.6296.101.2.11.1.1.1.19
		-- 1.3.6.1.4.1.6296.101.2.11.1.1.1.19
		sleSlotSystemBootReason OBJECT-TYPE
			SYNTAX INTEGER
				{
				powerBoot(1),
				powerBootByLocal(2),
				hwResetBySW(3),
				hardWdogByLocal(4),
				hwRebootByMate(5),
				hwRebootBySwitchover(6),
				swReboot(10),
				swRebootByLocal(11),
				swRebootBySFU(12),
				swRebootBySwitchover(13),
				swRebootByPanic(14),
				watchdog(20),
				watchdogByLocal(21),
				swWatchdog(30),
				swWatchdogByCpuOver(31),
				swWatchdogByMemoryLow(32),
				error(255)
				}
			MAX-ACCESS read-only
			STATUS current
			DESCRIPTION
				"The system slot boot reason."
			::= { sleSlotSystemInfoEntry 19 }

		
--     1.3.6.1.4.1.6296.101.2.11.1.1.1.20
-- 1.3.6.1.4.1.6296.101.2.11.1.1.1.20
-- 1.3.6.1.4.1.6296.101.2.11.1.1.1.20
-- 1.3.6.1.4.1.6296.101.2.11.1.1.1.20
		-- 1.3.6.1.4.1.6296.101.2.11.1.1.1.20
		sleSlotSystemBootTime OBJECT-TYPE
			SYNTAX Gauge32
			UNITS "1 second"
			MAX-ACCESS read-only
			STATUS current
			DESCRIPTION
				"The system slot boot time.
				The time since the Epoch (00:00:00 UTC, January 1, 1970), measured in seconds.
				"
			::= { sleSlotSystemInfoEntry 20 }

		
--     1.3.6.1.4.1.6296.101.2.11.1.1.1.21
-- 1.3.6.1.4.1.6296.101.2.11.1.1.1.21
-- 1.3.6.1.4.1.6296.101.2.11.1.1.1.21
-- 1.3.6.1.4.1.6296.101.2.11.1.1.1.21
		-- 1.3.6.1.4.1.6296.101.2.11.1.1.1.21
		sleSlotSystemVoltage OBJECT-TYPE
			SYNTAX Gauge32
			UNITS "0.1 v"
			MAX-ACCESS read-only
			STATUS current
			DESCRIPTION
				"The system slot voltage."
			::= { sleSlotSystemInfoEntry 21 }

		
--     1.3.6.1.4.1.6296.101.2.11.1.1.1.22
-- 1.3.6.1.4.1.6296.101.2.11.1.1.1.22
-- 1.3.6.1.4.1.6296.101.2.11.1.1.1.22
-- 1.3.6.1.4.1.6296.101.2.11.1.1.1.22
		-- 1.3.6.1.4.1.6296.101.2.11.1.1.1.22
		sleSlotSystemPowerLevelStatus OBJECT-TYPE
			SYNTAX INTEGER
				{
				good(1),
				bad(2)
				}
			MAX-ACCESS read-only
			STATUS current
			DESCRIPTION
				"PCB Power level status."
			::= { sleSlotSystemInfoEntry 22 }

		
--     1.3.6.1.4.1.6296.101.2.11.1.1.1.23
-- 1.3.6.1.4.1.6296.101.2.11.1.1.1.23
-- 1.3.6.1.4.1.6296.101.2.11.1.1.1.23
-- 1.3.6.1.4.1.6296.101.2.11.1.1.1.23
		-- 1.3.6.1.4.1.6296.101.2.11.1.1.1.23
		sleSlotSystemInfoLEDStatus OBJECT-TYPE
			SYNTAX BITS
				{
				pwr(0),
				run(1),
				critical(2),
				major(3),
				minor(4),
				error(5)
				}
			MAX-ACCESS read-only
			STATUS current
			DESCRIPTION
				"The LED status of each slot."
			::= { sleSlotSystemInfoEntry 23 }

		
--     1.3.6.1.4.1.6296.101.2.11.1.1.1.24
-- 1.3.6.1.4.1.6296.101.2.11.1.1.1.24
-- 1.3.6.1.4.1.6296.101.2.11.1.1.1.24
-- 1.3.6.1.4.1.6296.101.2.11.1.1.1.24
		-- 1.3.6.1.4.1.6296.101.2.11.1.1.1.24
		sleSlotSystemInfoPackageVersion OBJECT-TYPE
			SYNTAX OCTET STRING
			MAX-ACCESS read-only
			STATUS current
			DESCRIPTION
				"The applied package revision."
			::= { sleSlotSystemInfoEntry 24 }

		
		-- 1.3.6.1.4.1.6296.101.2.11.1.1.1.25
		sleSlotSystemInfoManufacturer OBJECT-TYPE
			SYNTAX OCTET STRING
			MAX-ACCESS read-only
			STATUS current
			DESCRIPTION
				"Ths manufacturer name and country."
			::= { sleSlotSystemInfoEntry 25 }

		
		-- 1.3.6.1.4.1.6296.101.2.11.1.1.1.26
		sleSlotSystemInfoManufactureDate OBJECT-TYPE
			SYNTAX OCTET STRING
			MAX-ACCESS read-only
			STATUS current
			DESCRIPTION
				"Ths manufacture date."
			::= { sleSlotSystemInfoEntry 26 }

		
--     1.3.6.1.4.1.6296.101.2.11.1.2
-- 1.3.6.1.4.1.6296.101.2.11.1.2
-- 1.3.6.1.4.1.6296.101.2.11.1.2
-- 1.3.6.1.4.1.6296.101.2.11.1.2
		-- 1.3.6.1.4.1.6296.101.2.11.1.2
		sleSlotSystemControl OBJECT IDENTIFIER ::= { sleSlotSystemInfo 2 }

		
		-- 1.3.6.1.4.1.6296.101.2.11.1.2.1
		sleSlotSystemControlRequest OBJECT-TYPE
			SYNTAX INTEGER { setSlotRestart(1) }
			MAX-ACCESS read-write
			STATUS current
			DESCRIPTION
				"The request of a user command"
			::= { sleSlotSystemControl 1 }

		
		-- 1.3.6.1.4.1.6296.101.2.11.1.2.2
		sleSlotSystemControlStatus OBJECT-TYPE
			SYNTAX SleControlStatusType
			MAX-ACCESS read-only
			STATUS current
			DESCRIPTION
				"The status of user command"
			::= { sleSlotSystemControl 2 }

		
		-- 1.3.6.1.4.1.6296.101.2.11.1.2.3
		sleSlotSystemControlTimer OBJECT-TYPE
			SYNTAX Gauge32
			MAX-ACCESS read-write
			STATUS current
			DESCRIPTION
				"The maximum time for the manager for a long running user command"
			::= { sleSlotSystemControl 3 }

		
		-- 1.3.6.1.4.1.6296.101.2.11.1.2.4
		sleSlotSystemControlTimeStamp OBJECT-TYPE
			SYNTAX TimeTicks
			MAX-ACCESS read-only
			STATUS current
			DESCRIPTION
				"The time stamp of the last command(end of command)"
			::= { sleSlotSystemControl 4 }

		
		-- 1.3.6.1.4.1.6296.101.2.11.1.2.5
		sleSlotSystemControlReqResult OBJECT-TYPE
			SYNTAX SleControlRequestResultType
			MAX-ACCESS read-only
			STATUS current
			DESCRIPTION
				"The result of the last user command"
			::= { sleSlotSystemControl 5 }

		
--     1.3.6.1.4.1.6296.101.2.11.1.2.6
-- 1.3.6.1.4.1.6296.101.2.11.1.2.6
-- 1.3.6.1.4.1.6296.101.2.11.1.2.6
-- 1.3.6.1.4.1.6296.101.2.11.1.2.6
		-- 1.3.6.1.4.1.6296.101.2.11.1.2.6
		sleSlotSystemControlSlotIndex OBJECT-TYPE
			SYNTAX Integer32
			MAX-ACCESS read-write
			STATUS current
			DESCRIPTION
				"The system slot index."
			::= { sleSlotSystemControl 6 }

		
--     1.3.6.1.4.1.6296.101.2.11.1.3
-- 1.3.6.1.4.1.6296.101.2.11.1.3
-- 1.3.6.1.4.1.6296.101.2.11.1.3
-- 1.3.6.1.4.1.6296.101.2.11.1.3
		-- 1.3.6.1.4.1.6296.101.2.11.1.3
		sleSlotSystemNotification OBJECT IDENTIFIER ::= { sleSlotSystemInfo 3 }

		
--     1.3.6.1.4.1.6296.101.2.11.1.3.1
-- 1.3.6.1.4.1.6296.101.2.11.1.3.1
-- 1.3.6.1.4.1.6296.101.2.11.1.3.1
-- 1.3.6.1.4.1.6296.101.2.11.1.3.1
		-- 1.3.6.1.4.1.6296.101.2.11.1.3.1
		sleSlotSystemRestart NOTIFICATION-TYPE
			OBJECTS { sleSlotSystemControlRequest, sleSlotSystemControlTimeStamp, sleSlotSystemControlReqResult, sleSlotSystemControlSlotIndex }
			STATUS current
			DESCRIPTION 
				"Description."
			::= { sleSlotSystemNotification 1 }

		
		-- 1.3.6.1.4.1.6296.101.2.11.2
		sleSlotStatusInfo OBJECT IDENTIFIER ::= { sleSlot 2 }

		
		-- 1.3.6.1.4.1.6296.101.2.11.2.1
		sleSlotStatusInfoTable OBJECT-TYPE
			SYNTAX SEQUENCE OF SleSlotStatusInfoEntry
			MAX-ACCESS not-accessible
			STATUS current
			DESCRIPTION
				"Description."
			::= { sleSlotStatusInfo 1 }

		
		-- 1.3.6.1.4.1.6296.101.2.11.2.1.1
		sleSlotStatusInfoEntry OBJECT-TYPE
			SYNTAX SleSlotStatusInfoEntry
			MAX-ACCESS not-accessible
			STATUS current
			DESCRIPTION
				"Description."
			INDEX { sleSlotSystemIndex }
			::= { sleSlotStatusInfoTable 1 }

		
		SleSlotStatusInfoEntry ::=
			SEQUENCE { 
				sleSlotStatusPlan
					INTEGER,
				sleSlotStatusPlanCardType
					INTEGER,
				sleSlotStatusCurrentInstall
					INTEGER,
				sleSlotStatusCurrentInstallCardType
					INTEGER,
				sleSlotStatusCardOperation
					INTEGER,
				sleSlotStatusLock
					INTEGER,
				sleSlotStatusUpgradeMode
					INTEGER,
				sleSlotStatusActionEvent
					INTEGER,
				sleSlotStatusState
					INTEGER,
				sleSlotStatusPower
					INTEGER,
				sleSlotStatusSerialNumber
					OCTET STRING,
				sleSlotStatusHealthState
					INTEGER
			 }

		-- 1.3.6.1.4.1.6296.101.2.11.2.1.1.1
		sleSlotStatusPlan OBJECT-TYPE
			SYNTAX INTEGER
				{
				notPlanned(1),
				planned(2)
				}
			MAX-ACCESS read-only
			STATUS current
			DESCRIPTION
				"Planning status of slot."
			::= { sleSlotStatusInfoEntry 1 }

		
		-- 1.3.6.1.4.1.6296.101.2.11.2.1.1.2
		sleSlotStatusPlanCardType OBJECT-TYPE
			SYNTAX INTEGER
				{
				unknown(1),
				siuGE12(2),
				siuEPON12(3),
				siuGPON4(4),
				niuGE12(5),
				sfu(6),
				v5548gGE12(7),
				siuGPON4r(8),
				niuGE8(9),
				siuGE4(10),
				niu10GPlus(11),
				iu10GE(12),
				iuGE6(13),
				iuGE4(14),
				siuTDM(15),
				siuGE24(16),
				siuFE48(17),
				niu10GE2(18),
				siu10GE48(19),
				siuGE10(20),
				niu10Ge2Plus(21),
				iuGT4(22),
				iuGT6(23),
				iuTDM6(24),
				siuGE6(25),
				siuGE8(26),
				siuGT6(27),
				niuGE2(28),
				niuGE4(29),
				iuGEPON4(30),
				iu10GE8(31),
				iuGEPON8(32),
				iu10GEPON8(33),
				iuGE8(34)
				}
			MAX-ACCESS read-only
			STATUS current
			DESCRIPTION
				"Planning card type status of slot."
			::= { sleSlotStatusInfoEntry 2 }

		
		-- 1.3.6.1.4.1.6296.101.2.11.2.1.1.3
		sleSlotStatusCurrentInstall OBJECT-TYPE
			SYNTAX INTEGER
				{
				notInstalled(1),
				installed(2),
				failed(3)
				}
			MAX-ACCESS read-only
			STATUS current
			DESCRIPTION
				"Currently installation status of slot."
			::= { sleSlotStatusInfoEntry 3 }

		
		-- 1.3.6.1.4.1.6296.101.2.11.2.1.1.4
		sleSlotStatusCurrentInstallCardType OBJECT-TYPE
			SYNTAX INTEGER
				{
				unknown(1),
				siuGE12(2),
				siuEPON12(3),
				siuGPON4(4),
				niuGE12(5),
				sfu(6),
				v5548gGE12(7),
				siuGPON4r(8),
				niuGE8(9),
				siuGE4(10),
				niu10GPlus(11),
				iuGE10(12),
				iuGE6(13),
				iuGE4(14),
				siuTDM(15),
				siuGE24(16),
				siuFE48(17),
				niu10GE2(18),
				siu10GE48(19),
				siuGE10(20),
				niu10Ge2Plus(21),
				iuGT4(22),
				iuGT6(23),
				iuTDM6(24),
				siuGE6(25),
				siuGE8(26),
				siuGT6(27),
				niuGE2(28),
				niuGE4(29),
				iuGEPON4(30),
				iu10GE8(31),
				iuGEPON8(32),
				iu10GEPON8(33),
				iuGE8(34)
				}
			MAX-ACCESS read-only
			STATUS current
			DESCRIPTION
				"Currently installation card type status of slot."
			::= { sleSlotStatusInfoEntry 4 }

		
		-- 1.3.6.1.4.1.6296.101.2.11.2.1.1.5
		sleSlotStatusCardOperation OBJECT-TYPE
			SYNTAX INTEGER
				{
				disable(1),
				init(2),
				enable(3),
				enableActive(4),
				enableStandby(5)
				}
			MAX-ACCESS read-only
			STATUS current
			DESCRIPTION
				"Currently operation status of slot."
			::= { sleSlotStatusInfoEntry 5 }

		
		-- 1.3.6.1.4.1.6296.101.2.11.2.1.1.6
		sleSlotStatusLock OBJECT-TYPE
			SYNTAX INTEGER
				{
				unlocked(1),
				locked(2)
				}
			MAX-ACCESS read-only
			STATUS current
			DESCRIPTION
				"Lock status of slot."
			::= { sleSlotStatusInfoEntry 6 }

		
		-- 1.3.6.1.4.1.6296.101.2.11.2.1.1.7
		sleSlotStatusUpgradeMode OBJECT-TYPE
			SYNTAX INTEGER
				{
				manual(1),
				auto(2)
				}
			MAX-ACCESS read-only
			STATUS current
			DESCRIPTION
				"Upgrade mode status of slot."
			::= { sleSlotStatusInfoEntry 7 }

		
		-- 1.3.6.1.4.1.6296.101.2.11.2.1.1.8
		sleSlotStatusActionEvent OBJECT-TYPE
			SYNTAX INTEGER
				{
				uninstallAction(1),
				installAction(2),
				noPlanningAction(3),
				planningAction(4),
				lockAction(5),
				unlockAction(6),
				matchedEvent(7),
				unMatchedEvent(8),
				bootEndEvent(9),
				configEndEvent(10),
				configFailEvent(11)
				}
			MAX-ACCESS accessible-for-notify
			STATUS current
			DESCRIPTION
				"Event of slot. (accessible-for-notify)"
			::= { sleSlotStatusInfoEntry 8 }

		
		-- 1.3.6.1.4.1.6296.101.2.11.2.1.1.9
		sleSlotStatusState OBJECT-TYPE
			SYNTAX INTEGER
				{
				default(1),
				planningWait(2),
				installWait(3),
				operationReady(4),
				actionBootReady(5),
				actionConfig(6),
				actionEnableReady(7),
				actionEnable(8),
				actionEnableLock(9),
				actionDisable(10)
				}
			MAX-ACCESS accessible-for-notify
			STATUS current
			DESCRIPTION
				"Status of slot. (accessible-for-notify)"
			::= { sleSlotStatusInfoEntry 9 }

		
		-- 1.3.6.1.4.1.6296.101.2.11.2.1.1.10
		sleSlotStatusPower OBJECT-TYPE
			SYNTAX INTEGER
				{
				up(1),
				down(2)
				}
			MAX-ACCESS read-only
			STATUS current
			DESCRIPTION
				"Currently power status of slot."
			::= { sleSlotStatusInfoEntry 10 }

		
		-- 1.3.6.1.4.1.6296.101.2.11.2.1.1.11
		sleSlotStatusSerialNumber OBJECT-TYPE
			SYNTAX OCTET STRING
			MAX-ACCESS read-only
			STATUS current
			DESCRIPTION
				"The serial number"
			::= { sleSlotStatusInfoEntry 11 }

		
		-- 1.3.6.1.4.1.6296.101.2.11.2.1.1.12
		sleSlotStatusHealthState OBJECT-TYPE
			SYNTAX INTEGER
				{
				well(0),
				warning(1),
				timeout(2)
				}
			MAX-ACCESS read-only
			STATUS current
			DESCRIPTION
				"The slot health status"
			::= { sleSlotStatusInfoEntry 12 }

		
		-- 1.3.6.1.4.1.6296.101.2.11.2.2
		sleSlotStatusControl OBJECT IDENTIFIER ::= { sleSlotStatusInfo 2 }

		
		-- 1.3.6.1.4.1.6296.101.2.11.2.2.1
		sleSlotStatusControlRequest OBJECT-TYPE
			SYNTAX INTEGER
				{
				setSlotLock(1),
				setSlotUnlock(2),
				setSlotPlanning(3),
				setSlotNoplanning(4),
				setSlotUpgradeMode(5),
				setSlotPowerUp(6),
				setSlotPowerDown(7),
				setSlotPowerReset(8)
				}
			MAX-ACCESS read-write
			STATUS current
			DESCRIPTION
				"The request of a user command"
			::= { sleSlotStatusControl 1 }

		
		-- 1.3.6.1.4.1.6296.101.2.11.2.2.2
		sleSlotStatusControlStatus OBJECT-TYPE
			SYNTAX SleControlStatusType
			MAX-ACCESS read-only
			STATUS current
			DESCRIPTION
				"The status of user command"
			::= { sleSlotStatusControl 2 }

		
		-- 1.3.6.1.4.1.6296.101.2.11.2.2.3
		sleSlotStatusControlTimer OBJECT-TYPE
			SYNTAX Gauge32
			MAX-ACCESS read-write
			STATUS current
			DESCRIPTION
				"The maximum time for the manager for a long running user command"
			::= { sleSlotStatusControl 3 }

		
		-- 1.3.6.1.4.1.6296.101.2.11.2.2.4
		sleSlotStatusControlTimeStamp OBJECT-TYPE
			SYNTAX TimeTicks
			MAX-ACCESS read-only
			STATUS current
			DESCRIPTION
				"The time stamp of the last command(end of command)"
			::= { sleSlotStatusControl 4 }

		
		-- 1.3.6.1.4.1.6296.101.2.11.2.2.5
		sleSlotStatusControlReqResult OBJECT-TYPE
			SYNTAX SleControlRequestResultType
			MAX-ACCESS read-only
			STATUS current
			DESCRIPTION
				"The result of the last user command"
			::= { sleSlotStatusControl 5 }

		
		-- 1.3.6.1.4.1.6296.101.2.11.2.2.6
		sleSlotStatusControlSlotIndex OBJECT-TYPE
			SYNTAX Integer32
			MAX-ACCESS read-write
			STATUS current
			DESCRIPTION
				"The system slot index.
				255 is means all slot."
			::= { sleSlotStatusControl 6 }

		
		-- 1.3.6.1.4.1.6296.101.2.11.2.2.7
		sleSlotStatusControlPlanCardType OBJECT-TYPE
			SYNTAX INTEGER
				{
				unknown(1),
				siuGE12(2),
				siuEPON12(3),
				siuGPON4(4),
				niuGE12(5),
				sfu(6),
				v5548gGE12(7),
				siuGPON4r(8),
				niuGE8(9),
				siuGE4(10),
				niu10GPlus(11),
				iuGE10(12),
				iuGE6(13),
				iuGE4(14),
				siuTDM(15),
				siuGE24(16),
				siuFE48(17),
				niu10GE2(18),
				siu10GE48(19),
				siuGE10(20),
				niu10Ge2Plus(21),
				iuGT4(22),
				iuGT6(23),
				iuTDM6(24),
				siuGE6(25),
				siuGE8(26),
				siuGT6(27),
				niuGE2(28),
				niuGE4(29),
				iuGEPON4(30),
				iu10GE8(31),
				iuGEPON8(32),
				iu10GEPON8(33)
				}
			MAX-ACCESS read-write
			STATUS current
			DESCRIPTION
				"Planning card type status of slot."
			::= { sleSlotStatusControl 7 }

		
		-- 1.3.6.1.4.1.6296.101.2.11.2.2.8
		sleSlotStatusControlUpgradeMode OBJECT-TYPE
			SYNTAX INTEGER
				{
				manual(1),
				auto(2),
				autoUpgradeManualReset(3)
				}
			MAX-ACCESS read-write
			STATUS current
			DESCRIPTION
				"Upgrade mode status of slot."
			::= { sleSlotStatusControl 8 }

		
		-- 1.3.6.1.4.1.6296.101.2.11.2.3
		sleSlotStatusNotification OBJECT IDENTIFIER ::= { sleSlotStatusInfo 3 }

		
		-- 1.3.6.1.4.1.6296.101.2.11.2.3.1
		sleSlotStatusLocked NOTIFICATION-TYPE
			OBJECTS { sleSlotStatusControlRequest, sleSlotStatusControlTimeStamp, sleSlotStatusControlReqResult, sleSlotStatusControlSlotIndex }
			STATUS current
			DESCRIPTION 
				"Description."
			::= { sleSlotStatusNotification 1 }

		
		-- 1.3.6.1.4.1.6296.101.2.11.2.3.2
		sleSlotStatusUnlocked NOTIFICATION-TYPE
			OBJECTS { sleSlotStatusControlRequest, sleSlotStatusControlTimeStamp, sleSlotStatusControlReqResult, sleSlotStatusControlSlotIndex }
			STATUS current
			DESCRIPTION 
				"Description."
			::= { sleSlotStatusNotification 2 }

		
		-- 1.3.6.1.4.1.6296.101.2.11.2.3.3
		sleSlotStatusPlanning NOTIFICATION-TYPE
			OBJECTS { sleSlotStatusControlRequest, sleSlotStatusControlTimeStamp, sleSlotStatusControlReqResult, sleSlotStatusControlSlotIndex, sleSlotStatusControlPlanCardType
				 }
			STATUS current
			DESCRIPTION 
				"Description."
			::= { sleSlotStatusNotification 3 }

		
		-- 1.3.6.1.4.1.6296.101.2.11.2.3.4
		sleSlotStatusNoPlanning NOTIFICATION-TYPE
			OBJECTS { sleSlotStatusControlRequest, sleSlotStatusControlTimeStamp, sleSlotStatusControlReqResult, sleSlotStatusControlSlotIndex }
			STATUS current
			DESCRIPTION 
				"Description."
			::= { sleSlotStatusNotification 4 }

		
		-- 1.3.6.1.4.1.6296.101.2.11.2.3.5
		sleSlotStatusUpgradeModeChanged NOTIFICATION-TYPE
			OBJECTS { sleSlotStatusControlRequest, sleSlotStatusControlTimeStamp, sleSlotStatusControlReqResult, sleSlotStatusControlSlotIndex, sleSlotStatusControlUpgradeMode
				 }
			STATUS current
			DESCRIPTION 
				"Description."
			::= { sleSlotStatusNotification 5 }

		
		-- 1.3.6.1.4.1.6296.101.2.11.2.3.6
		sleSlotStatusPowerUp NOTIFICATION-TYPE
			OBJECTS { sleSlotStatusControlRequest, sleSlotStatusControlTimeStamp, sleSlotStatusControlReqResult, sleSlotStatusControlSlotIndex }
			STATUS current
			DESCRIPTION 
				"Description."
			::= { sleSlotStatusNotification 6 }

		
		-- 1.3.6.1.4.1.6296.101.2.11.2.3.7
		sleSlotStatusPowerDown NOTIFICATION-TYPE
			OBJECTS { sleSlotStatusControlRequest, sleSlotStatusControlTimeStamp, sleSlotStatusControlReqResult, sleSlotStatusControlSlotIndex }
			STATUS current
			DESCRIPTION 
				"Description."
			::= { sleSlotStatusNotification 7 }

		
		-- 1.3.6.1.4.1.6296.101.2.11.2.3.8
		sleSlotStatusPowerReset NOTIFICATION-TYPE
			OBJECTS { sleSlotStatusControlRequest, sleSlotStatusControlTimeStamp, sleSlotStatusControlReqResult, sleSlotStatusControlSlotIndex }
			STATUS current
			DESCRIPTION 
				"Description."
			::= { sleSlotStatusNotification 8 }

		
		-- 1.3.6.1.4.1.6296.101.2.11.3
		sleSlotNosInfo OBJECT IDENTIFIER ::= { sleSlot 3 }

		
--     1.3.6.1.4.1.6296.101.2.11.3.1
-- 1.3.6.1.4.1.6296.101.2.11.3.1
-- 1.3.6.1.4.1.6296.101.2.11.3.1
-- 1.3.6.1.4.1.6296.101.2.11.3.1
		-- 1.3.6.1.4.1.6296.101.2.11.3.1
		sleSlotNosInfoTable OBJECT-TYPE
			SYNTAX SEQUENCE OF SleSlotNosInfoEntry
			MAX-ACCESS not-accessible
			STATUS current
			DESCRIPTION
				"Description."
			::= { sleSlotNosInfo 1 }

		
--     1.3.6.1.4.1.6296.101.2.11.3.1.1
-- 1.3.6.1.4.1.6296.101.2.11.3.1.1
-- 1.3.6.1.4.1.6296.101.2.11.3.1.1
-- 1.3.6.1.4.1.6296.101.2.11.3.1.1
		-- 1.3.6.1.4.1.6296.101.2.11.3.1.1
		sleSlotNosInfoEntry OBJECT-TYPE
			SYNTAX SleSlotNosInfoEntry
			MAX-ACCESS not-accessible
			STATUS current
			DESCRIPTION
				"Description."
			INDEX { sleSlotSystemIndex }
			::= { sleSlotNosInfoTable 1 }

		
		SleSlotNosInfoEntry ::=
			SEQUENCE { 
				sleSlotNosVersion
					OCTET STRING,
				sleSlotNosRevision
					OCTET STRING,
				sleSlotNosSize
					Unsigned32,
				sleSlotNosUpgradeStatus
					INTEGER,
				sleSlotNosStbVersion
					OCTET STRING,
				sleSlotNosStbRevision
					OCTET STRING,
				sleSlotNosStbSize
					Unsigned32
			 }

--     1.3.6.1.4.1.6296.101.2.11.3.1.1.1
-- 1.3.6.1.4.1.6296.101.2.11.3.1.1.1
-- 1.3.6.1.4.1.6296.101.2.11.3.1.1.1
-- 1.3.6.1.4.1.6296.101.2.11.3.1.1.1
		-- 1.3.6.1.4.1.6296.101.2.11.3.1.1.1
		sleSlotNosVersion OBJECT-TYPE
			SYNTAX OCTET STRING
			MAX-ACCESS read-only
			STATUS current
			DESCRIPTION
				"NOS version of slot."
			::= { sleSlotNosInfoEntry 1 }

		
--     1.3.6.1.4.1.6296.101.2.11.3.1.1.2
-- 1.3.6.1.4.1.6296.101.2.11.3.1.1.2
-- 1.3.6.1.4.1.6296.101.2.11.3.1.1.2
-- 1.3.6.1.4.1.6296.101.2.11.3.1.1.2
		-- 1.3.6.1.4.1.6296.101.2.11.3.1.1.2
		sleSlotNosRevision OBJECT-TYPE
			SYNTAX OCTET STRING
			MAX-ACCESS read-only
			STATUS current
			DESCRIPTION
				"NOS revision of slot."
			::= { sleSlotNosInfoEntry 2 }

		
--     1.3.6.1.4.1.6296.101.2.11.3.1.1.3
-- 1.3.6.1.4.1.6296.101.2.11.3.1.1.3
-- 1.3.6.1.4.1.6296.101.2.11.3.1.1.3
-- 1.3.6.1.4.1.6296.101.2.11.3.1.1.3
		-- 1.3.6.1.4.1.6296.101.2.11.3.1.1.3
		sleSlotNosSize OBJECT-TYPE
			SYNTAX Unsigned32
			MAX-ACCESS read-only
			STATUS current
			DESCRIPTION
				"NOS size of slot."
			::= { sleSlotNosInfoEntry 3 }

		
--     1.3.6.1.4.1.6296.101.2.11.3.1.1.4
-- 1.3.6.1.4.1.6296.101.2.11.3.1.1.4
-- 1.3.6.1.4.1.6296.101.2.11.3.1.1.4
-- 1.3.6.1.4.1.6296.101.2.11.3.1.1.4
		-- 1.3.6.1.4.1.6296.101.2.11.3.1.1.4
		sleSlotNosUpgradeStatus OBJECT-TYPE
			SYNTAX INTEGER
				{
				upgradeIdle(1),
				upgradeStart(2),
				upgradeDone(3),
				upgradeFail(4)
				}
			MAX-ACCESS read-only
			STATUS current
			DESCRIPTION
				"NOS upgrade status of slot."
			::= { sleSlotNosInfoEntry 4 }

		
--     1.3.6.1.4.1.6296.101.2.11.3.1.1.5
-- 1.3.6.1.4.1.6296.101.2.11.3.1.1.5
-- 1.3.6.1.4.1.6296.101.2.11.3.1.1.5
-- 1.3.6.1.4.1.6296.101.2.11.3.1.1.5
		-- 1.3.6.1.4.1.6296.101.2.11.3.1.1.5
		sleSlotNosStbVersion OBJECT-TYPE
			SYNTAX OCTET STRING
			MAX-ACCESS read-only
			STATUS current
			DESCRIPTION
				"Stand by NOS version of slot"
			::= { sleSlotNosInfoEntry 5 }

		
--     1.3.6.1.4.1.6296.101.2.11.3.1.1.6
-- 1.3.6.1.4.1.6296.101.2.11.3.1.1.6
-- 1.3.6.1.4.1.6296.101.2.11.3.1.1.6
-- 1.3.6.1.4.1.6296.101.2.11.3.1.1.6
		-- 1.3.6.1.4.1.6296.101.2.11.3.1.1.6
		sleSlotNosStbRevision OBJECT-TYPE
			SYNTAX OCTET STRING
			MAX-ACCESS read-only
			STATUS current
			DESCRIPTION
				"Stand by NOS revision of slot."
			::= { sleSlotNosInfoEntry 6 }

		
--     1.3.6.1.4.1.6296.101.2.11.3.1.1.7
-- 1.3.6.1.4.1.6296.101.2.11.3.1.1.7
-- 1.3.6.1.4.1.6296.101.2.11.3.1.1.7
-- 1.3.6.1.4.1.6296.101.2.11.3.1.1.7
		-- 1.3.6.1.4.1.6296.101.2.11.3.1.1.7
		sleSlotNosStbSize OBJECT-TYPE
			SYNTAX Unsigned32
			MAX-ACCESS read-only
			STATUS current
			DESCRIPTION
				"Stand by NOS size of slot."
			::= { sleSlotNosInfoEntry 7 }

		
--     1.3.6.1.4.1.6296.101.2.11.3.2
-- 1.3.6.1.4.1.6296.101.2.11.3.2
-- 1.3.6.1.4.1.6296.101.2.11.3.2
-- 1.3.6.1.4.1.6296.101.2.11.3.2
		-- 1.3.6.1.4.1.6296.101.2.11.3.2
		sleSlotNosControl OBJECT IDENTIFIER ::= { sleSlotNosInfo 2 }

		
--     1.3.6.1.4.1.6296.101.2.11.3.2.1
-- 1.3.6.1.4.1.6296.101.2.11.3.2.1
-- 1.3.6.1.4.1.6296.101.2.11.3.2.1
-- 1.3.6.1.4.1.6296.101.2.11.3.2.1
		-- 1.3.6.1.4.1.6296.101.2.11.3.2.1
		sleSlotNosControlRequest OBJECT-TYPE
			SYNTAX INTEGER
				{
				setSlotUpgarde(1),
				downloadSlotNos(2),
				upgradeSlotBootloader(3)
				}
			MAX-ACCESS read-write
			STATUS current
			DESCRIPTION
				"The request of a user command"
			::= { sleSlotNosControl 1 }

		
--     1.3.6.1.4.1.6296.101.2.11.3.2.2
-- 1.3.6.1.4.1.6296.101.2.11.3.2.2
-- 1.3.6.1.4.1.6296.101.2.11.3.2.2
-- 1.3.6.1.4.1.6296.101.2.11.3.2.2
		-- 1.3.6.1.4.1.6296.101.2.11.3.2.2
		sleSlotNosControlStatus OBJECT-TYPE
			SYNTAX SleControlStatusType
			MAX-ACCESS read-only
			STATUS current
			DESCRIPTION
				"The status of user command"
			::= { sleSlotNosControl 2 }

		
--     1.3.6.1.4.1.6296.101.2.11.3.2.3
-- 1.3.6.1.4.1.6296.101.2.11.3.2.3
-- 1.3.6.1.4.1.6296.101.2.11.3.2.3
-- 1.3.6.1.4.1.6296.101.2.11.3.2.3
		-- 1.3.6.1.4.1.6296.101.2.11.3.2.3
		sleSlotNosControlTimer OBJECT-TYPE
			SYNTAX Gauge32
			MAX-ACCESS read-write
			STATUS current
			DESCRIPTION
				"The maximum time for the manager for a long running user command"
			::= { sleSlotNosControl 3 }

		
--     1.3.6.1.4.1.6296.101.2.11.3.2.4
-- 1.3.6.1.4.1.6296.101.2.11.3.2.4
-- 1.3.6.1.4.1.6296.101.2.11.3.2.4
-- 1.3.6.1.4.1.6296.101.2.11.3.2.4
		-- 1.3.6.1.4.1.6296.101.2.11.3.2.4
		sleSlotNosControlTimeStamp OBJECT-TYPE
			SYNTAX TimeTicks
			MAX-ACCESS read-only
			STATUS current
			DESCRIPTION
				"The time stamp of the last command(end of command)"
			::= { sleSlotNosControl 4 }

		
--     1.3.6.1.4.1.6296.101.2.11.3.2.5
-- 1.3.6.1.4.1.6296.101.2.11.3.2.5
-- 1.3.6.1.4.1.6296.101.2.11.3.2.5
-- 1.3.6.1.4.1.6296.101.2.11.3.2.5
		-- 1.3.6.1.4.1.6296.101.2.11.3.2.5
		sleSlotNosControlReqResult OBJECT-TYPE
			SYNTAX SleControlRequestResultType
			MAX-ACCESS read-only
			STATUS current
			DESCRIPTION
				"The result of the last user command"
			::= { sleSlotNosControl 5 }

		
--     1.3.6.1.4.1.6296.101.2.11.3.2.6
-- 1.3.6.1.4.1.6296.101.2.11.3.2.6
-- 1.3.6.1.4.1.6296.101.2.11.3.2.6
-- 1.3.6.1.4.1.6296.101.2.11.3.2.6
		-- 1.3.6.1.4.1.6296.101.2.11.3.2.6
		sleSlotNosControlSlotIndex OBJECT-TYPE
			SYNTAX Integer32
			MAX-ACCESS read-write
			STATUS current
			DESCRIPTION
				"The system slot index."
			::= { sleSlotNosControl 6 }

		
--     1.3.6.1.4.1.6296.101.2.11.3.2.7
-- 1.3.6.1.4.1.6296.101.2.11.3.2.7
-- 1.3.6.1.4.1.6296.101.2.11.3.2.7
-- 1.3.6.1.4.1.6296.101.2.11.3.2.7
		-- 1.3.6.1.4.1.6296.101.2.11.3.2.7
		sleSlotNosControlUpDownMethod OBJECT-TYPE
			SYNTAX INTEGER
				{
				ftp(1),
				tftp(2)
				}
			MAX-ACCESS read-write
			STATUS current
			DESCRIPTION
				"1: using FTP
				2: using TFTP
				"
			::= { sleSlotNosControl 7 }

		
--     1.3.6.1.4.1.6296.101.2.11.3.2.8
-- 1.3.6.1.4.1.6296.101.2.11.3.2.8
-- 1.3.6.1.4.1.6296.101.2.11.3.2.8
-- 1.3.6.1.4.1.6296.101.2.11.3.2.8
		-- 1.3.6.1.4.1.6296.101.2.11.3.2.8
		sleSlotNosControlUpDownFlag OBJECT-TYPE
			SYNTAX INTEGER
				{
				upload(1),
				download(2)
				}
			MAX-ACCESS read-write
			STATUS current
			DESCRIPTION
				"1. Uploading slot nos to the remote-host.
				2. Downloading slot nos from the remote-host."
			::= { sleSlotNosControl 8 }

		
--     1.3.6.1.4.1.6296.101.2.11.3.2.9
-- 1.3.6.1.4.1.6296.101.2.11.3.2.9
-- 1.3.6.1.4.1.6296.101.2.11.3.2.9
-- 1.3.6.1.4.1.6296.101.2.11.3.2.9
		-- 1.3.6.1.4.1.6296.101.2.11.3.2.9
		sleSlotNosControlServerAddress OBJECT-TYPE
			SYNTAX IpAddress
			MAX-ACCESS read-write
			STATUS current
			DESCRIPTION
				"The remote-host's IP address."
			::= { sleSlotNosControl 9 }

		
--     1.3.6.1.4.1.6296.101.2.11.3.2.10
-- 1.3.6.1.4.1.6296.101.2.11.3.2.10
-- 1.3.6.1.4.1.6296.101.2.11.3.2.10
-- 1.3.6.1.4.1.6296.101.2.11.3.2.10
		-- 1.3.6.1.4.1.6296.101.2.11.3.2.10
		sleSlotNosControlUserID OBJECT-TYPE
			SYNTAX OCTET STRING
			MAX-ACCESS read-write
			STATUS current
			DESCRIPTION
				"Account-name."
			::= { sleSlotNosControl 10 }

		
--     1.3.6.1.4.1.6296.101.2.11.3.2.11
-- 1.3.6.1.4.1.6296.101.2.11.3.2.11
-- 1.3.6.1.4.1.6296.101.2.11.3.2.11
-- 1.3.6.1.4.1.6296.101.2.11.3.2.11
		-- 1.3.6.1.4.1.6296.101.2.11.3.2.11
		sleSlotNosControlPassword OBJECT-TYPE
			SYNTAX OCTET STRING
			MAX-ACCESS read-write
			STATUS current
			DESCRIPTION
				"Account-password."
			::= { sleSlotNosControl 11 }

		
--     1.3.6.1.4.1.6296.101.2.11.3.2.12
-- 1.3.6.1.4.1.6296.101.2.11.3.2.12
-- 1.3.6.1.4.1.6296.101.2.11.3.2.12
-- 1.3.6.1.4.1.6296.101.2.11.3.2.12
		-- 1.3.6.1.4.1.6296.101.2.11.3.2.12
		sleSlotNosControlFileName OBJECT-TYPE
			SYNTAX OCTET STRING
			MAX-ACCESS read-write
			STATUS current
			DESCRIPTION
				"Slot nos file name."
			::= { sleSlotNosControl 12 }

		
--     1.3.6.1.4.1.6296.101.2.11.3.3
-- 1.3.6.1.4.1.6296.101.2.11.3.3
-- 1.3.6.1.4.1.6296.101.2.11.3.3
-- 1.3.6.1.4.1.6296.101.2.11.3.3
		-- 1.3.6.1.4.1.6296.101.2.11.3.3
		sleSlotNosNotification OBJECT IDENTIFIER ::= { sleSlotNosInfo 3 }

		
--     1.3.6.1.4.1.6296.101.2.11.3.3.1
-- 1.3.6.1.4.1.6296.101.2.11.3.3.1
-- 1.3.6.1.4.1.6296.101.2.11.3.3.1
-- 1.3.6.1.4.1.6296.101.2.11.3.3.1
		-- 1.3.6.1.4.1.6296.101.2.11.3.3.1
		sleSlotNosUpgrade NOTIFICATION-TYPE
			OBJECTS { sleSlotNosControlRequest, sleSlotNosControlTimeStamp, sleSlotNosControlReqResult, sleSlotNosControlSlotIndex }
			STATUS current
			DESCRIPTION 
				"Description."
			::= { sleSlotNosNotification 1 }

		
--     1.3.6.1.4.1.6296.101.2.11.3.3.2
-- 1.3.6.1.4.1.6296.101.2.11.3.3.2
-- 1.3.6.1.4.1.6296.101.2.11.3.3.2
-- 1.3.6.1.4.1.6296.101.2.11.3.3.2
		-- 1.3.6.1.4.1.6296.101.2.11.3.3.2
		sleSlotNosDownload NOTIFICATION-TYPE
			OBJECTS { sleSlotNosControlRequest, sleSlotNosControlTimeStamp, sleSlotNosControlReqResult, sleSlotNosControlUpDownMethod, sleSlotNosControlUpDownFlag, 
				sleSlotNosControlServerAddress, sleSlotNosControlUserID, sleSlotNosControlPassword, sleSlotNosControlFileName }
			STATUS current
			DESCRIPTION 
				"Description."
			::= { sleSlotNosNotification 2 }

		
--     1.3.6.1.4.1.6296.101.2.11.3.3.3
-- 1.3.6.1.4.1.6296.101.2.11.3.3.3
-- 1.3.6.1.4.1.6296.101.2.11.3.3.3
-- 1.3.6.1.4.1.6296.101.2.11.3.3.3
		-- 1.3.6.1.4.1.6296.101.2.11.3.3.3
		sleSlotNosBootloaderUpgrade NOTIFICATION-TYPE
			OBJECTS { sleSlotNosControlRequest, sleSlotNosControlTimeStamp, sleSlotNosControlReqResult, sleSlotNosControlSlotIndex, sleSlotNosControlServerAddress, 
				sleSlotNosControlUserID, sleSlotNosControlPassword, sleSlotNosControlFileName }
			STATUS current
			DESCRIPTION 
				"Description."
			::= { sleSlotNosNotification 3 }

		
		-- 1.3.6.1.4.1.6296.101.2.11.4
		sleSlotReleasedIUNosInfo OBJECT IDENTIFIER ::= { sleSlot 4 }

		
		-- 1.3.6.1.4.1.6296.101.2.11.4.1
		sleSlotReleasedNIUNosVersion OBJECT-TYPE
			SYNTAX OCTET STRING
			MAX-ACCESS read-only
			STATUS current
			DESCRIPTION
				"Released NIU NOS image version on SFU."
			::= { sleSlotReleasedIUNosInfo 1 }

		
--     1.3.6.1.4.1.6296.101.2.11.4.2
-- 1.3.6.1.4.1.6296.101.2.11.4.2
-- 1.3.6.1.4.1.6296.101.2.11.4.2
-- 1.3.6.1.4.1.6296.101.2.11.4.2
		-- 1.3.6.1.4.1.6296.101.2.11.4.2
		sleSlotReleasedNIUNosRevision OBJECT-TYPE
			SYNTAX OCTET STRING
			MAX-ACCESS read-only
			STATUS current
			DESCRIPTION
				"Released NIU NOS image revision on SFU."
			::= { sleSlotReleasedIUNosInfo 2 }

		
--     1.3.6.1.4.1.6296.101.2.11.4.3
-- 1.3.6.1.4.1.6296.101.2.11.4.3
-- 1.3.6.1.4.1.6296.101.2.11.4.3
-- 1.3.6.1.4.1.6296.101.2.11.4.3
		-- 1.3.6.1.4.1.6296.101.2.11.4.3
		sleSlotReleasedNIUNosSize OBJECT-TYPE
			SYNTAX Unsigned32
			MAX-ACCESS read-only
			STATUS current
			DESCRIPTION
				"Released NIU NOS image size on SFU."
			::= { sleSlotReleasedIUNosInfo 3 }

		
--     1.3.6.1.4.1.6296.101.2.11.4.4
-- 1.3.6.1.4.1.6296.101.2.11.4.4
-- 1.3.6.1.4.1.6296.101.2.11.4.4
-- 1.3.6.1.4.1.6296.101.2.11.4.4
		-- 1.3.6.1.4.1.6296.101.2.11.4.4
		sleSlotReleasedGPIUNosVersion OBJECT-TYPE
			SYNTAX OCTET STRING
			MAX-ACCESS read-only
			STATUS current
			DESCRIPTION
				"Released GPIU NOS image version on SFU."
			::= { sleSlotReleasedIUNosInfo 4 }

		
--     1.3.6.1.4.1.6296.101.2.11.4.5
-- 1.3.6.1.4.1.6296.101.2.11.4.5
-- 1.3.6.1.4.1.6296.101.2.11.4.5
-- 1.3.6.1.4.1.6296.101.2.11.4.5
		-- 1.3.6.1.4.1.6296.101.2.11.4.5
		sleSlotReleasedGPIUNosRevision OBJECT-TYPE
			SYNTAX OCTET STRING
			MAX-ACCESS read-only
			STATUS current
			DESCRIPTION
				"Released GPIU NOS image revision on SFU."
			::= { sleSlotReleasedIUNosInfo 5 }

		
--     1.3.6.1.4.1.6296.101.2.11.4.6
-- 1.3.6.1.4.1.6296.101.2.11.4.6
-- 1.3.6.1.4.1.6296.101.2.11.4.6
-- 1.3.6.1.4.1.6296.101.2.11.4.6
		-- 1.3.6.1.4.1.6296.101.2.11.4.6
		sleSlotReleasedGPIUNosSize OBJECT-TYPE
			SYNTAX Unsigned32
			MAX-ACCESS read-only
			STATUS current
			DESCRIPTION
				"Released GPIU NOS image size on SFU."
			::= { sleSlotReleasedIUNosInfo 6 }

		
--  1.3.6.1.4.1.6296.101.2.11.4.7
		-- 1.3.6.1.4.1.6296.101.2.11.4.7
		sleSlotReleasedSIUNosVersion OBJECT-TYPE
			SYNTAX OCTET STRING
			MAX-ACCESS read-only
			STATUS current
			DESCRIPTION
				"Released SIU NOS image version on SFU."
			::= { sleSlotReleasedIUNosInfo 7 }

		
--  1.3.6.1.4.1.6296.101.2.11.4.8
		-- 1.3.6.1.4.1.6296.101.2.11.4.8
		sleSlotReleasedSIUNosRevision OBJECT-TYPE
			SYNTAX OCTET STRING
			MAX-ACCESS read-only
			STATUS current
			DESCRIPTION
				"Released SIU NOS image revision on SFU."
			::= { sleSlotReleasedIUNosInfo 8 }

		
--  1.3.6.1.4.1.6296.101.2.11.4.9
		-- 1.3.6.1.4.1.6296.101.2.11.4.9
		sleSlotReleasedSIUNosSize OBJECT-TYPE
			SYNTAX Integer32
			MAX-ACCESS read-only
			STATUS current
			DESCRIPTION
				"Released SIU NOS image size on SFU."
			::= { sleSlotReleasedIUNosInfo 9 }

		
		-- 1.3.6.1.4.1.6296.101.2.11.4.10
		sleSlotReleasedIU10GE8NosVersion OBJECT-TYPE
			SYNTAX OCTET STRING
			MAX-ACCESS read-only
			STATUS current
			DESCRIPTION
				"Released IU_10GE8 NOS image version on SFU."
			::= { sleSlotReleasedIUNosInfo 10 }

		
		-- 1.3.6.1.4.1.6296.101.2.11.4.11
		sleSlotReleasedIU10GE8NosRevision OBJECT-TYPE
			SYNTAX OCTET STRING
			MAX-ACCESS read-only
			STATUS current
			DESCRIPTION
				"Released IU_10GE8 NOS image revision on SFU."
			::= { sleSlotReleasedIUNosInfo 11 }

		
		-- 1.3.6.1.4.1.6296.101.2.11.4.12
		sleSlotReleasedIU10GE8NosSize OBJECT-TYPE
			SYNTAX Integer32
			MAX-ACCESS read-only
			STATUS current
			DESCRIPTION
				"Released IU_10GE8 NOS image size on SFU."
			::= { sleSlotReleasedIUNosInfo 12 }

		
		-- 1.3.6.1.4.1.6296.101.2.11.4.13
		sleSlotReleasedIU10GEPON8NosVersion OBJECT-TYPE
			SYNTAX OCTET STRING
			MAX-ACCESS read-only
			STATUS current
			DESCRIPTION
				"Released IU_10GEPON8 NOS image version on SFU."
			::= { sleSlotReleasedIUNosInfo 13 }

		
		-- 1.3.6.1.4.1.6296.101.2.11.4.14
		sleSlotReleasedIU10GEPON8NosRevision OBJECT-TYPE
			SYNTAX OCTET STRING
			MAX-ACCESS read-only
			STATUS current
			DESCRIPTION
				"Released IU_10GEPON8 NOS image revision on SFU."
			::= { sleSlotReleasedIUNosInfo 14 }

		
		-- 1.3.6.1.4.1.6296.101.2.11.4.15
		sleSlotReleasedIU10GEPON8NosSize OBJECT-TYPE
			SYNTAX Integer32
			MAX-ACCESS read-only
			STATUS current
			DESCRIPTION
				"Released IU_10GEPON8 NOS image size on SFU."
			::= { sleSlotReleasedIUNosInfo 15 }

		
		-- 1.3.6.1.4.1.6296.101.2.11.4.16
		sleSlotReleasedIUGEPON8NosVersion OBJECT-TYPE
			SYNTAX OCTET STRING
			MAX-ACCESS read-only
			STATUS current
			DESCRIPTION
				"Released IU_GEPON8 NOS image version on SFU."
			::= { sleSlotReleasedIUNosInfo 16 }

		
		-- 1.3.6.1.4.1.6296.101.2.11.4.17
		sleSlotReleasedIUGEPON8NosRevision OBJECT-TYPE
			SYNTAX OCTET STRING
			MAX-ACCESS read-only
			STATUS current
			DESCRIPTION
				"Released IU_GEPON8 NOS image revision on SFU"
			::= { sleSlotReleasedIUNosInfo 17 }

		
		-- 1.3.6.1.4.1.6296.101.2.11.4.18
		sleSlotReleasedIUGEPON8NosSize OBJECT-TYPE
			SYNTAX Integer32
			MAX-ACCESS read-only
			STATUS current
			DESCRIPTION
				"Released IU_GEPON8 NOS image size on SFU."
			::= { sleSlotReleasedIUNosInfo 18 }

		
		-- 1.3.6.1.4.1.6296.101.2.11.5
		sleSlotPowerMon OBJECT IDENTIFIER ::= { sleSlot 5 }

		
--     1.3.6.1.4.1.6296.101.2.11.5.1
-- 1.3.6.1.4.1.6296.101.2.11.5.1
-- 1.3.6.1.4.1.6296.101.2.11.5.1
-- 1.3.6.1.4.1.6296.101.2.11.5.1
		-- 1.3.6.1.4.1.6296.101.2.11.5.1
		sleSlotPowerMonTable OBJECT-TYPE
			SYNTAX SEQUENCE OF SleSlotPowerMonEntry
			MAX-ACCESS not-accessible
			STATUS current
			DESCRIPTION
				"The Power-Monitoring table."
			::= { sleSlotPowerMon 1 }

		
--     1.3.6.1.4.1.6296.101.2.11.5.1.1
-- 1.3.6.1.4.1.6296.101.2.11.5.1.1
-- 1.3.6.1.4.1.6296.101.2.11.5.1.1
-- 1.3.6.1.4.1.6296.101.2.11.5.1.1
		-- 1.3.6.1.4.1.6296.101.2.11.5.1.1
		sleSlotPowerMonEntry OBJECT-TYPE
			SYNTAX SleSlotPowerMonEntry
			MAX-ACCESS not-accessible
			STATUS current
			DESCRIPTION
				"The Power-Monitoring entry."
			INDEX { sleSlotSystemIndex, sleSlotPowerMonIndex }
			::= { sleSlotPowerMonTable 1 }

		
		SleSlotPowerMonEntry ::=
			SEQUENCE { 
				sleSlotPowerMonIndex
					INTEGER,
				sleSlotPowerMonStatus
					INTEGER,
				sleSlotPowerMonVoltage
					Gauge32
			 }

--     1.3.6.1.4.1.6296.101.2.11.5.1.1.1
-- 1.3.6.1.4.1.6296.101.2.11.5.1.1.1
-- 1.3.6.1.4.1.6296.101.2.11.5.1.1.1
-- 1.3.6.1.4.1.6296.101.2.11.5.1.1.1
		-- 1.3.6.1.4.1.6296.101.2.11.5.1.1.1
		sleSlotPowerMonIndex OBJECT-TYPE
			SYNTAX INTEGER (1..255)
			MAX-ACCESS read-only
			STATUS current
			DESCRIPTION
				"The physical index of power-monitoring object."
			::= { sleSlotPowerMonEntry 1 }

		
--     1.3.6.1.4.1.6296.101.2.11.5.1.1.2
-- 1.3.6.1.4.1.6296.101.2.11.5.1.1.2
-- 1.3.6.1.4.1.6296.101.2.11.5.1.1.2
-- 1.3.6.1.4.1.6296.101.2.11.5.1.1.2
		-- 1.3.6.1.4.1.6296.101.2.11.5.1.1.2
		sleSlotPowerMonStatus OBJECT-TYPE
			SYNTAX INTEGER
				{
				unknown(1),
				good(2),
				bad(3),
				over(4),
				under(5),
				overUnder(6)
				}
			MAX-ACCESS read-only
			STATUS current
			DESCRIPTION
				"The monitoring status of power-monitoring object."
			::= { sleSlotPowerMonEntry 2 }

		
--     1.3.6.1.4.1.6296.101.2.11.5.1.1.3
-- 1.3.6.1.4.1.6296.101.2.11.5.1.1.3
-- 1.3.6.1.4.1.6296.101.2.11.5.1.1.3
-- 1.3.6.1.4.1.6296.101.2.11.5.1.1.3
		-- 1.3.6.1.4.1.6296.101.2.11.5.1.1.3
		sleSlotPowerMonVoltage OBJECT-TYPE
			SYNTAX Gauge32
			UNITS "0.1v"
			MAX-ACCESS read-only
			STATUS current
			DESCRIPTION
				"The voltage value of power-monitoring object.
				value 10000(1000v) indicate that FUSE."
			::= { sleSlotPowerMonEntry 3 }

		
		-- 1.3.6.1.4.1.6296.101.2.11.6
		sleSlotAiu OBJECT IDENTIFIER ::= { sleSlot 6 }

		
--  1.3.6.1.4.1.6296.101.2.11.6.1
		-- 1.3.6.1.4.1.6296.101.2.11.6.1
		sleSlotAiuRunStatus OBJECT-TYPE
			SYNTAX INTEGER
				{
				off(0),
				on(1)
				}
			MAX-ACCESS read-only
			STATUS current
			DESCRIPTION
				"The slot AIU run status."
			::= { sleSlotAiu 1 }

		
--  1.3.6.1.4.1.6296.101.2.11.6.2
		-- 1.3.6.1.4.1.6296.101.2.11.6.2
		sleSlotAiuAlarmStatus OBJECT-TYPE
			SYNTAX INTEGER
				{
				off(0),
				on(1)
				}
			MAX-ACCESS read-only
			STATUS current
			DESCRIPTION
				"The slot AIU alarm status."
			::= { sleSlotAiu 2 }

		
		-- 1.3.6.1.4.1.6296.101.2.11.7
		sleSlotProtection OBJECT IDENTIFIER ::= { sleSlot 7 }

		
		-- 1.3.6.1.4.1.6296.101.2.11.7.1
		sleSlotProtectionBase OBJECT IDENTIFIER ::= { sleSlotProtection 1 }

		
		-- 1.3.6.1.4.1.6296.101.2.11.7.1.1
		sleSlotProtectionInfo OBJECT IDENTIFIER ::= { sleSlotProtectionBase 1 }

		
		-- 1.3.6.1.4.1.6296.101.2.11.7.1.1.1
		sleSlotProtectionSystemStatus OBJECT-TYPE
			SYNTAX INTEGER
				{
				enable(1),
				disable(2)
				}
			MAX-ACCESS read-only
			STATUS current
			DESCRIPTION
				"The system admin status(enable or disable) of overtemperature shutdown function."
			::= { sleSlotProtectionInfo 1 }

		
		-- 1.3.6.1.4.1.6296.101.2.11.7.1.1.2
		sleSlotProtectionSystemThreshold OBJECT-TYPE
			SYNTAX Integer32
			MAX-ACCESS read-only
			STATUS current
			DESCRIPTION
				"The system admin threshold of overtemperature shutdown function."
			::= { sleSlotProtectionInfo 2 }

		
		-- 1.3.6.1.4.1.6296.101.2.11.7.1.1.3
		sleSlotProtectionIUPowerStatus OBJECT-TYPE
			SYNTAX INTEGER
				{
				enable(1),
				disable(2)
				}
			MAX-ACCESS read-write
			STATUS current
			DESCRIPTION
				"The slot power shutdown status"
			::= { sleSlotProtectionInfo 3 }

		
		-- 1.3.6.1.4.1.6296.101.2.11.7.1.2
		sleSlotProtectionControl OBJECT IDENTIFIER ::= { sleSlotProtectionBase 2 }

		
		-- 1.3.6.1.4.1.6296.101.2.11.7.1.2.1
		sleSlotProtectionControlRequest OBJECT-TYPE
			SYNTAX INTEGER
				{
				setSlotProtectionSystemStatus(1),
				setSlotProtectionSystemThresh(2),
				setslotProtectionIUPowerStatus(3)
				}
			MAX-ACCESS read-write
			STATUS current
			DESCRIPTION
				"The request of a user command"
			::= { sleSlotProtectionControl 1 }

		
		-- 1.3.6.1.4.1.6296.101.2.11.7.1.2.2
		sleSlotProtectionControlStatus OBJECT-TYPE
			SYNTAX SleControlStatusType
			MAX-ACCESS read-only
			STATUS current
			DESCRIPTION
				"The status of user command"
			::= { sleSlotProtectionControl 2 }

		
		-- 1.3.6.1.4.1.6296.101.2.11.7.1.2.3
		sleSlotProtectionControlTimer OBJECT-TYPE
			SYNTAX Gauge32
			MAX-ACCESS read-write
			STATUS current
			DESCRIPTION
				"The maximum time for the manager for a long running user command"
			::= { sleSlotProtectionControl 3 }

		
		-- 1.3.6.1.4.1.6296.101.2.11.7.1.2.4
		sleSlotProtectionControlTimeStamp OBJECT-TYPE
			SYNTAX TimeTicks
			MAX-ACCESS read-only
			STATUS current
			DESCRIPTION
				"The time stamp of the last command(end of command)"
			::= { sleSlotProtectionControl 4 }

		
		-- 1.3.6.1.4.1.6296.101.2.11.7.1.2.5
		sleSlotProtectionControlReqResult OBJECT-TYPE
			SYNTAX SleControlRequestResultType
			MAX-ACCESS read-only
			STATUS current
			DESCRIPTION
				"The result of the last user command"
			::= { sleSlotProtectionControl 5 }

		
		-- 1.3.6.1.4.1.6296.101.2.11.7.1.2.6
		sleSlotProtectionControlSystemStatus OBJECT-TYPE
			SYNTAX INTEGER
				{
				enable(1),
				disable(2)
				}
			MAX-ACCESS read-write
			STATUS current
			DESCRIPTION
				"The system admin status(enable or disable) of overtemperature shutdown function."
			::= { sleSlotProtectionControl 6 }

		
		-- 1.3.6.1.4.1.6296.101.2.11.7.1.2.7
		sleSlotProtectionControlSystemThreshold OBJECT-TYPE
			SYNTAX Integer32
			MAX-ACCESS read-write
			STATUS current
			DESCRIPTION
				"The system admin threshold of overtemperature shutdown function."
			::= { sleSlotProtectionControl 7 }

		
		-- 1.3.6.1.4.1.6296.101.2.11.7.1.2.8
		sleSlotProtectionControlIUPowerStatus OBJECT-TYPE
			SYNTAX INTEGER
				{
				enable(1),
				disable(2)
				}
			MAX-ACCESS read-write
			STATUS current
			DESCRIPTION
				"The slot power shutdown status"
			::= { sleSlotProtectionControl 8 }

		
		-- 1.3.6.1.4.1.6296.101.2.11.7.1.3
		sleSlotProtectionNotification OBJECT IDENTIFIER ::= { sleSlotProtectionBase 3 }

		
		-- 1.3.6.1.4.1.6296.101.2.11.7.1.3.1
		sleSlotProtectionSystemStatusChanged NOTIFICATION-TYPE
			OBJECTS { sleSlotProtectionControlRequest, sleSlotProtectionControlTimeStamp, sleSlotProtectionControlReqResult, sleSlotProtectionControlSystemStatus }
			STATUS current
			DESCRIPTION 
				"Description."
			::= { sleSlotProtectionNotification 1 }

		
		-- 1.3.6.1.4.1.6296.101.2.11.7.1.3.2
		sleSlotProtectionSystemThreshChanged NOTIFICATION-TYPE
			OBJECTS { sleSlotProtectionControlRequest, sleSlotProtectionControlTimeStamp, sleSlotProtectionControlReqResult, sleSlotProtectionControlSystemThreshold }
			STATUS current
			DESCRIPTION 
				"Description."
			::= { sleSlotProtectionNotification 2 }

		
		-- 1.3.6.1.4.1.6296.101.2.11.7.1.3.3
		sleSlotProtectionIUPowerStatusChanged NOTIFICATION-TYPE
			OBJECTS { sleSlotProtectionControlRequest, sleSlotProtectionControlTimeStamp, sleSlotProtectionControlReqResult, sleSlotProtectionControlIUPowerStatus }
			STATUS current
			DESCRIPTION 
				"Description."
			::= { sleSlotProtectionNotification 3 }

		
		-- 1.3.6.1.4.1.6296.101.2.11.7.2
		sleSlotProtectionIU OBJECT IDENTIFIER ::= { sleSlotProtection 2 }

		
		-- 1.3.6.1.4.1.6296.101.2.11.7.2.1
		sleSlotProtectionIUTable OBJECT-TYPE
			SYNTAX SEQUENCE OF SleSlotProtectionIUEntry
			MAX-ACCESS not-accessible
			STATUS current
			DESCRIPTION
				"Description."
			::= { sleSlotProtectionIU 1 }

		
		-- 1.3.6.1.4.1.6296.101.2.11.7.2.1.1
		sleSlotProtectionIUEntry OBJECT-TYPE
			SYNTAX SleSlotProtectionIUEntry
			MAX-ACCESS not-accessible
			STATUS current
			DESCRIPTION
				"Description."
			AUGMENTS { sleSlotSystemInfoEntry }
			::= { sleSlotProtectionIUTable 1 }

		
		SleSlotProtectionIUEntry ::=
			SEQUENCE { 
				sleSlotProtectionIUTemperHighThresh
					Integer32,
				sleSlotProtectionIUTemperLowThresh
					Integer32,
				sleSlotProtectionIUPowerThresh
					Integer32,
				sleSlotProtectionIUTemper
					Integer32
			 }

		-- 1.3.6.1.4.1.6296.101.2.11.7.2.1.1.1
		sleSlotProtectionIUTemperHighThresh OBJECT-TYPE
			SYNTAX Integer32 (1..65535)
			MAX-ACCESS read-only
			STATUS current
			DESCRIPTION
				"The Slot temperature High-threshold of overtemperature alarm"
			::= { sleSlotProtectionIUEntry 1 }

		
		-- 1.3.6.1.4.1.6296.101.2.11.7.2.1.1.2
		sleSlotProtectionIUTemperLowThresh OBJECT-TYPE
			SYNTAX Integer32 (1..65535)
			MAX-ACCESS read-only
			STATUS current
			DESCRIPTION
				"The Slot temperature Low-threshold of overtemperature alarm"
			::= { sleSlotProtectionIUEntry 2 }

		
		-- 1.3.6.1.4.1.6296.101.2.11.7.2.1.1.3
		sleSlotProtectionIUPowerThresh OBJECT-TYPE
			SYNTAX Integer32 (1..65535)
			MAX-ACCESS read-only
			STATUS current
			DESCRIPTION
				"The Slot temperature threshold of overtemperature power shutdown."
			::= { sleSlotProtectionIUEntry 3 }

		
		-- 1.3.6.1.4.1.6296.101.2.11.7.2.1.1.4
		sleSlotProtectionIUTemper OBJECT-TYPE
			SYNTAX Integer32 (1..65535)
			MAX-ACCESS read-only
			STATUS current
			DESCRIPTION
				"The Slot temperature."
			::= { sleSlotProtectionIUEntry 4 }

		
		-- 1.3.6.1.4.1.6296.101.2.11.7.2.2
		sleSlotProtectionIUControl OBJECT IDENTIFIER ::= { sleSlotProtectionIU 2 }

		
		-- 1.3.6.1.4.1.6296.101.2.11.7.2.2.1
		sleSlotProtectionIUControlRequest OBJECT-TYPE
			SYNTAX INTEGER
				{
				setSlotTempThreshold(1),
				setSlotPowerThresh(2)
				}
			MAX-ACCESS read-write
			STATUS current
			DESCRIPTION
				"The request of a user command"
			::= { sleSlotProtectionIUControl 1 }

		
		-- 1.3.6.1.4.1.6296.101.2.11.7.2.2.2
		sleSlotProtectionIUControlStatus OBJECT-TYPE
			SYNTAX SleControlStatusType
			MAX-ACCESS read-only
			STATUS current
			DESCRIPTION
				"The status of user command"
			::= { sleSlotProtectionIUControl 2 }

		
		-- 1.3.6.1.4.1.6296.101.2.11.7.2.2.3
		sleSlotProtectionIUControlTimer OBJECT-TYPE
			SYNTAX Gauge32
			MAX-ACCESS read-write
			STATUS current
			DESCRIPTION
				"The maximum time for the manager for a long running user command"
			::= { sleSlotProtectionIUControl 3 }

		
		-- 1.3.6.1.4.1.6296.101.2.11.7.2.2.4
		sleSlotProtectionIUControlTimeStamp OBJECT-TYPE
			SYNTAX TimeTicks
			MAX-ACCESS read-only
			STATUS current
			DESCRIPTION
				"The time stamp of the last command(end of command)"
			::= { sleSlotProtectionIUControl 4 }

		
		-- 1.3.6.1.4.1.6296.101.2.11.7.2.2.5
		sleSlotProtectionIUControlReqResult OBJECT-TYPE
			SYNTAX SleControlRequestResultType
			MAX-ACCESS read-only
			STATUS current
			DESCRIPTION
				"The result of the last user command"
			::= { sleSlotProtectionIUControl 5 }

		
		-- 1.3.6.1.4.1.6296.101.2.11.7.2.2.6
		sleSlotProtectionIUControlindex OBJECT-TYPE
			SYNTAX Integer32
			MAX-ACCESS read-write
			STATUS current
			DESCRIPTION
				"the slot index"
			::= { sleSlotProtectionIUControl 6 }

		
		-- 1.3.6.1.4.1.6296.101.2.11.7.2.2.7
		sleSlotProtectionIUControlTemperHighThresh OBJECT-TYPE
			SYNTAX Integer32
			MAX-ACCESS read-write
			STATUS current
			DESCRIPTION
				"The Slot temperature High-threshold of overtemperature alarm"
			::= { sleSlotProtectionIUControl 7 }

		
		-- 1.3.6.1.4.1.6296.101.2.11.7.2.2.8
		sleSlotProtectionIUControlTemperLowThresh OBJECT-TYPE
			SYNTAX Integer32
			MAX-ACCESS read-write
			STATUS current
			DESCRIPTION
				"The Slot temperature Low-threshold of overtemperature alarm"
			::= { sleSlotProtectionIUControl 8 }

		
		-- 1.3.6.1.4.1.6296.101.2.11.7.2.2.9
		sleSlotProtectionIUControlPowerThresh OBJECT-TYPE
			SYNTAX Integer32
			MAX-ACCESS read-write
			STATUS current
			DESCRIPTION
				"The Slot temperature threshold of overtemperature power shutdown."
			::= { sleSlotProtectionIUControl 9 }

		
		-- 1.3.6.1.4.1.6296.101.2.11.7.2.3
		sleSlotProtectionIUNotification OBJECT IDENTIFIER ::= { sleSlotProtectionIU 3 }

		
		-- 1.3.6.1.4.1.6296.101.2.11.7.2.3.1
		sleSlotProtectionIUTemperThreshChanged NOTIFICATION-TYPE
			OBJECTS { sleSlotProtectionIUControlRequest, sleSlotProtectionIUControlTimeStamp, sleSlotProtectionIUControlReqResult, sleSlotProtectionIUControlTemperHighThresh, sleSlotProtectionIUControlTemperLowThresh, 
				sleSlotProtectionIUControlindex }
			STATUS current
			DESCRIPTION 
				"Description."
			::= { sleSlotProtectionIUNotification 1 }

		
		-- 1.3.6.1.4.1.6296.101.2.11.7.2.3.2
		sleSlotProtectionIUPowerThreshChanged NOTIFICATION-TYPE
			OBJECTS { sleSlotProtectionIUControlRequest, sleSlotProtectionIUControlTimeStamp, sleSlotProtectionIUControlReqResult, sleSlotProtectionIUControlindex, sleSlotProtectionIUControlPowerThresh
				 }
			STATUS current
			DESCRIPTION 
				"Description."
			::= { sleSlotProtectionIUNotification 2 }

		
		-- 1.3.6.1.4.1.6296.101.2.12
		sleRF OBJECT IDENTIFIER ::= { sleDevice 12 }

		
--     1.3.6.1.4.1.6296.101.2.12.1
-- 1.3.6.1.4.1.6296.101.2.12.1
-- 1.3.6.1.4.1.6296.101.2.12.1
-- 1.3.6.1.4.1.6296.101.2.12.1
		-- 1.3.6.1.4.1.6296.101.2.12.1
		sleRfBaseInfo OBJECT IDENTIFIER ::= { sleRF 1 }

		
--     1.3.6.1.4.1.6296.101.2.12.1.1
-- 1.3.6.1.4.1.6296.101.2.12.1.1
-- 1.3.6.1.4.1.6296.101.2.12.1.1
-- 1.3.6.1.4.1.6296.101.2.12.1.1
		-- 1.3.6.1.4.1.6296.101.2.12.1.1
		sleRfConnectStatus OBJECT-TYPE
			SYNTAX INTEGER
				{
				connect(1),
				disconnect(2)
				}
			MAX-ACCESS read-only
			STATUS current
			DESCRIPTION
				"The RF connect status."
			::= { sleRfBaseInfo 1 }

		
--     1.3.6.1.4.1.6296.101.2.12.1.1
-- 1.3.6.1.4.1.6296.101.2.12.1.1
-- 1.3.6.1.4.1.6296.101.2.12.1.2
-- 1.3.6.1.4.1.6296.101.2.12.1.2
		-- 1.3.6.1.4.1.6296.101.2.12.1.2
		sleRfPowerStatus OBJECT-TYPE
			SYNTAX INTEGER
				{
				poweroff(0),
				poweron(1)
				}
			MAX-ACCESS read-only
			STATUS current
			DESCRIPTION
				"The RF power status."
			::= { sleRfBaseInfo 2 }

		
--   1.3.6.1.4.1.6296.101.2.12.1.3
-- 1.3.6.1.4.1.6296.101.2.12.1.3
		-- 1.3.6.1.4.1.6296.101.2.12.1.3
		sleRfEthertype OBJECT-TYPE
			SYNTAX OCTET STRING
			MAX-ACCESS read-only
			STATUS current
			DESCRIPTION
				"The RF ethertype."
			::= { sleRfBaseInfo 3 }

		
--   1.3.6.1.4.1.6296.101.2.12.1.4
-- 1.3.6.1.4.1.6296.101.2.12.1.4
		-- 1.3.6.1.4.1.6296.101.2.12.1.4
		sleRfSrcAddress OBJECT-TYPE
			SYNTAX OCTET STRING
			MAX-ACCESS read-only
			STATUS current
			DESCRIPTION
				"The RF source address."
			::= { sleRfBaseInfo 4 }

		
--   1.3.6.1.4.1.6296.101.2.12.1.5
-- 1.3.6.1.4.1.6296.101.2.12.1.5
		-- 1.3.6.1.4.1.6296.101.2.12.1.5
		sleRfDesAddress OBJECT-TYPE
			SYNTAX OCTET STRING
			MAX-ACCESS read-only
			STATUS current
			DESCRIPTION
				"The RF destination address."
			::= { sleRfBaseInfo 5 }

		
--   1.3.6.1.4.1.6296.101.2.12.2
-- 1.3.6.1.4.1.6296.101.2.12.2
		-- 1.3.6.1.4.1.6296.101.2.12.2
		sleRfBaseControl OBJECT IDENTIFIER ::= { sleRF 2 }

		
--   1.3.6.1.4.1.6296.101.2.12.2.1
-- 1.3.6.1.4.1.6296.101.2.12.2.1
		-- 1.3.6.1.4.1.6296.101.2.12.2.1
		sleRfBaseControlRequest OBJECT-TYPE
			SYNTAX INTEGER
				{
				setRfEthertype(1),
				resetRfEthertype(2)
				}
			MAX-ACCESS read-write
			STATUS current
			DESCRIPTION
				"The request of a user command."
			::= { sleRfBaseControl 1 }

		
--   1.3.6.1.4.1.6296.101.2.12.2.2
-- 1.3.6.1.4.1.6296.101.2.12.2.2
		-- 1.3.6.1.4.1.6296.101.2.12.2.2
		sleRfBaseControlStatus OBJECT-TYPE
			SYNTAX SleControlStatusType
			MAX-ACCESS read-only
			STATUS current
			DESCRIPTION
				"The status of user command."
			::= { sleRfBaseControl 2 }

		
--   1.3.6.1.4.1.6296.101.2.12.2.3
-- 1.3.6.1.4.1.6296.101.2.12.2.3
		-- 1.3.6.1.4.1.6296.101.2.12.2.3
		sleRfBaseControlTimer OBJECT-TYPE
			SYNTAX Integer32
			MAX-ACCESS read-write
			STATUS current
			DESCRIPTION
				"The maximum time for the manager for a long running user command."
			::= { sleRfBaseControl 3 }

		
--   1.3.6.1.4.1.6296.101.2.12.2.4
-- 1.3.6.1.4.1.6296.101.2.12.2.4
		-- 1.3.6.1.4.1.6296.101.2.12.2.4
		sleRfBaseControlTimeStamp OBJECT-TYPE
			SYNTAX TimeTicks
			MAX-ACCESS read-only
			STATUS current
			DESCRIPTION
				"The time stamp of the last command(end of command)."
			::= { sleRfBaseControl 4 }

		
--   1.3.6.1.4.1.6296.101.2.12.2.5
-- 1.3.6.1.4.1.6296.101.2.12.2.5
		-- 1.3.6.1.4.1.6296.101.2.12.2.5
		sleRfBaseControlReqResult OBJECT-TYPE
			SYNTAX SleControlRequestResultType
			MAX-ACCESS read-only
			STATUS current
			DESCRIPTION
				"The result of user command."
			::= { sleRfBaseControl 5 }

		
--   1.3.6.1.4.1.6296.101.2.12.2.6
-- 1.3.6.1.4.1.6296.101.2.12.2.6
		-- 1.3.6.1.4.1.6296.101.2.12.2.6
		sleRfBaseControlRfEthertype OBJECT-TYPE
			SYNTAX OCTET STRING
			MAX-ACCESS read-write
			STATUS current
			DESCRIPTION
				"The Rf ethertype ,the format is 0xXXXX, default value is 0x8864."
			::= { sleRfBaseControl 6 }

		
--   1.3.6.1.4.1.6296.101.2.12.3
-- 1.3.6.1.4.1.6296.101.2.12.3
		-- 1.3.6.1.4.1.6296.101.2.12.3
		sleRfBaseNotification OBJECT IDENTIFIER ::= { sleRF 3 }

		
--   1.3.6.1.4.1.6296.101.2.12.3.1
-- 1.3.6.1.4.1.6296.101.2.12.3.1
		-- 1.3.6.1.4.1.6296.101.2.12.3.1
		sleRFBaseEthertypeChanged NOTIFICATION-TYPE
			OBJECTS { sleRfBaseControlRequest, sleRfBaseControlTimeStamp, sleRfBaseControlReqResult, sleRfBaseControlRfEthertype }
			STATUS current
			DESCRIPTION 
				"Description."
			::= { sleRfBaseNotification 1 }

		
--   1.3.6.1.4.1.6296.101.2.12.3.2
-- 1.3.6.1.4.1.6296.101.2.12.3.2
		-- 1.3.6.1.4.1.6296.101.2.12.3.2
		sleRFBaseEthertypeResetChanged NOTIFICATION-TYPE
			OBJECTS { sleRfBaseControlRequest, sleRfBaseControlTimeStamp, sleRfBaseControlReqResult, sleRfBaseControlRfEthertype }
			STATUS current
			DESCRIPTION 
				"Description."
			::= { sleRfBaseNotification 2 }

		
--   1.3.6.1.4.1.6296.101.2.12.4
-- 1.3.6.1.4.1.6296.101.2.12.4
		-- 1.3.6.1.4.1.6296.101.2.12.4
		sleRfPortTable OBJECT-TYPE
			SYNTAX SEQUENCE OF SleRfPortEntry
			MAX-ACCESS not-accessible
			STATUS current
			DESCRIPTION
				"Description."
			::= { sleRF 4 }

		
--   1.3.6.1.4.1.6296.101.2.12.4.1
-- 1.3.6.1.4.1.6296.101.2.12.4.1
-- 1.3.6.1.4.1.6296.101.2.12.4.1
		-- 1.3.6.1.4.1.6296.101.2.12.4.1
		sleRfPortEntry OBJECT-TYPE
			SYNTAX SleRfPortEntry
			MAX-ACCESS not-accessible
			STATUS current
			DESCRIPTION
				"Description."
			INDEX { sleRfPortIndex }
			::= { sleRfPortTable 1 }

		
		SleRfPortEntry ::=
			SEQUENCE { 
				sleRfPortIndex
					INTEGER,
				sleRfPortAdminStatus
					INTEGER,
				sleRfPortOperStatus
					INTEGER
			 }

--   1.3.6.1.4.1.6296.101.2.12.4.1.1
-- 1.3.6.1.4.1.6296.101.2.12.4.1.1
		-- 1.3.6.1.4.1.6296.101.2.12.4.1.1
		sleRfPortIndex OBJECT-TYPE
			SYNTAX INTEGER (1..256)
			MAX-ACCESS read-write
			STATUS current
			DESCRIPTION
				"The RF port index."
			::= { sleRfPortEntry 1 }

		
--   1.3.6.1.4.1.6296.101.2.12.4.1.2
-- 1.3.6.1.4.1.6296.101.2.12.4.1.2
		-- 1.3.6.1.4.1.6296.101.2.12.4.1.2
		sleRfPortAdminStatus OBJECT-TYPE
			SYNTAX INTEGER
				{
				enable(1),
				disable(2),
				na(255)
				}
			MAX-ACCESS read-write
			STATUS current
			DESCRIPTION
				"The RF port adminStatus."
			::= { sleRfPortEntry 2 }

		
--   1.3.6.1.4.1.6296.101.2.12.4.1.3
-- 1.3.6.1.4.1.6296.101.2.12.4.1.3
		-- 1.3.6.1.4.1.6296.101.2.12.4.1.3
		sleRfPortOperStatus OBJECT-TYPE
			SYNTAX INTEGER
				{
				enable(1),
				disable(2),
				na(255)
				}
			MAX-ACCESS read-write
			STATUS current
			DESCRIPTION
				"The RF port operStatus."
			::= { sleRfPortEntry 3 }

		
--   1.3.6.1.4.1.6296.101.2.12.5
-- 1.3.6.1.4.1.6296.101.2.12.5
		-- 1.3.6.1.4.1.6296.101.2.12.5
		sleRFPortControl OBJECT IDENTIFIER ::= { sleRF 5 }

		
--   1.3.6.1.4.1.6296.101.2.12.5.1
-- 1.3.6.1.4.1.6296.101.2.12.5.1
		-- 1.3.6.1.4.1.6296.101.2.12.5.1
		sleRfPortControlRequest OBJECT-TYPE
			SYNTAX INTEGER { setRfPortStatus(1) }
			MAX-ACCESS read-write
			STATUS current
			DESCRIPTION
				"The request of a user command."
			::= { sleRFPortControl 1 }

		
--   1.3.6.1.4.1.6296.101.2.12.5.2
-- 1.3.6.1.4.1.6296.101.2.12.5.2
		-- 1.3.6.1.4.1.6296.101.2.12.5.2
		sleRfPortControlStatus OBJECT-TYPE
			SYNTAX SleControlStatusType
			MAX-ACCESS read-only
			STATUS current
			DESCRIPTION
				"The status of user command."
			::= { sleRFPortControl 2 }

		
--   1.3.6.1.4.1.6296.101.2.12.5.3
-- 1.3.6.1.4.1.6296.101.2.12.5.3
		-- 1.3.6.1.4.1.6296.101.2.12.5.3
		sleRfPortControlTimer OBJECT-TYPE
			SYNTAX Integer32
			MAX-ACCESS read-write
			STATUS current
			DESCRIPTION
				"The maximum time for the manager for a long running user command."
			::= { sleRFPortControl 3 }

		
--   1.3.6.1.4.1.6296.101.2.12.5.4
-- 1.3.6.1.4.1.6296.101.2.12.5.4
		-- 1.3.6.1.4.1.6296.101.2.12.5.4
		sleRfPortControlTimeStamp OBJECT-TYPE
			SYNTAX TimeTicks
			MAX-ACCESS read-only
			STATUS current
			DESCRIPTION
				"The time stamp of the last command(end of command)."
			::= { sleRFPortControl 4 }

		
--   1.3.6.1.4.1.6296.101.2.12.5.5
-- 1.3.6.1.4.1.6296.101.2.12.5.5
		-- 1.3.6.1.4.1.6296.101.2.12.5.5
		sleRfPortControlReqResult OBJECT-TYPE
			SYNTAX SleControlRequestResultType
			MAX-ACCESS read-only
			STATUS current
			DESCRIPTION
				"The result of user command.
				"
			::= { sleRFPortControl 5 }

		
--   1.3.6.1.4.1.6296.101.2.12.5.6
-- 1.3.6.1.4.1.6296.101.2.12.5.6
		-- 1.3.6.1.4.1.6296.101.2.12.5.6
		sleRfPortControlIndex OBJECT-TYPE
			SYNTAX Integer32 (1..8)
			MAX-ACCESS read-write
			STATUS current
			DESCRIPTION
				"The RF port index <1-8>."
			::= { sleRFPortControl 6 }

		
--   1.3.6.1.4.1.6296.101.2.12.5.7
-- 1.3.6.1.4.1.6296.101.2.12.5.7
		-- 1.3.6.1.4.1.6296.101.2.12.5.7
		sleRfPortControlAdminStatus OBJECT-TYPE
			SYNTAX INTEGER
				{
				enable(1),
				disable(2)
				}
			MAX-ACCESS read-write
			STATUS current
			DESCRIPTION
				"The RF port adminStatus."
			::= { sleRFPortControl 7 }

		
--   1.3.6.1.4.1.6296.101.2.12.6
-- 1.3.6.1.4.1.6296.101.2.12.6
		-- 1.3.6.1.4.1.6296.101.2.12.6
		sleRFPortNotification OBJECT IDENTIFIER ::= { sleRF 6 }

		
--   1.3.6.1.4.1.6296.101.2.12.6.1
-- 1.3.6.1.4.1.6296.101.2.12.6.1
		-- 1.3.6.1.4.1.6296.101.2.12.6.1
		sleRfPortStatusChanged NOTIFICATION-TYPE
			OBJECTS { sleRfPortControlRequest, sleRfPortControlTimeStamp, sleRfPortControlReqResult, sleRfPortControlIndex, sleRfPortControlAdminStatus
				 }
			STATUS current
			DESCRIPTION 
				"Description."
			::= { sleRFPortNotification 1 }

		
		-- 1.3.6.1.4.1.6296.101.2.13
		sleEnvironmentMonitor OBJECT IDENTIFIER ::= { sleDevice 13 }

		
--  1.3.6.1.4.1.6296.101.2.13.1
		-- 1.3.6.1.4.1.6296.101.2.13.1
		sleEMTable OBJECT-TYPE
			SYNTAX SEQUENCE OF SleEMEntry
			MAX-ACCESS not-accessible
			STATUS current
			DESCRIPTION
				"Description."
			::= { sleEnvironmentMonitor 1 }

		
--  1.3.6.1.4.1.6296.101.2.13.1.1
		-- 1.3.6.1.4.1.6296.101.2.13.1.1
		sleEMEntry OBJECT-TYPE
			SYNTAX SleEMEntry
			MAX-ACCESS not-accessible
			STATUS current
			DESCRIPTION
				"Description."
			INDEX { sleEMInputIndex }
			::= { sleEMTable 1 }

		
		SleEMEntry ::=
			SEQUENCE { 
				sleEMInputIndex
					Integer32,
				sleEMAlarmString
					OCTET STRING,
				sleEMAlarmSeverity
					INTEGER,
				sleEMmode
					INTEGER
			 }

--  1.3.6.1.4.1.6296.101.2.13.1.1.1
		-- 1.3.6.1.4.1.6296.101.2.13.1.1.1
		sleEMInputIndex OBJECT-TYPE
			SYNTAX Integer32 (1..4)
			MAX-ACCESS read-only
			STATUS current
			DESCRIPTION
				"The environment monitoring input index(1-4)."
			::= { sleEMEntry 1 }

		
--  1.3.6.1.4.1.6296.101.2.13.1.1.2
		-- 1.3.6.1.4.1.6296.101.2.13.1.1.2
		sleEMAlarmString OBJECT-TYPE
			SYNTAX OCTET STRING
			MAX-ACCESS read-only
			STATUS current
			DESCRIPTION
				"The alarm string"
			::= { sleEMEntry 2 }

		
--  1.3.6.1.4.1.6296.101.2.13.1.1.3
		-- 1.3.6.1.4.1.6296.101.2.13.1.1.3
		sleEMAlarmSeverity OBJECT-TYPE
			SYNTAX INTEGER
				{
				none(0),
				critical(1),
				major(2),
				minor(3),
				warning(4),
				intermediate(5)
				}
			MAX-ACCESS read-only
			STATUS current
			DESCRIPTION
				"The alarm severity."
			::= { sleEMEntry 3 }

		
--  1.3.6.1.4.1.6296.101.2.13.1.1.4
		-- 1.3.6.1.4.1.6296.101.2.13.1.1.4
		sleEMmode OBJECT-TYPE
			SYNTAX INTEGER
				{
				normalClose(0),
				normalOpen(1)
				}
			MAX-ACCESS read-only
			STATUS current
			DESCRIPTION
				"The environment monitoring mode.(default:normal-close)"
			::= { sleEMEntry 4 }

		
--  1.3.6.1.4.1.6296.101.2.13.2
		-- 1.3.6.1.4.1.6296.101.2.13.2
		sleEMControl OBJECT IDENTIFIER ::= { sleEnvironmentMonitor 2 }

		
--  1.3.6.1.4.1.6296.101.2.13.2.1
		-- 1.3.6.1.4.1.6296.101.2.13.2.1
		sleEMControlRequest OBJECT-TYPE
			SYNTAX INTEGER
				{
				setEM(1),
				delEM(2)
				}
			MAX-ACCESS read-write
			STATUS current
			DESCRIPTION
				"The request of a user command."
			::= { sleEMControl 1 }

		
--    1.3.6.1.4.1.6296.101.2.12.3.2
-- 1.3.6.1.4.1.6296.101.2.12.3.2
-- 1.3.6.1.4.1.6296.101.2.13.2.2
		-- 1.3.6.1.4.1.6296.101.2.13.2.2
		sleEMControlStatus OBJECT-TYPE
			SYNTAX SleControlStatusType
			MAX-ACCESS read-only
			STATUS current
			DESCRIPTION
				"Description."
			::= { sleEMControl 2 }

		
--  1.3.6.1.4.1.6296.101.2.13.2.3
		-- 1.3.6.1.4.1.6296.101.2.13.2.3
		sleEMControlTimer OBJECT-TYPE
			SYNTAX Gauge32
			MAX-ACCESS read-only
			STATUS current
			DESCRIPTION
				"The maximum time for the manager for a long running user command.
				Apply your setting.
				"
			::= { sleEMControl 3 }

		
--  1.3.6.1.4.1.6296.101.2.13.2.4
		-- 1.3.6.1.4.1.6296.101.2.13.2.4
		sleEMControlTimeStamp OBJECT-TYPE
			SYNTAX TimeTicks
			MAX-ACCESS read-only
			STATUS current
			DESCRIPTION
				"Description."
			::= { sleEMControl 4 }

		
--  1.3.6.1.4.1.6296.101.2.13.2.5
		-- 1.3.6.1.4.1.6296.101.2.13.2.5
		sleEMControlReqResult OBJECT-TYPE
			SYNTAX SleControlRequestResultType
			MAX-ACCESS read-only
			STATUS current
			DESCRIPTION
				"Description."
			::= { sleEMControl 5 }

		
--  1.3.6.1.4.1.6296.101.2.13.2.6
		-- 1.3.6.1.4.1.6296.101.2.13.2.6
		sleEMControlInputIndex OBJECT-TYPE
			SYNTAX Integer32 (1..4)
			MAX-ACCESS read-write
			STATUS current
			DESCRIPTION
				"The environment monitoring input index(1-4)."
			::= { sleEMControl 6 }

		
--  1.3.6.1.4.1.6296.101.2.13.2.7
		-- 1.3.6.1.4.1.6296.101.2.13.2.7
		sleEMControlAlarmString OBJECT-TYPE
			SYNTAX OCTET STRING
			MAX-ACCESS read-write
			STATUS current
			DESCRIPTION
				"The alarm string"
			::= { sleEMControl 7 }

		
--  1.3.6.1.4.1.6296.101.2.13.2.8
		-- 1.3.6.1.4.1.6296.101.2.13.2.8
		sleEMControlAlarmSeverity OBJECT-TYPE
			SYNTAX INTEGER
				{
				none(0),
				critical(1),
				major(2),
				minor(3),
				warning(4),
				intermediate(5)
				}
			MAX-ACCESS read-write
			STATUS current
			DESCRIPTION
				"The alarm severity."
			::= { sleEMControl 8 }

		
--  1.3.6.1.4.1.6296.101.2.13.2.9
		-- 1.3.6.1.4.1.6296.101.2.13.2.9
		sleEMControlmode OBJECT-TYPE
			SYNTAX INTEGER
				{
				normalClose(0),
				normalOpen(1)
				}
			MAX-ACCESS read-write
			STATUS current
			DESCRIPTION
				"The environment monitoring mode.(default:normal-close)"
			::= { sleEMControl 9 }

		
--  1.3.6.1.4.1.6296.101.2.13.3
		-- 1.3.6.1.4.1.6296.101.2.13.3
		sleEMNotification OBJECT IDENTIFIER ::= { sleEnvironmentMonitor 3 }

		
--  1.3.6.1.4.1.6296.101.2.13.3.1
		-- 1.3.6.1.4.1.6296.101.2.13.3.1
		sleEMChanged NOTIFICATION-TYPE
			OBJECTS { sleEMControlRequest, sleEMControlTimeStamp, sleEMControlReqResult, sleEMControlInputIndex, sleEMControlAlarmString, 
				sleEMControlAlarmSeverity, sleEMControlmode }
			STATUS current
			DESCRIPTION 
				"Description."
			::= { sleEMNotification 1 }

		
--  1.3.6.1.4.1.6296.101.2.13.3.2
		-- 1.3.6.1.4.1.6296.101.2.13.3.2
		sleEMDeleted NOTIFICATION-TYPE
			OBJECTS { sleEMControlRequest, sleEMControlTimeStamp, sleEMControlReqResult, sleEMControlInputIndex }
			STATUS current
			DESCRIPTION 
				"Description."
			::= { sleEMNotification 2 }

		
		-- 1.3.6.1.4.1.6296.101.2.14
		sleBypass OBJECT IDENTIFIER ::= { sleDevice 14 }

		
		-- 1.3.6.1.4.1.6296.101.2.14.1
		sleBypassBase OBJECT IDENTIFIER ::= { sleBypass 1 }

		
		-- 1.3.6.1.4.1.6296.101.2.14.1.1
		sleBypassBaseInfo OBJECT IDENTIFIER ::= { sleBypassBase 1 }

		
		-- 1.3.6.1.4.1.6296.101.2.14.1.1.1
		sleBypassMode OBJECT-TYPE
			SYNTAX INTEGER
				{
				on(1),
				off(2),
				auto(3)
				}
			MAX-ACCESS read-only
			STATUS current
			DESCRIPTION
				"optic bypass mode"
			DEFVAL { 2 }
			::= { sleBypassBaseInfo 1 }

		
		-- 1.3.6.1.4.1.6296.101.2.14.1.1.2
		sleBypassStatus OBJECT-TYPE
			SYNTAX INTEGER
				{
				enable(1),
				disable(2)
				}
			MAX-ACCESS read-only
			STATUS current
			DESCRIPTION
				"optic bypass status
				"
			::= { sleBypassBaseInfo 2 }

		
		-- 1.3.6.1.4.1.6296.101.2.14.1.2
		sleBypassBaseControl OBJECT IDENTIFIER ::= { sleBypassBase 2 }

		
		-- 1.3.6.1.4.1.6296.101.2.14.1.2.1
		sleBypassBaseControlRequest OBJECT-TYPE
			SYNTAX INTEGER { setBypassMode(1) }
			MAX-ACCESS read-write
			STATUS current
			DESCRIPTION
				"Description."
			::= { sleBypassBaseControl 1 }

		
--   1.3.6.1.4.1.6296.101.2.12.2.2
-- 1.3.6.1.4.1.6296.101.2.12.2.2
		-- 1.3.6.1.4.1.6296.101.2.14.1.2.2
		sleBypassBaseControlStatus OBJECT-TYPE
			SYNTAX SleControlStatusType
			MAX-ACCESS read-only
			STATUS current
			DESCRIPTION
				"The status of user command."
			::= { sleBypassBaseControl 2 }

		
--   1.3.6.1.4.1.6296.101.2.12.2.3
-- 1.3.6.1.4.1.6296.101.2.12.2.3
		-- 1.3.6.1.4.1.6296.101.2.14.1.2.3
		sleBypassBaseControlTimer OBJECT-TYPE
			SYNTAX Integer32
			MAX-ACCESS read-write
			STATUS current
			DESCRIPTION
				"The maximum time for the manager for a long running user command."
			::= { sleBypassBaseControl 3 }

		
--   1.3.6.1.4.1.6296.101.2.12.2.4
-- 1.3.6.1.4.1.6296.101.2.12.2.4
		-- 1.3.6.1.4.1.6296.101.2.14.1.2.4
		sleBypassBaseControlTimeStamp OBJECT-TYPE
			SYNTAX TimeTicks
			MAX-ACCESS read-only
			STATUS current
			DESCRIPTION
				"The time stamp of the last command(end of command)."
			::= { sleBypassBaseControl 4 }

		
--   1.3.6.1.4.1.6296.101.2.12.2.5
-- 1.3.6.1.4.1.6296.101.2.12.2.5
		-- 1.3.6.1.4.1.6296.101.2.14.1.2.5
		sleBypassBaseControlReqResult OBJECT-TYPE
			SYNTAX SleControlRequestResultType
			MAX-ACCESS read-only
			STATUS current
			DESCRIPTION
				"The result of user command."
			::= { sleBypassBaseControl 5 }

		
		-- 1.3.6.1.4.1.6296.101.2.14.1.2.6
		sleBypassBaseControlMode OBJECT-TYPE
			SYNTAX INTEGER
				{
				on(1),
				off(2),
				auto(3)
				}
			MAX-ACCESS read-write
			STATUS current
			DESCRIPTION
				"optic bypass mode"
			::= { sleBypassBaseControl 6 }

		
		-- 1.3.6.1.4.1.6296.101.2.14.1.3
		sleBypassBaseNotification OBJECT IDENTIFIER ::= { sleBypassBase 3 }

		
		-- 1.3.6.1.4.1.6296.101.2.14.1.3.1
		sleBypassModeChanged NOTIFICATION-TYPE
			OBJECTS { sleBypassBaseControlRequest, sleBypassBaseControlTimeStamp, sleBypassBaseControlReqResult, sleBypassBaseControlMode }
			STATUS current
			DESCRIPTION 
				"setBypassMode(1)"
			::= { sleBypassBaseNotification 1 }

		
		-- 1.3.6.1.4.1.6296.101.2.14.2
		sleBypassOption OBJECT IDENTIFIER ::= { sleBypass 2 }

		
		-- 1.3.6.1.4.1.6296.101.2.14.2.1
		sleBypassOptionConnectivityTable OBJECT-TYPE
			SYNTAX SEQUENCE OF SleBypassOptionConnectivityEntry
			MAX-ACCESS not-accessible
			STATUS current
			DESCRIPTION
				"The connectivity option of bypass"
			::= { sleBypassOption 1 }

		
		-- 1.3.6.1.4.1.6296.101.2.14.2.1.1
		sleBypassOptionConnectivityEntry OBJECT-TYPE
			SYNTAX SleBypassOptionConnectivityEntry
			MAX-ACCESS not-accessible
			STATUS current
			DESCRIPTION
				"Description."
			INDEX { sleBypassOptionConnectivityAddress, sleBypassOptionConnectivityPort }
			::= { sleBypassOptionConnectivityTable 1 }

		
		SleBypassOptionConnectivityEntry ::=
			SEQUENCE { 
				sleBypassOptionConnectivityAddress
					IpAddress,
				sleBypassOptionConnectivityPort
					Integer32
			 }

		-- 1.3.6.1.4.1.6296.101.2.14.2.1.1.1
		sleBypassOptionConnectivityAddress OBJECT-TYPE
			SYNTAX IpAddress
			MAX-ACCESS read-only
			STATUS current
			DESCRIPTION
				"The target IP address of bypass health-checking"
			::= { sleBypassOptionConnectivityEntry 1 }

		
		-- 1.3.6.1.4.1.6296.101.2.14.2.1.1.2
		sleBypassOptionConnectivityPort OBJECT-TYPE
			SYNTAX Integer32 (1..65535)
			MAX-ACCESS read-only
			STATUS current
			DESCRIPTION
				"The target port of bypass health-checking."
			::= { sleBypassOptionConnectivityEntry 2 }

		
		-- 1.3.6.1.4.1.6296.101.2.14.2.2
		sleBypassOptionConnectivityControl OBJECT IDENTIFIER ::= { sleBypassOption 2 }

		
		-- 1.3.6.1.4.1.6296.101.2.14.2.2.1
		sleBypassOptionConnectivityControlRequest OBJECT-TYPE
			SYNTAX INTEGER
				{
				setBypassConnectivity(1),
				unsetBypassConnectivity(2)
				}
			MAX-ACCESS read-write
			STATUS current
			DESCRIPTION
				"setBypassConnectivity(1)   : bypass-check-option connectivity (A.B.C.D) PORT
				unsetBypassConnectivity(2) : no bypass-check option connectivity"
			::= { sleBypassOptionConnectivityControl 1 }

		
--   1.3.6.1.4.1.6296.101.2.12.2.2
-- 1.3.6.1.4.1.6296.101.2.12.2.2
		-- 1.3.6.1.4.1.6296.101.2.14.2.2.2
		sleBypassOptionConnectivityControlStatus OBJECT-TYPE
			SYNTAX SleControlStatusType
			MAX-ACCESS read-only
			STATUS current
			DESCRIPTION
				"The status of user command."
			::= { sleBypassOptionConnectivityControl 2 }

		
--   1.3.6.1.4.1.6296.101.2.12.2.3
-- 1.3.6.1.4.1.6296.101.2.12.2.3
		-- 1.3.6.1.4.1.6296.101.2.14.2.2.3
		sleBypassOptionConnectivityControlTimer OBJECT-TYPE
			SYNTAX Integer32
			MAX-ACCESS read-write
			STATUS current
			DESCRIPTION
				"The maximum time for the manager for a long running user command."
			::= { sleBypassOptionConnectivityControl 3 }

		
--   1.3.6.1.4.1.6296.101.2.12.2.4
-- 1.3.6.1.4.1.6296.101.2.12.2.4
		-- 1.3.6.1.4.1.6296.101.2.14.2.2.4
		sleBypassOptionConnectivityControlTimeStamp OBJECT-TYPE
			SYNTAX TimeTicks
			MAX-ACCESS read-only
			STATUS current
			DESCRIPTION
				"The time stamp of the last command(end of command)."
			::= { sleBypassOptionConnectivityControl 4 }

		
--   1.3.6.1.4.1.6296.101.2.12.2.5
-- 1.3.6.1.4.1.6296.101.2.12.2.5
		-- 1.3.6.1.4.1.6296.101.2.14.2.2.5
		sleBypassOptionConnectivityControlReqResult OBJECT-TYPE
			SYNTAX SleControlRequestResultType
			MAX-ACCESS read-only
			STATUS current
			DESCRIPTION
				"The result of user command."
			::= { sleBypassOptionConnectivityControl 5 }

		
		-- 1.3.6.1.4.1.6296.101.2.14.2.2.6
		sleBypassOptionConnectivityControlAddress OBJECT-TYPE
			SYNTAX IpAddress
			MAX-ACCESS read-write
			STATUS current
			DESCRIPTION
				"The target IP address of bypass health-checking"
			::= { sleBypassOptionConnectivityControl 6 }

		
		-- 1.3.6.1.4.1.6296.101.2.14.2.2.7
		sleBypassOptionConnectivityControlPort OBJECT-TYPE
			SYNTAX Integer32
			MAX-ACCESS read-write
			STATUS current
			DESCRIPTION
				"he target port of bypass health-checking"
			::= { sleBypassOptionConnectivityControl 7 }

		
		-- 1.3.6.1.4.1.6296.101.2.14.2.3
		sleBypassOptionConnectivityNotification OBJECT IDENTIFIER ::= { sleBypassOption 3 }

		
		-- 1.3.6.1.4.1.6296.101.2.14.2.3.1
		sleBypassOptionConnectivitySet NOTIFICATION-TYPE
			OBJECTS { sleBypassOptionConnectivityControlRequest, sleBypassOptionConnectivityControlTimeStamp, sleBypassOptionConnectivityControlReqResult, sleBypassOptionConnectivityControlAddress, sleBypassOptionConnectivityControlPort
				 }
			STATUS current
			DESCRIPTION 
				"Description."
			::= { sleBypassOptionConnectivityNotification 1 }

		
		-- 1.3.6.1.4.1.6296.101.2.14.2.3.2
		sleBypassOptionConnectivityUnset NOTIFICATION-TYPE
			OBJECTS { sleBypassOptionConnectivityControlRequest, sleBypassOptionConnectivityControlTimeStamp, sleBypassOptionConnectivityControlReqResult, sleBypassOptionConnectivityControlAddress, sleBypassOptionConnectivityControlPort
				 }
			STATUS current
			DESCRIPTION 
				"Description."
			::= { sleBypassOptionConnectivityNotification 2 }

		
		-- 1.3.6.1.4.1.6296.101.2.14.2.4
		sleBypassOptionPingTable OBJECT-TYPE
			SYNTAX SEQUENCE OF SleBypassOptionPingEntry
			MAX-ACCESS not-accessible
			STATUS current
			DESCRIPTION
				"Description."
			::= { sleBypassOption 4 }

		
		-- 1.3.6.1.4.1.6296.101.2.14.2.4.1
		sleBypassOptionPingEntry OBJECT-TYPE
			SYNTAX SleBypassOptionPingEntry
			MAX-ACCESS not-accessible
			STATUS current
			DESCRIPTION
				"Description."
			INDEX { sleBypassOptionPingAddress }
			::= { sleBypassOptionPingTable 1 }

		
		SleBypassOptionPingEntry ::=
			SEQUENCE { 
				sleBypassOptionPingAddress
					IpAddress,
				sleBypassOptionPingTransInterval
					Integer32,
				sleBypassOptionPingTranNumber
					Integer32,
				sleBypassOptionPingReqInterval
					Integer32,
				sleBypassOptionPingReqTimeout
					Integer32,
				sleBypassOptionPingLossThresh
					Integer32
			 }

		-- 1.3.6.1.4.1.6296.101.2.14.2.4.1.1
		sleBypassOptionPingAddress OBJECT-TYPE
			SYNTAX IpAddress
			MAX-ACCESS read-only
			STATUS current
			DESCRIPTION
				"The target IP address of bypass ping health checking"
			::= { sleBypassOptionPingEntry 1 }

		
		-- 1.3.6.1.4.1.6296.101.2.14.2.4.1.2
		sleBypassOptionPingTransInterval OBJECT-TYPE
			SYNTAX Integer32
			MAX-ACCESS read-only
			STATUS current
			DESCRIPTION
				"The ping transaction interval"
			::= { sleBypassOptionPingEntry 2 }

		
		-- 1.3.6.1.4.1.6296.101.2.14.2.4.1.3
		sleBypassOptionPingTranNumber OBJECT-TYPE
			SYNTAX Integer32
			MAX-ACCESS read-only
			STATUS current
			DESCRIPTION
				"The ping transaction request number"
			::= { sleBypassOptionPingEntry 3 }

		
		-- 1.3.6.1.4.1.6296.101.2.14.2.4.1.4
		sleBypassOptionPingReqInterval OBJECT-TYPE
			SYNTAX Integer32
			MAX-ACCESS read-only
			STATUS current
			DESCRIPTION
				"The ping request interval"
			::= { sleBypassOptionPingEntry 4 }

		
		-- 1.3.6.1.4.1.6296.101.2.14.2.4.1.5
		sleBypassOptionPingReqTimeout OBJECT-TYPE
			SYNTAX Integer32
			MAX-ACCESS read-only
			STATUS current
			DESCRIPTION
				"The ping request timeout"
			::= { sleBypassOptionPingEntry 5 }

		
		-- 1.3.6.1.4.1.6296.101.2.14.2.4.1.6
		sleBypassOptionPingLossThresh OBJECT-TYPE
			SYNTAX Integer32
			MAX-ACCESS read-only
			STATUS current
			DESCRIPTION
				"The ping loss threshold"
			::= { sleBypassOptionPingEntry 6 }

		
		-- 1.3.6.1.4.1.6296.101.2.14.2.5
		sleBypassOptionPingControl OBJECT IDENTIFIER ::= { sleBypassOption 5 }

		
		-- 1.3.6.1.4.1.6296.101.2.14.2.5.1
		sleBypassOptionPingControlRequest OBJECT-TYPE
			SYNTAX INTEGER
				{
				setBypassPing(1),
				unsetBypassPing(2)
				}
			MAX-ACCESS read-write
			STATUS current
			DESCRIPTION
				"The request of a user command."
			::= { sleBypassOptionPingControl 1 }
-- 
-- 
		
--   1.3.6.1.4.1.6296.101.2.12.2.2
-- 1.3.6.1.4.1.6296.101.2.12.2.2
		-- 1.3.6.1.4.1.6296.101.2.14.2.5.2
		sleBypassOptionPingControlStatus OBJECT-TYPE
			SYNTAX SleControlStatusType
			MAX-ACCESS read-only
			STATUS current
			DESCRIPTION
				"The status of user command."
			::= { sleBypassOptionPingControl 2 }

		
--   1.3.6.1.4.1.6296.101.2.12.2.3
-- 1.3.6.1.4.1.6296.101.2.12.2.3
		-- 1.3.6.1.4.1.6296.101.2.14.2.5.3
		sleBypassOptionPingControlTimer OBJECT-TYPE
			SYNTAX Integer32
			MAX-ACCESS read-write
			STATUS current
			DESCRIPTION
				"The maximum time for the manager for a long running user command."
			::= { sleBypassOptionPingControl 3 }

		
--   1.3.6.1.4.1.6296.101.2.12.2.4
-- 1.3.6.1.4.1.6296.101.2.12.2.4
		-- 1.3.6.1.4.1.6296.101.2.14.2.5.4
		sleBypassOptionPingControlTimeStamp OBJECT-TYPE
			SYNTAX TimeTicks
			MAX-ACCESS read-only
			STATUS current
			DESCRIPTION
				"The time stamp of the last command(end of command)."
			::= { sleBypassOptionPingControl 4 }

		
--   1.3.6.1.4.1.6296.101.2.12.2.5
-- 1.3.6.1.4.1.6296.101.2.12.2.5
		-- 1.3.6.1.4.1.6296.101.2.14.2.5.5
		sleBypassOptionPingControlReqResult OBJECT-TYPE
			SYNTAX SleControlRequestResultType
			MAX-ACCESS read-only
			STATUS current
			DESCRIPTION
				"The result of user command."
			::= { sleBypassOptionPingControl 5 }

		
		-- 1.3.6.1.4.1.6296.101.2.14.2.5.6
		sleBypassOptionPingControlAddress OBJECT-TYPE
			SYNTAX IpAddress
			MAX-ACCESS read-write
			STATUS current
			DESCRIPTION
				"The target IP address of bypass ping health-checking"
			::= { sleBypassOptionPingControl 6 }

		
		-- 1.3.6.1.4.1.6296.101.2.14.2.5.7
		sleBypassOptionPingControlTransInterval OBJECT-TYPE
			SYNTAX Integer32
			MAX-ACCESS read-write
			STATUS current
			DESCRIPTION
				"The ping transaction interval"
			::= { sleBypassOptionPingControl 7 }

		
		-- 1.3.6.1.4.1.6296.101.2.14.2.5.8
		sleBypassOptionPingControlTranNumber OBJECT-TYPE
			SYNTAX Integer32
			MAX-ACCESS read-write
			STATUS current
			DESCRIPTION
				"The ping transaction request number"
			::= { sleBypassOptionPingControl 8 }

		
		-- 1.3.6.1.4.1.6296.101.2.14.2.5.9
		sleBypassOptionPingControlReqInterval OBJECT-TYPE
			SYNTAX Integer32
			MAX-ACCESS read-write
			STATUS current
			DESCRIPTION
				"The ping request interval"
			::= { sleBypassOptionPingControl 9 }

		
		-- 1.3.6.1.4.1.6296.101.2.14.2.5.10
		sleBypassOptionPingControlReqTimeout OBJECT-TYPE
			SYNTAX Integer32
			MAX-ACCESS read-write
			STATUS current
			DESCRIPTION
				"The ping request timeout"
			::= { sleBypassOptionPingControl 10 }

		
		-- 1.3.6.1.4.1.6296.101.2.14.2.5.11
		sleBypassOptionPingControlLossThresh OBJECT-TYPE
			SYNTAX Integer32
			MAX-ACCESS read-write
			STATUS current
			DESCRIPTION
				"The ping loss threshold"
			::= { sleBypassOptionPingControl 11 }

		
		-- 1.3.6.1.4.1.6296.101.2.14.2.6
		sleBypassOptionPingNotification OBJECT IDENTIFIER ::= { sleBypassOption 6 }

		
		-- 1.3.6.1.4.1.6296.101.2.14.2.6.1
		sleBypassOptionPingSet NOTIFICATION-TYPE
			OBJECTS { sleBypassOptionPingControlRequest, sleBypassOptionPingControlTimeStamp, sleBypassOptionPingControlReqResult, sleBypassOptionPingControlTranNumber, sleBypassOptionPingControlReqInterval, 
				sleBypassOptionPingControlReqTimeout, sleBypassOptionPingControlLossThresh, sleBypassOptionPingControlAddress, sleBypassOptionPingControlTransInterval }
			STATUS current
			DESCRIPTION 
				"Description."
			::= { sleBypassOptionPingNotification 1 }

		
		-- 1.3.6.1.4.1.6296.101.2.14.2.6.2
		sleBypassOptionPingUnset NOTIFICATION-TYPE
			OBJECTS { sleBypassOptionPingControlRequest, sleBypassOptionPingControlTimeStamp, sleBypassOptionPingControlReqResult, sleBypassOptionPingControlAddress }
			STATUS current
			DESCRIPTION 
				"Description."
			::= { sleBypassOptionPingNotification 2 }

		
		-- 1.3.6.1.4.1.6296.101.2.14.2.7
		sleBypassOptionLinkMonitorTable OBJECT-TYPE
			SYNTAX SEQUENCE OF SleBypassOptionLinkMonitorEntry
			MAX-ACCESS not-accessible
			STATUS current
			DESCRIPTION
				"Description."
			::= { sleBypassOption 7 }

		
		-- 1.3.6.1.4.1.6296.101.2.14.2.7.1
		sleBypassOptionLinkMonitorEntry OBJECT-TYPE
			SYNTAX SleBypassOptionLinkMonitorEntry
			MAX-ACCESS not-accessible
			STATUS current
			DESCRIPTION
				"Description."
			INDEX { sleBypassOptionLinkMonitorPort }
			::= { sleBypassOptionLinkMonitorTable 1 }

		
		SleBypassOptionLinkMonitorEntry ::=
			SEQUENCE { 
				sleBypassOptionLinkMonitorPort
					Integer32,
				sleBypassOptionLinkMonitorPortStatus
					INTEGER
			 }

		-- 1.3.6.1.4.1.6296.101.2.14.2.7.1.1
		sleBypassOptionLinkMonitorPort OBJECT-TYPE
			SYNTAX Integer32 (1..65535)
			MAX-ACCESS read-only
			STATUS current
			DESCRIPTION
				"The port of bypass link health-checking"
			::= { sleBypassOptionLinkMonitorEntry 1 }

		
		-- 1.3.6.1.4.1.6296.101.2.14.2.7.1.2
		sleBypassOptionLinkMonitorPortStatus OBJECT-TYPE
			SYNTAX INTEGER { enable(1) }
			MAX-ACCESS read-only
			STATUS current
			DESCRIPTION
				"The port status of bypass link health-checking"
			::= { sleBypassOptionLinkMonitorEntry 2 }

		
		-- 1.3.6.1.4.1.6296.101.2.14.2.8
		sleBypassOptionLinkMonitorControl OBJECT IDENTIFIER ::= { sleBypassOption 8 }

		
		-- 1.3.6.1.4.1.6296.101.2.14.2.8.1
		sleBypassOptionLinkMonitorControlRequest OBJECT-TYPE
			SYNTAX INTEGER { setBypassLinkMonitor(1) }
			MAX-ACCESS read-write
			STATUS current
			DESCRIPTION
				"The request of a user command."
			::= { sleBypassOptionLinkMonitorControl 1 }
-- 
-- 
		
--   1.3.6.1.4.1.6296.101.2.12.2.2
-- 1.3.6.1.4.1.6296.101.2.12.2.2
		-- 1.3.6.1.4.1.6296.101.2.14.2.8.2
		sleBypassOptionLinkMonitorControlStatus OBJECT-TYPE
			SYNTAX SleControlStatusType
			MAX-ACCESS read-only
			STATUS current
			DESCRIPTION
				"The status of user command."
			::= { sleBypassOptionLinkMonitorControl 2 }

		
--   1.3.6.1.4.1.6296.101.2.12.2.3
-- 1.3.6.1.4.1.6296.101.2.12.2.3
		-- 1.3.6.1.4.1.6296.101.2.14.2.8.3
		sleBypassOptionLinkMonitorControlTimer OBJECT-TYPE
			SYNTAX Integer32
			MAX-ACCESS read-write
			STATUS current
			DESCRIPTION
				"The maximum time for the manager for a long running user command."
			::= { sleBypassOptionLinkMonitorControl 3 }

		
--   1.3.6.1.4.1.6296.101.2.12.2.4
-- 1.3.6.1.4.1.6296.101.2.12.2.4
		-- 1.3.6.1.4.1.6296.101.2.14.2.8.4
		sleBypassOptionLinkMonitorControlTimeStamp OBJECT-TYPE
			SYNTAX TimeTicks
			MAX-ACCESS read-only
			STATUS current
			DESCRIPTION
				"The time stamp of the last command(end of command)."
			::= { sleBypassOptionLinkMonitorControl 4 }

		
--   1.3.6.1.4.1.6296.101.2.12.2.5
-- 1.3.6.1.4.1.6296.101.2.12.2.5
		-- 1.3.6.1.4.1.6296.101.2.14.2.8.5
		sleBypassOptionLinkMonitorControlReqResult OBJECT-TYPE
			SYNTAX SleControlRequestResultType
			MAX-ACCESS read-only
			STATUS current
			DESCRIPTION
				"The result of user command."
			::= { sleBypassOptionLinkMonitorControl 5 }

		
		-- 1.3.6.1.4.1.6296.101.2.14.2.8.6
		sleBypassOptionLinkMonitorControlPort OBJECT-TYPE
			SYNTAX Integer32
			MAX-ACCESS read-write
			STATUS current
			DESCRIPTION
				"The port of bypass link health-checking"
			::= { sleBypassOptionLinkMonitorControl 6 }

		
		-- 1.3.6.1.4.1.6296.101.2.14.2.8.7
		sleBypassOptionLinkMonitorControlPortStatus OBJECT-TYPE
			SYNTAX INTEGER
				{
				enable(1),
				disable(2)
				}
			MAX-ACCESS read-write
			STATUS current
			DESCRIPTION
				"The port status of bypass link health-checking"
			::= { sleBypassOptionLinkMonitorControl 7 }

		
		-- 1.3.6.1.4.1.6296.101.2.14.2.9
		sleBypassOptioLinkMonitorNotification OBJECT IDENTIFIER ::= { sleBypassOption 9 }

		
		-- 1.3.6.1.4.1.6296.101.2.14.2.9.1
		sleBypassOptionLinkMonitorChanged NOTIFICATION-TYPE
			OBJECTS { sleBypassOptionLinkMonitorControlRequest, sleBypassOptionLinkMonitorControlStatus, sleBypassOptionLinkMonitorControlTimeStamp, sleBypassOptionLinkMonitorControlReqResult, sleBypassOptionLinkMonitorControlPort, 
				sleBypassOptionLinkMonitorControlPortStatus }
			STATUS current
			DESCRIPTION 
				"Description."
			::= { sleBypassOptioLinkMonitorNotification 1 }

		
		-- 1.3.6.1.4.1.6296.101.2.15
		sleDeviceGroup OBJECT-GROUP
			OBJECTS { sleRfConnectStatus, sleRfPortIndex, sleRfPortAdminStatus, sleRfPortOperStatus, sleDeviceEthernetPortNum, 
				sleDevicePowerNum, sleDeviceFanModuleNum, sleDeviceTemperatureNum, sleDeviceFanStartTemperature, sleDeviceFanStopTemperature, 
				sleDeviceControlRequest, sleDeviceControlStatus, sleDeviceControlTimer, sleDeviceControlTimeStamp, sleDeviceControlReqResult, 
				sleDeviceControlFanStartTemperature, sleDeviceControlFanStopTemperature, sleEthernetPortIndex, sleEthernetPortPhyIndex, sleEthernetPortType, 
				sleEthernetPortAdminStatus, sleEthernetPortOperStatus, sleEthernetPortTransmissionRate, sleEthernetPortDuplexMode, sleEthernetPortFlowControl, 
				sleEthernetPortNegotiationMode, sleEthernetPortJumboFrameSize, sleEthernetPortSfpTransceiver, sleEthernetPortSfpVendorName, sleEthernetPortSfpVendorPartNumber, 
				sleEthernetPortSfpVendorRevision, sleEthernetPortSfpVendorSerialNumber, sleEthernetPortSfpDateCode, sleEthernetPortPhysicalRemoteChassis, sleEthernetPortPhysicalRemoteSlot, 
				sleEthernetPortPhysicalRemotePort, sleEthernetPortPhysicalLinkDiscoveryMode, sleEthernetPortControlRequest, sleEthernetPortControlStatus, sleEthernetPortControlTimer, 
				sleEthernetPortControlTimeStamp, sleEthernetPortControlReqResult, sleEthernetPortControlIndex, sleEthernetPortControlType, sleEthernetPortControlAdminStatus, 
				sleEthernetPortControlTransmissionRate, sleEthernetPortControlDuplexMode, sleEthernetPortControlFlowControl, sleEthernetPortControlJumboFrameSize, sleEthernetPortControlPhysicalRemoteChassis, 
				sleEthernetPortControlPhysicalRemoteSlot, sleEthernetPortControlPhysicalRemotePort, sleEthernetPortControlPhysicalLinkDiscoveryMode, slePowerIndex, slePowerPhyIndex, 
				slePowerState, sleFanModuleIndex, sleFanModulePhyIndex, sleFanModuleUnitNum, sleFanModuleAdminState, 
				sleFanModuleControlRequest, sleFanModuleControlStatus, sleFanModuleControlTimer, sleFanModuleControlTimeStamp, sleFanModuleControlReqResult, 
				sleFanModuleControlIndex, sleFanModuleControlAdminState, sleFanUnitIndex, sleFanUnitOperState, sleTemperatureIndex, 
				sleTemperatureState, sleTemperatureValue, sleBatteryIndex, sleDoorStatus, sleOperationPowerType, 
				sleOperationPowerInfo, slePSUACPowerState, slePSUTemperture, slePSUOutVoltage, slePSUOverTemp, 
				slePSUFirmwareVer, sleRBUEquipState, sleRBUModeStaus, sleBatteryBackupFile, sleBatteryBackupControlRequest, 
				sleBatteryBackupControlStatus, sleBatteryBackupControlTimer, sleBatteryBackupControlTimeStamp, sleBatteryBackupControlReqResult, sleBatteryBackupControlServerIP, 
				sleBatteryBackupControlUserID, sleBatteryBackupControlPassword, sleBatteryBackupControlFlag, sleBatteryBackupControlLocalFile, sleBatteryBackupControlRemoteFile, 
				sleCpuProcessor, sleCpuModel, sleCpuRevision, sleCpuBogomips, sleCpuManufacturer, 
				sleCpuClock, sleCpuBusClock, sleRBUTemperature1, slePSUTempThreshold, sleRBUTemperature2, 
				sleRBUOutVoltage, sleRBUChargeCurrent, sleRBURemainCapacity, sleRBUOverTemp, sleBatteryLow, 
				sleRBUBTStatus, sleRBUBTThreshold, sleRBURechargeVoltage, sleBatteryCellStatus, sleBPSUACHardwareVer, 
				sleBatteryControlRequest, sleBatteryControlStatus, sleBatteryControlTimer, sleBatteryControlTimeStamp, sleBatteryControlReqResult, 
				sleBatteryControlRBUBTStatus, sleBatteryControlRBUBTThreshold, sleBatteryControlRBURechargeVoltage, sleBatteryControlTemperThresh1, sleBatteryControlTemperThresh2, 
				sleRBUTempHighThreshold, slePowerType, sleClockModuleIndex, sleClockModuleBoardId, sleClockModuleInstallStatus, 
				sleClockModuleInitStatus, sleSlotSystemIndex, sleSlotSystemUptime, sleSlotSystemModelName, sleSlotSystemSerialNumber, 
				sleSlotSystemHWVersion, sleSlotSystemBLVersion, sleSlotSystemSWCompatibility, sleSlotSystemOSVersion, sleSlotSystemMacAddress, 
				sleSlotSystemCPULoadAll, sleSlotSystemCPULoadInterrupt, sleSlotSystemMemoryTotal, sleSlotSystemMemoryFree, sleSlotSystemMemoryShared, 
				sleSlotSystemMemoryBuffers, sleSlotSystemMemoryCached, sleSlotSystemMemorySwapTotal, sleSlotSystemMemorySwapFree, sleSlotSystemBootReason, 
				sleSlotSystemBootTime, sleSlotSystemVoltage, sleSlotSystemControlRequest, sleSlotSystemControlStatus, sleSlotSystemControlTimer, 
				sleSlotSystemControlTimeStamp, sleSlotSystemControlReqResult, sleSlotSystemControlSlotIndex, sleSlotStatusPlan, sleSlotStatusPlanCardType, 
				sleSlotStatusCurrentInstall, sleSlotStatusCurrentInstallCardType, sleSlotStatusCardOperation, sleSlotStatusLock, sleSlotStatusUpgradeMode, 
				sleSlotStatusActionEvent, sleSlotStatusState, sleSlotStatusControlRequest, sleSlotStatusControlStatus, sleSlotStatusControlTimer, 
				sleSlotStatusControlTimeStamp, sleSlotStatusControlReqResult, sleSlotStatusControlSlotIndex, sleSlotStatusControlPlanCardType, sleSlotStatusControlUpgradeMode, 
				sleSlotNosVersion, sleSlotNosRevision, sleSlotNosSize, sleSlotNosUpgradeStatus, sleSlotNosControlRequest, 
				sleSlotNosControlStatus, sleSlotNosControlTimer, sleSlotNosControlTimeStamp, sleSlotNosControlReqResult, sleSlotNosControlSlotIndex, 
				sleSlotReleasedNIUNosVersion, sleSlotReleasedNIUNosRevision, sleSlotReleasedNIUNosSize, sleSlotReleasedGPIUNosVersion, sleSlotReleasedGPIUNosRevision, 
				sleSlotReleasedGPIUNosSize, sleSlotSystemPowerLevelStatus, sleSlotPowerMonStatus, sleSlotPowerMonVoltage, sleEthernetPortDMIIndex, 
				sleEthernetPortDMITemper, sleEthernetPortDMIVoltage, sleEthernetPortDMITxBias, sleEthernetPortDMITxPower, sleEthernetPortDMIRxPower, 
				sleEthernetPortSfpTransceiverType, sleSlotNosControlUpDownMethod, sleSlotNosControlUpDownFlag, sleSlotNosControlServerAddress, sleSlotNosControlUserID, 
				sleSlotNosControlPassword, sleSlotNosControlFileName, sleFanUnitSpeed, sleSlotSystemInfoLEDStatus, sleFanModuleSpeedThreshold, 
				sleFanModuleControlSpeedThreshold, sleEthernetPortSfpTransceiverDetailType, sleClockModuleOPMode, sleClockInfoInSrcType, sleClockInfoInSrcAISStatus, 
				sleClockInfoInSrcLoSStatus, sleClockInfoInSrcLDSCStatus, sleClockInfoInSrcNtrClockType, sleDeviceJumboFrameStatus, sleDeviceControlJumboFrameStatus, 
				slePowerPSUType, sleSlotSystemInfoPackageVersion, sleEthernetSfpIndex, sleEthernetSfpTransceiver, sleEthernetSfpVendorName, 
				sleEthernetSfpVendorPartNumber, sleEthernetSfpDateCode, sleEthernetSfpTransceiverType, sleEthernetSfpTransceiverDetailType, sleTemperatureHighThreshold, 
				sleTemperatureLowThreshold, sleTemperatureControlRequest, sleTemperatureControlStatus, sleTemperatureControlTimer, sleTemperatureControlTimeStamp, 
				sleTemperatureControlReqResult, sleTemperatureControlIndex, sleTemperatureControlHighThreshold, sleTemperatureControlLowThreshold, sleEthernetSFPControlRequest, 
				sleEthernetSFPControlStatus, sleEthernetSFPControlTimer, sleEthernetSFPControlTimeStamp, sleEthernetSFPControlReqResult, sleEthernetSFPControlIndex, 
				sleTemperatureWarnHighThreshold, sleTemperatureWarnLowThreshold, sleTemperatureWarnDuration, sleTemperatureAlarmHighThreshold, sleTemperatureAlarmLowThreshold, 
				sleTemperatureAlarmDuration, sleTemperatureControlDuration, sleSlotPowerMonIndex, sleEthernetPortSlotIndex, sleEthernetPortSlotPortIndex, 
				sleEthernetSfpVendorRevision, sleEthernetSfpVendorSerialNumber, sleEthernetSfpTransceiverCodes, sleSlotNosStbVersion, sleSlotNosStbRevision, 
				sleSlotNosStbSize, sleDeviceEnvironmentMonitoringStatus, sleDeviceControlEnvironmentMonitoringStatus, sleRfPowerStatus, sleSlotAiuRunStatus, 
				sleSlotAiuAlarmStatus, sleEthernetPortAdminTransmissionRate, sleEthernetPortAdminDuplexMode, sleEthernetPortAdminFlowControl, sleEthernetPortAdminNegotiationMode, 
				sleSlotReleasedSIUNosVersion, sleSlotReleasedSIUNosRevision, sleSlotReleasedSIUNosSize, sleEMInputIndex, sleEMAlarmString, 
				sleEMAlarmSeverity, sleEMmode, sleEMControlRequest, sleEMControlStatus, sleEMControlInputIndex, 
				sleEMControlAlarmString, sleEMControlAlarmSeverity, sleEMControlmode, sleEthernetSfpSpeed, sleEthernetSfpLength, 
				sleEthernetSfpWaveLength, sleRfEthertype, sleRfSrcAddress, sleRfDesAddress, sleRBUTempLowThreshold, 
				sleEthernetPortControlNegotiationMode, sleSlotStatusPower, sleSlotStatusSerialNumber, sleEMControlTimer, sleEMControlTimeStamp, 
				sleEthernetPortAdminReason, sleEMControlReqResult, sleRfBaseControlRequest, sleRfBaseControlStatus, sleRfBaseControlTimer, 
				sleRfBaseControlTimeStamp, sleRfBaseControlReqResult, sleRfBaseControlRfEthertype, sleRfPortControlRequest, sleRfPortControlStatus, 
				sleRfPortControlTimer, sleRfPortControlTimeStamp, sleRfPortControlReqResult, sleRfPortControlIndex, sleBypassMode, 
				sleBypassStatus, sleBypassBaseControlRequest, sleBypassBaseControlStatus, sleBypassBaseControlTimer, sleBypassBaseControlTimeStamp, 
				sleBypassBaseControlReqResult, sleBypassBaseControlMode, sleBypassOptionConnectivityAddress, sleBypassOptionConnectivityPort, sleBypassOptionConnectivityControlRequest, 
				sleBypassOptionConnectivityControlStatus, sleBypassOptionConnectivityControlTimer, sleBypassOptionConnectivityControlTimeStamp, sleBypassOptionConnectivityControlReqResult, sleBypassOptionConnectivityControlAddress, 
				sleBypassOptionConnectivityControlPort, sleBypassOptionPingAddress, sleBypassOptionPingTransInterval, sleBypassOptionPingTranNumber, sleBypassOptionPingReqInterval, 
				sleBypassOptionPingReqTimeout, sleBypassOptionPingLossThresh, sleBypassOptionPingControlRequest, sleBypassOptionPingControlStatus, sleBypassOptionPingControlTimer, 
				sleBypassOptionPingControlTimeStamp, sleBypassOptionPingControlReqResult, sleBypassOptionPingControlAddress, sleBypassOptionPingControlTransInterval, sleBypassOptionPingControlTranNumber, 
				sleBypassOptionPingControlReqInterval, sleBypassOptionPingControlReqTimeout, sleBypassOptionPingControlLossThresh, sleBypassOptionLinkMonitorPort, sleBypassOptionLinkMonitorPortStatus, 
				sleBypassOptionLinkMonitorControlRequest, sleBypassOptionLinkMonitorControlStatus, sleBypassOptionLinkMonitorControlTimer, sleBypassOptionLinkMonitorControlTimeStamp, sleBypassOptionLinkMonitorControlReqResult, 
				sleBypassOptionLinkMonitorControlPort, sleBypassOptionLinkMonitorControlPortStatus, sleSlotSystemInfoManufacturer, sleSlotSystemInfoManufactureDate, sleSlotStatusHealthState, 
				sleRfPortControlAdminStatus, sleClockInfoInSrcStatus, sleEthernetSfpMultimodeLengthOm1, sleEthernetSfpMultimodeLengthOm2, sleEthernetSfpTransceiverDetailTypeStr, 
				sleEthernetSfpTransceiverLengthStr, sleEthernetSfpWaveLengthStr, sleEthernetSfpConnectorType, sleSlotReleasedIU10GE8NosVersion, sleSlotReleasedIU10GE8NosRevision, 
				sleSlotReleasedIU10GE8NosSize, sleSlotReleasedIU10GEPON8NosVersion, sleSlotReleasedIU10GEPON8NosRevision, sleSlotReleasedIU10GEPON8NosSize, sleSlotReleasedIUGEPON8NosVersion, 
				sleSlotReleasedIUGEPON8NosRevision, sleSlotReleasedIUGEPON8NosSize, sleEthernetSfpMultimodeLengthOm3, sleSlotProtectionSystemStatus, sleSlotProtectionSystemThreshold, 
				sleSlotProtectionControlRequest, sleSlotProtectionControlStatus, sleSlotProtectionControlTimer, sleSlotProtectionControlTimeStamp, sleSlotProtectionControlReqResult, 
				sleSlotProtectionControlSystemStatus, sleSlotProtectionControlSystemThreshold, sleSlotProtectionIUControlRequest, sleSlotProtectionIUControlStatus, sleSlotProtectionIUControlTimer, 
				sleSlotProtectionIUControlTimeStamp, sleSlotProtectionIUControlReqResult, sleSlotProtectionIUControlTemperHighThresh, sleSlotProtectionIUControlTemperLowThresh, sleSlotProtectionIUControlPowerThresh, 
				sleSlotProtectionIUTemperHighThresh, sleSlotProtectionIUTemperLowThresh, sleSlotProtectionIUPowerStatus, sleSlotProtectionIUPowerThresh, sleSlotProtectionIUTemper, 
				sleSlotProtectionIUControlindex, sleSlotProtectionControlIUPowerStatus }
			STATUS current
			DESCRIPTION 
				"Description."
			::= { sleDevice 15 }

		
		-- 1.3.6.1.4.1.6296.101.2.16
		sleDeviceNotificationGroup NOTIFICATION-GROUP
			NOTIFICATIONS { sleDeviceTemperatureThresholdChanged, sleEthernetPortChanged, sleFanAdminStateChanged, sleBatteryBackupProfileChanged, sleBatteryBackupUpgraded, 
				sleSlotSystemRestart, sleSlotStatusLocked, sleSlotStatusUnlocked, sleSlotStatusPlanning, sleSlotStatusNoPlanning, 
				sleSlotStatusUpgradeModeChanged, sleSlotNosUpgrade, sleSlotStatusPowerUp, sleSlotStatusPowerDown, sleSlotStatusPowerReset, 
				sleSlotNosDownload, sleSlotNosBootloaderUpgrade, sleFanSpeedThresholdChanged, sleDeviceJumboFrameChanged, sleTemperatureThresholdChanged, 
				sleDeviceLEDTestChanged, sleEthernetSFPRemoteReset, sleRfPortStatusChanged, sleDeviceEnvironmentMonitoringStatusChanged, sleEMChanged, 
				sleEMDeleted, sleRFBaseEthertypeChanged, sleRFBaseEthertypeResetChanged, sleBypassModeChanged, sleBypassOptionConnectivitySet, 
				sleBypassOptionConnectivityUnset, sleBypassOptionPingSet, sleBypassOptionPingUnset, sleBypassOptionLinkMonitorChanged, sleSlotProtectionSystemStatusChanged, 
				sleSlotProtectionSystemThreshChanged, sleSlotProtectionIUTemperThreshChanged, sleSlotProtectionIUPowerThreshChanged, sleSlotProtectionIUPowerStatusChanged, sleBatteryBackupTableCleared, 
				sleBatteryForceChargeChanged, sleBatteryChargingStartChanged, sleBatteryForceChargeNonStopChanged, sleBatteryRBUBTStatusChanged, sleBatteryRBUBTThresholdChanged, 
				sleBatteryRBURechargeVoltageChanged, sleBatteryPsuAcTemperThreshChanged, sleBatteryRBUTemperThreshChanged }
			STATUS current
			DESCRIPTION 
				"Description."
			::= { sleDevice 16 }

		
	
	END

--
-- sle-device-mib.mib
--
